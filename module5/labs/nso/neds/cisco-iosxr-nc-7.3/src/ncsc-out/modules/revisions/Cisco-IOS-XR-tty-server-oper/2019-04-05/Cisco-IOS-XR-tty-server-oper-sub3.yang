submodule Cisco-IOS-XR-tty-server-oper-sub3 {
  // Generated by yanger -t ncs
  tailf:mount-id "cisco-iosxr-nc-7.3:cisco-iosxr-nc-7.3";

  belongs-to Cisco-IOS-XR-tty-server-oper {
    prefix Cisco-IOS-XR-tty-server-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tty-server package operational data.

     Copyright (c) 2013-2019 by Cisco Systems, Inc.
     All rights reserved.";

  revision 2019-04-05 {
    description
      "Establish semantic version baseline.";
    semver:module-version "1.0.0";
  }
  revision 2019-02-25 {
    description
      "Fixed unconstrained data type issues";
  }
  revision 2017-09-07 {
    description
      "Fixed type translation error.";
  }
  revision 2015-07-30 {
    description
      "Descriptions updated.";
  }
  revision 2015-01-07 {
    description
      "IOS XR 5.3.1 revision.";
  }

  grouping ncs_template_TTY-EXEC-PROP-STATS {
    description
      "exec_prop statistics";
    leaf time-stamp-enabled {
      type string;
      description
        "Specifies whether timestamp is enabled or not";
    }
  }

  grouping ncs_rpc_notif_TTY-EXEC-PROP-STATS {
    description
      "exec_prop statistics";
    leaf time-stamp-enabled {
      type boolean;
      description
        "Specifies whether timestamp is enabled or not";
    }
  }

  grouping live_ncs_TTY-EXEC-PROP-STATS {
    description
      "exec_prop statistics";
    leaf time-stamp-enabled {
      type boolean;
      description
        "Specifies whether timestamp is enabled or not";
    }
  }

  grouping TTY-EXEC-PROP-STATS {
    description
      "exec_prop statistics";
    leaf time-stamp-enabled {
      type boolean;
      description
        "Specifies whether timestamp is enabled or not";
    }
  }
}

module Cisco-IOS-XR-sysadmin-ethsw-esdma-clear {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-clear";
  prefix esdma_clear;

  import tailf-common {
    prefix tailf;
  }
  import Cisco-IOS-XR-sysadmin-ethsw-esdma-types {
    prefix esdma_types;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'clear controller switch' commands.

     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-07-06 {
    description
      "Initial revision with content extracted from esdma_cli.yang.";
  }

  grouping ncs_template_switch-clear-statistics {
    container statistics {
      list location {
        // NCS patched for predictable order
        ordered-by user;
        key "rack card switch-id";
        leaf rack {
          type esdma_types:ncs_template_esdma-rack-num-enum;
        }
        leaf card {
          type esdma_types:ncs_template_esdma-cpu;
        }
        leaf switch-id {
          type esdma_types:ncs_template_esdma-switch-type-enum;
        }
      }
    }
  }

  grouping ncs_template_switch-clear-mlap {
    container mlap {
      container statistics {
        list location {
          // NCS patched for predictable order
          ordered-by user;
          key "rack card switch-id";
          leaf rack {
            type esdma_types:ncs_template_esdma-rack-num-enum;
          }
          leaf card {
            type esdma_types:ncs_template_esdma-cpu;
          }
          leaf switch-id {
            type esdma_types:ncs_template_esdma-switch-type-enum;
          }
        }
      }
    }
  }

  grouping ncs_template_switch-clear-sdr {
    container sdr {
      container statistics {
        list location {
          // NCS patched for predictable order
          ordered-by user;
          key "rack card switch-id";
          leaf rack {
            type esdma_types:ncs_template_esdma-rack-num-enum;
          }
          leaf card {
            type esdma_types:ncs_template_esdma-cpu;
          }
          leaf switch-id {
            type esdma_types:ncs_template_esdma-switch-type-enum;
          }
        }
      }
    }
  }

  grouping ncs_template_switch-clear-fdb {
    container fdb {
      list location {
        // NCS patched for predictable order
        ordered-by user;
        key "rack card switch-id";
        leaf rack {
          type esdma_types:ncs_template_esdma-rack-num-enum;
        }
        leaf card {
          type esdma_types:ncs_template_esdma-cpu;
        }
        leaf switch-id {
          type esdma_types:ncs_template_esdma-switch-type-enum;
        }
      }
    }
  }

  grouping ncs_rpc_notif_switch-clear-statistics {
    container statistics {
      list location {
        key "rack card switch-id";
        leaf rack {
          type esdma_types:ncs_rpc_notif_esdma-rack-num-enum;
        }
        leaf card {
          type esdma_types:ncs_rpc_notif_esdma-cpu;
        }
        leaf switch-id {
          type esdma_types:ncs_rpc_notif_esdma-switch-type-enum;
        }
      }
    }
  }

  grouping ncs_rpc_notif_switch-clear-mlap {
    container mlap {
      container statistics {
        list location {
          key "rack card switch-id";
          leaf rack {
            type esdma_types:ncs_rpc_notif_esdma-rack-num-enum;
          }
          leaf card {
            type esdma_types:ncs_rpc_notif_esdma-cpu;
          }
          leaf switch-id {
            type esdma_types:ncs_rpc_notif_esdma-switch-type-enum;
          }
        }
      }
    }
  }

  grouping ncs_rpc_notif_switch-clear-sdr {
    container sdr {
      container statistics {
        list location {
          key "rack card switch-id";
          leaf rack {
            type esdma_types:ncs_rpc_notif_esdma-rack-num-enum;
          }
          leaf card {
            type esdma_types:ncs_rpc_notif_esdma-cpu;
          }
          leaf switch-id {
            type esdma_types:ncs_rpc_notif_esdma-switch-type-enum;
          }
        }
      }
    }
  }

  grouping ncs_rpc_notif_switch-clear-fdb {
    container fdb {
      list location {
        key "rack card switch-id";
        leaf rack {
          type esdma_types:ncs_rpc_notif_esdma-rack-num-enum;
        }
        leaf card {
          type esdma_types:ncs_rpc_notif_esdma-cpu;
        }
        leaf switch-id {
          type esdma_types:ncs_rpc_notif_esdma-switch-type-enum;
        }
      }
    }
  }

  grouping live_ncs_switch-clear-statistics {
    container statistics {
      list location {
        key "rack card switch-id";
        leaf rack {
          type esdma_types:live_ncs_esdma-rack-num-enum;
        }
        leaf card {
          type esdma_types:live_ncs_esdma-cpu;
        }
        leaf switch-id {
          type esdma_types:live_ncs_esdma-switch-type-enum;
        }
      }
    }
  }

  grouping live_ncs_switch-clear-mlap {
    container mlap {
      container statistics {
        list location {
          key "rack card switch-id";
          leaf rack {
            type esdma_types:live_ncs_esdma-rack-num-enum;
          }
          leaf card {
            type esdma_types:live_ncs_esdma-cpu;
          }
          leaf switch-id {
            type esdma_types:live_ncs_esdma-switch-type-enum;
          }
        }
      }
    }
  }

  grouping live_ncs_switch-clear-sdr {
    container sdr {
      container statistics {
        list location {
          key "rack card switch-id";
          leaf rack {
            type esdma_types:live_ncs_esdma-rack-num-enum;
          }
          leaf card {
            type esdma_types:live_ncs_esdma-cpu;
          }
          leaf switch-id {
            type esdma_types:live_ncs_esdma-switch-type-enum;
          }
        }
      }
    }
  }

  grouping live_ncs_switch-clear-fdb {
    container fdb {
      list location {
        key "rack card switch-id";
        leaf rack {
          type esdma_types:live_ncs_esdma-rack-num-enum;
        }
        leaf card {
          type esdma_types:live_ncs_esdma-cpu;
        }
        leaf switch-id {
          type esdma_types:live_ncs_esdma-switch-type-enum;
        }
      }
    }
  }

  grouping switch-clear-statistics {
    container statistics {
      list location {
        key "rack card switch-id";
        leaf rack {
          type esdma_types:esdma-rack-num-enum;
        }
        leaf card {
          type esdma_types:esdma-cpu;
        }
        leaf switch-id {
          type esdma_types:esdma-switch-type-enum;
        }
      }
    }
  }

  grouping switch-clear-mlap {
    container mlap {
      container statistics {
        list location {
          key "rack card switch-id";
          leaf rack {
            type esdma_types:esdma-rack-num-enum;
          }
          leaf card {
            type esdma_types:esdma-cpu;
          }
          leaf switch-id {
            type esdma_types:esdma-switch-type-enum;
          }
        }
      }
    }
  }

  grouping switch-clear-sdr {
    container sdr {
      container statistics {
        list location {
          key "rack card switch-id";
          leaf rack {
            type esdma_types:esdma-rack-num-enum;
          }
          leaf card {
            type esdma_types:esdma-cpu;
          }
          leaf switch-id {
            type esdma_types:esdma-switch-type-enum;
          }
        }
      }
    }
  }

  grouping switch-clear-fdb {
    container fdb {
      list location {
        key "rack card switch-id";
        leaf rack {
          type esdma_types:esdma-rack-num-enum;
        }
        leaf card {
          type esdma_types:esdma-cpu;
        }
        leaf switch-id {
          type esdma_types:esdma-switch-type-enum;
        }
      }
    }
  }
}

module Cisco-IOS-XR-tty-management-cfg {
  // Generated by yanger -t ncs
  tailf:mount-id "cisco-iosxr-nc-7.3:cisco-iosxr-nc-7.3";
  tailf:ncs-device-type "netconf";

  namespace "http://cisco.com/ns/yang/Cisco-IOS-XR-tty-management-cfg";
  prefix tty-management-cfg;

  import Cisco-IOS-XR-types {
    prefix xr;
  }
  import cisco-semver {
    prefix semver;
  }
  import Cisco-IOS-XR-tty-management-datatypes {
    prefix dt1;
  }
  import Cisco-IOS-XR-tty-server-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tty-management package configuration.

     This YANG module augments the
       Cisco-IOS-XR-tty-server-cfg
     module with configuration data.

     Copyright (c) 2013-2020 by Cisco Systems, Inc.
     All rights reserved.";

  revision 2020-10-05 {
    description
      "Added autocommand and syntax check yang query";
    semver:module-version "1.1.0";
  }
  revision 2019-04-05 {
    description
      "Establish semantic version baseline.";
    semver:module-version "1.0.1";
  }
  revision 2017-09-07 {
    description
      "Fixed type translation error.";
  }
  revision 2015-09-25 {
    description
      "Descriptions updated.";
  }
  revision 2015-01-07 {
    description
      "IOS XR 5.3.1 revision.";
  }

  augment "/ncs:devices/ncs:template/ncs:ned-id/ncs:config/a1:tty/a1:tty-lines/a1:tty-line" {
    description
      "This augment extends the configuration data of
       'Cisco-IOS-XR-tty-server-cfg'";
    container connection {
      description
        "Management connection configuration";
      container transport-input {
        description
          "Protocols to use when connecting to the
           terminal server";
        leaf select {
          type dt1:ncs_template_Tty-transport-protocol-select;
          // NCS drop default statement
          description
            "Choose transport protocols";
        }
        leaf protocol1 {
          // NCS drop when statement
          type dt1:ncs_template_Tty-transport-protocol;
          description
            "Transport protocol1";
        }
        leaf protocol2 {
          // NCS drop when statement
          type dt1:ncs_template_Tty-transport-protocol;
          description
            "Transport protocol2";
        }
        leaf none {
          type string;
          description
            "Not used";
        }
      }
      container transport-output {
        presence "Indicates a transport-output node is configured.";
        description
          "Protocols to use for outgoing connections";
        leaf select {
          type dt1:ncs_template_Tty-transport-protocol-select;
          // NCS drop mandatory statement
          description
            "Choose transport protocols";
        }
        leaf protocol1 {
          type dt1:ncs_template_Tty-transport-protocol;
          description
            "Transport protocol1";
        }
        leaf protocol2 {
          type dt1:ncs_template_Tty-transport-protocol;
          description
            "Transport protocol2";
        }
        leaf none {
          type string;
          description
            "Not used";
        }
      }
      container session-timeout {
        presence "Indicates a session-timeout node is configured.";
        description
          "Interval for closing connection when there is
           no input traffic";
        leaf timeout {
          type string;
          // NCS drop mandatory statement
          description
            "Session timeout interval in minutes";
        }
        leaf direction {
          type dt1:ncs_template_Tty-session-timeout-direction;
          // NCS drop mandatory statement
          description
            "Include output traffic as well as input
             traffic";
        }
      }
      leaf disconnect-character {
        type xr:ncs_template_Char-num;
        description
          "Disconnect character's decimal equivalent value
           or Character ";
      }
      leaf auto-command {
        type string;
        description
          "Line template's auto command";
      }
      leaf acl-in {
        type string;
        description
          "ACL to filter ingoing connections";
      }
      leaf acl-out {
        type string;
        description
          "ACL to filter outgoing connections";
      }
      leaf cli-white-space-completion {
        type empty;
        description
          "Command completion on whitespace";
      }
      leaf session-limit {
        type string;
        // NCS drop default statement
        description
          "The number of outgoing connections";
      }
      leaf escape-character {
        type xr:ncs_template_Tty-escape-char-num;
        // NCS drop default statement
        description
          "Escape character or ASCII decimal equivalent
           value orspecial strings NONE,DEFAULT,BREAK";
      }
      leaf transport-preferred {
        type dt1:ncs_template_Tty-transport-protocol;
        description
          "The preferred protocol to use";
      }
      leaf interactive-syntax-check {
        type string;
        description
          "Set to true to turn on interactive syntax check";
      }
    }
  }
  augment "/ncs:devices/ncs:device/ncs:live-status/a1:tty/a1:tty-lines/a1:tty-line" {
    description
      "This augment extends the configuration data of
       'Cisco-IOS-XR-tty-server-cfg'";
    container connection {
      tailf:ncs-device-type "netconf";
      tailf:display-when "not(../../../../../ncs:module) or ../../../../../ncs:module[ncs:name='Cisco-IOS-XR-tty-management-cfg'] or (../../../../../ncs:live-status-protocol[not(ncs:capability)]) or (../../../../../ncs:live-status-protocol/ncs:capability/ncs:module[.='Cisco-IOS-XR-tty-management-cfg'])";
      description
        "Management connection configuration";
      container transport-input {
        description
          "Protocols to use when connecting to the
           terminal server";
        leaf select {
          type dt1:live_ncs_Tty-transport-protocol-select;
          // NCS drop default statement
          description
            "Choose transport protocols";
        }
        leaf protocol1 {
          // NCS drop when statement
          type dt1:live_ncs_Tty-transport-protocol;
          description
            "Transport protocol1";
        }
        leaf protocol2 {
          // NCS drop when statement
          type dt1:live_ncs_Tty-transport-protocol;
          description
            "Transport protocol2";
        }
        leaf none {
          type uint32;
          description
            "Not used";
        }
      }
      container transport-output {
        presence "Indicates a transport-output node is configured.";
        description
          "Protocols to use for outgoing connections";
        leaf select {
          type dt1:live_ncs_Tty-transport-protocol-select;
          // NCS drop mandatory statement
          description
            "Choose transport protocols";
        }
        leaf protocol1 {
          type dt1:live_ncs_Tty-transport-protocol;
          description
            "Transport protocol1";
        }
        leaf protocol2 {
          type dt1:live_ncs_Tty-transport-protocol;
          description
            "Transport protocol2";
        }
        leaf none {
          type uint32;
          description
            "Not used";
        }
      }
      container session-timeout {
        presence "Indicates a session-timeout node is configured.";
        description
          "Interval for closing connection when there is
           no input traffic";
        leaf timeout {
          type uint32 {
            range "0..35791";
          }
          // NCS drop mandatory statement
          description
            "Session timeout interval in minutes";
        }
        leaf direction {
          type dt1:live_ncs_Tty-session-timeout-direction;
          // NCS drop mandatory statement
          description
            "Include output traffic as well as input
             traffic";
        }
      }
      leaf disconnect-character {
        type xr:live_ncs_Char-num;
        description
          "Disconnect character's decimal equivalent value
           or Character ";
      }
      leaf auto-command {
        type string;
        description
          "Line template's auto command";
      }
      leaf acl-in {
        type string;
        description
          "ACL to filter ingoing connections";
      }
      leaf acl-out {
        type string;
        description
          "ACL to filter outgoing connections";
      }
      leaf cli-white-space-completion {
        type empty;
        description
          "Command completion on whitespace";
      }
      leaf session-limit {
        type uint32 {
          range "0..20";
        }
        // NCS drop default statement
        description
          "The number of outgoing connections";
      }
      leaf escape-character {
        type xr:live_ncs_Tty-escape-char-num;
        // NCS drop default statement
        description
          "Escape character or ASCII decimal equivalent
           value orspecial strings NONE,DEFAULT,BREAK";
      }
      leaf transport-preferred {
        type dt1:live_ncs_Tty-transport-protocol;
        description
          "The preferred protocol to use";
      }
      leaf interactive-syntax-check {
        type boolean;
        description
          "Set to true to turn on interactive syntax check";
      }
    }
  }
  augment "/ncs:devices/ncs:device/ncs:config/a1:tty/a1:tty-lines/a1:tty-line" {
    description
      "This augment extends the configuration data of
       'Cisco-IOS-XR-tty-server-cfg'";
    container connection {
      tailf:ncs-device-type "netconf";
      tailf:display-when "not(../../../../../ncs:module) or ../../../../../ncs:module[ncs:name='Cisco-IOS-XR-tty-management-cfg']";
      description
        "Management connection configuration";
      container transport-input {
        description
          "Protocols to use when connecting to the
           terminal server";
        leaf select {
          type dt1:Tty-transport-protocol-select;
          default "all";
          description
            "Choose transport protocols";
        }
        leaf protocol1 {
          when "../select = 'some'" {
            tailf:xpath-root 3;
            description
              "../Select = Some";
          }
          type dt1:Tty-transport-protocol;
          description
            "Transport protocol1";
        }
        leaf protocol2 {
          when "../select = 'some'" {
            tailf:xpath-root 3;
            description
              "../Select = Some";
          }
          type dt1:Tty-transport-protocol;
          description
            "Transport protocol2";
        }
        leaf none {
          type uint32;
          description
            "Not used";
        }
      }
      container transport-output {
        presence "Indicates a transport-output node is configured.";
        description
          "Protocols to use for outgoing connections";
        leaf select {
          type dt1:Tty-transport-protocol-select;
          mandatory true;
          description
            "Choose transport protocols";
        }
        leaf protocol1 {
          type dt1:Tty-transport-protocol;
          description
            "Transport protocol1";
        }
        leaf protocol2 {
          type dt1:Tty-transport-protocol;
          description
            "Transport protocol2";
        }
        leaf none {
          type uint32;
          description
            "Not used";
        }
      }
      container session-timeout {
        presence "Indicates a session-timeout node is configured.";
        description
          "Interval for closing connection when there is
           no input traffic";
        leaf timeout {
          type uint32 {
            range "0..35791";
          }
          mandatory true;
          description
            "Session timeout interval in minutes";
        }
        leaf direction {
          type dt1:Tty-session-timeout-direction;
          mandatory true;
          description
            "Include output traffic as well as input
             traffic";
        }
      }
      leaf disconnect-character {
        type xr:Char-num;
        description
          "Disconnect character's decimal equivalent value
           or Character ";
      }
      leaf auto-command {
        type string;
        description
          "Line template's auto command";
      }
      leaf acl-in {
        type string;
        description
          "ACL to filter ingoing connections";
      }
      leaf acl-out {
        type string;
        description
          "ACL to filter outgoing connections";
      }
      leaf cli-white-space-completion {
        type empty;
        description
          "Command completion on whitespace";
      }
      leaf session-limit {
        type uint32 {
          range "0..20";
        }
        default "6";
        description
          "The number of outgoing connections";
      }
      leaf escape-character {
        type xr:Tty-escape-char-num;
        default "30";
        description
          "Escape character or ASCII decimal equivalent
           value orspecial strings NONE,DEFAULT,BREAK";
      }
      leaf transport-preferred {
        type dt1:Tty-transport-protocol;
        description
          "The preferred protocol to use";
      }
      leaf interactive-syntax-check {
        type boolean;
        description
          "Set to true to turn on interactive syntax check";
      }
    }
  }
  augment "/ncs:devices/ncs:template/ncs:ned-id/ncs:config/a1:tty/a1:tty-lines/a1:tty-line" {
    description
      "This augment extends the configuration data of
       'Cisco-IOS-XR-tty-server-cfg'";
    container exec-mode {
      description
        "Exec Mode Pager  configurtion";
      leaf pager {
        type dt1:ncs_template_Tty-pager;
        // NCS drop default statement
        description
          "Preferred Paging Utility";
      }
    }
  }
  augment "/ncs:devices/ncs:device/ncs:live-status/a1:tty/a1:tty-lines/a1:tty-line" {
    description
      "This augment extends the configuration data of
       'Cisco-IOS-XR-tty-server-cfg'";
    container exec-mode {
      tailf:ncs-device-type "netconf";
      tailf:display-when "not(../../../../../ncs:module) or ../../../../../ncs:module[ncs:name='Cisco-IOS-XR-tty-management-cfg'] or (../../../../../ncs:live-status-protocol[not(ncs:capability)]) or (../../../../../ncs:live-status-protocol/ncs:capability/ncs:module[.='Cisco-IOS-XR-tty-management-cfg'])";
      description
        "Exec Mode Pager  configurtion";
      leaf pager {
        type dt1:live_ncs_Tty-pager;
        // NCS drop default statement
        description
          "Preferred Paging Utility";
      }
    }
  }
  augment "/ncs:devices/ncs:device/ncs:config/a1:tty/a1:tty-lines/a1:tty-line" {
    description
      "This augment extends the configuration data of
       'Cisco-IOS-XR-tty-server-cfg'";
    container exec-mode {
      tailf:ncs-device-type "netconf";
      tailf:display-when "not(../../../../../ncs:module) or ../../../../../ncs:module[ncs:name='Cisco-IOS-XR-tty-management-cfg']";
      description
        "Exec Mode Pager  configurtion";
      leaf pager {
        type dt1:Tty-pager;
        default "more";
        description
          "Preferred Paging Utility";
      }
    }
  }
}

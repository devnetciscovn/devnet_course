submodule Cisco-IOS-XR-pfm-oper-sub1 {
  // Generated by yanger -t ncs
  tailf:mount-id "cisco-iosxr-nc-7.3:cisco-iosxr-nc-7.3";

  belongs-to Cisco-IOS-XR-pfm-oper {
    prefix Cisco-IOS-XR-pfm-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR pfm package operational data.

     Copyright (c) 2013-2021 by Cisco Systems, Inc.
     All rights reserved.";

  revision 2021-07-10 {
    description
      "IOS-XR 7.3.2 revision.";
    semver:module-version "1.0.0";
  }
  revision 2019-04-05 {
    description
      "Establish semantic version baseline.";
  }
  revision 2017-03-28 {
    description
      "IOS-XR 6.3.1 revision.";
  }
  revision 2015-11-09 {
    description
      "IOS XR 6.0 revision.";
  }

  grouping ncs_template_PFM-SHOW-DEV-HW-FAULTS-XML {
    description
      "Hardware fault info for XML";
    leaf db-ver {
      type string;
      description
        "DB Version";
    }
    leaf proc-id {
      type string;
      description
        "Process ID";
    }
    leaf slot-num {
      type string;
      description
        "Slot Number";
    }
    leaf dev-key {
      type string;
      description
        "Device Key";
    }
    leaf dev-desc {
      type string;
      description
        "Device Description";
    }
    leaf cond-desc {
      type string;
      description
        "Condition Description";
    }
    leaf cond-name {
      type string;
      description
        "Condition Name";
    }
    leaf cond-sev {
      type string;
      description
        "Condition Severity";
    }
    leaf cond-raised-timestamp {
      type string;
      description
        "Condition Raised Time Stamp";
    }
  }

  grouping ncs_rpc_notif_PFM-SHOW-DEV-HW-FAULTS-XML {
    description
      "Hardware fault info for XML";
    leaf db-ver {
      type uint32;
      description
        "DB Version";
    }
    leaf proc-id {
      type uint32;
      description
        "Process ID";
    }
    leaf slot-num {
      type uint32;
      description
        "Slot Number";
    }
    leaf dev-key {
      type string;
      description
        "Device Key";
    }
    leaf dev-desc {
      type string;
      description
        "Device Description";
    }
    leaf cond-desc {
      type string;
      description
        "Condition Description";
    }
    leaf cond-name {
      type string;
      description
        "Condition Name";
    }
    leaf cond-sev {
      type string;
      description
        "Condition Severity";
    }
    leaf cond-raised-timestamp {
      type string;
      description
        "Condition Raised Time Stamp";
    }
  }

  grouping live_ncs_PFM-SHOW-DEV-HW-FAULTS-XML {
    description
      "Hardware fault info for XML";
    leaf db-ver {
      type uint32;
      description
        "DB Version";
    }
    leaf proc-id {
      type uint32;
      description
        "Process ID";
    }
    leaf slot-num {
      type uint32;
      description
        "Slot Number";
    }
    leaf dev-key {
      type string;
      description
        "Device Key";
    }
    leaf dev-desc {
      type string;
      description
        "Device Description";
    }
    leaf cond-desc {
      type string;
      description
        "Condition Description";
    }
    leaf cond-name {
      type string;
      description
        "Condition Name";
    }
    leaf cond-sev {
      type string;
      description
        "Condition Severity";
    }
    leaf cond-raised-timestamp {
      type string;
      description
        "Condition Raised Time Stamp";
    }
  }

  grouping PFM-SHOW-DEV-HW-FAULTS-XML {
    description
      "Hardware fault info for XML";
    leaf db-ver {
      type uint32;
      description
        "DB Version";
    }
    leaf proc-id {
      type uint32;
      description
        "Process ID";
    }
    leaf slot-num {
      type uint32;
      description
        "Slot Number";
    }
    leaf dev-key {
      type string;
      description
        "Device Key";
    }
    leaf dev-desc {
      type string;
      description
        "Device Description";
    }
    leaf cond-desc {
      type string;
      description
        "Condition Description";
    }
    leaf cond-name {
      type string;
      description
        "Condition Name";
    }
    leaf cond-sev {
      type string;
      description
        "Condition Severity";
    }
    leaf cond-raised-timestamp {
      type string;
      description
        "Condition Raised Time Stamp";
    }
  }
}

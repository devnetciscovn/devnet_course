module SNMP-COMMUNITY-MIB {
  // Generated by yanger -t ncs
  tailf:mount-id "cisco-iosxr-nc-7.3:cisco-iosxr-nc-7.3";
  tailf:ncs-device-type "netconf";

  namespace "http://tail-f.com/ns/mibs/SNMP-COMMUNITY-MIB/200308060000Z";
  prefix SNMP_COMMUNITY_MIB;

  import tailf-common {
    prefix tailf;
  }
  import SNMPv2-TC {
    prefix SNMPv2_TC;
  }
  import SNMP-TARGET-MIB {
    prefix SNMP_TARGET_MIB;
  }
  import SNMP-FRAMEWORK-MIB {
    prefix SNMP_FRAMEWORK_MIB;
  }
  import tailf-ncs {
    prefix ncs;
  }

  revision 2003-08-06 {
    description
      "";
  }

  typedef ncs_template_snmpCommunityIndexType {
    type string;
  }

  typedef ncs_template_snmpCommunityNameType {
    type string;
  }

  typedef ncs_template_snmpCommunitySecurityNameType {
    type string;
  }

  typedef ncs_template_snmpCommunityContextNameType {
    type string;
  }

  typedef ncs_template_snmpTargetAddrNameType {
    type string;
  }

  typedef ncs_template_snmpTargetAddrTMaskType {
    type string;
  }

  typedef ncs_template_snmpTargetAddrMMSType {
    type string;
  }

  typedef ncs_rpc_notif_snmpCommunityIndexType {
    type string {
      length "1 .. 32";
    }
  }

  typedef ncs_rpc_notif_snmpCommunityNameType {
    type string;
  }

  typedef ncs_rpc_notif_snmpCommunitySecurityNameType {
    type string {
      length "1 .. 32";
    }
  }

  typedef ncs_rpc_notif_snmpCommunityContextNameType {
    type string {
      length "min .. 32";
    }
  }

  typedef ncs_rpc_notif_snmpTargetAddrNameType {
    type string {
      length "1 .. 32";
    }
  }

  typedef ncs_rpc_notif_snmpTargetAddrTMaskType {
    type tailf:hex-list {
      pattern '(((([0-9A-Fa-f]{2}):){0,254}([0-9A-Fa-f]{2}))){0,1}';
      tailf:value-length "min .. 255";
    }
  }

  typedef ncs_rpc_notif_snmpTargetAddrMMSType {
    type int32 {
      range "0 .. 2147483647";
    }
  }

  typedef live_ncs_snmpCommunityIndexType {
    type string {
      length "1 .. 32";
    }
  }

  typedef live_ncs_snmpCommunityNameType {
    type string;
  }

  typedef live_ncs_snmpCommunitySecurityNameType {
    type string {
      length "1 .. 32";
    }
  }

  typedef live_ncs_snmpCommunityContextNameType {
    type string {
      length "min .. 32";
    }
  }

  typedef live_ncs_snmpTargetAddrNameType {
    type string {
      length "1 .. 32";
    }
  }

  typedef live_ncs_snmpTargetAddrTMaskType {
    type tailf:hex-list {
      pattern '(((([0-9A-Fa-f]{2}):){0,254}([0-9A-Fa-f]{2}))){0,1}';
      tailf:value-length "min .. 255";
    }
  }

  typedef live_ncs_snmpTargetAddrMMSType {
    type int32 {
      range "0 .. 2147483647";
    }
  }

  typedef snmpCommunityIndexType {
    type string {
      length "1 .. 32";
    }
  }

  typedef snmpCommunityNameType {
    type string;
  }

  typedef snmpCommunitySecurityNameType {
    type string {
      length "1 .. 32";
    }
  }

  typedef snmpCommunityContextNameType {
    type string {
      length "min .. 32";
    }
  }

  typedef snmpTargetAddrNameType {
    type string {
      length "1 .. 32";
    }
  }

  typedef snmpTargetAddrTMaskType {
    type tailf:hex-list {
      pattern '(((([0-9A-Fa-f]{2}):){0,254}([0-9A-Fa-f]{2}))){0,1}';
      tailf:value-length "min .. 255";
    }
  }

  typedef snmpTargetAddrMMSType {
    type int32 {
      range "0 .. 2147483647";
    }
  }

  augment "/ncs:devices/ncs:device/ncs:config" {
    container SNMP-COMMUNITY-MIB {
      tailf:ncs-device-type "netconf";
      tailf:display-when "not(../../ncs:module) or ../../ncs:module[ncs:name='SNMP-COMMUNITY-MIB']";
      container snmpCommunityTable {
        list snmpCommunityEntry {
          key "snmpCommunityIndex";
          leaf snmpCommunityIndex {
            type snmpCommunityIndexType;
          }
          leaf snmpCommunityName {
            type snmpCommunityNameType;
            mandatory true;
          }
          leaf snmpCommunitySecurityName {
            type snmpCommunitySecurityNameType;
            mandatory true;
          }
          leaf snmpCommunityContextEngineID {
            type SNMP_FRAMEWORK_MIB:SnmpEngineID;
            mandatory true;
          }
          leaf snmpCommunityContextName {
            type snmpCommunityContextNameType;
            default "";
          }
          leaf snmpCommunityTransportTag {
            type SNMP_TARGET_MIB:SnmpTagValue;
            default "";
          }
          leaf snmpCommunityStorageType {
            type SNMPv2_TC:StorageType;
            default "permanent";
          }
        }
      }
    }
  }
  augment "/ncs:devices/ncs:device/ncs:live-status" {
    container SNMP-COMMUNITY-MIB {
      tailf:ncs-device-type "netconf";
      tailf:display-when "not(../../ncs:module) or ../../ncs:module[ncs:name='SNMP-COMMUNITY-MIB'] or (../../ncs:live-status-protocol[not(ncs:capability)]) or (../../ncs:live-status-protocol/ncs:capability/ncs:module[.='SNMP-COMMUNITY-MIB'])";
      container snmpCommunityTable {
        list snmpCommunityEntry {
          key "snmpCommunityIndex";
          leaf snmpCommunityIndex {
            type live_ncs_snmpCommunityIndexType;
          }
          leaf snmpCommunityName {
            type live_ncs_snmpCommunityNameType;
            // NCS drop mandatory statement
          }
          leaf snmpCommunitySecurityName {
            type live_ncs_snmpCommunitySecurityNameType;
            // NCS drop mandatory statement
          }
          leaf snmpCommunityContextEngineID {
            type SNMP_FRAMEWORK_MIB:live_ncs_SnmpEngineID;
            // NCS drop mandatory statement
          }
          leaf snmpCommunityContextName {
            type live_ncs_snmpCommunityContextNameType;
            // NCS drop default statement
          }
          leaf snmpCommunityTransportTag {
            type SNMP_TARGET_MIB:live_ncs_SnmpTagValue;
            // NCS drop default statement
          }
          leaf snmpCommunityStorageType {
            type SNMPv2_TC:live_ncs_StorageType;
            // NCS drop default statement
          }
        }
      }
    }
  }
  augment "/ncs:devices/ncs:template/ncs:ned-id/ncs:config" {
    container SNMP-COMMUNITY-MIB {
      container snmpCommunityTable {
        list snmpCommunityEntry {
          // NCS patched for predictable order
          ordered-by user;
          key "snmpCommunityIndex";
          leaf snmpCommunityIndex {
            type ncs_template_snmpCommunityIndexType;
          }
          leaf snmpCommunityName {
            type ncs_template_snmpCommunityNameType;
            // NCS drop mandatory statement
          }
          leaf snmpCommunitySecurityName {
            type ncs_template_snmpCommunitySecurityNameType;
            // NCS drop mandatory statement
          }
          leaf snmpCommunityContextEngineID {
            type SNMP_FRAMEWORK_MIB:ncs_template_SnmpEngineID;
            // NCS drop mandatory statement
          }
          leaf snmpCommunityContextName {
            type ncs_template_snmpCommunityContextNameType;
            // NCS drop default statement
          }
          leaf snmpCommunityTransportTag {
            type SNMP_TARGET_MIB:ncs_template_SnmpTagValue;
            // NCS drop default statement
          }
          leaf snmpCommunityStorageType {
            type SNMPv2_TC:ncs_template_StorageType;
            // NCS drop default statement
          }
        }
      }
    }
  }
}

module Cisco-IOS-XR-sysadmin-fabric-ncs5501 {
  // Generated by yanger -t ncs
  tailf:mount-id "cisco-iosxr-nc-7.3:cisco-iosxr-nc-7.3";
  tailf:ncs-device-type "netconf";

  namespace "http://www.cisco.com/ns/yang/Cisco-IOS-XR-sysadmin-fabric-ncs5501";
  prefix fabric;

  import Cisco-IOS-XR-sysadmin-fabric-mgr-fgid-ncs5500 {
    prefix fabric-fgid;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2020-07-31 {
    description
      "importing platform specific yang as required";
    semver:module-version "1.1.0";
  }
  revision 2019-04-15 {
    description
      "Establish semantic version baseline.";
    semver:module-version "1.0.0";
  }
  revision 2017-05-01 {
    description
      "Namespace change to comply with Cisco guidelines on namespace";
  }

  grouping ncs_template_fabric {
    container fabric {
      description
        "Fabric resource commands";
      // NCS drop config false container oper
    }
  }

  grouping ncs_rpc_notif_fabric {
    container fabric {
      description
        "Fabric resource commands";
      container oper {
        config false;
        uses fabric-fgid:ncs_rpc_notif_fgid;
      }
    }
  }

  grouping live_ncs_fabric {
    container fabric {
      description
        "Fabric resource commands";
      container oper {
        uses fabric-fgid:live_ncs_fgid;
      }
    }
  }

  grouping fabric {
    container fabric {
      description
        "Fabric resource commands";
      // NCS drop config false container oper
    }
  }
}

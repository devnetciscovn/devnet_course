module Cisco-IOS-XR-sysadmin-entity-state-mib {
  // Generated by yanger -t ncs
  tailf:mount-id "cisco-iosxr-nc-7.3:cisco-iosxr-nc-7.3";
  tailf:ncs-device-type "netconf";

  namespace "http://www.cisco.com/ns/yang/Cisco-IOS-XR-sysadmin-entity-state-mib";
  prefix ENTITY_STATE_MIB;

  import ietf-yang-types {
    prefix yang;
  }
  import tailf-common {
    prefix tailf;
  }
  import Cisco-IOS-XR-sysadmin-entity-state-tc-mib {
    prefix ENTITY-STATE-TC-MIB;
  }
  import Cisco-IOS-XR-sysadmin-entity-mib {
    prefix ENTITY-MIB;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright (c) 2015-2020 by Cisco Systems, Inc.
     All rights reserved.";

  revision 2019-04-15 {
    description
      "Establish semantic version baseline.";
    semver:module-version "1.0.0";
  }
  revision 2017-04-12 {
    description
      "Changed namespace and module name";
  }
  revision 2005-11-22 {
    description
      "";
  }

  augment "/ncs:devices/ncs:device/ncs:config" {
    container ENTITY-STATE-MIB {
      tailf:ncs-device-type "netconf";
      tailf:display-when "not(../../ncs:module) or ../../ncs:module[ncs:name='Cisco-IOS-XR-sysadmin-entity-state-mib']";
      // NCS drop config false container entStateTable
    }
  }
  augment "/ncs:devices/ncs:device/ncs:live-status" {
    container ENTITY-STATE-MIB {
      tailf:ncs-device-type "netconf";
      tailf:display-when "not(../../ncs:module) or ../../ncs:module[ncs:name='Cisco-IOS-XR-sysadmin-entity-state-mib'] or (../../ncs:live-status-protocol[not(ncs:capability)]) or (../../ncs:live-status-protocol/ncs:capability/ncs:module[.='Cisco-IOS-XR-sysadmin-entity-state-mib'])";
      container entStateTable {
        list entStateEntry {
          key "entPhysicalIndex";
          leaf entPhysicalIndex {
            type ENTITY-MIB:live_ncs_PhysicalIndex;
          }
          leaf entStateLastChanged {
            type yang:date-and-time;
          }
          leaf entStateAdmin {
            type ENTITY-STATE-TC-MIB:live_ncs_EntityAdminState;
          }
          leaf entStateOper {
            type ENTITY-STATE-TC-MIB:live_ncs_EntityOperState;
          }
          leaf entStateUsage {
            type ENTITY-STATE-TC-MIB:live_ncs_EntityUsageState;
          }
          leaf entStateAlarm {
            type ENTITY-STATE-TC-MIB:live_ncs_EntityAlarmStatus;
          }
          leaf entStateStandby {
            type ENTITY-STATE-TC-MIB:live_ncs_EntityStandbyStatus;
          }
        }
      }
    }
  }
  augment "/ncs:devices/ncs:template/ncs:ned-id/ncs:config" {
    container ENTITY-STATE-MIB {
      // NCS drop config false container entStateTable
    }
  }
}

module Cisco-IOS-XR-mpls-ldp-mldp-oper {
  // Generated by yanger -t ncs
  tailf:mount-id "cisco-iosxr-nc-7.3:cisco-iosxr-nc-7.3";
  tailf:ncs-device-type "netconf";

  namespace "http://cisco.com/ns/yang/Cisco-IOS-XR-mpls-ldp-mldp-oper";
  prefix mpls-ldp-mldp-oper;

  import ietf-inet-types {
    prefix inet;
  }
  import Cisco-IOS-XR-types {
    prefix xr;
  }
  import cisco-semver {
    prefix semver;
  }
  include Cisco-IOS-XR-mpls-ldp-mldp-oper-sub1 {
    revision-date 2020-10-18;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-ldp-mldp package operational data.

     This module contains definitions
     for the following management objects:
       mpls-mldp: MPLS MLDP operational data

     Copyright (c) 2013-2020 by Cisco Systems, Inc.
     All rights reserved.";

  revision 2020-10-18 {
    description
      "Backward compatible removal in telemetry event Cisco-IOS-XR-types, event-telemetry was removed.";
    semver:module-version "1.1.0";
  }
  revision 2019-04-05 {
    description
      "Establish semantic version baseline.";
    semver:module-version "1.1.0";
  }
  revision 2018-08-30 {
    description
      "Operational Yang model for mLDP.";
  }
  revision 2015-11-09 {
    description
      "IOS XR 6.0 revision.";
  }

  typedef ncs_template_Lsp {
    type string;
    description
      "Lsp";
  }

  typedef ncs_template_Opaque {
    type string;
    description
      "Opaque";
  }

  typedef ncs_rpc_notif_Lsp {
    type enumeration {
      enum "invalid" {
        value 0;
        description
          "Invalid LSP Type";
      }
      enum "any" {
        value 1;
        description
          "Any LSP Type";
      }
      enum "p2mp" {
        value 2;
        description
          "P2MP LSP Type";
      }
      enum "mp2mp-upstream" {
        value 3;
        description
          "MP2MP Upstream LSP Type";
      }
      enum "mp2mp-downstream" {
        value 4;
        description
          "MP2MP Downstream LSP Type";
      }
      enum "mp2mp" {
        value 5;
        description
          "MP2MP LSP Type";
      }
    }
    description
      "Lsp";
  }

  typedef ncs_rpc_notif_Opaque {
    type enumeration {
      enum "static-id" {
        value 0;
        description
          "Static ID Opaque Type";
      }
      enum "global-id" {
        value 1;
        description
          "Global ID Opaque Type";
      }
      enum "vpn-id" {
        value 2;
        description
          "VPN ID Opaque Type";
      }
      enum "ipv4" {
        value 3;
        description
          "IPv4 Opaque Type";
      }
      enum "ipv6" {
        value 4;
        description
          "IPv6 Opaque Type";
      }
      enum "ipv4-bidir" {
        value 5;
        description
          "IPv4 Bidir Opaque Type";
      }
      enum "ipv6-bidir" {
        value 6;
        description
          "IPv6 Bidir Opaque Type";
      }
      enum "recursive" {
        value 7;
        description
          "Recursive Opaque Type";
      }
      enum "recursive-route-distinguisher" {
        value 8;
        description
          "Recursive Route Distinguisher Opaque Type";
      }
      enum "vpnv4" {
        value 250;
        description
          "VPNv4 Opaque Type";
      }
      enum "vpnv6" {
        value 251;
        description
          "VPNv6 Opaque Type";
      }
    }
    description
      "Opaque";
  }

  typedef live_ncs_Lsp {
    type enumeration {
      enum "invalid" {
        value 0;
        description
          "Invalid LSP Type";
      }
      enum "any" {
        value 1;
        description
          "Any LSP Type";
      }
      enum "p2mp" {
        value 2;
        description
          "P2MP LSP Type";
      }
      enum "mp2mp-upstream" {
        value 3;
        description
          "MP2MP Upstream LSP Type";
      }
      enum "mp2mp-downstream" {
        value 4;
        description
          "MP2MP Downstream LSP Type";
      }
      enum "mp2mp" {
        value 5;
        description
          "MP2MP LSP Type";
      }
    }
    description
      "Lsp";
  }

  typedef live_ncs_Opaque {
    type enumeration {
      enum "static-id" {
        value 0;
        description
          "Static ID Opaque Type";
      }
      enum "global-id" {
        value 1;
        description
          "Global ID Opaque Type";
      }
      enum "vpn-id" {
        value 2;
        description
          "VPN ID Opaque Type";
      }
      enum "ipv4" {
        value 3;
        description
          "IPv4 Opaque Type";
      }
      enum "ipv6" {
        value 4;
        description
          "IPv6 Opaque Type";
      }
      enum "ipv4-bidir" {
        value 5;
        description
          "IPv4 Bidir Opaque Type";
      }
      enum "ipv6-bidir" {
        value 6;
        description
          "IPv6 Bidir Opaque Type";
      }
      enum "recursive" {
        value 7;
        description
          "Recursive Opaque Type";
      }
      enum "recursive-route-distinguisher" {
        value 8;
        description
          "Recursive Route Distinguisher Opaque Type";
      }
      enum "vpnv4" {
        value 250;
        description
          "VPNv4 Opaque Type";
      }
      enum "vpnv6" {
        value 251;
        description
          "VPNv6 Opaque Type";
      }
    }
    description
      "Opaque";
  }

  typedef Lsp {
    type enumeration {
      enum "invalid" {
        value 0;
        description
          "Invalid LSP Type";
      }
      enum "any" {
        value 1;
        description
          "Any LSP Type";
      }
      enum "p2mp" {
        value 2;
        description
          "P2MP LSP Type";
      }
      enum "mp2mp-upstream" {
        value 3;
        description
          "MP2MP Upstream LSP Type";
      }
      enum "mp2mp-downstream" {
        value 4;
        description
          "MP2MP Downstream LSP Type";
      }
      enum "mp2mp" {
        value 5;
        description
          "MP2MP LSP Type";
      }
    }
    description
      "Lsp";
  }

  typedef Opaque {
    type enumeration {
      enum "static-id" {
        value 0;
        description
          "Static ID Opaque Type";
      }
      enum "global-id" {
        value 1;
        description
          "Global ID Opaque Type";
      }
      enum "vpn-id" {
        value 2;
        description
          "VPN ID Opaque Type";
      }
      enum "ipv4" {
        value 3;
        description
          "IPv4 Opaque Type";
      }
      enum "ipv6" {
        value 4;
        description
          "IPv6 Opaque Type";
      }
      enum "ipv4-bidir" {
        value 5;
        description
          "IPv4 Bidir Opaque Type";
      }
      enum "ipv6-bidir" {
        value 6;
        description
          "IPv6 Bidir Opaque Type";
      }
      enum "recursive" {
        value 7;
        description
          "Recursive Opaque Type";
      }
      enum "recursive-route-distinguisher" {
        value 8;
        description
          "Recursive Route Distinguisher Opaque Type";
      }
      enum "vpnv4" {
        value 250;
        description
          "VPNv4 Opaque Type";
      }
      enum "vpnv6" {
        value 251;
        description
          "VPNv6 Opaque Type";
      }
    }
    description
      "Opaque";
  }

  grouping ncs_template_VRF-TABLE {
    description
      "Common node of active, standby";
    container vrfs {
      description
        "VRF specific operational data";
      list vrf {
        // NCS patched for predictable order
        ordered-by user;
        key "vrf-name";
        description
          "Operational data for given VRF";
        leaf vrf-name {
          type xr:ncs_template_Cisco-ios-xr-string;
          description
            "VRF Name";
        }
        uses ncs_template_NEIGHBOR-ADDRESS-TABLE;
        uses ncs_template_DATABASE-TABLE;
        uses ncs_template_ROOT-ADDRESS-TABLE;
        uses ncs_template_CONTEXT;
        uses ncs_template_NEIGHBOR-TABLE;
      }
    }
  }

  grouping ncs_template_MFI-ENTRY-TABLE {
    description
      "Common node of active, standby";
    container mfi-entries {
      description
        "MLDP MFI Table";
      list mfi-entry {
        // NCS patched for predictable order
        ordered-by user;
        key "mpls-label";
        description
          "MLDP MFI Information";
        leaf mpls-label {
          type string;
          description
            "MPLS Label";
        }
        uses ncs_template_MLDP-MFI-RW-BAG;
      }
    }
  }

  grouping ncs_template_LSM-ID-TABLE {
    description
      "Common node of active, standby";
    container lsm-ids {
      description
        "MLDP LSM-ID";
      list lsm-id {
        // NCS patched for predictable order
        ordered-by user;
        key "lsm-id";
        description
          "MLDP LSMID Information";
        leaf lsm-id {
          type string;
          description
            "LSM ID";
        }
        uses ncs_template_MLDP-DATABASE-BAG;
      }
    }
  }

  grouping ncs_template_NEIGHBOR-ADDRESS-TABLE {
    description
      "Common node of vrf, default-context";
    container neighbor-addresses {
      description
        "MLDP Neighbors Addresses";
      list neighbor-address {
        // NCS patched for predictable order
        ordered-by user;
        key "address";
        description
          "Neighbor Address Information";
        leaf address {
          type string;
          description
            "The Neighbor IP address";
        }
        uses ncs_template_MLDP-NEIGHBOR-ADDR-BAG;
      }
    }
  }

  grouping ncs_template_ROOT-ADDRESS-TABLE {
    description
      "Common node of vrf, default-context";
    container root-addresses {
      description
        "MLDP Root Table";
      list root-address {
        // NCS patched for predictable order
        ordered-by user;
        key "root-address";
        description
          "MLDP Root Information";
        leaf root-address {
          type string;
          description
            "Root address";
        }
        uses ncs_template_MLDP-ROOT-BAG;
      }
    }
  }

  grouping ncs_template_STATUS {
    description
      "Common node of active, standby";
    container status {
      description
        "MLDP Status";
      uses ncs_template_MLDP-STATUS-BAG;
    }
  }

  grouping ncs_template_CONTEXT {
    description
      "Common node of vrf, default-context";
    container context {
      description
        "MLDP Context";
      uses ncs_template_MLDP-CONTEXT-BAG;
    }
  }

  grouping ncs_template_DATABASE-TABLE {
    description
      "Common node of vrf, default-context";
    container databases {
      description
        "MLDP Database";
      list database {
        // NCS patched for predictable order
        ordered-by user;
        key "lsp-type root-address opaque-type opaque-value-string";
        description
          "MLDP Database Information";
        leaf lsp-type {
          type ncs_template_Lsp;
          description
            "LSP Type";
        }
        leaf root-address {
          type string;
          description
            "Root address";
        }
        leaf opaque-type {
          type ncs_template_Opaque;
          description
            "Opaque Type";
        }
        leaf opaque-value-string {
          type xr:ncs_template_Cisco-ios-xr-string;
          description
            "OpaqueValue";
        }
        uses ncs_template_MLDP-DATABASE-BAG;
      }
    }
  }

  grouping ncs_template_LSP-BINDINGS-TABLE {
    description
      "Common node of active, standby";
    container lsp-bindings {
      description
        "MLDP LSP Bindings Table";
      list lsp-binding {
        // NCS patched for predictable order
        ordered-by user;
        key "lsm-id";
        description
          "MLDP LSP Binding Information";
        leaf lsm-id {
          type string;
          description
            "LSM ID";
        }
        uses ncs_template_MLDP-BINDING-LSP-BAG;
      }
    }
  }

  grouping ncs_template_DEFAULT-CONTEXT {
    description
      "Common node of active, standby";
    container default-context {
      description
        "Default context specific operational data";
      uses ncs_template_NEIGHBOR-ADDRESS-TABLE;
      uses ncs_template_DATABASE-TABLE;
      uses ncs_template_ROOT-ADDRESS-TABLE;
      uses ncs_template_CONTEXT;
      uses ncs_template_NEIGHBOR-TABLE;
    }
  }

  grouping ncs_template_NEIGHBOR-TABLE {
    description
      "Common node of vrf, default-context";
    container neighbors {
      description
        "MLDP Neighbors";
      list neighbor {
        // NCS patched for predictable order
        ordered-by user;
        key "address";
        description
          "Neighbor Information";
        leaf address {
          type string;
          description
            "The Neighbor IP address";
        }
        uses ncs_template_MLDP-NEIGHBOR-BAG;
      }
    }
  }

  grouping ncs_rpc_notif_VRF-TABLE {
    description
      "Common node of active, standby";
    container vrfs {
      description
        "VRF specific operational data";
      list vrf {
        key "vrf-name";
        description
          "Operational data for given VRF";
        leaf vrf-name {
          type xr:ncs_rpc_notif_Cisco-ios-xr-string;
          description
            "VRF Name";
        }
        uses ncs_rpc_notif_NEIGHBOR-ADDRESS-TABLE;
        uses ncs_rpc_notif_DATABASE-TABLE;
        uses ncs_rpc_notif_ROOT-ADDRESS-TABLE;
        uses ncs_rpc_notif_CONTEXT;
        uses ncs_rpc_notif_NEIGHBOR-TABLE;
      }
    }
  }

  grouping ncs_rpc_notif_MFI-ENTRY-TABLE {
    description
      "Common node of active, standby";
    container mfi-entries {
      description
        "MLDP MFI Table";
      list mfi-entry {
        key "mpls-label";
        description
          "MLDP MFI Information";
        leaf mpls-label {
          type uint32;
          description
            "MPLS Label";
        }
        uses ncs_rpc_notif_MLDP-MFI-RW-BAG;
      }
    }
  }

  grouping ncs_rpc_notif_LSM-ID-TABLE {
    description
      "Common node of active, standby";
    container lsm-ids {
      description
        "MLDP LSM-ID";
      list lsm-id {
        key "lsm-id";
        description
          "MLDP LSMID Information";
        leaf lsm-id {
          type uint32;
          description
            "LSM ID";
        }
        uses ncs_rpc_notif_MLDP-DATABASE-BAG;
      }
    }
  }

  grouping ncs_rpc_notif_NEIGHBOR-ADDRESS-TABLE {
    description
      "Common node of vrf, default-context";
    container neighbor-addresses {
      description
        "MLDP Neighbors Addresses";
      list neighbor-address {
        key "address";
        description
          "Neighbor Address Information";
        leaf address {
          type inet:ipv4-address-no-zone;
          description
            "The Neighbor IP address";
        }
        uses ncs_rpc_notif_MLDP-NEIGHBOR-ADDR-BAG;
      }
    }
  }

  grouping ncs_rpc_notif_ROOT-ADDRESS-TABLE {
    description
      "Common node of vrf, default-context";
    container root-addresses {
      description
        "MLDP Root Table";
      list root-address {
        key "root-address";
        description
          "MLDP Root Information";
        leaf root-address {
          type inet:ipv4-address-no-zone;
          description
            "Root address";
        }
        uses ncs_rpc_notif_MLDP-ROOT-BAG;
      }
    }
  }

  grouping ncs_rpc_notif_STATUS {
    description
      "Common node of active, standby";
    container status {
      description
        "MLDP Status";
      uses ncs_rpc_notif_MLDP-STATUS-BAG;
    }
  }

  grouping ncs_rpc_notif_CONTEXT {
    description
      "Common node of vrf, default-context";
    container context {
      description
        "MLDP Context";
      uses ncs_rpc_notif_MLDP-CONTEXT-BAG;
    }
  }

  grouping ncs_rpc_notif_DATABASE-TABLE {
    description
      "Common node of vrf, default-context";
    container databases {
      description
        "MLDP Database";
      list database {
        key "lsp-type root-address opaque-type opaque-value-string";
        description
          "MLDP Database Information";
        leaf lsp-type {
          type ncs_rpc_notif_Lsp;
          description
            "LSP Type";
        }
        leaf root-address {
          type inet:ipv4-address-no-zone;
          description
            "Root address";
        }
        leaf opaque-type {
          type ncs_rpc_notif_Opaque;
          description
            "Opaque Type";
        }
        leaf opaque-value-string {
          type xr:ncs_rpc_notif_Cisco-ios-xr-string;
          description
            "OpaqueValue";
        }
        uses ncs_rpc_notif_MLDP-DATABASE-BAG;
      }
    }
  }

  grouping ncs_rpc_notif_LSP-BINDINGS-TABLE {
    description
      "Common node of active, standby";
    container lsp-bindings {
      description
        "MLDP LSP Bindings Table";
      list lsp-binding {
        key "lsm-id";
        description
          "MLDP LSP Binding Information";
        leaf lsm-id {
          type uint32;
          description
            "LSM ID";
        }
        uses ncs_rpc_notif_MLDP-BINDING-LSP-BAG;
      }
    }
  }

  grouping ncs_rpc_notif_DEFAULT-CONTEXT {
    description
      "Common node of active, standby";
    container default-context {
      description
        "Default context specific operational data";
      uses ncs_rpc_notif_NEIGHBOR-ADDRESS-TABLE;
      uses ncs_rpc_notif_DATABASE-TABLE;
      uses ncs_rpc_notif_ROOT-ADDRESS-TABLE;
      uses ncs_rpc_notif_CONTEXT;
      uses ncs_rpc_notif_NEIGHBOR-TABLE;
    }
  }

  grouping ncs_rpc_notif_NEIGHBOR-TABLE {
    description
      "Common node of vrf, default-context";
    container neighbors {
      description
        "MLDP Neighbors";
      list neighbor {
        key "address";
        description
          "Neighbor Information";
        leaf address {
          type inet:ipv4-address-no-zone;
          description
            "The Neighbor IP address";
        }
        uses ncs_rpc_notif_MLDP-NEIGHBOR-BAG;
      }
    }
  }

  grouping live_ncs_VRF-TABLE {
    description
      "Common node of active, standby";
    container vrfs {
      description
        "VRF specific operational data";
      list vrf {
        key "vrf-name";
        description
          "Operational data for given VRF";
        leaf vrf-name {
          type xr:live_ncs_Cisco-ios-xr-string;
          description
            "VRF Name";
        }
        uses live_ncs_NEIGHBOR-ADDRESS-TABLE;
        uses live_ncs_DATABASE-TABLE;
        uses live_ncs_ROOT-ADDRESS-TABLE;
        uses live_ncs_CONTEXT;
        uses live_ncs_NEIGHBOR-TABLE;
      }
    }
  }

  grouping live_ncs_MFI-ENTRY-TABLE {
    description
      "Common node of active, standby";
    container mfi-entries {
      description
        "MLDP MFI Table";
      list mfi-entry {
        key "mpls-label";
        description
          "MLDP MFI Information";
        leaf mpls-label {
          type uint32;
          description
            "MPLS Label";
        }
        uses live_ncs_MLDP-MFI-RW-BAG;
      }
    }
  }

  grouping live_ncs_LSM-ID-TABLE {
    description
      "Common node of active, standby";
    container lsm-ids {
      description
        "MLDP LSM-ID";
      list lsm-id {
        key "lsm-id";
        description
          "MLDP LSMID Information";
        leaf lsm-id {
          type uint32;
          description
            "LSM ID";
        }
        uses live_ncs_MLDP-DATABASE-BAG;
      }
    }
  }

  grouping live_ncs_NEIGHBOR-ADDRESS-TABLE {
    description
      "Common node of vrf, default-context";
    container neighbor-addresses {
      description
        "MLDP Neighbors Addresses";
      list neighbor-address {
        key "address";
        description
          "Neighbor Address Information";
        leaf address {
          type inet:ipv4-address-no-zone;
          description
            "The Neighbor IP address";
        }
        uses live_ncs_MLDP-NEIGHBOR-ADDR-BAG;
      }
    }
  }

  grouping live_ncs_ROOT-ADDRESS-TABLE {
    description
      "Common node of vrf, default-context";
    container root-addresses {
      description
        "MLDP Root Table";
      list root-address {
        key "root-address";
        description
          "MLDP Root Information";
        leaf root-address {
          type inet:ipv4-address-no-zone;
          description
            "Root address";
        }
        uses live_ncs_MLDP-ROOT-BAG;
      }
    }
  }

  grouping live_ncs_STATUS {
    description
      "Common node of active, standby";
    container status {
      description
        "MLDP Status";
      uses live_ncs_MLDP-STATUS-BAG;
    }
  }

  grouping live_ncs_CONTEXT {
    description
      "Common node of vrf, default-context";
    container context {
      description
        "MLDP Context";
      uses live_ncs_MLDP-CONTEXT-BAG;
    }
  }

  grouping live_ncs_DATABASE-TABLE {
    description
      "Common node of vrf, default-context";
    container databases {
      description
        "MLDP Database";
      list database {
        key "lsp-type root-address opaque-type opaque-value-string";
        description
          "MLDP Database Information";
        leaf lsp-type {
          type live_ncs_Lsp;
          description
            "LSP Type";
        }
        leaf root-address {
          type inet:ipv4-address-no-zone;
          description
            "Root address";
        }
        leaf opaque-type {
          type live_ncs_Opaque;
          description
            "Opaque Type";
        }
        leaf opaque-value-string {
          type xr:live_ncs_Cisco-ios-xr-string;
          description
            "OpaqueValue";
        }
        uses live_ncs_MLDP-DATABASE-BAG;
      }
    }
  }

  grouping live_ncs_LSP-BINDINGS-TABLE {
    description
      "Common node of active, standby";
    container lsp-bindings {
      description
        "MLDP LSP Bindings Table";
      list lsp-binding {
        key "lsm-id";
        description
          "MLDP LSP Binding Information";
        leaf lsm-id {
          type uint32;
          description
            "LSM ID";
        }
        uses live_ncs_MLDP-BINDING-LSP-BAG;
      }
    }
  }

  grouping live_ncs_DEFAULT-CONTEXT {
    description
      "Common node of active, standby";
    container default-context {
      description
        "Default context specific operational data";
      uses live_ncs_NEIGHBOR-ADDRESS-TABLE;
      uses live_ncs_DATABASE-TABLE;
      uses live_ncs_ROOT-ADDRESS-TABLE;
      uses live_ncs_CONTEXT;
      uses live_ncs_NEIGHBOR-TABLE;
    }
  }

  grouping live_ncs_NEIGHBOR-TABLE {
    description
      "Common node of vrf, default-context";
    container neighbors {
      description
        "MLDP Neighbors";
      list neighbor {
        key "address";
        description
          "Neighbor Information";
        leaf address {
          type inet:ipv4-address-no-zone;
          description
            "The Neighbor IP address";
        }
        uses live_ncs_MLDP-NEIGHBOR-BAG;
      }
    }
  }

  grouping VRF-TABLE {
    description
      "Common node of active, standby";
    container vrfs {
      description
        "VRF specific operational data";
      list vrf {
        key "vrf-name";
        description
          "Operational data for given VRF";
        leaf vrf-name {
          type xr:Cisco-ios-xr-string {
            length "1..32";
          }
          description
            "VRF Name";
        }
        uses NEIGHBOR-ADDRESS-TABLE;
        uses DATABASE-TABLE;
        uses ROOT-ADDRESS-TABLE;
        uses CONTEXT;
        uses NEIGHBOR-TABLE;
      }
    }
  }

  grouping MFI-ENTRY-TABLE {
    description
      "Common node of active, standby";
    container mfi-entries {
      description
        "MLDP MFI Table";
      list mfi-entry {
        key "mpls-label";
        description
          "MLDP MFI Information";
        leaf mpls-label {
          type uint32;
          description
            "MPLS Label";
        }
        uses MLDP-MFI-RW-BAG;
      }
    }
  }

  grouping LSM-ID-TABLE {
    description
      "Common node of active, standby";
    container lsm-ids {
      description
        "MLDP LSM-ID";
      list lsm-id {
        key "lsm-id";
        description
          "MLDP LSMID Information";
        leaf lsm-id {
          type uint32;
          description
            "LSM ID";
        }
        uses MLDP-DATABASE-BAG;
      }
    }
  }

  grouping NEIGHBOR-ADDRESS-TABLE {
    description
      "Common node of vrf, default-context";
    container neighbor-addresses {
      description
        "MLDP Neighbors Addresses";
      list neighbor-address {
        key "address";
        description
          "Neighbor Address Information";
        leaf address {
          type inet:ipv4-address-no-zone;
          description
            "The Neighbor IP address";
        }
        uses MLDP-NEIGHBOR-ADDR-BAG;
      }
    }
  }

  grouping ROOT-ADDRESS-TABLE {
    description
      "Common node of vrf, default-context";
    container root-addresses {
      description
        "MLDP Root Table";
      list root-address {
        key "root-address";
        description
          "MLDP Root Information";
        leaf root-address {
          type inet:ipv4-address-no-zone;
          description
            "Root address";
        }
        uses MLDP-ROOT-BAG;
      }
    }
  }

  grouping STATUS {
    description
      "Common node of active, standby";
    container status {
      description
        "MLDP Status";
      uses MLDP-STATUS-BAG;
    }
  }

  grouping CONTEXT {
    description
      "Common node of vrf, default-context";
    container context {
      description
        "MLDP Context";
      uses MLDP-CONTEXT-BAG;
    }
  }

  grouping DATABASE-TABLE {
    description
      "Common node of vrf, default-context";
    container databases {
      description
        "MLDP Database";
      list database {
        key "lsp-type root-address opaque-type opaque-value-string";
        description
          "MLDP Database Information";
        leaf lsp-type {
          type Lsp;
          description
            "LSP Type";
        }
        leaf root-address {
          type inet:ipv4-address-no-zone;
          description
            "Root address";
        }
        leaf opaque-type {
          type Opaque;
          description
            "Opaque Type";
        }
        leaf opaque-value-string {
          type xr:Cisco-ios-xr-string {
            length "1..255";
          }
          description
            "OpaqueValue";
        }
        uses MLDP-DATABASE-BAG;
      }
    }
  }

  grouping LSP-BINDINGS-TABLE {
    description
      "Common node of active, standby";
    container lsp-bindings {
      description
        "MLDP LSP Bindings Table";
      list lsp-binding {
        key "lsm-id";
        description
          "MLDP LSP Binding Information";
        leaf lsm-id {
          type uint32;
          description
            "LSM ID";
        }
        uses MLDP-BINDING-LSP-BAG;
      }
    }
  }

  grouping DEFAULT-CONTEXT {
    description
      "Common node of active, standby";
    container default-context {
      description
        "Default context specific operational data";
      uses NEIGHBOR-ADDRESS-TABLE;
      uses DATABASE-TABLE;
      uses ROOT-ADDRESS-TABLE;
      uses CONTEXT;
      uses NEIGHBOR-TABLE;
    }
  }

  grouping NEIGHBOR-TABLE {
    description
      "Common node of vrf, default-context";
    container neighbors {
      description
        "MLDP Neighbors";
      list neighbor {
        key "address";
        description
          "Neighbor Information";
        leaf address {
          type inet:ipv4-address-no-zone;
          description
            "The Neighbor IP address";
        }
        uses MLDP-NEIGHBOR-BAG;
      }
    }
  }

  augment "/ncs:devices/ncs:device/ncs:config" {
    // NCS drop config false container 'mpls-mldp'
  }
  augment "/ncs:devices/ncs:device/ncs:live-status" {
    container mpls-mldp {
      tailf:ncs-device-type "netconf";
      tailf:display-when "not(../../ncs:module) or ../../ncs:module[ncs:name='Cisco-IOS-XR-mpls-ldp-mldp-oper'] or (../../ncs:live-status-protocol[not(ncs:capability)]) or (../../ncs:live-status-protocol/ncs:capability/ncs:module[.='Cisco-IOS-XR-mpls-ldp-mldp-oper'])";
      description
        "MPLS MLDP operational data";
      container active {
        description
          "Active MPLS MLDP operational data";
        uses live_ncs_STATUS;
        uses live_ncs_MFI-ENTRY-TABLE;
        uses live_ncs_LSP-BINDINGS-TABLE;
        uses live_ncs_LSM-ID-TABLE;
        uses live_ncs_VRF-TABLE;
        uses live_ncs_DEFAULT-CONTEXT;
      }
      container standby {
        description
          "Standby MPLS MLDP operational data";
        uses live_ncs_STATUS;
        uses live_ncs_MFI-ENTRY-TABLE;
        uses live_ncs_LSP-BINDINGS-TABLE;
        uses live_ncs_LSM-ID-TABLE;
        uses live_ncs_VRF-TABLE;
        uses live_ncs_DEFAULT-CONTEXT;
      }
    }
  }
  augment "/ncs:devices/ncs:template/ncs:ned-id/ncs:config" {
    // NCS drop config false container 'mpls-mldp'
  }
}

module Cisco-IOS-XR-hw-module-cfg-deviations {
  // Generated by yanger -t ncs
  tailf:mount-id "cisco-iosxr-nc-7.3:cisco-iosxr-nc-7.3";
  tailf:ncs-device-type "netconf";

  namespace "http://cisco.com/ns/yang/Cisco-IOS-XR-hw-module-cfg-deviations";
  prefix cisco-ios-xr-hw-module-cfg-dev;

  import Cisco-IOS-XR-hw-module-cfg {
    prefix hw-module-cfg;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations of HW-module cfg data
     model set for Cisco IOS-XR.

     Copyright (c) 2013-2020 by Cisco Systems, Inc.
     All rights reserved.";

  revision 2020-05-27 {
    description
      "Initial revision applicable to IOS-XR 7. 3. 1 and older releases";
  }

  deviation "/ncs:devices/ncs:template/ncs:ned-id/ncs:config/hw-module-cfg:hw-module/hw-module-cfg:nodes/hw-module-cfg:node/hw-module-cfg:config/hw-module-cfg:auto-reset-disable" {
    deviate not-supported;
  }
  deviation "/ncs:devices/ncs:device/ncs:live-status/hw-module-cfg:hw-module/hw-module-cfg:nodes/hw-module-cfg:node/hw-module-cfg:config/hw-module-cfg:auto-reset-disable" {
    deviate not-supported;
  }
  deviation "/ncs:devices/ncs:device/ncs:config/hw-module-cfg:hw-module/hw-module-cfg:nodes/hw-module-cfg:node/hw-module-cfg:config/hw-module-cfg:auto-reset-disable" {
    deviate not-supported;
  }
  deviation "/ncs:devices/ncs:template/ncs:ned-id/ncs:config/hw-module-cfg:hw-module/hw-module-cfg:nodes/hw-module-cfg:node/hw-module-cfg:config/hw-module-cfg:attention-led" {
    deviate not-supported;
  }
  deviation "/ncs:devices/ncs:device/ncs:live-status/hw-module-cfg:hw-module/hw-module-cfg:nodes/hw-module-cfg:node/hw-module-cfg:config/hw-module-cfg:attention-led" {
    deviate not-supported;
  }
  deviation "/ncs:devices/ncs:device/ncs:config/hw-module-cfg:hw-module/hw-module-cfg:nodes/hw-module-cfg:node/hw-module-cfg:config/hw-module-cfg:attention-led" {
    deviate not-supported;
  }
}

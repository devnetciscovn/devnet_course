module Cisco-IOS-XR-mrib-oper {
  // Generated by yanger -t ncs
  tailf:mount-id "cisco-iosxr-nc-7.3:cisco-iosxr-nc-7.3";
  tailf:ncs-device-type "netconf";

  namespace "http://cisco.com/ns/yang/Cisco-IOS-XR-mrib-oper";
  prefix mrib-oper;

  import ietf-inet-types {
    prefix inet;
  }
  import Cisco-IOS-XR-types {
    prefix xr;
  }
  import cisco-semver {
    prefix semver;
  }
  include Cisco-IOS-XR-mrib-oper-sub1 {
    revision-date 2020-10-11;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mrib package operational data.

     This module contains definitions
     for the following management objects:
       ipv6-mrib: IPv6 MRIB operational data
       mrib: MRIB operational data

     Copyright (c) 2013-2020 by Cisco Systems, Inc.
     All rights reserved.";

  revision 2020-10-11 {
    description
      "Backward compatible addition in leaf table-mdt-name-tree-sid,table-tree-sid-turnaround and reference-count.";
    semver:module-version "2.0.0";
  }
  revision 2020-02-13 {
    description
      "Fixing CSCvr71562.";
  }
  revision 2019-08-27 {
    description
      "Providing MRIB information.";
  }
  revision 2019-04-05 {
    description
      "Establish semantic version baseline.";
  }
  revision 2015-11-09 {
    description
      "IOS XR 6.0 revision.";
  }

  typedef ncs_template_Mrib-core-tree-id {
    type string;
    description
      "Mrib core tree id";
  }

  typedef ncs_rpc_notif_Mrib-core-tree-id {
    type enumeration {
      enum "any" {
        value 0;
        description
          "Any";
      }
      enum "lsm-source-pe-ipv4" {
        value 1;
        description
          "IPv4 LSM Source PE";
      }
      enum "lsm-interface-handle-ipv4" {
        value 2;
        description
          "IPv4 LSM Interface Handle";
      }
      enum "lsm-source-pe-ipv6" {
        value 3;
        description
          "IPv6 LSM Source PE";
      }
      enum "lsm-interface-handle-ipv6" {
        value 4;
        description
          "IPv6 LSM Interface Handle";
      }
      enum "lsm-id" {
        value 5;
        description
          "LSM ID";
      }
      enum "ipv4" {
        value 6;
        description
          "IPv4";
      }
      enum "ipv6" {
        value 7;
        description
          "IPv6";
      }
      enum "mldp-interface-handle-ipv4" {
        value 8;
        description
          "IPv4 MLDP Interface Handle";
      }
      enum "mldp-interface-handle-ipv6" {
        value 9;
        description
          "IPv6 MLDP Interface Handle";
      }
      enum "none" {
        value 10;
        description
          "None";
      }
      enum "ti-mo-frr-tail" {
        value 11;
        description
          "TI MoFRR Tail";
      }
      enum "ti-mo-frr-head" {
        value 12;
        description
          "TI MoFRR Head";
      }
    }
    description
      "Mrib core tree id";
  }

  typedef live_ncs_Mrib-core-tree-id {
    type enumeration {
      enum "any" {
        value 0;
        description
          "Any";
      }
      enum "lsm-source-pe-ipv4" {
        value 1;
        description
          "IPv4 LSM Source PE";
      }
      enum "lsm-interface-handle-ipv4" {
        value 2;
        description
          "IPv4 LSM Interface Handle";
      }
      enum "lsm-source-pe-ipv6" {
        value 3;
        description
          "IPv6 LSM Source PE";
      }
      enum "lsm-interface-handle-ipv6" {
        value 4;
        description
          "IPv6 LSM Interface Handle";
      }
      enum "lsm-id" {
        value 5;
        description
          "LSM ID";
      }
      enum "ipv4" {
        value 6;
        description
          "IPv4";
      }
      enum "ipv6" {
        value 7;
        description
          "IPv6";
      }
      enum "mldp-interface-handle-ipv4" {
        value 8;
        description
          "IPv4 MLDP Interface Handle";
      }
      enum "mldp-interface-handle-ipv6" {
        value 9;
        description
          "IPv6 MLDP Interface Handle";
      }
      enum "none" {
        value 10;
        description
          "None";
      }
      enum "ti-mo-frr-tail" {
        value 11;
        description
          "TI MoFRR Tail";
      }
      enum "ti-mo-frr-head" {
        value 12;
        description
          "TI MoFRR Head";
      }
    }
    description
      "Mrib core tree id";
  }

  typedef Mrib-core-tree-id {
    type enumeration {
      enum "any" {
        value 0;
        description
          "Any";
      }
      enum "lsm-source-pe-ipv4" {
        value 1;
        description
          "IPv4 LSM Source PE";
      }
      enum "lsm-interface-handle-ipv4" {
        value 2;
        description
          "IPv4 LSM Interface Handle";
      }
      enum "lsm-source-pe-ipv6" {
        value 3;
        description
          "IPv6 LSM Source PE";
      }
      enum "lsm-interface-handle-ipv6" {
        value 4;
        description
          "IPv6 LSM Interface Handle";
      }
      enum "lsm-id" {
        value 5;
        description
          "LSM ID";
      }
      enum "ipv4" {
        value 6;
        description
          "IPv4";
      }
      enum "ipv6" {
        value 7;
        description
          "IPv6";
      }
      enum "mldp-interface-handle-ipv4" {
        value 8;
        description
          "IPv4 MLDP Interface Handle";
      }
      enum "mldp-interface-handle-ipv6" {
        value 9;
        description
          "IPv6 MLDP Interface Handle";
      }
      enum "none" {
        value 10;
        description
          "None";
      }
      enum "ti-mo-frr-tail" {
        value 11;
        description
          "TI MoFRR Tail";
      }
      enum "ti-mo-frr-head" {
        value 12;
        description
          "TI MoFRR Head";
      }
    }
    description
      "Mrib core tree id";
  }

  grouping ncs_template_REMOTE-TABLE-LINE-CARD {
    description
      "Common node of database, default-context";
    container remote-table-line-card {
      description
        "Show the linked remote entry";
      uses ncs_template_MRIB-TLC-BAG;
    }
  }

  grouping ncs_template_ROUTE-TABLE {
    description
      "Common node of database, default-context";
    container routes {
      description
        "The set of MRIB RouteDB operations";
      list route {
        // NCS patched for predictable order
        ordered-by user;
        key "source-address group-address prefix-length";
        description
          "MRIB Route DB Entry Information";
        leaf source-address {
          type string;
          description
            "Source Address";
        }
        leaf group-address {
          type string;
          description
            "Group Address";
        }
        leaf prefix-length {
          type string;
          description
            "Prefix Length";
        }
        uses ncs_template_MRIB-ROUTE-BAG;
      }
    }
  }

  grouping ncs_template_GW-SUMMARY-TABLE {
    description
      "Common node of database, default-context";
    container gw-summaries {
      description
        "MRIB AMT Gateway Summary Information";
      list gw-summary {
        // NCS patched for predictable order
        ordered-by user;
        key "gateway-address gateway-port";
        description
          "MRIB AMT Gateway DB Entry";
        leaf gateway-address {
          type string;
          description
            "Gateway Address";
        }
        leaf gateway-port {
          type string;
          description
            "Gateway Port";
        }
        uses ncs_template_MRIB-AMT-GW-SUMMARY-BAG;
      }
    }
  }

  grouping ncs_template_TABLE-LINE-CARD {
    description
      "Common node of database, default-context";
    container table-line-card {
      description
        "MRIB Table-LineCard database";
      uses ncs_template_MRIB-TLC-BAG;
    }
  }

  grouping ncs_template_ROUTE-OUTGOING-INTERFACE-TABLE {
    description
      "Common node of database, default-context";
    container route-outgoing-interfaces {
      description
        "MRIB RouteDB Outgoing Interface Table ";
      list route-outgoing-interface {
        // NCS patched for predictable order
        ordered-by user;
        key "source-address group-address prefix-length";
        description
          "MRIB Route DB Outgoing Interface Entry
           Information";
        leaf source-address {
          type string;
          description
            "Source Address";
        }
        leaf group-address {
          type string;
          description
            "Group Address";
        }
        leaf prefix-length {
          type string;
          description
            "Prefix Length";
        }
        uses ncs_template_MRIB-ROUTE-OLE-BAG;
      }
    }
  }

  grouping ncs_template_AMT-ROUTE-TABLE {
    description
      "Common node of database, default-context";
    container amt-routes {
      description
        "The set of AMT Route table information";
      list amt-route {
        // NCS patched for predictable order
        ordered-by user;
        key "source-address group-address prefix-length";
        description
          "MRIB AMT Route DB Entry Information";
        leaf source-address {
          type string;
          description
            "Source Address";
        }
        leaf group-address {
          type string;
          description
            "Group Address";
        }
        leaf prefix-length {
          type string;
          description
            "Prefix Length";
        }
        uses ncs_template_MRIB-AMT-ROUTE-BAG;
      }
    }
  }

  grouping ncs_template_PROCESS {
    description
      "Common node of active, standby";
    container process {
      description
        "Process";
      container registration-database-entries {
        description
          "MRIB Registration Database Table";
        list registration-database-entry {
          // NCS patched for predictable order
          ordered-by user;
          key "vrf-name entry-type next-hop-address";
          description
            "MRIB Registration Database Entry Information";
          leaf vrf-name {
            type xr:ncs_template_Cisco-ios-xr-string;
            description
              "VRF Name";
          }
          leaf entry-type {
            type string;
            description
              "Entry Type";
          }
          leaf next-hop-address {
            type string;
            description
              "Next-Hop Address";
          }
          uses ncs_template_MRIB-REGDB-BAG;
        }
      }
      container cofo {
        description
          "Collapsed forwarding Information";
        container encap-entries {
          description
            "EncapID information exchanged for collapsed
             forwarding";
          list encap-entry {
            // NCS patched for predictable order
            ordered-by user;
            key "encap-id";
            description
              "EncapID information exchanged for collapsed
               forwarding";
            leaf encap-id {
              type string;
              description
                "Encap Identifier";
            }
            uses ncs_template_MRIB-COFO-ENCAP-BAG;
          }
        }
        container ip-multicast-infos {
          description
            "IP multicast information exchanged for
             collapsed forwarding";
          list ip-multicast-info {
            // NCS patched for predictable order
            ordered-by user;
            key "source group";
            description
              "IP multicast information exchanged for
               collapsed forwarding";
            leaf source {
              type string;
              description
                "Source Address";
            }
            leaf group {
              type string;
              description
                "Group Address Prefix";
            }
            uses ncs_template_MRIB-COFO-BAG;
          }
        }
        container lsm-infos {
          description
            "LSM information exchanged for collapsed
             forwarding";
          list lsm-info {
            // NCS patched for predictable order
            ordered-by user;
            key "fec";
            description
              "LSM information exchanged for collapsed
               forwarding";
            leaf fec {
              type xr:ncs_template_Cisco-ios-xr-string;
              description
                "The FEC of the local label for which
                 node-set or FGID data is being exchanged";
            }
            uses ncs_template_LMRIB-COFO-BAG;
          }
        }
        container summary {
          description
            "Summary of statistics for collapsed forwarding";
          uses ncs_template_MRIB-COFO-SUMMARY-BAG;
        }
      }
      container nsr-ends {
        description
          "NSR End Table";
        list nsr-end {
          // NCS patched for predictable order
          ordered-by user;
          key "index";
          description
            "NSR End";
          leaf index {
            type string;
            description
              "Index";
          }
          uses ncs_template_MRIB-NSR-END-INFO;
        }
      }
      container mrib-bvi-interfaces {
        description
          "MRIB BVI interface mapping";
        list mrib-bvi-interface {
          // NCS patched for predictable order
          ordered-by user;
          key "interface-name";
          description
            "BVI Interface Handle";
          leaf interface-name {
            type xr:ncs_template_Interface-name;
            description
              "Interface Name";
          }
          uses ncs_template_MRIB-BVI-INTERFACE-BAG;
        }
      }
      container mrib-bvi-routes {
        description
          "MRIB BVI route table";
        list mrib-bvi-route {
          // NCS patched for predictable order
          ordered-by user;
          key "interface-name source-address group-address prefix-length";
          description
            "MRIB BVI route entry";
          leaf interface-name {
            type xr:ncs_template_Interface-name;
            description
              "Interface Name";
          }
          leaf source-address {
            type string;
            description
              "Source Address";
          }
          leaf group-address {
            type string;
            description
              "Group Address";
          }
          leaf prefix-length {
            type string;
            description
              "Prefix Length";
          }
          uses ncs_template_MRIB-BVI-ROUTE-BAG;
        }
      }
      container evpn {
        description
          "EVPN information";
        container bucket-entries {
          description
            "EVPN Bucket DataBase Table information";
          list bucket-entry {
            // NCS patched for predictable order
            ordered-by user;
            description
              "Mrib EVPN Bucket Database Entry";
            leaf bucket-id {
              type string;
              description
                "Bucket Identifier";
            }
            leaf parent-if-handle {
              type xr:ncs_template_Hex-integer;
              description
                "Parent Handle";
            }
            uses ncs_template_MRIB-EVPN-BKT-BAG;
          }
        }
      }
      container checkpoint-statistics {
        description
          "Checkpoint Statistics";
        uses ncs_template_MRIB-CHKPT-STATS;
      }
      container mdt-interfaces {
        description
          "MRIB IIR interface DB";
        list mdt-interface {
          // NCS patched for predictable order
          ordered-by user;
          key "interface-name";
          description
            "Interface handle";
          leaf interface-name {
            type xr:ncs_template_Interface-name;
            description
              "Interface Name";
          }
          uses ncs_template_MRIB-MDT-IFH-BAG;
        }
      }
      container clients {
        description
          "MRIB Client Table";
        list client {
          // NCS patched for predictable order
          ordered-by user;
          key "client-name instance-name";
          description
            "MRIB Client DB Entry Information";
          leaf client-name {
            type xr:ncs_template_Cisco-ios-xr-string;
            description
              "Client Name";
          }
          leaf instance-name {
            type xr:ncs_template_Cisco-ios-xr-string;
            description
              "Instance Name";
          }
          uses ncs_template_MRIB-CLIENT-BAG;
        }
      }
      container mpls-forwardings {
        description
          "MRIB Label Table";
        list mpls-forwarding {
          // NCS patched for predictable order
          ordered-by user;
          key "label";
          description
            "MRIB Label DB Information";
          leaf label {
            type string;
            description
              "Label";
          }
          uses ncs_template_MRIB-MPLS-FORWARDING-BAG;
        }
      }
      container nsf {
        description
          "NSF Information";
        uses ncs_template_MRIB-NSF-BAG;
      }
      container rpf-identifiers {
        description
          "RPF Identifier Table";
        list rpf-identifier {
          // NCS patched for predictable order
          ordered-by user;
          key "source-pe-address mrib-allocated";
          description
            "RPF Identifier";
          leaf source-pe-address {
            type string;
            description
              "Source PE Address";
          }
          leaf mrib-allocated {
            type string;
            description
              "MRIB Allocated";
          }
          uses ncs_template_MRIB-RPFID-SPE-INFO;
        }
      }
      container client-filters {
        description
          "MRIB Client Filter Table";
        list client-filter {
          // NCS patched for predictable order
          ordered-by user;
          key "client-name instance-name";
          description
            "MRIB Client Filter DB Entry Information";
          leaf client-name {
            type xr:ncs_template_Cisco-ios-xr-string;
            description
              "Client Name";
          }
          leaf instance-name {
            type xr:ncs_template_Cisco-ios-xr-string;
            description
              "Instance Name";
          }
          uses ncs_template_MRIB-FILTER-BAG;
        }
      }
      container encap-identifiers {
        description
          "Encap Identifier Table";
        list encap-identifier {
          // NCS patched for predictable order
          ordered-by user;
          key "encap-id";
          description
            "Encap Identifier";
          leaf encap-id {
            type string;
            description
              "Encap Identifier";
          }
          uses ncs_template_MRIB-ENCAPID-BAG;
        }
      }
    }
  }

  grouping ncs_template_ROUTE-COLLAPSE-IPC {
    description
      "Common node of database, default-context";
    container route-collapse-ipc {
      description
        "MRIB Route Collapse IPC Core-egress-node
         Information";
      uses ncs_template_MRIB-RC-IPC-BAG;
    }
  }

  grouping ncs_template_LABEL-INFO {
    description
      "Common node of database, default-context";
    container label-info {
      description
        "MRIB Label Table Information";
      uses ncs_template_MRIB-LABEL-TABLE-INFO-BAG;
    }
  }

  grouping ncs_template_AMT-ROUTEDB-SUMMARY-TABLE {
    description
      "Common node of database, default-context";
    container amt-routedb-summaries {
      description
        "MRIB AMT RouteDB Summary Information";
      list amt-routedb-summary {
        // NCS patched for predictable order
        ordered-by user;
        key "source-address group-address";
        description
          "MRIB AMT Route Summary Entry";
        leaf source-address {
          type string;
          description
            "Source Address";
        }
        leaf group-address {
          type string;
          description
            "Group Address";
        }
        uses ncs_template_MRIB-AMT-ROUTE-SUMMARY-BAG;
      }
    }
  }

  grouping ncs_template_ROUTE-COLLAPSE-TABLE {
    description
      "Common node of database, default-context";
    container route-collapses {
      description
        "MRIB Route Collapse database";
      list route-collapse {
        // NCS patched for predictable order
        ordered-by user;
        key "type group-address";
        description
          "Route Collapse Information";
        leaf type {
          type xr:ncs_template_Cisco-ios-xr-string;
          description
            "Type";
        }
        leaf group-address {
          type string;
          description
            "Input MDT grp or prev group";
        }
        uses ncs_template_MRIB-RC-MDT-BAG;
      }
    }
  }

  grouping ncs_template_ACTIVE {
    description
      "Common node of mrib, ipv6-mrib";
    container active {
      description
        "Active Process";
      uses ncs_template_PROCESS;
      uses ncs_template_DEFAULT-CONTEXT;
      uses ncs_template_DATABASE-TABLE;
    }
  }

  grouping ncs_template_AMT-ROUTEDB-EXPIRED-TABLE {
    description
      "Common node of database, default-context";
    container amt-routedb-expireds {
      description
        "MRIB AMT Route Expired Information";
      list amt-routedb-expired {
        // NCS patched for predictable order
        ordered-by user;
        key "source-address group-address gw-address port";
        description
          "MRIB AMT Route Expired Entry";
        leaf source-address {
          type string;
          description
            "Source Address";
        }
        leaf group-address {
          type string;
          description
            "Group Address";
        }
        leaf gw-address {
          type string;
          description
            "GW Address";
        }
        leaf port {
          type string;
          description
            "Prefix Length";
        }
        uses ncs_template_MRIB-AMT-ROUTE-EX-BAG;
      }
    }
  }

  grouping ncs_template_SUMMARY {
    description
      "Common node of database, default-context";
    container summary {
      description
        "MRIB RouteDB Summary Information";
      uses ncs_template_MRIB-DB-SUMM-BAG;
    }
  }

  grouping ncs_template_GW-EXPIRED-TABLE {
    description
      "Common node of database, default-context";
    container gw-expireds {
      description
        "MRIB AMT Gateway DB Expired Information";
      list gw-expired {
        // NCS patched for predictable order
        ordered-by user;
        key "gateway-address gateway-port";
        description
          "MRIB AMT Gateway Expired Entry";
        leaf gateway-address {
          type string;
          description
            "Gateway Address";
        }
        leaf gateway-port {
          type string;
          description
            "Gateway Port";
        }
        uses ncs_template_MRIB-AMT-GW-EX-BAG;
      }
    }
  }

  grouping ncs_template_AMT-GATEWAY-DB-TABLE {
    description
      "Common node of database, default-context";
    container amt-gateway-dbs {
      description
        "The set of AMT Gateway DataBase Table
         information";
      list amt-gateway-db {
        // NCS patched for predictable order
        ordered-by user;
        key "gateway-address gateway-port";
        description
          "MRIB AMT Gateway DB Entry";
        leaf gateway-address {
          type string;
          description
            "Gateway Address";
        }
        leaf gateway-port {
          type string;
          description
            "Gateway Port";
        }
        uses ncs_template_MRIB-AMT-GW-BAG;
      }
    }
  }

  grouping ncs_template_DATABASE-TABLE {
    description
      "Common node of active, standby";
    container databases {
      description
        "Database Table";
      list database {
        // NCS patched for predictable order
        ordered-by user;
        key "database-name";
        description
          "MRIB Table Information";
        leaf database-name {
          type xr:ncs_template_Cisco-ios-xr-string;
          description
            "Database Name";
        }
        uses ncs_template_ROUTE-COLLAPSE-IPC-TLC;
        uses ncs_template_GW-SUMMARY-TABLE;
        uses ncs_template_ROUTE-COLLAPSE-IPC;
        uses ncs_template_MPLSTE-BACKUP-TABLE;
        uses ncs_template_ROUTE-TABLE;
        uses ncs_template_TABLE-LINE-CARD;
        uses ncs_template_FRR-SUMMARY;
        uses ncs_template_IIR-INTERFACE-TABLE;
        uses ncs_template_AMT-GATEWAY-DB-TABLE;
        uses ncs_template_ROUTE-OUTGOING-INTERFACE-TABLE;
        uses ncs_template_GW-EXPIRED-TABLE;
        uses ncs_template_REMOTE-TABLE-LINE-CARD;
        uses ncs_template_AMT-ROUTEDB-SUMMARY-TABLE;
        uses ncs_template_ROUTE-COLLAPSE-TABLE;
        uses ncs_template_LABEL-INFO;
        uses ncs_template_FRR-TABLE;
        uses ncs_template_AMT-ROUTEDB-EXPIRED-TABLE;
        uses ncs_template_TABLE-INFORMATION;
        uses ncs_template_SUMMARY;
        uses ncs_template_AMT-ROUTE-TABLE;
      }
    }
  }

  grouping ncs_template_FRR-SUMMARY {
    description
      "Common node of database, default-context";
    container frr-summary {
      description
        "MRIB FRR DB Summary Information";
      uses ncs_template_MRIB-MPLS-FRR-SUMMARY-BAG;
    }
  }

  grouping ncs_template_ROUTE-COLLAPSE-IPC-TLC {
    description
      "Common node of database, default-context";
    container route-collapse-ipc-tlc {
      description
        "Route Collapse IPC TLC Information";
      uses ncs_template_MRIB-RC-IPC-BAG;
    }
  }

  grouping ncs_template_FRR-TABLE {
    description
      "Common node of database, default-context";
    container frrs {
      description
        "FRR Table";
      list frr {
        // NCS patched for predictable order
        ordered-by user;
        key "start-label";
        description
          "MRIB FRR DB Information";
        leaf start-label {
          type string;
          description
            "Start Label";
        }
        uses ncs_template_MRIB-MPLS-FRR-BAG;
      }
    }
  }

  grouping ncs_template_MPLSTE-BACKUP-TABLE {
    description
      "Common node of database, default-context";
    container mplste-backups {
      description
        "MRIB MPLS TE Backup Database Information";
      list mplste-backup {
        // NCS patched for predictable order
        ordered-by user;
        key "interface-name";
        description
          "MRIB MPLS TE Backup Database Information";
        leaf interface-name {
          type xr:ncs_template_Interface-name;
          description
            "Interface Name";
        }
        uses ncs_template_MRIB-MPLS-BKUP-BAG;
      }
    }
  }

  grouping ncs_template_DEFAULT-CONTEXT {
    description
      "Common node of active, standby";
    container default-context {
      description
        "Default context";
      container mroutes {
        description
          "MRIB mpls mroute Table";
        list mroute {
          // NCS patched for predictable order
          ordered-by user;
          key "tunnel core-tree-id-type";
          description
            "MRIB MPLS MRoute information";
          leaf tunnel {
            type string;
            description
              "Tunnel Interface Handle";
          }
          leaf core-tree-id-type {
            type ncs_template_Mrib-core-tree-id;
            description
              "Core Tree ID Type";
          }
          uses ncs_template_MRIB-MPLS-DB-BAG;
        }
      }
      uses ncs_template_ROUTE-COLLAPSE-IPC-TLC;
      uses ncs_template_GW-SUMMARY-TABLE;
      uses ncs_template_ROUTE-COLLAPSE-IPC;
      uses ncs_template_MPLSTE-BACKUP-TABLE;
      uses ncs_template_ROUTE-TABLE;
      uses ncs_template_TABLE-LINE-CARD;
      uses ncs_template_FRR-SUMMARY;
      uses ncs_template_IIR-INTERFACE-TABLE;
      uses ncs_template_AMT-GATEWAY-DB-TABLE;
      uses ncs_template_ROUTE-OUTGOING-INTERFACE-TABLE;
      uses ncs_template_GW-EXPIRED-TABLE;
      uses ncs_template_REMOTE-TABLE-LINE-CARD;
      uses ncs_template_AMT-ROUTEDB-SUMMARY-TABLE;
      uses ncs_template_ROUTE-COLLAPSE-TABLE;
      uses ncs_template_LABEL-INFO;
      uses ncs_template_FRR-TABLE;
      uses ncs_template_AMT-ROUTEDB-EXPIRED-TABLE;
      uses ncs_template_TABLE-INFORMATION;
      uses ncs_template_SUMMARY;
      uses ncs_template_AMT-ROUTE-TABLE;
    }
  }

  grouping ncs_template_STANDBY {
    description
      "Common node of mrib, ipv6-mrib";
    container standby {
      description
        "Standby Process";
      uses ncs_template_PROCESS;
      uses ncs_template_DEFAULT-CONTEXT;
      uses ncs_template_DATABASE-TABLE;
    }
  }

  grouping ncs_template_TABLE-INFORMATION {
    description
      "Common node of database, default-context";
    container table-information {
      description
        "MRIB VRF table information";
      uses ncs_template_MRIB-TABLE-INFO-BAG;
    }
  }

  grouping ncs_template_IIR-INTERFACE-TABLE {
    description
      "Common node of database, default-context";
    container iir-interfaces {
      description
        "MRIB IIR interface DB";
      list iir-interface {
        // NCS patched for predictable order
        ordered-by user;
        key "interface-name";
        description
          "MRIB Interface information";
        leaf interface-name {
          type xr:ncs_template_Interface-name;
          description
            "Interface Name";
        }
        uses ncs_template_MRIB-IIR-INTF-BAG;
      }
    }
  }

  grouping ncs_rpc_notif_REMOTE-TABLE-LINE-CARD {
    description
      "Common node of database, default-context";
    container remote-table-line-card {
      description
        "Show the linked remote entry";
      uses ncs_rpc_notif_MRIB-TLC-BAG;
    }
  }

  grouping ncs_rpc_notif_ROUTE-TABLE {
    description
      "Common node of database, default-context";
    container routes {
      description
        "The set of MRIB RouteDB operations";
      list route {
        key "source-address group-address prefix-length";
        description
          "MRIB Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses ncs_rpc_notif_MRIB-ROUTE-BAG;
      }
    }
  }

  grouping ncs_rpc_notif_GW-SUMMARY-TABLE {
    description
      "Common node of database, default-context";
    container gw-summaries {
      description
        "MRIB AMT Gateway Summary Information";
      list gw-summary {
        key "gateway-address gateway-port";
        description
          "MRIB AMT Gateway DB Entry";
        leaf gateway-address {
          type inet:ip-address-no-zone;
          description
            "Gateway Address";
        }
        leaf gateway-port {
          type uint32;
          description
            "Gateway Port";
        }
        uses ncs_rpc_notif_MRIB-AMT-GW-SUMMARY-BAG;
      }
    }
  }

  grouping ncs_rpc_notif_TABLE-LINE-CARD {
    description
      "Common node of database, default-context";
    container table-line-card {
      description
        "MRIB Table-LineCard database";
      uses ncs_rpc_notif_MRIB-TLC-BAG;
    }
  }

  grouping ncs_rpc_notif_ROUTE-OUTGOING-INTERFACE-TABLE {
    description
      "Common node of database, default-context";
    container route-outgoing-interfaces {
      description
        "MRIB RouteDB Outgoing Interface Table ";
      list route-outgoing-interface {
        key "source-address group-address prefix-length";
        description
          "MRIB Route DB Outgoing Interface Entry
           Information";
        leaf source-address {
          type inet:ip-address-no-zone;
          description
            "Source Address";
        }
        leaf group-address {
          type inet:ip-address-no-zone;
          description
            "Group Address";
        }
        leaf prefix-length {
          type uint32;
          description
            "Prefix Length";
        }
        uses ncs_rpc_notif_MRIB-ROUTE-OLE-BAG;
      }
    }
  }

  grouping ncs_rpc_notif_AMT-ROUTE-TABLE {
    description
      "Common node of database, default-context";
    container amt-routes {
      description
        "The set of AMT Route table information";
      list amt-route {
        key "source-address group-address prefix-length";
        description
          "MRIB AMT Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses ncs_rpc_notif_MRIB-AMT-ROUTE-BAG;
      }
    }
  }

  grouping ncs_rpc_notif_PROCESS {
    description
      "Common node of active, standby";
    container process {
      description
        "Process";
      container registration-database-entries {
        description
          "MRIB Registration Database Table";
        list registration-database-entry {
          key "vrf-name entry-type next-hop-address";
          description
            "MRIB Registration Database Entry Information";
          leaf vrf-name {
            type xr:ncs_rpc_notif_Cisco-ios-xr-string;
            description
              "VRF Name";
          }
          leaf entry-type {
            type uint32;
            description
              "Entry Type";
          }
          leaf next-hop-address {
            type inet:ip-address-no-zone;
            description
              "Next-Hop Address";
          }
          uses ncs_rpc_notif_MRIB-REGDB-BAG;
        }
      }
      container cofo {
        description
          "Collapsed forwarding Information";
        container encap-entries {
          description
            "EncapID information exchanged for collapsed
             forwarding";
          list encap-entry {
            key "encap-id";
            description
              "EncapID information exchanged for collapsed
               forwarding";
            leaf encap-id {
              type uint32;
              description
                "Encap Identifier";
            }
            uses ncs_rpc_notif_MRIB-COFO-ENCAP-BAG;
          }
        }
        container ip-multicast-infos {
          description
            "IP multicast information exchanged for
             collapsed forwarding";
          list ip-multicast-info {
            key "source group";
            description
              "IP multicast information exchanged for
               collapsed forwarding";
            leaf source {
              type inet:ip-address-no-zone;
              description
                "Source Address";
            }
            leaf group {
              type inet:ip-prefix;
              description
                "Group Address Prefix";
            }
            uses ncs_rpc_notif_MRIB-COFO-BAG;
          }
        }
        container lsm-infos {
          description
            "LSM information exchanged for collapsed
             forwarding";
          list lsm-info {
            key "fec";
            description
              "LSM information exchanged for collapsed
               forwarding";
            leaf fec {
              type xr:ncs_rpc_notif_Cisco-ios-xr-string;
              description
                "The FEC of the local label for which
                 node-set or FGID data is being exchanged";
            }
            uses ncs_rpc_notif_LMRIB-COFO-BAG;
          }
        }
        container summary {
          description
            "Summary of statistics for collapsed forwarding";
          uses ncs_rpc_notif_MRIB-COFO-SUMMARY-BAG;
        }
      }
      container nsr-ends {
        description
          "NSR End Table";
        list nsr-end {
          key "index";
          description
            "NSR End";
          leaf index {
            type uint32;
            description
              "Index";
          }
          uses ncs_rpc_notif_MRIB-NSR-END-INFO;
        }
      }
      container mrib-bvi-interfaces {
        description
          "MRIB BVI interface mapping";
        list mrib-bvi-interface {
          key "interface-name";
          description
            "BVI Interface Handle";
          leaf interface-name {
            type xr:ncs_rpc_notif_Interface-name;
            description
              "Interface Name";
          }
          uses ncs_rpc_notif_MRIB-BVI-INTERFACE-BAG;
        }
      }
      container mrib-bvi-routes {
        description
          "MRIB BVI route table";
        list mrib-bvi-route {
          key "interface-name source-address group-address prefix-length";
          description
            "MRIB BVI route entry";
          leaf interface-name {
            type xr:ncs_rpc_notif_Interface-name;
            description
              "Interface Name";
          }
          leaf source-address {
            type inet:ip-address-no-zone;
            description
              "Source Address";
          }
          leaf group-address {
            type inet:ip-address-no-zone;
            description
              "Group Address";
          }
          leaf prefix-length {
            type uint32;
            description
              "Prefix Length";
          }
          uses ncs_rpc_notif_MRIB-BVI-ROUTE-BAG;
        }
      }
      container evpn {
        description
          "EVPN information";
        container bucket-entries {
          description
            "EVPN Bucket DataBase Table information";
          list bucket-entry {
            description
              "Mrib EVPN Bucket Database Entry";
            leaf bucket-id {
              type uint32;
              description
                "Bucket Identifier";
            }
            leaf parent-if-handle {
              type xr:ncs_rpc_notif_Hex-integer;
              description
                "Parent Handle";
            }
            uses ncs_rpc_notif_MRIB-EVPN-BKT-BAG;
          }
        }
      }
      container checkpoint-statistics {
        description
          "Checkpoint Statistics";
        uses ncs_rpc_notif_MRIB-CHKPT-STATS;
      }
      container mdt-interfaces {
        description
          "MRIB IIR interface DB";
        list mdt-interface {
          key "interface-name";
          description
            "Interface handle";
          leaf interface-name {
            type xr:ncs_rpc_notif_Interface-name;
            description
              "Interface Name";
          }
          uses ncs_rpc_notif_MRIB-MDT-IFH-BAG;
        }
      }
      container clients {
        description
          "MRIB Client Table";
        list client {
          key "client-name instance-name";
          description
            "MRIB Client DB Entry Information";
          leaf client-name {
            type xr:ncs_rpc_notif_Cisco-ios-xr-string;
            description
              "Client Name";
          }
          leaf instance-name {
            type xr:ncs_rpc_notif_Cisco-ios-xr-string;
            description
              "Instance Name";
          }
          uses ncs_rpc_notif_MRIB-CLIENT-BAG;
        }
      }
      container mpls-forwardings {
        description
          "MRIB Label Table";
        list mpls-forwarding {
          key "label";
          description
            "MRIB Label DB Information";
          leaf label {
            type uint32;
            description
              "Label";
          }
          uses ncs_rpc_notif_MRIB-MPLS-FORWARDING-BAG;
        }
      }
      container nsf {
        description
          "NSF Information";
        uses ncs_rpc_notif_MRIB-NSF-BAG;
      }
      container rpf-identifiers {
        description
          "RPF Identifier Table";
        list rpf-identifier {
          key "source-pe-address mrib-allocated";
          description
            "RPF Identifier";
          leaf source-pe-address {
            type inet:ipv4-address-no-zone;
            description
              "Source PE Address";
          }
          leaf mrib-allocated {
            type boolean;
            description
              "MRIB Allocated";
          }
          uses ncs_rpc_notif_MRIB-RPFID-SPE-INFO;
        }
      }
      container client-filters {
        description
          "MRIB Client Filter Table";
        list client-filter {
          key "client-name instance-name";
          description
            "MRIB Client Filter DB Entry Information";
          leaf client-name {
            type xr:ncs_rpc_notif_Cisco-ios-xr-string;
            description
              "Client Name";
          }
          leaf instance-name {
            type xr:ncs_rpc_notif_Cisco-ios-xr-string;
            description
              "Instance Name";
          }
          uses ncs_rpc_notif_MRIB-FILTER-BAG;
        }
      }
      container encap-identifiers {
        description
          "Encap Identifier Table";
        list encap-identifier {
          key "encap-id";
          description
            "Encap Identifier";
          leaf encap-id {
            type uint32;
            description
              "Encap Identifier";
          }
          uses ncs_rpc_notif_MRIB-ENCAPID-BAG;
        }
      }
    }
  }

  grouping ncs_rpc_notif_ROUTE-COLLAPSE-IPC {
    description
      "Common node of database, default-context";
    container route-collapse-ipc {
      description
        "MRIB Route Collapse IPC Core-egress-node
         Information";
      uses ncs_rpc_notif_MRIB-RC-IPC-BAG;
    }
  }

  grouping ncs_rpc_notif_LABEL-INFO {
    description
      "Common node of database, default-context";
    container label-info {
      description
        "MRIB Label Table Information";
      uses ncs_rpc_notif_MRIB-LABEL-TABLE-INFO-BAG;
    }
  }

  grouping ncs_rpc_notif_AMT-ROUTEDB-SUMMARY-TABLE {
    description
      "Common node of database, default-context";
    container amt-routedb-summaries {
      description
        "MRIB AMT RouteDB Summary Information";
      list amt-routedb-summary {
        key "source-address group-address";
        description
          "MRIB AMT Route Summary Entry";
        leaf source-address {
          type inet:ip-address-no-zone;
          description
            "Source Address";
        }
        leaf group-address {
          type inet:ip-address-no-zone;
          description
            "Group Address";
        }
        uses ncs_rpc_notif_MRIB-AMT-ROUTE-SUMMARY-BAG;
      }
    }
  }

  grouping ncs_rpc_notif_ROUTE-COLLAPSE-TABLE {
    description
      "Common node of database, default-context";
    container route-collapses {
      description
        "MRIB Route Collapse database";
      list route-collapse {
        key "type group-address";
        description
          "Route Collapse Information";
        leaf type {
          type xr:ncs_rpc_notif_Cisco-ios-xr-string;
          description
            "Type";
        }
        leaf group-address {
          type inet:ip-address-no-zone;
          description
            "Input MDT grp or prev group";
        }
        uses ncs_rpc_notif_MRIB-RC-MDT-BAG;
      }
    }
  }

  grouping ncs_rpc_notif_ACTIVE {
    description
      "Common node of mrib, ipv6-mrib";
    container active {
      description
        "Active Process";
      uses ncs_rpc_notif_PROCESS;
      uses ncs_rpc_notif_DEFAULT-CONTEXT;
      uses ncs_rpc_notif_DATABASE-TABLE;
    }
  }

  grouping ncs_rpc_notif_AMT-ROUTEDB-EXPIRED-TABLE {
    description
      "Common node of database, default-context";
    container amt-routedb-expireds {
      description
        "MRIB AMT Route Expired Information";
      list amt-routedb-expired {
        key "source-address group-address gw-address port";
        description
          "MRIB AMT Route Expired Entry";
        leaf source-address {
          type inet:ip-address-no-zone;
          description
            "Source Address";
        }
        leaf group-address {
          type inet:ip-address-no-zone;
          description
            "Group Address";
        }
        leaf gw-address {
          type inet:ip-address-no-zone;
          description
            "GW Address";
        }
        leaf port {
          type uint32;
          description
            "Prefix Length";
        }
        uses ncs_rpc_notif_MRIB-AMT-ROUTE-EX-BAG;
      }
    }
  }

  grouping ncs_rpc_notif_SUMMARY {
    description
      "Common node of database, default-context";
    container summary {
      description
        "MRIB RouteDB Summary Information";
      uses ncs_rpc_notif_MRIB-DB-SUMM-BAG;
    }
  }

  grouping ncs_rpc_notif_GW-EXPIRED-TABLE {
    description
      "Common node of database, default-context";
    container gw-expireds {
      description
        "MRIB AMT Gateway DB Expired Information";
      list gw-expired {
        key "gateway-address gateway-port";
        description
          "MRIB AMT Gateway Expired Entry";
        leaf gateway-address {
          type inet:ip-address-no-zone;
          description
            "Gateway Address";
        }
        leaf gateway-port {
          type uint32;
          description
            "Gateway Port";
        }
        uses ncs_rpc_notif_MRIB-AMT-GW-EX-BAG;
      }
    }
  }

  grouping ncs_rpc_notif_AMT-GATEWAY-DB-TABLE {
    description
      "Common node of database, default-context";
    container amt-gateway-dbs {
      description
        "The set of AMT Gateway DataBase Table
         information";
      list amt-gateway-db {
        key "gateway-address gateway-port";
        description
          "MRIB AMT Gateway DB Entry";
        leaf gateway-address {
          type inet:ip-address-no-zone;
          description
            "Gateway Address";
        }
        leaf gateway-port {
          type uint32;
          description
            "Gateway Port";
        }
        uses ncs_rpc_notif_MRIB-AMT-GW-BAG;
      }
    }
  }

  grouping ncs_rpc_notif_DATABASE-TABLE {
    description
      "Common node of active, standby";
    container databases {
      description
        "Database Table";
      list database {
        key "database-name";
        description
          "MRIB Table Information";
        leaf database-name {
          type xr:ncs_rpc_notif_Cisco-ios-xr-string;
          description
            "Database Name";
        }
        uses ncs_rpc_notif_ROUTE-COLLAPSE-IPC-TLC;
        uses ncs_rpc_notif_GW-SUMMARY-TABLE;
        uses ncs_rpc_notif_ROUTE-COLLAPSE-IPC;
        uses ncs_rpc_notif_MPLSTE-BACKUP-TABLE;
        uses ncs_rpc_notif_ROUTE-TABLE;
        uses ncs_rpc_notif_TABLE-LINE-CARD;
        uses ncs_rpc_notif_FRR-SUMMARY;
        uses ncs_rpc_notif_IIR-INTERFACE-TABLE;
        uses ncs_rpc_notif_AMT-GATEWAY-DB-TABLE;
        uses ncs_rpc_notif_ROUTE-OUTGOING-INTERFACE-TABLE;
        uses ncs_rpc_notif_GW-EXPIRED-TABLE;
        uses ncs_rpc_notif_REMOTE-TABLE-LINE-CARD;
        uses ncs_rpc_notif_AMT-ROUTEDB-SUMMARY-TABLE;
        uses ncs_rpc_notif_ROUTE-COLLAPSE-TABLE;
        uses ncs_rpc_notif_LABEL-INFO;
        uses ncs_rpc_notif_FRR-TABLE;
        uses ncs_rpc_notif_AMT-ROUTEDB-EXPIRED-TABLE;
        uses ncs_rpc_notif_TABLE-INFORMATION;
        uses ncs_rpc_notif_SUMMARY;
        uses ncs_rpc_notif_AMT-ROUTE-TABLE;
      }
    }
  }

  grouping ncs_rpc_notif_FRR-SUMMARY {
    description
      "Common node of database, default-context";
    container frr-summary {
      description
        "MRIB FRR DB Summary Information";
      uses ncs_rpc_notif_MRIB-MPLS-FRR-SUMMARY-BAG;
    }
  }

  grouping ncs_rpc_notif_ROUTE-COLLAPSE-IPC-TLC {
    description
      "Common node of database, default-context";
    container route-collapse-ipc-tlc {
      description
        "Route Collapse IPC TLC Information";
      uses ncs_rpc_notif_MRIB-RC-IPC-BAG;
    }
  }

  grouping ncs_rpc_notif_FRR-TABLE {
    description
      "Common node of database, default-context";
    container frrs {
      description
        "FRR Table";
      list frr {
        key "start-label";
        description
          "MRIB FRR DB Information";
        leaf start-label {
          type uint32;
          description
            "Start Label";
        }
        uses ncs_rpc_notif_MRIB-MPLS-FRR-BAG;
      }
    }
  }

  grouping ncs_rpc_notif_MPLSTE-BACKUP-TABLE {
    description
      "Common node of database, default-context";
    container mplste-backups {
      description
        "MRIB MPLS TE Backup Database Information";
      list mplste-backup {
        key "interface-name";
        description
          "MRIB MPLS TE Backup Database Information";
        leaf interface-name {
          type xr:ncs_rpc_notif_Interface-name;
          description
            "Interface Name";
        }
        uses ncs_rpc_notif_MRIB-MPLS-BKUP-BAG;
      }
    }
  }

  grouping ncs_rpc_notif_DEFAULT-CONTEXT {
    description
      "Common node of active, standby";
    container default-context {
      description
        "Default context";
      container mroutes {
        description
          "MRIB mpls mroute Table";
        list mroute {
          key "tunnel core-tree-id-type";
          description
            "MRIB MPLS MRoute information";
          leaf tunnel {
            type uint32;
            description
              "Tunnel Interface Handle";
          }
          leaf core-tree-id-type {
            type ncs_rpc_notif_Mrib-core-tree-id;
            description
              "Core Tree ID Type";
          }
          uses ncs_rpc_notif_MRIB-MPLS-DB-BAG;
        }
      }
      uses ncs_rpc_notif_ROUTE-COLLAPSE-IPC-TLC;
      uses ncs_rpc_notif_GW-SUMMARY-TABLE;
      uses ncs_rpc_notif_ROUTE-COLLAPSE-IPC;
      uses ncs_rpc_notif_MPLSTE-BACKUP-TABLE;
      uses ncs_rpc_notif_ROUTE-TABLE;
      uses ncs_rpc_notif_TABLE-LINE-CARD;
      uses ncs_rpc_notif_FRR-SUMMARY;
      uses ncs_rpc_notif_IIR-INTERFACE-TABLE;
      uses ncs_rpc_notif_AMT-GATEWAY-DB-TABLE;
      uses ncs_rpc_notif_ROUTE-OUTGOING-INTERFACE-TABLE;
      uses ncs_rpc_notif_GW-EXPIRED-TABLE;
      uses ncs_rpc_notif_REMOTE-TABLE-LINE-CARD;
      uses ncs_rpc_notif_AMT-ROUTEDB-SUMMARY-TABLE;
      uses ncs_rpc_notif_ROUTE-COLLAPSE-TABLE;
      uses ncs_rpc_notif_LABEL-INFO;
      uses ncs_rpc_notif_FRR-TABLE;
      uses ncs_rpc_notif_AMT-ROUTEDB-EXPIRED-TABLE;
      uses ncs_rpc_notif_TABLE-INFORMATION;
      uses ncs_rpc_notif_SUMMARY;
      uses ncs_rpc_notif_AMT-ROUTE-TABLE;
    }
  }

  grouping ncs_rpc_notif_STANDBY {
    description
      "Common node of mrib, ipv6-mrib";
    container standby {
      description
        "Standby Process";
      uses ncs_rpc_notif_PROCESS;
      uses ncs_rpc_notif_DEFAULT-CONTEXT;
      uses ncs_rpc_notif_DATABASE-TABLE;
    }
  }

  grouping ncs_rpc_notif_TABLE-INFORMATION {
    description
      "Common node of database, default-context";
    container table-information {
      description
        "MRIB VRF table information";
      uses ncs_rpc_notif_MRIB-TABLE-INFO-BAG;
    }
  }

  grouping ncs_rpc_notif_IIR-INTERFACE-TABLE {
    description
      "Common node of database, default-context";
    container iir-interfaces {
      description
        "MRIB IIR interface DB";
      list iir-interface {
        key "interface-name";
        description
          "MRIB Interface information";
        leaf interface-name {
          type xr:ncs_rpc_notif_Interface-name;
          description
            "Interface Name";
        }
        uses ncs_rpc_notif_MRIB-IIR-INTF-BAG;
      }
    }
  }

  grouping live_ncs_REMOTE-TABLE-LINE-CARD {
    description
      "Common node of database, default-context";
    container remote-table-line-card {
      description
        "Show the linked remote entry";
      uses live_ncs_MRIB-TLC-BAG;
    }
  }

  grouping live_ncs_ROUTE-TABLE {
    description
      "Common node of database, default-context";
    container routes {
      description
        "The set of MRIB RouteDB operations";
      list route {
        key "source-address group-address prefix-length";
        description
          "MRIB Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses live_ncs_MRIB-ROUTE-BAG;
      }
    }
  }

  grouping live_ncs_GW-SUMMARY-TABLE {
    description
      "Common node of database, default-context";
    container gw-summaries {
      description
        "MRIB AMT Gateway Summary Information";
      list gw-summary {
        key "gateway-address gateway-port";
        description
          "MRIB AMT Gateway DB Entry";
        leaf gateway-address {
          type inet:ip-address-no-zone;
          description
            "Gateway Address";
        }
        leaf gateway-port {
          type uint32;
          description
            "Gateway Port";
        }
        uses live_ncs_MRIB-AMT-GW-SUMMARY-BAG;
      }
    }
  }

  grouping live_ncs_TABLE-LINE-CARD {
    description
      "Common node of database, default-context";
    container table-line-card {
      description
        "MRIB Table-LineCard database";
      uses live_ncs_MRIB-TLC-BAG;
    }
  }

  grouping live_ncs_ROUTE-OUTGOING-INTERFACE-TABLE {
    description
      "Common node of database, default-context";
    container route-outgoing-interfaces {
      description
        "MRIB RouteDB Outgoing Interface Table ";
      list route-outgoing-interface {
        key "source-address group-address prefix-length";
        description
          "MRIB Route DB Outgoing Interface Entry
           Information";
        leaf source-address {
          type inet:ip-address-no-zone;
          description
            "Source Address";
        }
        leaf group-address {
          type inet:ip-address-no-zone;
          description
            "Group Address";
        }
        leaf prefix-length {
          type uint32;
          description
            "Prefix Length";
        }
        uses live_ncs_MRIB-ROUTE-OLE-BAG;
      }
    }
  }

  grouping live_ncs_AMT-ROUTE-TABLE {
    description
      "Common node of database, default-context";
    container amt-routes {
      description
        "The set of AMT Route table information";
      list amt-route {
        key "source-address group-address prefix-length";
        description
          "MRIB AMT Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses live_ncs_MRIB-AMT-ROUTE-BAG;
      }
    }
  }

  grouping live_ncs_PROCESS {
    description
      "Common node of active, standby";
    container process {
      description
        "Process";
      container registration-database-entries {
        description
          "MRIB Registration Database Table";
        list registration-database-entry {
          key "vrf-name entry-type next-hop-address";
          description
            "MRIB Registration Database Entry Information";
          leaf vrf-name {
            type xr:live_ncs_Cisco-ios-xr-string;
            description
              "VRF Name";
          }
          leaf entry-type {
            type uint32;
            description
              "Entry Type";
          }
          leaf next-hop-address {
            type inet:ip-address-no-zone;
            description
              "Next-Hop Address";
          }
          uses live_ncs_MRIB-REGDB-BAG;
        }
      }
      container cofo {
        description
          "Collapsed forwarding Information";
        container encap-entries {
          description
            "EncapID information exchanged for collapsed
             forwarding";
          list encap-entry {
            key "encap-id";
            description
              "EncapID information exchanged for collapsed
               forwarding";
            leaf encap-id {
              type uint32;
              description
                "Encap Identifier";
            }
            uses live_ncs_MRIB-COFO-ENCAP-BAG;
          }
        }
        container ip-multicast-infos {
          description
            "IP multicast information exchanged for
             collapsed forwarding";
          list ip-multicast-info {
            key "source group";
            description
              "IP multicast information exchanged for
               collapsed forwarding";
            leaf source {
              type inet:ip-address-no-zone;
              description
                "Source Address";
            }
            leaf group {
              type inet:ip-prefix;
              description
                "Group Address Prefix";
            }
            uses live_ncs_MRIB-COFO-BAG;
          }
        }
        container lsm-infos {
          description
            "LSM information exchanged for collapsed
             forwarding";
          list lsm-info {
            key "fec";
            description
              "LSM information exchanged for collapsed
               forwarding";
            leaf fec {
              type xr:live_ncs_Cisco-ios-xr-string;
              description
                "The FEC of the local label for which
                 node-set or FGID data is being exchanged";
            }
            uses live_ncs_LMRIB-COFO-BAG;
          }
        }
        container summary {
          description
            "Summary of statistics for collapsed forwarding";
          uses live_ncs_MRIB-COFO-SUMMARY-BAG;
        }
      }
      container nsr-ends {
        description
          "NSR End Table";
        list nsr-end {
          key "index";
          description
            "NSR End";
          leaf index {
            type uint32;
            description
              "Index";
          }
          uses live_ncs_MRIB-NSR-END-INFO;
        }
      }
      container mrib-bvi-interfaces {
        description
          "MRIB BVI interface mapping";
        list mrib-bvi-interface {
          key "interface-name";
          description
            "BVI Interface Handle";
          leaf interface-name {
            type xr:live_ncs_Interface-name;
            description
              "Interface Name";
          }
          uses live_ncs_MRIB-BVI-INTERFACE-BAG;
        }
      }
      container mrib-bvi-routes {
        description
          "MRIB BVI route table";
        list mrib-bvi-route {
          key "interface-name source-address group-address prefix-length";
          description
            "MRIB BVI route entry";
          leaf interface-name {
            type xr:live_ncs_Interface-name;
            description
              "Interface Name";
          }
          leaf source-address {
            type inet:ip-address-no-zone;
            description
              "Source Address";
          }
          leaf group-address {
            type inet:ip-address-no-zone;
            description
              "Group Address";
          }
          leaf prefix-length {
            type uint32;
            description
              "Prefix Length";
          }
          uses live_ncs_MRIB-BVI-ROUTE-BAG;
        }
      }
      container evpn {
        description
          "EVPN information";
        container bucket-entries {
          description
            "EVPN Bucket DataBase Table information";
          list bucket-entry {
            description
              "Mrib EVPN Bucket Database Entry";
            leaf bucket-id {
              type uint32;
              description
                "Bucket Identifier";
            }
            leaf parent-if-handle {
              type xr:live_ncs_Hex-integer;
              description
                "Parent Handle";
            }
            uses live_ncs_MRIB-EVPN-BKT-BAG;
          }
        }
      }
      container checkpoint-statistics {
        description
          "Checkpoint Statistics";
        uses live_ncs_MRIB-CHKPT-STATS;
      }
      container mdt-interfaces {
        description
          "MRIB IIR interface DB";
        list mdt-interface {
          key "interface-name";
          description
            "Interface handle";
          leaf interface-name {
            type xr:live_ncs_Interface-name;
            description
              "Interface Name";
          }
          uses live_ncs_MRIB-MDT-IFH-BAG;
        }
      }
      container clients {
        description
          "MRIB Client Table";
        list client {
          key "client-name instance-name";
          description
            "MRIB Client DB Entry Information";
          leaf client-name {
            type xr:live_ncs_Cisco-ios-xr-string;
            description
              "Client Name";
          }
          leaf instance-name {
            type xr:live_ncs_Cisco-ios-xr-string;
            description
              "Instance Name";
          }
          uses live_ncs_MRIB-CLIENT-BAG;
        }
      }
      container mpls-forwardings {
        description
          "MRIB Label Table";
        list mpls-forwarding {
          key "label";
          description
            "MRIB Label DB Information";
          leaf label {
            type uint32;
            description
              "Label";
          }
          uses live_ncs_MRIB-MPLS-FORWARDING-BAG;
        }
      }
      container nsf {
        description
          "NSF Information";
        uses live_ncs_MRIB-NSF-BAG;
      }
      container rpf-identifiers {
        description
          "RPF Identifier Table";
        list rpf-identifier {
          key "source-pe-address mrib-allocated";
          description
            "RPF Identifier";
          leaf source-pe-address {
            type inet:ipv4-address-no-zone;
            description
              "Source PE Address";
          }
          leaf mrib-allocated {
            type boolean;
            description
              "MRIB Allocated";
          }
          uses live_ncs_MRIB-RPFID-SPE-INFO;
        }
      }
      container client-filters {
        description
          "MRIB Client Filter Table";
        list client-filter {
          key "client-name instance-name";
          description
            "MRIB Client Filter DB Entry Information";
          leaf client-name {
            type xr:live_ncs_Cisco-ios-xr-string;
            description
              "Client Name";
          }
          leaf instance-name {
            type xr:live_ncs_Cisco-ios-xr-string;
            description
              "Instance Name";
          }
          uses live_ncs_MRIB-FILTER-BAG;
        }
      }
      container encap-identifiers {
        description
          "Encap Identifier Table";
        list encap-identifier {
          key "encap-id";
          description
            "Encap Identifier";
          leaf encap-id {
            type uint32;
            description
              "Encap Identifier";
          }
          uses live_ncs_MRIB-ENCAPID-BAG;
        }
      }
    }
  }

  grouping live_ncs_ROUTE-COLLAPSE-IPC {
    description
      "Common node of database, default-context";
    container route-collapse-ipc {
      description
        "MRIB Route Collapse IPC Core-egress-node
         Information";
      uses live_ncs_MRIB-RC-IPC-BAG;
    }
  }

  grouping live_ncs_LABEL-INFO {
    description
      "Common node of database, default-context";
    container label-info {
      description
        "MRIB Label Table Information";
      uses live_ncs_MRIB-LABEL-TABLE-INFO-BAG;
    }
  }

  grouping live_ncs_AMT-ROUTEDB-SUMMARY-TABLE {
    description
      "Common node of database, default-context";
    container amt-routedb-summaries {
      description
        "MRIB AMT RouteDB Summary Information";
      list amt-routedb-summary {
        key "source-address group-address";
        description
          "MRIB AMT Route Summary Entry";
        leaf source-address {
          type inet:ip-address-no-zone;
          description
            "Source Address";
        }
        leaf group-address {
          type inet:ip-address-no-zone;
          description
            "Group Address";
        }
        uses live_ncs_MRIB-AMT-ROUTE-SUMMARY-BAG;
      }
    }
  }

  grouping live_ncs_ROUTE-COLLAPSE-TABLE {
    description
      "Common node of database, default-context";
    container route-collapses {
      description
        "MRIB Route Collapse database";
      list route-collapse {
        key "type group-address";
        description
          "Route Collapse Information";
        leaf type {
          type xr:live_ncs_Cisco-ios-xr-string;
          description
            "Type";
        }
        leaf group-address {
          type inet:ip-address-no-zone;
          description
            "Input MDT grp or prev group";
        }
        uses live_ncs_MRIB-RC-MDT-BAG;
      }
    }
  }

  grouping live_ncs_ACTIVE {
    description
      "Common node of mrib, ipv6-mrib";
    container active {
      description
        "Active Process";
      uses live_ncs_PROCESS;
      uses live_ncs_DEFAULT-CONTEXT;
      uses live_ncs_DATABASE-TABLE;
    }
  }

  grouping live_ncs_AMT-ROUTEDB-EXPIRED-TABLE {
    description
      "Common node of database, default-context";
    container amt-routedb-expireds {
      description
        "MRIB AMT Route Expired Information";
      list amt-routedb-expired {
        key "source-address group-address gw-address port";
        description
          "MRIB AMT Route Expired Entry";
        leaf source-address {
          type inet:ip-address-no-zone;
          description
            "Source Address";
        }
        leaf group-address {
          type inet:ip-address-no-zone;
          description
            "Group Address";
        }
        leaf gw-address {
          type inet:ip-address-no-zone;
          description
            "GW Address";
        }
        leaf port {
          type uint32;
          description
            "Prefix Length";
        }
        uses live_ncs_MRIB-AMT-ROUTE-EX-BAG;
      }
    }
  }

  grouping live_ncs_SUMMARY {
    description
      "Common node of database, default-context";
    container summary {
      description
        "MRIB RouteDB Summary Information";
      uses live_ncs_MRIB-DB-SUMM-BAG;
    }
  }

  grouping live_ncs_GW-EXPIRED-TABLE {
    description
      "Common node of database, default-context";
    container gw-expireds {
      description
        "MRIB AMT Gateway DB Expired Information";
      list gw-expired {
        key "gateway-address gateway-port";
        description
          "MRIB AMT Gateway Expired Entry";
        leaf gateway-address {
          type inet:ip-address-no-zone;
          description
            "Gateway Address";
        }
        leaf gateway-port {
          type uint32;
          description
            "Gateway Port";
        }
        uses live_ncs_MRIB-AMT-GW-EX-BAG;
      }
    }
  }

  grouping live_ncs_AMT-GATEWAY-DB-TABLE {
    description
      "Common node of database, default-context";
    container amt-gateway-dbs {
      description
        "The set of AMT Gateway DataBase Table
         information";
      list amt-gateway-db {
        key "gateway-address gateway-port";
        description
          "MRIB AMT Gateway DB Entry";
        leaf gateway-address {
          type inet:ip-address-no-zone;
          description
            "Gateway Address";
        }
        leaf gateway-port {
          type uint32;
          description
            "Gateway Port";
        }
        uses live_ncs_MRIB-AMT-GW-BAG;
      }
    }
  }

  grouping live_ncs_DATABASE-TABLE {
    description
      "Common node of active, standby";
    container databases {
      description
        "Database Table";
      list database {
        key "database-name";
        description
          "MRIB Table Information";
        leaf database-name {
          type xr:live_ncs_Cisco-ios-xr-string;
          description
            "Database Name";
        }
        uses live_ncs_ROUTE-COLLAPSE-IPC-TLC;
        uses live_ncs_GW-SUMMARY-TABLE;
        uses live_ncs_ROUTE-COLLAPSE-IPC;
        uses live_ncs_MPLSTE-BACKUP-TABLE;
        uses live_ncs_ROUTE-TABLE;
        uses live_ncs_TABLE-LINE-CARD;
        uses live_ncs_FRR-SUMMARY;
        uses live_ncs_IIR-INTERFACE-TABLE;
        uses live_ncs_AMT-GATEWAY-DB-TABLE;
        uses live_ncs_ROUTE-OUTGOING-INTERFACE-TABLE;
        uses live_ncs_GW-EXPIRED-TABLE;
        uses live_ncs_REMOTE-TABLE-LINE-CARD;
        uses live_ncs_AMT-ROUTEDB-SUMMARY-TABLE;
        uses live_ncs_ROUTE-COLLAPSE-TABLE;
        uses live_ncs_LABEL-INFO;
        uses live_ncs_FRR-TABLE;
        uses live_ncs_AMT-ROUTEDB-EXPIRED-TABLE;
        uses live_ncs_TABLE-INFORMATION;
        uses live_ncs_SUMMARY;
        uses live_ncs_AMT-ROUTE-TABLE;
      }
    }
  }

  grouping live_ncs_FRR-SUMMARY {
    description
      "Common node of database, default-context";
    container frr-summary {
      description
        "MRIB FRR DB Summary Information";
      uses live_ncs_MRIB-MPLS-FRR-SUMMARY-BAG;
    }
  }

  grouping live_ncs_ROUTE-COLLAPSE-IPC-TLC {
    description
      "Common node of database, default-context";
    container route-collapse-ipc-tlc {
      description
        "Route Collapse IPC TLC Information";
      uses live_ncs_MRIB-RC-IPC-BAG;
    }
  }

  grouping live_ncs_FRR-TABLE {
    description
      "Common node of database, default-context";
    container frrs {
      description
        "FRR Table";
      list frr {
        key "start-label";
        description
          "MRIB FRR DB Information";
        leaf start-label {
          type uint32;
          description
            "Start Label";
        }
        uses live_ncs_MRIB-MPLS-FRR-BAG;
      }
    }
  }

  grouping live_ncs_MPLSTE-BACKUP-TABLE {
    description
      "Common node of database, default-context";
    container mplste-backups {
      description
        "MRIB MPLS TE Backup Database Information";
      list mplste-backup {
        key "interface-name";
        description
          "MRIB MPLS TE Backup Database Information";
        leaf interface-name {
          type xr:live_ncs_Interface-name;
          description
            "Interface Name";
        }
        uses live_ncs_MRIB-MPLS-BKUP-BAG;
      }
    }
  }

  grouping live_ncs_DEFAULT-CONTEXT {
    description
      "Common node of active, standby";
    container default-context {
      description
        "Default context";
      container mroutes {
        description
          "MRIB mpls mroute Table";
        list mroute {
          key "tunnel core-tree-id-type";
          description
            "MRIB MPLS MRoute information";
          leaf tunnel {
            type uint32;
            description
              "Tunnel Interface Handle";
          }
          leaf core-tree-id-type {
            type live_ncs_Mrib-core-tree-id;
            description
              "Core Tree ID Type";
          }
          uses live_ncs_MRIB-MPLS-DB-BAG;
        }
      }
      uses live_ncs_ROUTE-COLLAPSE-IPC-TLC;
      uses live_ncs_GW-SUMMARY-TABLE;
      uses live_ncs_ROUTE-COLLAPSE-IPC;
      uses live_ncs_MPLSTE-BACKUP-TABLE;
      uses live_ncs_ROUTE-TABLE;
      uses live_ncs_TABLE-LINE-CARD;
      uses live_ncs_FRR-SUMMARY;
      uses live_ncs_IIR-INTERFACE-TABLE;
      uses live_ncs_AMT-GATEWAY-DB-TABLE;
      uses live_ncs_ROUTE-OUTGOING-INTERFACE-TABLE;
      uses live_ncs_GW-EXPIRED-TABLE;
      uses live_ncs_REMOTE-TABLE-LINE-CARD;
      uses live_ncs_AMT-ROUTEDB-SUMMARY-TABLE;
      uses live_ncs_ROUTE-COLLAPSE-TABLE;
      uses live_ncs_LABEL-INFO;
      uses live_ncs_FRR-TABLE;
      uses live_ncs_AMT-ROUTEDB-EXPIRED-TABLE;
      uses live_ncs_TABLE-INFORMATION;
      uses live_ncs_SUMMARY;
      uses live_ncs_AMT-ROUTE-TABLE;
    }
  }

  grouping live_ncs_STANDBY {
    description
      "Common node of mrib, ipv6-mrib";
    container standby {
      description
        "Standby Process";
      uses live_ncs_PROCESS;
      uses live_ncs_DEFAULT-CONTEXT;
      uses live_ncs_DATABASE-TABLE;
    }
  }

  grouping live_ncs_TABLE-INFORMATION {
    description
      "Common node of database, default-context";
    container table-information {
      description
        "MRIB VRF table information";
      uses live_ncs_MRIB-TABLE-INFO-BAG;
    }
  }

  grouping live_ncs_IIR-INTERFACE-TABLE {
    description
      "Common node of database, default-context";
    container iir-interfaces {
      description
        "MRIB IIR interface DB";
      list iir-interface {
        key "interface-name";
        description
          "MRIB Interface information";
        leaf interface-name {
          type xr:live_ncs_Interface-name;
          description
            "Interface Name";
        }
        uses live_ncs_MRIB-IIR-INTF-BAG;
      }
    }
  }

  grouping REMOTE-TABLE-LINE-CARD {
    description
      "Common node of database, default-context";
    container remote-table-line-card {
      description
        "Show the linked remote entry";
      uses MRIB-TLC-BAG;
    }
  }

  grouping ROUTE-TABLE {
    description
      "Common node of database, default-context";
    container routes {
      description
        "The set of MRIB RouteDB operations";
      list route {
        key "source-address group-address prefix-length";
        description
          "MRIB Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses MRIB-ROUTE-BAG;
      }
    }
  }

  grouping GW-SUMMARY-TABLE {
    description
      "Common node of database, default-context";
    container gw-summaries {
      description
        "MRIB AMT Gateway Summary Information";
      list gw-summary {
        key "gateway-address gateway-port";
        description
          "MRIB AMT Gateway DB Entry";
        leaf gateway-address {
          type inet:ip-address-no-zone;
          description
            "Gateway Address";
        }
        leaf gateway-port {
          type uint32;
          description
            "Gateway Port";
        }
        uses MRIB-AMT-GW-SUMMARY-BAG;
      }
    }
  }

  grouping TABLE-LINE-CARD {
    description
      "Common node of database, default-context";
    container table-line-card {
      description
        "MRIB Table-LineCard database";
      uses MRIB-TLC-BAG;
    }
  }

  grouping ROUTE-OUTGOING-INTERFACE-TABLE {
    description
      "Common node of database, default-context";
    container route-outgoing-interfaces {
      description
        "MRIB RouteDB Outgoing Interface Table ";
      list route-outgoing-interface {
        key "source-address group-address prefix-length";
        description
          "MRIB Route DB Outgoing Interface Entry
           Information";
        leaf source-address {
          type inet:ip-address-no-zone;
          description
            "Source Address";
        }
        leaf group-address {
          type inet:ip-address-no-zone;
          description
            "Group Address";
        }
        leaf prefix-length {
          type uint32;
          description
            "Prefix Length";
        }
        uses MRIB-ROUTE-OLE-BAG;
      }
    }
  }

  grouping AMT-ROUTE-TABLE {
    description
      "Common node of database, default-context";
    container amt-routes {
      description
        "The set of AMT Route table information";
      list amt-route {
        key "source-address group-address prefix-length";
        description
          "MRIB AMT Route DB Entry Information";
        leaf source-address {
          type inet:ip-address-no-zone;
          description
            "Source Address";
        }
        leaf group-address {
          type inet:ip-address-no-zone;
          description
            "Group Address";
        }
        leaf prefix-length {
          type uint32;
          description
            "Prefix Length";
        }
        uses MRIB-AMT-ROUTE-BAG;
      }
    }
  }

  grouping PROCESS {
    description
      "Common node of active, standby";
    container process {
      description
        "Process";
      container registration-database-entries {
        description
          "MRIB Registration Database Table";
        list registration-database-entry {
          key "vrf-name entry-type next-hop-address";
          description
            "MRIB Registration Database Entry Information";
          leaf vrf-name {
            type xr:Cisco-ios-xr-string;
            description
              "VRF Name";
          }
          leaf entry-type {
            type uint32;
            description
              "Entry Type";
          }
          leaf next-hop-address {
            type inet:ip-address-no-zone;
            description
              "Next-Hop Address";
          }
          uses MRIB-REGDB-BAG;
        }
      }
      container cofo {
        description
          "Collapsed forwarding Information";
        container encap-entries {
          description
            "EncapID information exchanged for collapsed
             forwarding";
          list encap-entry {
            key "encap-id";
            description
              "EncapID information exchanged for collapsed
               forwarding";
            leaf encap-id {
              type uint32;
              description
                "Encap Identifier";
            }
            uses MRIB-COFO-ENCAP-BAG;
          }
        }
        container ip-multicast-infos {
          description
            "IP multicast information exchanged for
             collapsed forwarding";
          list ip-multicast-info {
            key "source group";
            description
              "IP multicast information exchanged for
               collapsed forwarding";
            leaf source {
              type inet:ip-address-no-zone;
              description
                "Source Address";
            }
            leaf group {
              type inet:ip-prefix;
              description
                "Group Address Prefix";
            }
            uses MRIB-COFO-BAG;
          }
        }
        container lsm-infos {
          description
            "LSM information exchanged for collapsed
             forwarding";
          list lsm-info {
            key "fec";
            description
              "LSM information exchanged for collapsed
               forwarding";
            leaf fec {
              type xr:Cisco-ios-xr-string {
                length "1..255";
              }
              description
                "The FEC of the local label for which
                 node-set or FGID data is being exchanged";
            }
            uses LMRIB-COFO-BAG;
          }
        }
        container summary {
          description
            "Summary of statistics for collapsed forwarding";
          uses MRIB-COFO-SUMMARY-BAG;
        }
      }
      container nsr-ends {
        description
          "NSR End Table";
        list nsr-end {
          key "index";
          description
            "NSR End";
          leaf index {
            type uint32;
            description
              "Index";
          }
          uses MRIB-NSR-END-INFO;
        }
      }
      container mrib-bvi-interfaces {
        description
          "MRIB BVI interface mapping";
        list mrib-bvi-interface {
          key "interface-name";
          description
            "BVI Interface Handle";
          leaf interface-name {
            type xr:Interface-name;
            description
              "Interface Name";
          }
          uses MRIB-BVI-INTERFACE-BAG;
        }
      }
      container mrib-bvi-routes {
        description
          "MRIB BVI route table";
        list mrib-bvi-route {
          key "interface-name source-address group-address prefix-length";
          description
            "MRIB BVI route entry";
          leaf interface-name {
            type xr:Interface-name;
            description
              "Interface Name";
          }
          leaf source-address {
            type inet:ip-address-no-zone;
            description
              "Source Address";
          }
          leaf group-address {
            type inet:ip-address-no-zone;
            description
              "Group Address";
          }
          leaf prefix-length {
            type uint32;
            description
              "Prefix Length";
          }
          uses MRIB-BVI-ROUTE-BAG;
        }
      }
      container evpn {
        description
          "EVPN information";
        container bucket-entries {
          description
            "EVPN Bucket DataBase Table information";
          list bucket-entry {
            description
              "Mrib EVPN Bucket Database Entry";
            leaf bucket-id {
              type uint32;
              description
                "Bucket Identifier";
            }
            leaf parent-if-handle {
              type xr:Hex-integer;
              description
                "Parent Handle";
            }
            uses MRIB-EVPN-BKT-BAG;
          }
        }
      }
      container checkpoint-statistics {
        description
          "Checkpoint Statistics";
        uses MRIB-CHKPT-STATS;
      }
      container mdt-interfaces {
        description
          "MRIB IIR interface DB";
        list mdt-interface {
          key "interface-name";
          description
            "Interface handle";
          leaf interface-name {
            type xr:Interface-name;
            description
              "Interface Name";
          }
          uses MRIB-MDT-IFH-BAG;
        }
      }
      container clients {
        description
          "MRIB Client Table";
        list client {
          key "client-name instance-name";
          description
            "MRIB Client DB Entry Information";
          leaf client-name {
            type xr:Cisco-ios-xr-string;
            description
              "Client Name";
          }
          leaf instance-name {
            type xr:Cisco-ios-xr-string;
            description
              "Instance Name";
          }
          uses MRIB-CLIENT-BAG;
        }
      }
      container mpls-forwardings {
        description
          "MRIB Label Table";
        list mpls-forwarding {
          key "label";
          description
            "MRIB Label DB Information";
          leaf label {
            type uint32;
            description
              "Label";
          }
          uses MRIB-MPLS-FORWARDING-BAG;
        }
      }
      container nsf {
        description
          "NSF Information";
        uses MRIB-NSF-BAG;
      }
      container rpf-identifiers {
        description
          "RPF Identifier Table";
        list rpf-identifier {
          key "source-pe-address mrib-allocated";
          description
            "RPF Identifier";
          leaf source-pe-address {
            type inet:ipv4-address-no-zone;
            description
              "Source PE Address";
          }
          leaf mrib-allocated {
            type boolean;
            description
              "MRIB Allocated";
          }
          uses MRIB-RPFID-SPE-INFO;
        }
      }
      container client-filters {
        description
          "MRIB Client Filter Table";
        list client-filter {
          key "client-name instance-name";
          description
            "MRIB Client Filter DB Entry Information";
          leaf client-name {
            type xr:Cisco-ios-xr-string;
            description
              "Client Name";
          }
          leaf instance-name {
            type xr:Cisco-ios-xr-string;
            description
              "Instance Name";
          }
          uses MRIB-FILTER-BAG;
        }
      }
      container encap-identifiers {
        description
          "Encap Identifier Table";
        list encap-identifier {
          key "encap-id";
          description
            "Encap Identifier";
          leaf encap-id {
            type uint32;
            description
              "Encap Identifier";
          }
          uses MRIB-ENCAPID-BAG;
        }
      }
    }
  }

  grouping ROUTE-COLLAPSE-IPC {
    description
      "Common node of database, default-context";
    container route-collapse-ipc {
      description
        "MRIB Route Collapse IPC Core-egress-node
         Information";
      uses MRIB-RC-IPC-BAG;
    }
  }

  grouping LABEL-INFO {
    description
      "Common node of database, default-context";
    container label-info {
      description
        "MRIB Label Table Information";
      uses MRIB-LABEL-TABLE-INFO-BAG;
    }
  }

  grouping AMT-ROUTEDB-SUMMARY-TABLE {
    description
      "Common node of database, default-context";
    container amt-routedb-summaries {
      description
        "MRIB AMT RouteDB Summary Information";
      list amt-routedb-summary {
        key "source-address group-address";
        description
          "MRIB AMT Route Summary Entry";
        leaf source-address {
          type inet:ip-address-no-zone;
          description
            "Source Address";
        }
        leaf group-address {
          type inet:ip-address-no-zone;
          description
            "Group Address";
        }
        uses MRIB-AMT-ROUTE-SUMMARY-BAG;
      }
    }
  }

  grouping ROUTE-COLLAPSE-TABLE {
    description
      "Common node of database, default-context";
    container route-collapses {
      description
        "MRIB Route Collapse database";
      list route-collapse {
        key "type group-address";
        description
          "Route Collapse Information";
        leaf type {
          type xr:Cisco-ios-xr-string;
          description
            "Type";
        }
        leaf group-address {
          type inet:ip-address-no-zone;
          description
            "Input MDT grp or prev group";
        }
        uses MRIB-RC-MDT-BAG;
      }
    }
  }

  grouping ACTIVE {
    description
      "Common node of mrib, ipv6-mrib";
    container active {
      description
        "Active Process";
      uses PROCESS;
      uses DEFAULT-CONTEXT;
      uses DATABASE-TABLE;
    }
  }

  grouping AMT-ROUTEDB-EXPIRED-TABLE {
    description
      "Common node of database, default-context";
    container amt-routedb-expireds {
      description
        "MRIB AMT Route Expired Information";
      list amt-routedb-expired {
        key "source-address group-address gw-address port";
        description
          "MRIB AMT Route Expired Entry";
        leaf source-address {
          type inet:ip-address-no-zone;
          description
            "Source Address";
        }
        leaf group-address {
          type inet:ip-address-no-zone;
          description
            "Group Address";
        }
        leaf gw-address {
          type inet:ip-address-no-zone;
          description
            "GW Address";
        }
        leaf port {
          type uint32;
          description
            "Prefix Length";
        }
        uses MRIB-AMT-ROUTE-EX-BAG;
      }
    }
  }

  grouping SUMMARY {
    description
      "Common node of database, default-context";
    container summary {
      description
        "MRIB RouteDB Summary Information";
      uses MRIB-DB-SUMM-BAG;
    }
  }

  grouping GW-EXPIRED-TABLE {
    description
      "Common node of database, default-context";
    container gw-expireds {
      description
        "MRIB AMT Gateway DB Expired Information";
      list gw-expired {
        key "gateway-address gateway-port";
        description
          "MRIB AMT Gateway Expired Entry";
        leaf gateway-address {
          type inet:ip-address-no-zone;
          description
            "Gateway Address";
        }
        leaf gateway-port {
          type uint32;
          description
            "Gateway Port";
        }
        uses MRIB-AMT-GW-EX-BAG;
      }
    }
  }

  grouping AMT-GATEWAY-DB-TABLE {
    description
      "Common node of database, default-context";
    container amt-gateway-dbs {
      description
        "The set of AMT Gateway DataBase Table
         information";
      list amt-gateway-db {
        key "gateway-address gateway-port";
        description
          "MRIB AMT Gateway DB Entry";
        leaf gateway-address {
          type inet:ip-address-no-zone;
          description
            "Gateway Address";
        }
        leaf gateway-port {
          type uint32;
          description
            "Gateway Port";
        }
        uses MRIB-AMT-GW-BAG;
      }
    }
  }

  grouping DATABASE-TABLE {
    description
      "Common node of active, standby";
    container databases {
      description
        "Database Table";
      list database {
        key "database-name";
        description
          "MRIB Table Information";
        leaf database-name {
          type xr:Cisco-ios-xr-string;
          description
            "Database Name";
        }
        uses ROUTE-COLLAPSE-IPC-TLC;
        uses GW-SUMMARY-TABLE;
        uses ROUTE-COLLAPSE-IPC;
        uses MPLSTE-BACKUP-TABLE;
        uses ROUTE-TABLE;
        uses TABLE-LINE-CARD;
        uses FRR-SUMMARY;
        uses IIR-INTERFACE-TABLE;
        uses AMT-GATEWAY-DB-TABLE;
        uses ROUTE-OUTGOING-INTERFACE-TABLE;
        uses GW-EXPIRED-TABLE;
        uses REMOTE-TABLE-LINE-CARD;
        uses AMT-ROUTEDB-SUMMARY-TABLE;
        uses ROUTE-COLLAPSE-TABLE;
        uses LABEL-INFO;
        uses FRR-TABLE;
        uses AMT-ROUTEDB-EXPIRED-TABLE;
        uses TABLE-INFORMATION;
        uses SUMMARY;
        uses AMT-ROUTE-TABLE;
      }
    }
  }

  grouping FRR-SUMMARY {
    description
      "Common node of database, default-context";
    container frr-summary {
      description
        "MRIB FRR DB Summary Information";
      uses MRIB-MPLS-FRR-SUMMARY-BAG;
    }
  }

  grouping ROUTE-COLLAPSE-IPC-TLC {
    description
      "Common node of database, default-context";
    container route-collapse-ipc-tlc {
      description
        "Route Collapse IPC TLC Information";
      uses MRIB-RC-IPC-BAG;
    }
  }

  grouping FRR-TABLE {
    description
      "Common node of database, default-context";
    container frrs {
      description
        "FRR Table";
      list frr {
        key "start-label";
        description
          "MRIB FRR DB Information";
        leaf start-label {
          type uint32;
          description
            "Start Label";
        }
        uses MRIB-MPLS-FRR-BAG;
      }
    }
  }

  grouping MPLSTE-BACKUP-TABLE {
    description
      "Common node of database, default-context";
    container mplste-backups {
      description
        "MRIB MPLS TE Backup Database Information";
      list mplste-backup {
        key "interface-name";
        description
          "MRIB MPLS TE Backup Database Information";
        leaf interface-name {
          type xr:Interface-name;
          description
            "Interface Name";
        }
        uses MRIB-MPLS-BKUP-BAG;
      }
    }
  }

  grouping DEFAULT-CONTEXT {
    description
      "Common node of active, standby";
    container default-context {
      description
        "Default context";
      container mroutes {
        description
          "MRIB mpls mroute Table";
        list mroute {
          key "tunnel core-tree-id-type";
          description
            "MRIB MPLS MRoute information";
          leaf tunnel {
            type uint32;
            description
              "Tunnel Interface Handle";
          }
          leaf core-tree-id-type {
            type Mrib-core-tree-id;
            description
              "Core Tree ID Type";
          }
          uses MRIB-MPLS-DB-BAG;
        }
      }
      uses ROUTE-COLLAPSE-IPC-TLC;
      uses GW-SUMMARY-TABLE;
      uses ROUTE-COLLAPSE-IPC;
      uses MPLSTE-BACKUP-TABLE;
      uses ROUTE-TABLE;
      uses TABLE-LINE-CARD;
      uses FRR-SUMMARY;
      uses IIR-INTERFACE-TABLE;
      uses AMT-GATEWAY-DB-TABLE;
      uses ROUTE-OUTGOING-INTERFACE-TABLE;
      uses GW-EXPIRED-TABLE;
      uses REMOTE-TABLE-LINE-CARD;
      uses AMT-ROUTEDB-SUMMARY-TABLE;
      uses ROUTE-COLLAPSE-TABLE;
      uses LABEL-INFO;
      uses FRR-TABLE;
      uses AMT-ROUTEDB-EXPIRED-TABLE;
      uses TABLE-INFORMATION;
      uses SUMMARY;
      uses AMT-ROUTE-TABLE;
    }
  }

  grouping STANDBY {
    description
      "Common node of mrib, ipv6-mrib";
    container standby {
      description
        "Standby Process";
      uses PROCESS;
      uses DEFAULT-CONTEXT;
      uses DATABASE-TABLE;
    }
  }

  grouping TABLE-INFORMATION {
    description
      "Common node of database, default-context";
    container table-information {
      description
        "MRIB VRF table information";
      uses MRIB-TABLE-INFO-BAG;
    }
  }

  grouping IIR-INTERFACE-TABLE {
    description
      "Common node of database, default-context";
    container iir-interfaces {
      description
        "MRIB IIR interface DB";
      list iir-interface {
        key "interface-name";
        description
          "MRIB Interface information";
        leaf interface-name {
          type xr:Interface-name;
          description
            "Interface Name";
        }
        uses MRIB-IIR-INTF-BAG;
      }
    }
  }

  augment "/ncs:devices/ncs:device/ncs:config" {
    // NCS drop config false container 'ipv6-mrib'
    // NCS drop config false container mrib
  }
  augment "/ncs:devices/ncs:device/ncs:live-status" {
    container ipv6-mrib {
      tailf:ncs-device-type "netconf";
      tailf:display-when "not(../../ncs:module) or ../../ncs:module[ncs:name='Cisco-IOS-XR-mrib-oper'] or (../../ncs:live-status-protocol[not(ncs:capability)]) or (../../ncs:live-status-protocol/ncs:capability/ncs:module[.='Cisco-IOS-XR-mrib-oper'])";
      description
        "IPv6 MRIB operational data";
      uses live_ncs_ACTIVE;
      uses live_ncs_STANDBY;
    }
    container mrib {
      tailf:ncs-device-type "netconf";
      tailf:display-when "not(../../ncs:module) or ../../ncs:module[ncs:name='Cisco-IOS-XR-mrib-oper'] or (../../ncs:live-status-protocol[not(ncs:capability)]) or (../../ncs:live-status-protocol/ncs:capability/ncs:module[.='Cisco-IOS-XR-mrib-oper'])";
      description
        "MRIB operational data";
      uses live_ncs_ACTIVE;
      uses live_ncs_STANDBY;
    }
  }
  augment "/ncs:devices/ncs:template/ncs:ned-id/ncs:config" {
    // NCS drop config false container 'ipv6-mrib'
    // NCS drop config false container mrib
  }
}

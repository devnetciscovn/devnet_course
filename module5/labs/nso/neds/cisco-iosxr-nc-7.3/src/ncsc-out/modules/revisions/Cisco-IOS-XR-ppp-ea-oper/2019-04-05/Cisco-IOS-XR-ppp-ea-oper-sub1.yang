submodule Cisco-IOS-XR-ppp-ea-oper-sub1 {
  // Generated by yanger -t ncs
  tailf:mount-id "cisco-iosxr-nc-7.3:cisco-iosxr-nc-7.3";

  belongs-to Cisco-IOS-XR-ppp-ea-oper {
    prefix Cisco-IOS-XR-ppp-ea-oper;
  }

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ppp-ea package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Ppp-ea-adj-state {
    type string;
    description
      "Ppp ea adj state";
  }

  typedef ncs_rpc_notif_Ppp-ea-adj-state {
    type enumeration {
      enum "ppp-ea-adj-state-not-installed" {
        value 0;
        description
          "Ajacency not installed in AIB";
      }
      enum "ppp-ea-adj-state-installed" {
        value 1;
        description
          "Adjacency installed in AIB";
      }
    }
    description
      "Ppp ea adj state";
  }

  typedef live_ncs_Ppp-ea-adj-state {
    type enumeration {
      enum "ppp-ea-adj-state-not-installed" {
        value 0;
        description
          "Ajacency not installed in AIB";
      }
      enum "ppp-ea-adj-state-installed" {
        value 1;
        description
          "Adjacency installed in AIB";
      }
    }
    description
      "Ppp ea adj state";
  }

  typedef Ppp-ea-adj-state {
    type enumeration {
      enum "ppp-ea-adj-state-not-installed" {
        value 0;
        description
          "Ajacency not installed in AIB";
      }
      enum "ppp-ea-adj-state-installed" {
        value 1;
        description
          "Adjacency installed in AIB";
      }
    }
    description
      "Ppp ea adj state";
  }

  grouping ncs_template_PPP-EA-INTERFACE-INFO {
    description
      "PPP EA interface information";
    leaf interface {
      type xr:ncs_template_Interface-name;
      description
        "Interface";
    }
    leaf is-lcp-running {
      type string;
      description
        "TRUE if LCP is running in the dataplane for the
         interface";
    }
    leaf is-ipcp-running {
      type string;
      description
        "TRUE if IPCP is running in the dataplane for the
         interface";
    }
    leaf is-ipv6cp-running {
      type string;
      description
        "TRUE if IPV6CP is running in the dataplane for
         the interface";
    }
    leaf is-mplscp-running {
      type string;
      description
        "TRUE if MPLSCP is running in the dataplane for
         the interface";
    }
    leaf local-mtu {
      type string;
      description
        "Local interface MTU";
    }
    leaf local-mrru {
      type string;
      description
        "Local MRRU";
    }
    leaf peer-mrru {
      type string;
      description
        "Peer MRRU";
    }
    leaf local-magic {
      type string;
      description
        "Local magic number";
    }
    leaf peer-magic {
      type string;
      description
        "Peer magic number";
    }
    leaf local-mcmp-classes {
      type string;
      description
        "Local number of MCMP Suspension classes";
    }
    leaf peer-mcmp-classes {
      type string;
      description
        "Peer number of MCMP Suspension classes";
    }
    leaf echo-request-interval {
      type string;
      description
        "Echo-Request interval";
    }
    leaf echo-request-retry-count {
      type string;
      description
        "Echo-Request retry count";
    }
    leaf is-multilink-bundle {
      type string;
      description
        "TRUE if this is a Multilink bundle interface";
    }
    leaf synchronized {
      type string;
      description
        "MA synchronization";
    }
    leaf forwarding-enabled {
      type string;
      description
        "Forwarding State";
    }
    leaf multilink-interface {
      type xr:ncs_template_Interface-name;
      description
        "Multilink interface that this interface is a
         member of, if any";
    }
    leaf l2-tunnel-enabled {
      type string;
      description
        "L2 Tunnel State";
    }
    leaf l2-provisioned {
      type string;
      description
        "L2 Provisioned State";
    }
    leaf l2ip-interworking-enabled {
      type string;
      description
        "L2 IP Interworking State";
    }
    leaf is-vpdn-tunneled {
      type string;
      description
        "Is VPDN tunneled";
    }
    leaf xconnect-id {
      type string;
      description
        "XConnect ID";
    }
    leaf parent-interface-handle {
      type xr:ncs_template_Interface-name;
      description
        "Parent Interface Handle";
    }
    leaf vrf-table-id {
      type string;
      description
        "IPCP VRF Table ID";
    }
    leaf ipv6vrf-table-id {
      type string;
      description
        "IPv6CP VRF Table ID";
    }
    leaf l2-adjacency-state {
      type ncs_template_Ppp-ea-adj-state;
      description
        "L2 adjacency state";
    }
    leaf l2ip-interworking-adjacency-state {
      type ncs_template_Ppp-ea-adj-state;
      description
        "L2 IP Interworking adjacency state";
    }
    leaf lac-adjacency-state {
      type ncs_template_Ppp-ea-adj-state;
      description
        "LAC adjacency state";
    }
    leaf interface-adjacency-state {
      type ncs_template_Ppp-ea-adj-state;
      description
        "Interface adjacency state";
    }
    leaf ipv4-adjacency-state {
      type ncs_template_Ppp-ea-adj-state;
      description
        "Ipv4 adjacency state";
    }
    leaf ipv6-adjacency-state {
      type ncs_template_Ppp-ea-adj-state;
      description
        "IPv6 adjacency state";
    }
    leaf mpls-adjacency-state {
      type ncs_template_Ppp-ea-adj-state;
      description
        "MPLS adjacency state";
    }
  }

  grouping ncs_rpc_notif_PPP-EA-INTERFACE-INFO {
    description
      "PPP EA interface information";
    leaf interface {
      type xr:ncs_rpc_notif_Interface-name;
      description
        "Interface";
    }
    leaf is-lcp-running {
      type boolean;
      description
        "TRUE if LCP is running in the dataplane for the
         interface";
    }
    leaf is-ipcp-running {
      type boolean;
      description
        "TRUE if IPCP is running in the dataplane for the
         interface";
    }
    leaf is-ipv6cp-running {
      type boolean;
      description
        "TRUE if IPV6CP is running in the dataplane for
         the interface";
    }
    leaf is-mplscp-running {
      type boolean;
      description
        "TRUE if MPLSCP is running in the dataplane for
         the interface";
    }
    leaf local-mtu {
      type uint16;
      description
        "Local interface MTU";
    }
    leaf local-mrru {
      type uint16;
      description
        "Local MRRU";
    }
    leaf peer-mrru {
      type uint16;
      description
        "Peer MRRU";
    }
    leaf local-magic {
      type uint32;
      description
        "Local magic number";
    }
    leaf peer-magic {
      type uint32;
      description
        "Peer magic number";
    }
    leaf local-mcmp-classes {
      type uint8;
      description
        "Local number of MCMP Suspension classes";
    }
    leaf peer-mcmp-classes {
      type uint8;
      description
        "Peer number of MCMP Suspension classes";
    }
    leaf echo-request-interval {
      type uint32;
      description
        "Echo-Request interval";
    }
    leaf echo-request-retry-count {
      type uint32;
      description
        "Echo-Request retry count";
    }
    leaf is-multilink-bundle {
      type boolean;
      description
        "TRUE if this is a Multilink bundle interface";
    }
    leaf synchronized {
      type boolean;
      description
        "MA synchronization";
    }
    leaf forwarding-enabled {
      type boolean;
      description
        "Forwarding State";
    }
    leaf multilink-interface {
      type xr:ncs_rpc_notif_Interface-name;
      description
        "Multilink interface that this interface is a
         member of, if any";
    }
    leaf l2-tunnel-enabled {
      type boolean;
      description
        "L2 Tunnel State";
    }
    leaf l2-provisioned {
      type boolean;
      description
        "L2 Provisioned State";
    }
    leaf l2ip-interworking-enabled {
      type boolean;
      description
        "L2 IP Interworking State";
    }
    leaf is-vpdn-tunneled {
      type boolean;
      description
        "Is VPDN tunneled";
    }
    leaf xconnect-id {
      type uint32;
      description
        "XConnect ID";
    }
    leaf parent-interface-handle {
      type xr:ncs_rpc_notif_Interface-name;
      description
        "Parent Interface Handle";
    }
    leaf vrf-table-id {
      type uint32;
      description
        "IPCP VRF Table ID";
    }
    leaf ipv6vrf-table-id {
      type uint32;
      description
        "IPv6CP VRF Table ID";
    }
    leaf l2-adjacency-state {
      type ncs_rpc_notif_Ppp-ea-adj-state;
      description
        "L2 adjacency state";
    }
    leaf l2ip-interworking-adjacency-state {
      type ncs_rpc_notif_Ppp-ea-adj-state;
      description
        "L2 IP Interworking adjacency state";
    }
    leaf lac-adjacency-state {
      type ncs_rpc_notif_Ppp-ea-adj-state;
      description
        "LAC adjacency state";
    }
    leaf interface-adjacency-state {
      type ncs_rpc_notif_Ppp-ea-adj-state;
      description
        "Interface adjacency state";
    }
    leaf ipv4-adjacency-state {
      type ncs_rpc_notif_Ppp-ea-adj-state;
      description
        "Ipv4 adjacency state";
    }
    leaf ipv6-adjacency-state {
      type ncs_rpc_notif_Ppp-ea-adj-state;
      description
        "IPv6 adjacency state";
    }
    leaf mpls-adjacency-state {
      type ncs_rpc_notif_Ppp-ea-adj-state;
      description
        "MPLS adjacency state";
    }
  }

  grouping live_ncs_PPP-EA-INTERFACE-INFO {
    description
      "PPP EA interface information";
    leaf interface {
      type xr:live_ncs_Interface-name;
      description
        "Interface";
    }
    leaf is-lcp-running {
      type boolean;
      description
        "TRUE if LCP is running in the dataplane for the
         interface";
    }
    leaf is-ipcp-running {
      type boolean;
      description
        "TRUE if IPCP is running in the dataplane for the
         interface";
    }
    leaf is-ipv6cp-running {
      type boolean;
      description
        "TRUE if IPV6CP is running in the dataplane for
         the interface";
    }
    leaf is-mplscp-running {
      type boolean;
      description
        "TRUE if MPLSCP is running in the dataplane for
         the interface";
    }
    leaf local-mtu {
      type uint16;
      description
        "Local interface MTU";
    }
    leaf local-mrru {
      type uint16;
      description
        "Local MRRU";
    }
    leaf peer-mrru {
      type uint16;
      description
        "Peer MRRU";
    }
    leaf local-magic {
      type uint32;
      description
        "Local magic number";
    }
    leaf peer-magic {
      type uint32;
      description
        "Peer magic number";
    }
    leaf local-mcmp-classes {
      type uint8;
      description
        "Local number of MCMP Suspension classes";
    }
    leaf peer-mcmp-classes {
      type uint8;
      description
        "Peer number of MCMP Suspension classes";
    }
    leaf echo-request-interval {
      type uint32;
      description
        "Echo-Request interval";
    }
    leaf echo-request-retry-count {
      type uint32;
      description
        "Echo-Request retry count";
    }
    leaf is-multilink-bundle {
      type boolean;
      description
        "TRUE if this is a Multilink bundle interface";
    }
    leaf synchronized {
      type boolean;
      description
        "MA synchronization";
    }
    leaf forwarding-enabled {
      type boolean;
      description
        "Forwarding State";
    }
    leaf multilink-interface {
      type xr:live_ncs_Interface-name;
      description
        "Multilink interface that this interface is a
         member of, if any";
    }
    leaf l2-tunnel-enabled {
      type boolean;
      description
        "L2 Tunnel State";
    }
    leaf l2-provisioned {
      type boolean;
      description
        "L2 Provisioned State";
    }
    leaf l2ip-interworking-enabled {
      type boolean;
      description
        "L2 IP Interworking State";
    }
    leaf is-vpdn-tunneled {
      type boolean;
      description
        "Is VPDN tunneled";
    }
    leaf xconnect-id {
      type uint32;
      description
        "XConnect ID";
    }
    leaf parent-interface-handle {
      type xr:live_ncs_Interface-name;
      description
        "Parent Interface Handle";
    }
    leaf vrf-table-id {
      type uint32;
      description
        "IPCP VRF Table ID";
    }
    leaf ipv6vrf-table-id {
      type uint32;
      description
        "IPv6CP VRF Table ID";
    }
    leaf l2-adjacency-state {
      type live_ncs_Ppp-ea-adj-state;
      description
        "L2 adjacency state";
    }
    leaf l2ip-interworking-adjacency-state {
      type live_ncs_Ppp-ea-adj-state;
      description
        "L2 IP Interworking adjacency state";
    }
    leaf lac-adjacency-state {
      type live_ncs_Ppp-ea-adj-state;
      description
        "LAC adjacency state";
    }
    leaf interface-adjacency-state {
      type live_ncs_Ppp-ea-adj-state;
      description
        "Interface adjacency state";
    }
    leaf ipv4-adjacency-state {
      type live_ncs_Ppp-ea-adj-state;
      description
        "Ipv4 adjacency state";
    }
    leaf ipv6-adjacency-state {
      type live_ncs_Ppp-ea-adj-state;
      description
        "IPv6 adjacency state";
    }
    leaf mpls-adjacency-state {
      type live_ncs_Ppp-ea-adj-state;
      description
        "MPLS adjacency state";
    }
  }

  grouping PPP-EA-INTERFACE-INFO {
    description
      "PPP EA interface information";
    leaf interface {
      type xr:Interface-name;
      description
        "Interface";
    }
    leaf is-lcp-running {
      type boolean;
      description
        "TRUE if LCP is running in the dataplane for the
         interface";
    }
    leaf is-ipcp-running {
      type boolean;
      description
        "TRUE if IPCP is running in the dataplane for the
         interface";
    }
    leaf is-ipv6cp-running {
      type boolean;
      description
        "TRUE if IPV6CP is running in the dataplane for
         the interface";
    }
    leaf is-mplscp-running {
      type boolean;
      description
        "TRUE if MPLSCP is running in the dataplane for
         the interface";
    }
    leaf local-mtu {
      type uint16;
      description
        "Local interface MTU";
    }
    leaf local-mrru {
      type uint16;
      description
        "Local MRRU";
    }
    leaf peer-mrru {
      type uint16;
      description
        "Peer MRRU";
    }
    leaf local-magic {
      type uint32;
      description
        "Local magic number";
    }
    leaf peer-magic {
      type uint32;
      description
        "Peer magic number";
    }
    leaf local-mcmp-classes {
      type uint8;
      description
        "Local number of MCMP Suspension classes";
    }
    leaf peer-mcmp-classes {
      type uint8;
      description
        "Peer number of MCMP Suspension classes";
    }
    leaf echo-request-interval {
      type uint32;
      description
        "Echo-Request interval";
    }
    leaf echo-request-retry-count {
      type uint32;
      description
        "Echo-Request retry count";
    }
    leaf is-multilink-bundle {
      type boolean;
      description
        "TRUE if this is a Multilink bundle interface";
    }
    leaf synchronized {
      type boolean;
      description
        "MA synchronization";
    }
    leaf forwarding-enabled {
      type boolean;
      description
        "Forwarding State";
    }
    leaf multilink-interface {
      type xr:Interface-name;
      description
        "Multilink interface that this interface is a
         member of, if any";
    }
    leaf l2-tunnel-enabled {
      type boolean;
      description
        "L2 Tunnel State";
    }
    leaf l2-provisioned {
      type boolean;
      description
        "L2 Provisioned State";
    }
    leaf l2ip-interworking-enabled {
      type boolean;
      description
        "L2 IP Interworking State";
    }
    leaf is-vpdn-tunneled {
      type boolean;
      description
        "Is VPDN tunneled";
    }
    leaf xconnect-id {
      type uint32;
      description
        "XConnect ID";
    }
    leaf parent-interface-handle {
      type xr:Interface-name;
      description
        "Parent Interface Handle";
    }
    leaf vrf-table-id {
      type uint32;
      description
        "IPCP VRF Table ID";
    }
    leaf ipv6vrf-table-id {
      type uint32;
      description
        "IPv6CP VRF Table ID";
    }
    leaf l2-adjacency-state {
      type Ppp-ea-adj-state;
      description
        "L2 adjacency state";
    }
    leaf l2ip-interworking-adjacency-state {
      type Ppp-ea-adj-state;
      description
        "L2 IP Interworking adjacency state";
    }
    leaf lac-adjacency-state {
      type Ppp-ea-adj-state;
      description
        "LAC adjacency state";
    }
    leaf interface-adjacency-state {
      type Ppp-ea-adj-state;
      description
        "Interface adjacency state";
    }
    leaf ipv4-adjacency-state {
      type Ppp-ea-adj-state;
      description
        "Ipv4 adjacency state";
    }
    leaf ipv6-adjacency-state {
      type Ppp-ea-adj-state;
      description
        "IPv6 adjacency state";
    }
    leaf mpls-adjacency-state {
      type Ppp-ea-adj-state;
      description
        "MPLS adjacency state";
    }
  }
}

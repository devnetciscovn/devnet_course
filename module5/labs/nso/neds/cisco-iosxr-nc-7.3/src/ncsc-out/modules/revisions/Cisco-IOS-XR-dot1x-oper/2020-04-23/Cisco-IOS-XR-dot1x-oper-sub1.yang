submodule Cisco-IOS-XR-dot1x-oper-sub1 {
  // Generated by yanger -t ncs
  tailf:mount-id "cisco-iosxr-nc-7.3:cisco-iosxr-nc-7.3";

  belongs-to Cisco-IOS-XR-dot1x-oper {
    prefix Cisco-IOS-XR-dot1x-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR dot1x package operational data.

     Copyright (c) 2013-2020 by Cisco Systems, Inc.
     All rights reserved.";

  revision 2020-04-23 {
    description
      "Dot1x Port Status";
    semver:module-version "2.1.0";
  }
  revision 2019-08-23 {
    description
      "Host Mode";
    semver:module-version "2.0.0";
  }
  revision 2019-04-05 {
    description
      "Establish semantic version baseline.";
    semver:module-version "1.0.0";
  }
  revision 2015-11-09 {
    description
      "IOS XR 6.0 revision.";
  }

  grouping ncs_template_DOT1X-INTERFACE-MKA {
    description
      "DOT1X INTERFACE MKA";
    leaf tie-break-role {
      type string;
      description
        "Dot1x Tie breaker role chosen for mka when PAE
         type is BOTH";
    }
    leaf eap-based-macsec {
      type string;
      description
        "EAP Mode status for MKA";
    }
    leaf mka-start-time {
      type string;
      description
        "Time stamp when Dot1x posting a message to  MKA
         to start session.";
    }
    leaf mka-stop-time {
      type string;
      description
        "Time stamp when Dot1x posting a message to  MKA
         to stop session.";
    }
    leaf mka-response-time {
      type string;
      description
        "Time Stamp of MKA acknowledgement to Dot1x";
    }
  }

  grouping ncs_template_DOT1X-INTERFACE-DETAIL {
    description
      "DOT1X INTERFACE DETAIL";
    container intf-info {
      description
        "Dot1x interface Info";
      uses ncs_template_DOT1X-INTERFACE-INFO;
    }
    container mka-status-info {
      description
        "MKA session secure status";
      uses ncs_template_DOT1X-INTERFACE-MKA;
    }
    leaf interface-name {
      type string;
      description
        "Interface Display name ";
    }
    leaf interface-sname {
      type string;
      description
        "Interface Display short_name ";
    }
    leaf if-handle {
      type string;
      description
        "Interface handle";
    }
    leaf mac {
      type string;
      description
        "formatted MAC Address";
    }
    leaf ethertype {
      type string;
      description
        "EAPOL Ethertype";
    }
    leaf eapol-addr {
      type string;
      description
        "EAPOL Destination Address";
    }
  }

  grouping ncs_template_DOT1X-GLOBAL-PORT-CONTROL-STATISTICS {
    description
      "DOT1X GLOBAL PORT CONTROL STATISTICS";
    leaf enable-succ {
      type string;
      description
        "EnableSucc";
    }
    leaf enable-fail {
      type string;
      description
        "EnableFail";
    }
    leaf disable-succ {
      type string;
      description
        "DisableSucc";
    }
    leaf disable-fail {
      type string;
      description
        "DisableFail";
    }
    leaf add-client-succ {
      type string;
      description
        "AddClientSucc";
    }
    leaf add-client-fail {
      type string;
      description
        "AddClientFail";
    }
    leaf remove-client-succ {
      type string;
      description
        "RemoveClientSucc";
    }
    leaf remove-client-fail {
      type string;
      description
        "RemoveClientFail";
    }
    leaf update-succ {
      type string;
      description
        "UpdateSucc";
    }
    leaf update-fail {
      type string;
      description
        "UpdateFail";
    }
  }

  grouping ncs_template_DOT1X-GLOBAL-STATISTICS {
    description
      "DOT1X GLOBAL STATISTICS";
    container port-control {
      description
        "PortControl";
      uses ncs_template_DOT1X-GLOBAL-PORT-CONTROL-STATISTICS;
    }
    leaf tx-total {
      type string;
      description
        "TxTotal";
    }
    leaf rx-total {
      type string;
      description
        "RxTotal";
    }
    leaf rx-no-idb {
      type string;
      description
        "RxNoIDB";
    }
    leaf packet-drop-no-config-received {
      type string;
      description
        "PacketDrop";
    }
  }

  grouping ncs_template_DOT1X-STATISTICS {
    description
      "DOT1X STATISTICS";
    container gl-stats {
      description
        "Global statistics";
      uses ncs_template_DOT1X-GLOBAL-STATISTICS;
    }
    list if-stats {
      // NCS patched for predictable order
      ordered-by user;
      description
        "dot1x interface statistics list";
      uses ncs_template_DOT1X-IF-STATISTICS;
    }
  }

  grouping ncs_template_DOT1X-SUPP-TIMERS {
    description
      "DOT1X SUPP TIMERS";
    leaf auth-period {
      type string;
      units "second";
      description
        "in Seconds, supplicant waits for a response from
         an authenticator except for EAPOL-START before
         timing out";
    }
    leaf held-period {
      type string;
      units "second";
      description
        "in Seconds, supplicant will stay in the HELD
         state (that is, the length of time it will wait
         before trying to send the credentials again
         after a failed attempt)";
    }
    leaf start-period {
      type string;
      units "second";
      description
        "Configures the interval, in seconds, between two
         successive EAPOL-Start frames when they are
         being retransmitted";
    }
    leaf max-start {
      type string;
      description
        "Max No. of EAPOL-Start frames supplicant can
         send to the authenticator";
    }
  }

  grouping ncs_template_DOT1X-AUTH-TIMERS {
    description
      "DOT1X AUTH TIMERS";
    leaf quiet-period {
      type string;
      units "second";
      description
        "in Seconds, authenticator remains quiet (in the
         HELD state) following a failed authentication
         exchange before trying to reauthenticate the
         client";
    }
    leaf tx-period {
      type string;
      units "second";
      description
        "in Seconds, Timeout for supplicant reply,
         authenticator-to-supplicant retransmission time
         for EAP-request-ID packets (assuming that no
         response is received) from the client";
    }
    leaf max-reauth-req {
      type string;
      description
        "Max No. of Reauthentication Attempts (or)
         retransmits an EAP-request-ID frame to the
         client before restarting the authentication
         process";
    }
    leaf supp-timeout {
      type string;
      units "second";
      description
        "in Seconds, Timeout for supplicant reply,
         authenticator-to-supplicant retransmission time
         for all EAP messages except for EAP Request ID
         packets";
    }
    leaf max-req {
      type string;
      description
        "Max No. of EAP-Req (except for EAP-Request-ID)
         retransmits (authenticator-to-supplicant) before
         sending EAP-Failure";
    }
    leaf reauth-period {
      type string;
      units "second";
      description
        "in Seconds,  after which an automatic
         reauthentication should be initiated";
    }
  }

  grouping ncs_template_DOT1X-DEFAULT {
    description
      "DOT1X DEFAULT";
    container auth-timers {
      description
        "Dot1x Authenticator default Timer values";
      uses ncs_template_DOT1X-AUTH-TIMERS;
    }
    container supp-timers {
      description
        "Dot1x Supllicant default Timer values";
      uses ncs_template_DOT1X-SUPP-TIMERS;
    }
    leaf version {
      type string;
      description
        "Dot1x Protocol Version";
    }
  }

  grouping ncs_template_DOT1X-SUPP-CLIENT-INFO {
    description
      "DOT1X SUPP CLIENT INFO";
    leaf mac {
      type string;
      description
        "formatted MAC Address";
    }
    leaf eap-method {
      type string;
      description
        "EAP Method";
    }
    leaf last-auth-time {
      type string;
      description
        "Last Authenticated Timestamp (formatted)";
    }
    leaf auth-sm-state {
      type string;
      description
        "supp SM State";
    }
    leaf auth-bend-sm-state {
      type string;
      description
        "supp back end SM State";
    }
    leaf port-status {
      type string;
      description
        "Supp port status";
    }
  }

  grouping ncs_template_DOT1X-SUPP-INFO {
    description
      "DOT1X SUPP INFO";
    leaf eap-profile {
      type string;
      description
        "EAP profile";
    }
    leaf config-dependency {
      type string;
      description
        "Configuration Dependency ";
    }
    list client {
      // NCS patched for predictable order
      ordered-by user;
      description
        "Supp Client info";
      uses ncs_template_DOT1X-SUPP-CLIENT-INFO;
    }
  }

  grouping ncs_template_DOT1X-AUTH-CLIENT-INFO {
    description
      "DOT1X AUTH CLIENT INFO";
    leaf mac {
      type string;
      description
        "formatted MAC Address";
    }
    leaf auth-sm-state {
      type string;
      description
        "Auth SM State";
    }
    leaf auth-bend-sm-state {
      type string;
      description
        "Auth back end SM State";
    }
    leaf time-to-next-reauth {
      type string;
      description
        "remaining time for next reauthentication";
    }
    leaf last-auth-time {
      type string;
      description
        "Last Authenticated Timestamp (formatted)";
    }
    leaf last-auth-server {
      type string;
      description
        "Last Authenticated Server";
    }
    leaf port-control {
      type string;
      description
        "Auth Client Port Control Status";
    }
    leaf port-status {
      type string;
      description
        "Auth Client Port Status";
    }
  }

  grouping ncs_template_DOT1X-AUTH-INFO {
    description
      "DOT1X AUTH INFO";
    leaf port-control {
      type string;
      description
        "Port Control Feature";
    }
    leaf reauth {
      type string;
      description
        "Re-Authentication enabled status";
    }
    leaf config-dependency {
      type string;
      description
        "Configuration Dependency ";
    }
    leaf eap-profile {
      type string;
      description
        "EAP profile";
    }
    leaf host-mode {
      type string;
      description
        "Host Mode";
    }
    list client {
      // NCS patched for predictable order
      ordered-by user;
      description
        "Authenticator client list";
      uses ncs_template_DOT1X-AUTH-CLIENT-INFO;
    }
  }

  grouping ncs_template_DOT1X-INTERFACE-INFO {
    description
      "DOT1X INTERFACE INFO";
    container auth-info {
      description
        "Dot1x Authenticator info";
      uses ncs_template_DOT1X-AUTH-INFO;
    }
    container supp-info {
      description
        "Dot1x Supplicant info";
      uses ncs_template_DOT1X-SUPP-INFO;
    }
    leaf pae {
      type string;
      description
        "PAE type on interface";
    }
    leaf dot1x-port-status {
      type string;
      description
        "Dot1x Port Status";
    }
    leaf dot1x-profile {
      type string;
      description
        "Dot1x Profile";
    }
    leaf l2-transport {
      type string;
      description
        "L2 Transport Info";
    }
  }

  grouping ncs_template_DOT1X-INTERFACE {
    description
      "DOT1X INTERFACE";
    container intf-info {
      description
        "Dot1x interface Info";
      uses ncs_template_DOT1X-INTERFACE-INFO;
    }
    leaf interface-name {
      type string;
      description
        "Interface Display name ";
    }
    leaf interface-sname {
      type string;
      description
        "Interface Display short_name ";
    }
  }

  grouping ncs_template_DOT1X-IF-LOCAL-EAP-STATISTICS {
    description
      "DOT1X IF LOCAL EAP STATISTICS";
    leaf requests {
      type string;
      description
        "Requests";
    }
    leaf replies {
      type string;
      description
        "Replies";
    }
    leaf timeout {
      type string;
      description
        "Timeout";
    }
    leaf dropped-no-eap {
      type string;
      description
        "DroppedNoEAP";
    }
    leaf dropped {
      type string;
      description
        "Dropped";
    }
    leaf success {
      type string;
      description
        "Success";
    }
    leaf failed {
      type string;
      description
        "Failed";
    }
  }

  grouping ncs_template_DOT1X-IF-SUPP-STATISTICS {
    description
      "DOT1X IF SUPP STATISTICS";
    leaf rx-req {
      type string;
      description
        "RxReq";
    }
    leaf rx-invalid {
      type string;
      description
        "RxInvalid";
    }
    leaf rx-len-err {
      type string;
      description
        "RxLenErr";
    }
    leaf rx-my-mac-err {
      type string;
      description
        "RxMyMacErr";
    }
    leaf rx-total {
      type string;
      description
        "RxTotal";
    }
    leaf tx-start {
      type string;
      description
        "TxStart";
    }
    leaf tx-logoff {
      type string;
      description
        "TxLogoff";
    }
    leaf tx-resp {
      type string;
      description
        "TxResp";
    }
    leaf tx-total {
      type string;
      description
        "TxTotal";
    }
  }

  grouping ncs_template_DOT1X-IF-PORT-CONTROL-STATISTICS {
    description
      "DOT1X IF PORT CONTROL STATISTICS";
    leaf enable-succ {
      type string;
      description
        "EnableSucc";
    }
    leaf enable-fail {
      type string;
      description
        "EnableFail";
    }
    leaf add-client-succ {
      type string;
      description
        "AddClientSucc";
    }
    leaf add-client-fail {
      type string;
      description
        "AddClientFail";
    }
    leaf remove-client-succ {
      type string;
      description
        "RemoveClientSucc";
    }
    leaf remove-client-fail {
      type string;
      description
        "RemoveClientFail";
    }
    leaf update-succ {
      type string;
      description
        "UpdateSucc";
    }
    leaf update-fail {
      type string;
      description
        "UpdateFail";
    }
  }

  grouping ncs_template_DOT1X-IF-AUTH-STATISTICS {
    description
      "DOT1X IF AUTH STATISTICS";
    container port-control {
      description
        "PortControl";
      uses ncs_template_DOT1X-IF-PORT-CONTROL-STATISTICS;
    }
    leaf rx-start {
      type string;
      description
        "RxStart";
    }
    leaf rx-logoff {
      type string;
      description
        "RxLogoff";
    }
    leaf rx-resp {
      type string;
      description
        "RxResp";
    }
    leaf rx-resp-id {
      type string;
      description
        "RxRespID";
    }
    leaf rx-invalid {
      type string;
      description
        "RxInvalid";
    }
    leaf rx-len-err {
      type string;
      description
        "RxLenErr";
    }
    leaf rx-my-mac-err {
      type string;
      description
        "RxMyMacErr";
    }
    leaf rx-total {
      type string;
      description
        "RxTotal";
    }
    leaf tx-req {
      type string;
      description
        "TxReq";
    }
    leaf tx-reqid {
      type string;
      description
        "TxReqID";
    }
    leaf tx-total {
      type string;
      description
        "TxTotal";
    }
    leaf packet-drop-no-config-received {
      type string;
      description
        "PacketDrop";
    }
  }

  grouping ncs_template_DOT1X-IDB-STATISTICS {
    description
      "DOT1X IDB STATISTICS";
    leaf rx-total {
      type string;
      description
        "RxTotal";
    }
    leaf tx-total {
      type string;
      description
        "TxTotal";
    }
    leaf no-rx-on-intf-down {
      type string;
      description
        "NoRxOnIntfDown";
    }
  }

  grouping ncs_template_DOT1X-IF-STATISTICS {
    description
      "DOT1X IF STATISTICS";
    container idb {
      description
        "Dot1x interface database Statistics";
      uses ncs_template_DOT1X-IDB-STATISTICS;
    }
    container auth {
      description
        "Dot1x Authenticator Port Statistics";
      uses ncs_template_DOT1X-IF-AUTH-STATISTICS;
    }
    container supp {
      description
        "Dot1x Supplicant Port Statistics";
      uses ncs_template_DOT1X-IF-SUPP-STATISTICS;
    }
    container local-eap {
      description
        "Dot1x Local EAP Port Statistics";
      uses ncs_template_DOT1X-IF-LOCAL-EAP-STATISTICS;
    }
    leaf interface-name {
      type string;
      description
        "Interface Display name ";
    }
    leaf pae {
      type string;
      description
        "PAE type on interface";
    }
  }

  grouping ncs_rpc_notif_DOT1X-INTERFACE-MKA {
    description
      "DOT1X INTERFACE MKA";
    leaf tie-break-role {
      type string;
      description
        "Dot1x Tie breaker role chosen for mka when PAE
         type is BOTH";
    }
    leaf eap-based-macsec {
      type string;
      description
        "EAP Mode status for MKA";
    }
    leaf mka-start-time {
      type string;
      description
        "Time stamp when Dot1x posting a message to  MKA
         to start session.";
    }
    leaf mka-stop-time {
      type string;
      description
        "Time stamp when Dot1x posting a message to  MKA
         to stop session.";
    }
    leaf mka-response-time {
      type string;
      description
        "Time Stamp of MKA acknowledgement to Dot1x";
    }
  }

  grouping ncs_rpc_notif_DOT1X-INTERFACE-DETAIL {
    description
      "DOT1X INTERFACE DETAIL";
    container intf-info {
      description
        "Dot1x interface Info";
      uses ncs_rpc_notif_DOT1X-INTERFACE-INFO;
    }
    container mka-status-info {
      description
        "MKA session secure status";
      uses ncs_rpc_notif_DOT1X-INTERFACE-MKA;
    }
    leaf interface-name {
      type string;
      description
        "Interface Display name ";
    }
    leaf interface-sname {
      type string;
      description
        "Interface Display short_name ";
    }
    leaf if-handle {
      type string;
      description
        "Interface handle";
    }
    leaf mac {
      type string;
      description
        "formatted MAC Address";
    }
    leaf ethertype {
      type string;
      description
        "EAPOL Ethertype";
    }
    leaf eapol-addr {
      type string;
      description
        "EAPOL Destination Address";
    }
  }

  grouping ncs_rpc_notif_DOT1X-GLOBAL-PORT-CONTROL-STATISTICS {
    description
      "DOT1X GLOBAL PORT CONTROL STATISTICS";
    leaf enable-succ {
      type uint32;
      description
        "EnableSucc";
    }
    leaf enable-fail {
      type uint32;
      description
        "EnableFail";
    }
    leaf disable-succ {
      type uint32;
      description
        "DisableSucc";
    }
    leaf disable-fail {
      type uint32;
      description
        "DisableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping ncs_rpc_notif_DOT1X-GLOBAL-STATISTICS {
    description
      "DOT1X GLOBAL STATISTICS";
    container port-control {
      description
        "PortControl";
      uses ncs_rpc_notif_DOT1X-GLOBAL-PORT-CONTROL-STATISTICS;
    }
    leaf tx-total {
      type uint32;
      description
        "TxTotal";
    }
    leaf rx-total {
      type uint32;
      description
        "RxTotal";
    }
    leaf rx-no-idb {
      type uint32;
      description
        "RxNoIDB";
    }
    leaf packet-drop-no-config-received {
      type uint32;
      description
        "PacketDrop";
    }
  }

  grouping ncs_rpc_notif_DOT1X-STATISTICS {
    description
      "DOT1X STATISTICS";
    container gl-stats {
      description
        "Global statistics";
      uses ncs_rpc_notif_DOT1X-GLOBAL-STATISTICS;
    }
    list if-stats {
      description
        "dot1x interface statistics list";
      uses ncs_rpc_notif_DOT1X-IF-STATISTICS;
    }
  }

  grouping ncs_rpc_notif_DOT1X-SUPP-TIMERS {
    description
      "DOT1X SUPP TIMERS";
    leaf auth-period {
      type uint32;
      units "second";
      description
        "in Seconds, supplicant waits for a response from
         an authenticator except for EAPOL-START before
         timing out";
    }
    leaf held-period {
      type uint32;
      units "second";
      description
        "in Seconds, supplicant will stay in the HELD
         state (that is, the length of time it will wait
         before trying to send the credentials again
         after a failed attempt)";
    }
    leaf start-period {
      type uint32;
      units "second";
      description
        "Configures the interval, in seconds, between two
         successive EAPOL-Start frames when they are
         being retransmitted";
    }
    leaf max-start {
      type uint32;
      description
        "Max No. of EAPOL-Start frames supplicant can
         send to the authenticator";
    }
  }

  grouping ncs_rpc_notif_DOT1X-AUTH-TIMERS {
    description
      "DOT1X AUTH TIMERS";
    leaf quiet-period {
      type uint32;
      units "second";
      description
        "in Seconds, authenticator remains quiet (in the
         HELD state) following a failed authentication
         exchange before trying to reauthenticate the
         client";
    }
    leaf tx-period {
      type uint32;
      units "second";
      description
        "in Seconds, Timeout for supplicant reply,
         authenticator-to-supplicant retransmission time
         for EAP-request-ID packets (assuming that no
         response is received) from the client";
    }
    leaf max-reauth-req {
      type uint32;
      description
        "Max No. of Reauthentication Attempts (or)
         retransmits an EAP-request-ID frame to the
         client before restarting the authentication
         process";
    }
    leaf supp-timeout {
      type uint32;
      units "second";
      description
        "in Seconds, Timeout for supplicant reply,
         authenticator-to-supplicant retransmission time
         for all EAP messages except for EAP Request ID
         packets";
    }
    leaf max-req {
      type uint32;
      description
        "Max No. of EAP-Req (except for EAP-Request-ID)
         retransmits (authenticator-to-supplicant) before
         sending EAP-Failure";
    }
    leaf reauth-period {
      type uint32;
      units "second";
      description
        "in Seconds,  after which an automatic
         reauthentication should be initiated";
    }
  }

  grouping ncs_rpc_notif_DOT1X-DEFAULT {
    description
      "DOT1X DEFAULT";
    container auth-timers {
      description
        "Dot1x Authenticator default Timer values";
      uses ncs_rpc_notif_DOT1X-AUTH-TIMERS;
    }
    container supp-timers {
      description
        "Dot1x Supllicant default Timer values";
      uses ncs_rpc_notif_DOT1X-SUPP-TIMERS;
    }
    leaf version {
      type uint32;
      description
        "Dot1x Protocol Version";
    }
  }

  grouping ncs_rpc_notif_DOT1X-SUPP-CLIENT-INFO {
    description
      "DOT1X SUPP CLIENT INFO";
    leaf mac {
      type string;
      description
        "formatted MAC Address";
    }
    leaf eap-method {
      type string;
      description
        "EAP Method";
    }
    leaf last-auth-time {
      type string;
      description
        "Last Authenticated Timestamp (formatted)";
    }
    leaf auth-sm-state {
      type string;
      description
        "supp SM State";
    }
    leaf auth-bend-sm-state {
      type string;
      description
        "supp back end SM State";
    }
    leaf port-status {
      type string;
      description
        "Supp port status";
    }
  }

  grouping ncs_rpc_notif_DOT1X-SUPP-INFO {
    description
      "DOT1X SUPP INFO";
    leaf eap-profile {
      type string;
      description
        "EAP profile";
    }
    leaf config-dependency {
      type string;
      description
        "Configuration Dependency ";
    }
    list client {
      description
        "Supp Client info";
      uses ncs_rpc_notif_DOT1X-SUPP-CLIENT-INFO;
    }
  }

  grouping ncs_rpc_notif_DOT1X-AUTH-CLIENT-INFO {
    description
      "DOT1X AUTH CLIENT INFO";
    leaf mac {
      type string;
      description
        "formatted MAC Address";
    }
    leaf auth-sm-state {
      type string;
      description
        "Auth SM State";
    }
    leaf auth-bend-sm-state {
      type string;
      description
        "Auth back end SM State";
    }
    leaf time-to-next-reauth {
      type string;
      description
        "remaining time for next reauthentication";
    }
    leaf last-auth-time {
      type string;
      description
        "Last Authenticated Timestamp (formatted)";
    }
    leaf last-auth-server {
      type string;
      description
        "Last Authenticated Server";
    }
    leaf port-control {
      type string;
      description
        "Auth Client Port Control Status";
    }
    leaf port-status {
      type string;
      description
        "Auth Client Port Status";
    }
  }

  grouping ncs_rpc_notif_DOT1X-AUTH-INFO {
    description
      "DOT1X AUTH INFO";
    leaf port-control {
      type string;
      description
        "Port Control Feature";
    }
    leaf reauth {
      type string;
      description
        "Re-Authentication enabled status";
    }
    leaf config-dependency {
      type string;
      description
        "Configuration Dependency ";
    }
    leaf eap-profile {
      type string;
      description
        "EAP profile";
    }
    leaf host-mode {
      type string;
      description
        "Host Mode";
    }
    list client {
      description
        "Authenticator client list";
      uses ncs_rpc_notif_DOT1X-AUTH-CLIENT-INFO;
    }
  }

  grouping ncs_rpc_notif_DOT1X-INTERFACE-INFO {
    description
      "DOT1X INTERFACE INFO";
    container auth-info {
      description
        "Dot1x Authenticator info";
      uses ncs_rpc_notif_DOT1X-AUTH-INFO;
    }
    container supp-info {
      description
        "Dot1x Supplicant info";
      uses ncs_rpc_notif_DOT1X-SUPP-INFO;
    }
    leaf pae {
      type string;
      description
        "PAE type on interface";
    }
    leaf dot1x-port-status {
      type string;
      description
        "Dot1x Port Status";
    }
    leaf dot1x-profile {
      type string;
      description
        "Dot1x Profile";
    }
    leaf l2-transport {
      type boolean;
      description
        "L2 Transport Info";
    }
  }

  grouping ncs_rpc_notif_DOT1X-INTERFACE {
    description
      "DOT1X INTERFACE";
    container intf-info {
      description
        "Dot1x interface Info";
      uses ncs_rpc_notif_DOT1X-INTERFACE-INFO;
    }
    leaf interface-name {
      type string;
      description
        "Interface Display name ";
    }
    leaf interface-sname {
      type string;
      description
        "Interface Display short_name ";
    }
  }

  grouping ncs_rpc_notif_DOT1X-IF-LOCAL-EAP-STATISTICS {
    description
      "DOT1X IF LOCAL EAP STATISTICS";
    leaf requests {
      type uint32;
      description
        "Requests";
    }
    leaf replies {
      type uint32;
      description
        "Replies";
    }
    leaf timeout {
      type uint32;
      description
        "Timeout";
    }
    leaf dropped-no-eap {
      type uint32;
      description
        "DroppedNoEAP";
    }
    leaf dropped {
      type uint32;
      description
        "Dropped";
    }
    leaf success {
      type uint32;
      description
        "Success";
    }
    leaf failed {
      type uint32;
      description
        "Failed";
    }
  }

  grouping ncs_rpc_notif_DOT1X-IF-SUPP-STATISTICS {
    description
      "DOT1X IF SUPP STATISTICS";
    leaf rx-req {
      type uint32;
      description
        "RxReq";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-start {
      type uint32;
      description
        "TxStart";
    }
    leaf tx-logoff {
      type uint32;
      description
        "TxLogoff";
    }
    leaf tx-resp {
      type uint32;
      description
        "TxResp";
    }
    leaf tx-total {
      type uint32;
      description
        "TxTotal";
    }
  }

  grouping ncs_rpc_notif_DOT1X-IF-PORT-CONTROL-STATISTICS {
    description
      "DOT1X IF PORT CONTROL STATISTICS";
    leaf enable-succ {
      type uint32;
      description
        "EnableSucc";
    }
    leaf enable-fail {
      type uint32;
      description
        "EnableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping ncs_rpc_notif_DOT1X-IF-AUTH-STATISTICS {
    description
      "DOT1X IF AUTH STATISTICS";
    container port-control {
      description
        "PortControl";
      uses ncs_rpc_notif_DOT1X-IF-PORT-CONTROL-STATISTICS;
    }
    leaf rx-start {
      type uint32;
      description
        "RxStart";
    }
    leaf rx-logoff {
      type uint32;
      description
        "RxLogoff";
    }
    leaf rx-resp {
      type uint32;
      description
        "RxResp";
    }
    leaf rx-resp-id {
      type uint32;
      description
        "RxRespID";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-req {
      type uint32;
      description
        "TxReq";
    }
    leaf tx-reqid {
      type uint32;
      description
        "TxReqID";
    }
    leaf tx-total {
      type uint32;
      description
        "TxTotal";
    }
    leaf packet-drop-no-config-received {
      type uint32;
      description
        "PacketDrop";
    }
  }

  grouping ncs_rpc_notif_DOT1X-IDB-STATISTICS {
    description
      "DOT1X IDB STATISTICS";
    leaf rx-total {
      type uint32;
      description
        "RxTotal";
    }
    leaf tx-total {
      type uint32;
      description
        "TxTotal";
    }
    leaf no-rx-on-intf-down {
      type uint32;
      description
        "NoRxOnIntfDown";
    }
  }

  grouping ncs_rpc_notif_DOT1X-IF-STATISTICS {
    description
      "DOT1X IF STATISTICS";
    container idb {
      description
        "Dot1x interface database Statistics";
      uses ncs_rpc_notif_DOT1X-IDB-STATISTICS;
    }
    container auth {
      description
        "Dot1x Authenticator Port Statistics";
      uses ncs_rpc_notif_DOT1X-IF-AUTH-STATISTICS;
    }
    container supp {
      description
        "Dot1x Supplicant Port Statistics";
      uses ncs_rpc_notif_DOT1X-IF-SUPP-STATISTICS;
    }
    container local-eap {
      description
        "Dot1x Local EAP Port Statistics";
      uses ncs_rpc_notif_DOT1X-IF-LOCAL-EAP-STATISTICS;
    }
    leaf interface-name {
      type string;
      description
        "Interface Display name ";
    }
    leaf pae {
      type string;
      description
        "PAE type on interface";
    }
  }

  grouping live_ncs_DOT1X-INTERFACE-MKA {
    description
      "DOT1X INTERFACE MKA";
    leaf tie-break-role {
      type string;
      description
        "Dot1x Tie breaker role chosen for mka when PAE
         type is BOTH";
    }
    leaf eap-based-macsec {
      type string;
      description
        "EAP Mode status for MKA";
    }
    leaf mka-start-time {
      type string;
      description
        "Time stamp when Dot1x posting a message to  MKA
         to start session.";
    }
    leaf mka-stop-time {
      type string;
      description
        "Time stamp when Dot1x posting a message to  MKA
         to stop session.";
    }
    leaf mka-response-time {
      type string;
      description
        "Time Stamp of MKA acknowledgement to Dot1x";
    }
  }

  grouping live_ncs_DOT1X-INTERFACE-DETAIL {
    description
      "DOT1X INTERFACE DETAIL";
    container intf-info {
      description
        "Dot1x interface Info";
      uses live_ncs_DOT1X-INTERFACE-INFO;
    }
    container mka-status-info {
      description
        "MKA session secure status";
      uses live_ncs_DOT1X-INTERFACE-MKA;
    }
    leaf interface-name {
      type string;
      description
        "Interface Display name ";
    }
    leaf interface-sname {
      type string;
      description
        "Interface Display short_name ";
    }
    leaf if-handle {
      type string;
      description
        "Interface handle";
    }
    leaf mac {
      type string;
      description
        "formatted MAC Address";
    }
    leaf ethertype {
      type string;
      description
        "EAPOL Ethertype";
    }
    leaf eapol-addr {
      type string;
      description
        "EAPOL Destination Address";
    }
  }

  grouping live_ncs_DOT1X-GLOBAL-PORT-CONTROL-STATISTICS {
    description
      "DOT1X GLOBAL PORT CONTROL STATISTICS";
    leaf enable-succ {
      type uint32;
      description
        "EnableSucc";
    }
    leaf enable-fail {
      type uint32;
      description
        "EnableFail";
    }
    leaf disable-succ {
      type uint32;
      description
        "DisableSucc";
    }
    leaf disable-fail {
      type uint32;
      description
        "DisableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping live_ncs_DOT1X-GLOBAL-STATISTICS {
    description
      "DOT1X GLOBAL STATISTICS";
    container port-control {
      description
        "PortControl";
      uses live_ncs_DOT1X-GLOBAL-PORT-CONTROL-STATISTICS;
    }
    leaf tx-total {
      type uint32;
      description
        "TxTotal";
    }
    leaf rx-total {
      type uint32;
      description
        "RxTotal";
    }
    leaf rx-no-idb {
      type uint32;
      description
        "RxNoIDB";
    }
    leaf packet-drop-no-config-received {
      type uint32;
      description
        "PacketDrop";
    }
  }

  grouping live_ncs_DOT1X-STATISTICS {
    description
      "DOT1X STATISTICS";
    container gl-stats {
      description
        "Global statistics";
      uses live_ncs_DOT1X-GLOBAL-STATISTICS;
    }
    list if-stats {
      description
        "dot1x interface statistics list";
      uses live_ncs_DOT1X-IF-STATISTICS;
    }
  }

  grouping live_ncs_DOT1X-SUPP-TIMERS {
    description
      "DOT1X SUPP TIMERS";
    leaf auth-period {
      type uint32;
      units "second";
      description
        "in Seconds, supplicant waits for a response from
         an authenticator except for EAPOL-START before
         timing out";
    }
    leaf held-period {
      type uint32;
      units "second";
      description
        "in Seconds, supplicant will stay in the HELD
         state (that is, the length of time it will wait
         before trying to send the credentials again
         after a failed attempt)";
    }
    leaf start-period {
      type uint32;
      units "second";
      description
        "Configures the interval, in seconds, between two
         successive EAPOL-Start frames when they are
         being retransmitted";
    }
    leaf max-start {
      type uint32;
      description
        "Max No. of EAPOL-Start frames supplicant can
         send to the authenticator";
    }
  }

  grouping live_ncs_DOT1X-AUTH-TIMERS {
    description
      "DOT1X AUTH TIMERS";
    leaf quiet-period {
      type uint32;
      units "second";
      description
        "in Seconds, authenticator remains quiet (in the
         HELD state) following a failed authentication
         exchange before trying to reauthenticate the
         client";
    }
    leaf tx-period {
      type uint32;
      units "second";
      description
        "in Seconds, Timeout for supplicant reply,
         authenticator-to-supplicant retransmission time
         for EAP-request-ID packets (assuming that no
         response is received) from the client";
    }
    leaf max-reauth-req {
      type uint32;
      description
        "Max No. of Reauthentication Attempts (or)
         retransmits an EAP-request-ID frame to the
         client before restarting the authentication
         process";
    }
    leaf supp-timeout {
      type uint32;
      units "second";
      description
        "in Seconds, Timeout for supplicant reply,
         authenticator-to-supplicant retransmission time
         for all EAP messages except for EAP Request ID
         packets";
    }
    leaf max-req {
      type uint32;
      description
        "Max No. of EAP-Req (except for EAP-Request-ID)
         retransmits (authenticator-to-supplicant) before
         sending EAP-Failure";
    }
    leaf reauth-period {
      type uint32;
      units "second";
      description
        "in Seconds,  after which an automatic
         reauthentication should be initiated";
    }
  }

  grouping live_ncs_DOT1X-DEFAULT {
    description
      "DOT1X DEFAULT";
    container auth-timers {
      description
        "Dot1x Authenticator default Timer values";
      uses live_ncs_DOT1X-AUTH-TIMERS;
    }
    container supp-timers {
      description
        "Dot1x Supllicant default Timer values";
      uses live_ncs_DOT1X-SUPP-TIMERS;
    }
    leaf version {
      type uint32;
      description
        "Dot1x Protocol Version";
    }
  }

  grouping live_ncs_DOT1X-SUPP-CLIENT-INFO {
    description
      "DOT1X SUPP CLIENT INFO";
    leaf mac {
      type string;
      description
        "formatted MAC Address";
    }
    leaf eap-method {
      type string;
      description
        "EAP Method";
    }
    leaf last-auth-time {
      type string;
      description
        "Last Authenticated Timestamp (formatted)";
    }
    leaf auth-sm-state {
      type string;
      description
        "supp SM State";
    }
    leaf auth-bend-sm-state {
      type string;
      description
        "supp back end SM State";
    }
    leaf port-status {
      type string;
      description
        "Supp port status";
    }
  }

  grouping live_ncs_DOT1X-SUPP-INFO {
    description
      "DOT1X SUPP INFO";
    leaf eap-profile {
      type string;
      description
        "EAP profile";
    }
    leaf config-dependency {
      type string;
      description
        "Configuration Dependency ";
    }
    list client {
      description
        "Supp Client info";
      uses live_ncs_DOT1X-SUPP-CLIENT-INFO;
    }
  }

  grouping live_ncs_DOT1X-AUTH-CLIENT-INFO {
    description
      "DOT1X AUTH CLIENT INFO";
    leaf mac {
      type string;
      description
        "formatted MAC Address";
    }
    leaf auth-sm-state {
      type string;
      description
        "Auth SM State";
    }
    leaf auth-bend-sm-state {
      type string;
      description
        "Auth back end SM State";
    }
    leaf time-to-next-reauth {
      type string;
      description
        "remaining time for next reauthentication";
    }
    leaf last-auth-time {
      type string;
      description
        "Last Authenticated Timestamp (formatted)";
    }
    leaf last-auth-server {
      type string;
      description
        "Last Authenticated Server";
    }
    leaf port-control {
      type string;
      description
        "Auth Client Port Control Status";
    }
    leaf port-status {
      type string;
      description
        "Auth Client Port Status";
    }
  }

  grouping live_ncs_DOT1X-AUTH-INFO {
    description
      "DOT1X AUTH INFO";
    leaf port-control {
      type string;
      description
        "Port Control Feature";
    }
    leaf reauth {
      type string;
      description
        "Re-Authentication enabled status";
    }
    leaf config-dependency {
      type string;
      description
        "Configuration Dependency ";
    }
    leaf eap-profile {
      type string;
      description
        "EAP profile";
    }
    leaf host-mode {
      type string;
      description
        "Host Mode";
    }
    list client {
      description
        "Authenticator client list";
      uses live_ncs_DOT1X-AUTH-CLIENT-INFO;
    }
  }

  grouping live_ncs_DOT1X-INTERFACE-INFO {
    description
      "DOT1X INTERFACE INFO";
    container auth-info {
      description
        "Dot1x Authenticator info";
      uses live_ncs_DOT1X-AUTH-INFO;
    }
    container supp-info {
      description
        "Dot1x Supplicant info";
      uses live_ncs_DOT1X-SUPP-INFO;
    }
    leaf pae {
      type string;
      description
        "PAE type on interface";
    }
    leaf dot1x-port-status {
      type string;
      description
        "Dot1x Port Status";
    }
    leaf dot1x-profile {
      type string;
      description
        "Dot1x Profile";
    }
    leaf l2-transport {
      type boolean;
      description
        "L2 Transport Info";
    }
  }

  grouping live_ncs_DOT1X-INTERFACE {
    description
      "DOT1X INTERFACE";
    container intf-info {
      description
        "Dot1x interface Info";
      uses live_ncs_DOT1X-INTERFACE-INFO;
    }
    leaf interface-name {
      type string;
      description
        "Interface Display name ";
    }
    leaf interface-sname {
      type string;
      description
        "Interface Display short_name ";
    }
  }

  grouping live_ncs_DOT1X-IF-LOCAL-EAP-STATISTICS {
    description
      "DOT1X IF LOCAL EAP STATISTICS";
    leaf requests {
      type uint32;
      description
        "Requests";
    }
    leaf replies {
      type uint32;
      description
        "Replies";
    }
    leaf timeout {
      type uint32;
      description
        "Timeout";
    }
    leaf dropped-no-eap {
      type uint32;
      description
        "DroppedNoEAP";
    }
    leaf dropped {
      type uint32;
      description
        "Dropped";
    }
    leaf success {
      type uint32;
      description
        "Success";
    }
    leaf failed {
      type uint32;
      description
        "Failed";
    }
  }

  grouping live_ncs_DOT1X-IF-SUPP-STATISTICS {
    description
      "DOT1X IF SUPP STATISTICS";
    leaf rx-req {
      type uint32;
      description
        "RxReq";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-start {
      type uint32;
      description
        "TxStart";
    }
    leaf tx-logoff {
      type uint32;
      description
        "TxLogoff";
    }
    leaf tx-resp {
      type uint32;
      description
        "TxResp";
    }
    leaf tx-total {
      type uint32;
      description
        "TxTotal";
    }
  }

  grouping live_ncs_DOT1X-IF-PORT-CONTROL-STATISTICS {
    description
      "DOT1X IF PORT CONTROL STATISTICS";
    leaf enable-succ {
      type uint32;
      description
        "EnableSucc";
    }
    leaf enable-fail {
      type uint32;
      description
        "EnableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping live_ncs_DOT1X-IF-AUTH-STATISTICS {
    description
      "DOT1X IF AUTH STATISTICS";
    container port-control {
      description
        "PortControl";
      uses live_ncs_DOT1X-IF-PORT-CONTROL-STATISTICS;
    }
    leaf rx-start {
      type uint32;
      description
        "RxStart";
    }
    leaf rx-logoff {
      type uint32;
      description
        "RxLogoff";
    }
    leaf rx-resp {
      type uint32;
      description
        "RxResp";
    }
    leaf rx-resp-id {
      type uint32;
      description
        "RxRespID";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-req {
      type uint32;
      description
        "TxReq";
    }
    leaf tx-reqid {
      type uint32;
      description
        "TxReqID";
    }
    leaf tx-total {
      type uint32;
      description
        "TxTotal";
    }
    leaf packet-drop-no-config-received {
      type uint32;
      description
        "PacketDrop";
    }
  }

  grouping live_ncs_DOT1X-IDB-STATISTICS {
    description
      "DOT1X IDB STATISTICS";
    leaf rx-total {
      type uint32;
      description
        "RxTotal";
    }
    leaf tx-total {
      type uint32;
      description
        "TxTotal";
    }
    leaf no-rx-on-intf-down {
      type uint32;
      description
        "NoRxOnIntfDown";
    }
  }

  grouping live_ncs_DOT1X-IF-STATISTICS {
    description
      "DOT1X IF STATISTICS";
    container idb {
      description
        "Dot1x interface database Statistics";
      uses live_ncs_DOT1X-IDB-STATISTICS;
    }
    container auth {
      description
        "Dot1x Authenticator Port Statistics";
      uses live_ncs_DOT1X-IF-AUTH-STATISTICS;
    }
    container supp {
      description
        "Dot1x Supplicant Port Statistics";
      uses live_ncs_DOT1X-IF-SUPP-STATISTICS;
    }
    container local-eap {
      description
        "Dot1x Local EAP Port Statistics";
      uses live_ncs_DOT1X-IF-LOCAL-EAP-STATISTICS;
    }
    leaf interface-name {
      type string;
      description
        "Interface Display name ";
    }
    leaf pae {
      type string;
      description
        "PAE type on interface";
    }
  }

  grouping DOT1X-INTERFACE-MKA {
    description
      "DOT1X INTERFACE MKA";
    leaf tie-break-role {
      type string;
      description
        "Dot1x Tie breaker role chosen for mka when PAE
         type is BOTH";
    }
    leaf eap-based-macsec {
      type string;
      description
        "EAP Mode status for MKA";
    }
    leaf mka-start-time {
      type string;
      description
        "Time stamp when Dot1x posting a message to  MKA
         to start session.";
    }
    leaf mka-stop-time {
      type string;
      description
        "Time stamp when Dot1x posting a message to  MKA
         to stop session.";
    }
    leaf mka-response-time {
      type string;
      description
        "Time Stamp of MKA acknowledgement to Dot1x";
    }
  }

  grouping DOT1X-INTERFACE-DETAIL {
    description
      "DOT1X INTERFACE DETAIL";
    container intf-info {
      description
        "Dot1x interface Info";
      uses DOT1X-INTERFACE-INFO;
    }
    container mka-status-info {
      description
        "MKA session secure status";
      uses DOT1X-INTERFACE-MKA;
    }
    leaf interface-name {
      type string;
      description
        "Interface Display name ";
    }
    leaf interface-sname {
      type string;
      description
        "Interface Display short_name ";
    }
    leaf if-handle {
      type string;
      description
        "Interface handle";
    }
    leaf mac {
      type string;
      description
        "formatted MAC Address";
    }
    leaf ethertype {
      type string;
      description
        "EAPOL Ethertype";
    }
    leaf eapol-addr {
      type string;
      description
        "EAPOL Destination Address";
    }
  }

  grouping DOT1X-GLOBAL-PORT-CONTROL-STATISTICS {
    description
      "DOT1X GLOBAL PORT CONTROL STATISTICS";
    leaf enable-succ {
      type uint32;
      description
        "EnableSucc";
    }
    leaf enable-fail {
      type uint32;
      description
        "EnableFail";
    }
    leaf disable-succ {
      type uint32;
      description
        "DisableSucc";
    }
    leaf disable-fail {
      type uint32;
      description
        "DisableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping DOT1X-GLOBAL-STATISTICS {
    description
      "DOT1X GLOBAL STATISTICS";
    container port-control {
      description
        "PortControl";
      uses DOT1X-GLOBAL-PORT-CONTROL-STATISTICS;
    }
    leaf tx-total {
      type uint32;
      description
        "TxTotal";
    }
    leaf rx-total {
      type uint32;
      description
        "RxTotal";
    }
    leaf rx-no-idb {
      type uint32;
      description
        "RxNoIDB";
    }
    leaf packet-drop-no-config-received {
      type uint32;
      description
        "PacketDrop";
    }
  }

  grouping DOT1X-STATISTICS {
    description
      "DOT1X STATISTICS";
    container gl-stats {
      description
        "Global statistics";
      uses DOT1X-GLOBAL-STATISTICS;
    }
    list if-stats {
      description
        "dot1x interface statistics list";
      uses DOT1X-IF-STATISTICS;
    }
  }

  grouping DOT1X-SUPP-TIMERS {
    description
      "DOT1X SUPP TIMERS";
    leaf auth-period {
      type uint32;
      units "second";
      description
        "in Seconds, supplicant waits for a response from
         an authenticator except for EAPOL-START before
         timing out";
    }
    leaf held-period {
      type uint32;
      units "second";
      description
        "in Seconds, supplicant will stay in the HELD
         state (that is, the length of time it will wait
         before trying to send the credentials again
         after a failed attempt)";
    }
    leaf start-period {
      type uint32;
      units "second";
      description
        "Configures the interval, in seconds, between two
         successive EAPOL-Start frames when they are
         being retransmitted";
    }
    leaf max-start {
      type uint32;
      description
        "Max No. of EAPOL-Start frames supplicant can
         send to the authenticator";
    }
  }

  grouping DOT1X-AUTH-TIMERS {
    description
      "DOT1X AUTH TIMERS";
    leaf quiet-period {
      type uint32;
      units "second";
      description
        "in Seconds, authenticator remains quiet (in the
         HELD state) following a failed authentication
         exchange before trying to reauthenticate the
         client";
    }
    leaf tx-period {
      type uint32;
      units "second";
      description
        "in Seconds, Timeout for supplicant reply,
         authenticator-to-supplicant retransmission time
         for EAP-request-ID packets (assuming that no
         response is received) from the client";
    }
    leaf max-reauth-req {
      type uint32;
      description
        "Max No. of Reauthentication Attempts (or)
         retransmits an EAP-request-ID frame to the
         client before restarting the authentication
         process";
    }
    leaf supp-timeout {
      type uint32;
      units "second";
      description
        "in Seconds, Timeout for supplicant reply,
         authenticator-to-supplicant retransmission time
         for all EAP messages except for EAP Request ID
         packets";
    }
    leaf max-req {
      type uint32;
      description
        "Max No. of EAP-Req (except for EAP-Request-ID)
         retransmits (authenticator-to-supplicant) before
         sending EAP-Failure";
    }
    leaf reauth-period {
      type uint32;
      units "second";
      description
        "in Seconds,  after which an automatic
         reauthentication should be initiated";
    }
  }

  grouping DOT1X-DEFAULT {
    description
      "DOT1X DEFAULT";
    container auth-timers {
      description
        "Dot1x Authenticator default Timer values";
      uses DOT1X-AUTH-TIMERS;
    }
    container supp-timers {
      description
        "Dot1x Supllicant default Timer values";
      uses DOT1X-SUPP-TIMERS;
    }
    leaf version {
      type uint32;
      description
        "Dot1x Protocol Version";
    }
  }

  grouping DOT1X-SUPP-CLIENT-INFO {
    description
      "DOT1X SUPP CLIENT INFO";
    leaf mac {
      type string;
      description
        "formatted MAC Address";
    }
    leaf eap-method {
      type string;
      description
        "EAP Method";
    }
    leaf last-auth-time {
      type string;
      description
        "Last Authenticated Timestamp (formatted)";
    }
    leaf auth-sm-state {
      type string;
      description
        "supp SM State";
    }
    leaf auth-bend-sm-state {
      type string;
      description
        "supp back end SM State";
    }
    leaf port-status {
      type string;
      description
        "Supp port status";
    }
  }

  grouping DOT1X-SUPP-INFO {
    description
      "DOT1X SUPP INFO";
    leaf eap-profile {
      type string;
      description
        "EAP profile";
    }
    leaf config-dependency {
      type string;
      description
        "Configuration Dependency ";
    }
    list client {
      description
        "Supp Client info";
      uses DOT1X-SUPP-CLIENT-INFO;
    }
  }

  grouping DOT1X-AUTH-CLIENT-INFO {
    description
      "DOT1X AUTH CLIENT INFO";
    leaf mac {
      type string;
      description
        "formatted MAC Address";
    }
    leaf auth-sm-state {
      type string;
      description
        "Auth SM State";
    }
    leaf auth-bend-sm-state {
      type string;
      description
        "Auth back end SM State";
    }
    leaf time-to-next-reauth {
      type string;
      description
        "remaining time for next reauthentication";
    }
    leaf last-auth-time {
      type string;
      description
        "Last Authenticated Timestamp (formatted)";
    }
    leaf last-auth-server {
      type string;
      description
        "Last Authenticated Server";
    }
    leaf port-control {
      type string;
      description
        "Auth Client Port Control Status";
    }
    leaf port-status {
      type string;
      description
        "Auth Client Port Status";
    }
  }

  grouping DOT1X-AUTH-INFO {
    description
      "DOT1X AUTH INFO";
    leaf port-control {
      type string;
      description
        "Port Control Feature";
    }
    leaf reauth {
      type string;
      description
        "Re-Authentication enabled status";
    }
    leaf config-dependency {
      type string;
      description
        "Configuration Dependency ";
    }
    leaf eap-profile {
      type string;
      description
        "EAP profile";
    }
    leaf host-mode {
      type string;
      description
        "Host Mode";
    }
    list client {
      description
        "Authenticator client list";
      uses DOT1X-AUTH-CLIENT-INFO;
    }
  }

  grouping DOT1X-INTERFACE-INFO {
    description
      "DOT1X INTERFACE INFO";
    container auth-info {
      description
        "Dot1x Authenticator info";
      uses DOT1X-AUTH-INFO;
    }
    container supp-info {
      description
        "Dot1x Supplicant info";
      uses DOT1X-SUPP-INFO;
    }
    leaf pae {
      type string;
      description
        "PAE type on interface";
    }
    leaf dot1x-port-status {
      type string;
      description
        "Dot1x Port Status";
    }
    leaf dot1x-profile {
      type string;
      description
        "Dot1x Profile";
    }
    leaf l2-transport {
      type boolean;
      description
        "L2 Transport Info";
    }
  }

  grouping DOT1X-INTERFACE {
    description
      "DOT1X INTERFACE";
    container intf-info {
      description
        "Dot1x interface Info";
      uses DOT1X-INTERFACE-INFO;
    }
    leaf interface-name {
      type string;
      description
        "Interface Display name ";
    }
    leaf interface-sname {
      type string;
      description
        "Interface Display short_name ";
    }
  }

  grouping DOT1X-IF-LOCAL-EAP-STATISTICS {
    description
      "DOT1X IF LOCAL EAP STATISTICS";
    leaf requests {
      type uint32;
      description
        "Requests";
    }
    leaf replies {
      type uint32;
      description
        "Replies";
    }
    leaf timeout {
      type uint32;
      description
        "Timeout";
    }
    leaf dropped-no-eap {
      type uint32;
      description
        "DroppedNoEAP";
    }
    leaf dropped {
      type uint32;
      description
        "Dropped";
    }
    leaf success {
      type uint32;
      description
        "Success";
    }
    leaf failed {
      type uint32;
      description
        "Failed";
    }
  }

  grouping DOT1X-IF-SUPP-STATISTICS {
    description
      "DOT1X IF SUPP STATISTICS";
    leaf rx-req {
      type uint32;
      description
        "RxReq";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-start {
      type uint32;
      description
        "TxStart";
    }
    leaf tx-logoff {
      type uint32;
      description
        "TxLogoff";
    }
    leaf tx-resp {
      type uint32;
      description
        "TxResp";
    }
    leaf tx-total {
      type uint32;
      description
        "TxTotal";
    }
  }

  grouping DOT1X-IF-PORT-CONTROL-STATISTICS {
    description
      "DOT1X IF PORT CONTROL STATISTICS";
    leaf enable-succ {
      type uint32;
      description
        "EnableSucc";
    }
    leaf enable-fail {
      type uint32;
      description
        "EnableFail";
    }
    leaf add-client-succ {
      type uint32;
      description
        "AddClientSucc";
    }
    leaf add-client-fail {
      type uint32;
      description
        "AddClientFail";
    }
    leaf remove-client-succ {
      type uint32;
      description
        "RemoveClientSucc";
    }
    leaf remove-client-fail {
      type uint32;
      description
        "RemoveClientFail";
    }
    leaf update-succ {
      type uint32;
      description
        "UpdateSucc";
    }
    leaf update-fail {
      type uint32;
      description
        "UpdateFail";
    }
  }

  grouping DOT1X-IF-AUTH-STATISTICS {
    description
      "DOT1X IF AUTH STATISTICS";
    container port-control {
      description
        "PortControl";
      uses DOT1X-IF-PORT-CONTROL-STATISTICS;
    }
    leaf rx-start {
      type uint32;
      description
        "RxStart";
    }
    leaf rx-logoff {
      type uint32;
      description
        "RxLogoff";
    }
    leaf rx-resp {
      type uint32;
      description
        "RxResp";
    }
    leaf rx-resp-id {
      type uint32;
      description
        "RxRespID";
    }
    leaf rx-invalid {
      type uint32;
      description
        "RxInvalid";
    }
    leaf rx-len-err {
      type uint32;
      description
        "RxLenErr";
    }
    leaf rx-my-mac-err {
      type uint32;
      description
        "RxMyMacErr";
    }
    leaf rx-total {
      type uint32;
      description
        "RxTotal";
    }
    leaf tx-req {
      type uint32;
      description
        "TxReq";
    }
    leaf tx-reqid {
      type uint32;
      description
        "TxReqID";
    }
    leaf tx-total {
      type uint32;
      description
        "TxTotal";
    }
    leaf packet-drop-no-config-received {
      type uint32;
      description
        "PacketDrop";
    }
  }

  grouping DOT1X-IDB-STATISTICS {
    description
      "DOT1X IDB STATISTICS";
    leaf rx-total {
      type uint32;
      description
        "RxTotal";
    }
    leaf tx-total {
      type uint32;
      description
        "TxTotal";
    }
    leaf no-rx-on-intf-down {
      type uint32;
      description
        "NoRxOnIntfDown";
    }
  }

  grouping DOT1X-IF-STATISTICS {
    description
      "DOT1X IF STATISTICS";
    container idb {
      description
        "Dot1x interface database Statistics";
      uses DOT1X-IDB-STATISTICS;
    }
    container auth {
      description
        "Dot1x Authenticator Port Statistics";
      uses DOT1X-IF-AUTH-STATISTICS;
    }
    container supp {
      description
        "Dot1x Supplicant Port Statistics";
      uses DOT1X-IF-SUPP-STATISTICS;
    }
    container local-eap {
      description
        "Dot1x Local EAP Port Statistics";
      uses DOT1X-IF-LOCAL-EAP-STATISTICS;
    }
    leaf interface-name {
      type string;
      description
        "Interface Display name ";
    }
    leaf pae {
      type string;
      description
        "PAE type on interface";
    }
  }
}

module Cisco-IOS-XR-ncs1001-otdr-oper {
  // Generated by yanger -t ncs
  tailf:mount-id "cisco-iosxr-nc-7.3:cisco-iosxr-nc-7.3";
  tailf:ncs-device-type "netconf";

  namespace "http://cisco.com/ns/yang/Cisco-IOS-XR-ncs1001-otdr-oper";
  prefix ncs1001-otdr-oper;

  import cisco-semver {
    prefix semver;
  }
  include Cisco-IOS-XR-ncs1001-otdr-oper-sub1 {
    revision-date 2020-12-12;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1001-otdr package operational data.

     This module contains definitions
     for the following management objects:
       hw-module: ncs1001 hw-module command chain

     Copyright (c) 2013-2020 by Cisco Systems, Inc.
     All rights reserved.";

  revision 2020-12-12 {
    description
      "XML query for CLI show hw-module ampli-trail-view/channel-trail-view does not return a response";
    semver:module-version "2.0.0";
  }
  revision 2019-05-28 {
    description
      "added OTDR periodic scan and event triggered auto scan";
    semver:module-version "1.1.0";
  }
  revision 2019-04-05 {
    description
      "Establish semantic version baseline.";
    semver:module-version "1.1.0";
  }
  revision 2018-03-15 {
    description
      "first release.";
  }
  revision 2015-11-09 {
    description
      "IOS XR 6.0 revision.";
  }

  typedef ncs_template_Ots-otdr-data {
    type string;
    description
      "Ots otdr data";
  }

  typedef ncs_template_Ots-otdr-data-type-details {
    type string;
    description
      "Ots otdr data type details";
  }

  typedef ncs_rpc_notif_Ots-otdr-data {
    type enumeration {
      enum "status" {
        value 0;
        description
          "Display otdr status";
      }
      enum "scan" {
        value 1;
        description
          "Display the list of saved measurements";
      }
      enum "base-line" {
        value 2;
        description
          "Display the list of saved baseline";
      }
    }
    description
      "Ots otdr data";
  }

  typedef ncs_rpc_notif_Ots-otdr-data-type-details {
    type enumeration {
      enum "scan-details" {
        value 1;
        description
          "Displays Scan Details";
      }
      enum "base-line-details" {
        value 2;
        description
          "Displays Baseline Details";
      }
    }
    description
      "Ots otdr data type details";
  }

  typedef live_ncs_Ots-otdr-data {
    type enumeration {
      enum "status" {
        value 0;
        description
          "Display otdr status";
      }
      enum "scan" {
        value 1;
        description
          "Display the list of saved measurements";
      }
      enum "base-line" {
        value 2;
        description
          "Display the list of saved baseline";
      }
    }
    description
      "Ots otdr data";
  }

  typedef live_ncs_Ots-otdr-data-type-details {
    type enumeration {
      enum "scan-details" {
        value 1;
        description
          "Displays Scan Details";
      }
      enum "base-line-details" {
        value 2;
        description
          "Displays Baseline Details";
      }
    }
    description
      "Ots otdr data type details";
  }

  typedef Ots-otdr-data {
    type enumeration {
      enum "status" {
        value 0;
        description
          "Display otdr status";
      }
      enum "scan" {
        value 1;
        description
          "Display the list of saved measurements";
      }
      enum "base-line" {
        value 2;
        description
          "Display the list of saved baseline";
      }
    }
    description
      "Ots otdr data";
  }

  typedef Ots-otdr-data-type-details {
    type enumeration {
      enum "scan-details" {
        value 1;
        description
          "Displays Scan Details";
      }
      enum "base-line-details" {
        value 2;
        description
          "Displays Baseline Details";
      }
    }
    description
      "Ots otdr data type details";
  }

  augment "/ncs:devices/ncs:device/ncs:config" {
    // NCS drop config false container 'hw-module'
  }
  augment "/ncs:devices/ncs:device/ncs:live-status" {
    container hw-module {
      tailf:ncs-device-type "netconf";
      tailf:display-when "not(../../ncs:module) or ../../ncs:module[ncs:name='Cisco-IOS-XR-ncs1001-otdr-oper'] or (../../ncs:live-status-protocol[not(ncs:capability)]) or (../../ncs:live-status-protocol/ncs:capability/ncs:module[.='Cisco-IOS-XR-ncs1001-otdr-oper'])";
      description
        "ncs1001 hw-module command chain";
      container otdr-root {
        description
          "Otdr Root Info";
        container otdrs {
          description
            "Otdr Table Info";
          list otdr {
            key "slot-id";
            description
              "Otdr Info";
            leaf slot-id {
              type uint32 {
                range "1..3";
              }
              description
                "Details associated with a particular slot
                 number";
            }
            list data-type {
              key "otdr-data-type";
              description
                "Dispaly data type list";
              leaf otdr-data-type {
                type live_ncs_Ots-otdr-data;
                description
                  "Details associated with a particular Data
                   type";
              }
              uses live_ncs_OTS-HWMOD-OTDR-OP;
            }
          }
        }
        container otdr-details {
          description
            "Otdr Details Root Info";
          list otdr-detail {
            key "slot-id";
            description
              "Otdr Details";
            leaf slot-id {
              type uint32 {
                range "1..3";
              }
              description
                "Details associated with a particular slot
                 number";
            }
            list data-type-detail {
              key "otdr-data-type-details";
              description
                "Dispaly data type list";
              leaf otdr-data-type-details {
                type live_ncs_Ots-otdr-data-type-details;
                description
                  "Details associated with a particular Data
                   type";
              }
              list identifier {
                key "scan-detail";
                description
                  "Dispaly details";
                leaf scan-detail {
                  type uint32;
                  description
                    "Dispaly details";
                }
                uses live_ncs_OTS-HWMOD-OTDR-OP;
              }
            }
          }
        }
      }
    }
  }
  augment "/ncs:devices/ncs:template/ncs:ned-id/ncs:config" {
    // NCS drop config false container 'hw-module'
  }
}

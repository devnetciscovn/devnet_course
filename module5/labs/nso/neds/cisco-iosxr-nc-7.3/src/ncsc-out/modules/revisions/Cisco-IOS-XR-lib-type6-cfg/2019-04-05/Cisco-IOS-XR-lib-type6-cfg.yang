module Cisco-IOS-XR-lib-type6-cfg {
  // Generated by yanger -t ncs
  tailf:mount-id "cisco-iosxr-nc-7.3:cisco-iosxr-nc-7.3";
  tailf:ncs-device-type "netconf";

  namespace "http://cisco.com/ns/yang/Cisco-IOS-XR-lib-type6-cfg";
  prefix lib-type6-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lib-type6 package configuration.

     This module contains definitions
     for the following management objects:
       password6: Configure masterkey

     Copyright (c) 2013-2019 by Cisco Systems, Inc.
     All rights reserved.";

  revision 2019-04-05 {
    description
      "Establish semantic version baseline.";
    semver:module-version "1.0.0";
  }
  revision 2018-09-22 {
    description
      "Fixed type translation error.";
  }
  revision 2015-11-09 {
    description
      "IOS XR 6.0 revision.";
  }

  typedef ncs_template_Password-encryption {
    type string;
    description
      "Password encryption";
  }

  typedef ncs_rpc_notif_Password-encryption {
    type enumeration {
      enum "type6" {
        value 2;
        description
          "Type6";
      }
    }
    description
      "Password encryption";
  }

  typedef live_ncs_Password-encryption {
    type enumeration {
      enum "type6" {
        value 2;
        description
          "Type6";
      }
    }
    description
      "Password encryption";
  }

  typedef Password-encryption {
    type enumeration {
      enum "type6" {
        value 2;
        description
          "Type6";
      }
    }
    description
      "Password encryption";
  }

  augment "/ncs:devices/ncs:device/ncs:config" {
    container password6 {
      tailf:ncs-device-type "netconf";
      tailf:display-when "not(../../ncs:module) or ../../ncs:module[ncs:name='Cisco-IOS-XR-lib-type6-cfg']";
      description
        "Configure masterkey";
      container encryption {
        description
          "Enable password encryption";
        leaf aes {
          type Password-encryption;
          description
            "encryption type used to store key";
        }
      }
    }
  }
  augment "/ncs:devices/ncs:device/ncs:live-status" {
    container password6 {
      tailf:ncs-device-type "netconf";
      tailf:display-when "not(../../ncs:module) or ../../ncs:module[ncs:name='Cisco-IOS-XR-lib-type6-cfg'] or (../../ncs:live-status-protocol[not(ncs:capability)]) or (../../ncs:live-status-protocol/ncs:capability/ncs:module[.='Cisco-IOS-XR-lib-type6-cfg'])";
      description
        "Configure masterkey";
      container encryption {
        description
          "Enable password encryption";
        leaf aes {
          type live_ncs_Password-encryption;
          description
            "encryption type used to store key";
        }
      }
    }
  }
  augment "/ncs:devices/ncs:template/ncs:ned-id/ncs:config" {
    container password6 {
      description
        "Configure masterkey";
      container encryption {
        description
          "Enable password encryption";
        leaf aes {
          type ncs_template_Password-encryption;
          description
            "encryption type used to store key";
        }
      }
    }
  }
}

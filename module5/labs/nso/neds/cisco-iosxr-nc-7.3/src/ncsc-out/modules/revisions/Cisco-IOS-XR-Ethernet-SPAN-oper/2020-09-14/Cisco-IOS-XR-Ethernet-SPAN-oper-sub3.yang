submodule Cisco-IOS-XR-Ethernet-SPAN-oper-sub3 {
  // Generated by yanger -t ncs
  tailf:mount-id "cisco-iosxr-nc-7.3:cisco-iosxr-nc-7.3";

  belongs-to Cisco-IOS-XR-Ethernet-SPAN-oper {
    prefix Cisco-IOS-XR-Ethernet-SPAN-oper;
  }

  import ietf-inet-types {
    prefix inet;
  }
  import Cisco-IOS-XR-types {
    prefix xr;
  }
  import cisco-semver {
    prefix semver;
  }
  include Cisco-IOS-XR-Ethernet-SPAN-oper-sub1 {
    revision-date 2020-09-14;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR Ethernet-SPAN package operational data.

     Copyright (c) 2013-2020 by Cisco Systems, Inc.
     All rights reserved.";

  revision 2020-09-14 {
    description
      "Added support for mirror rx and tx traffic to separate destinations";
    semver:module-version "4.0.0";
  }
  revision 2020-01-30 {
    description
      "Added support for L3 IPv4 and IPv6 ACLs on a L2 ethernet SPAN session
       2019-12-12
       Added support for file format and PCAP filter expressions under file
       2019-10-02
       Added support for UDP destinations and CloudSPAN.";
    semver:module-version "3.0.0";
  }
  revision 2019-05-12 {
    description
      "Added support for file destinations.";
    semver:module-version "2.0.0";
  }
  revision 2019-04-05 {
    description
      "Establish semantic version baseline.";
    semver:module-version "1.0.0";
  }
  revision 2015-11-09 {
    description
      "IOS XR 6.0 revision.";
  }

  grouping ncs_template_INJECT-INTERFACE-DATA {
    description
      "Inject interface data";
    leaf name {
      type string;
      description
        "Interface Name";
    }
  }

  grouping ncs_template_SPAN-MGR-BAG-SESS-DST-INFO {
    description
      "SPAN MGR BAG SESS DST INFO";
    container destination-data {
      description
        "Destination data";
      uses ncs_template_DESTINATION-STATE;
    }
    container destination-id {
      description
        "Destination ID";
      uses ncs_template_DESTINATION-ID;
    }
    leaf destination-error {
      type string;
      description
        "Last error observed for the destination ";
    }
  }

  grouping ncs_template_DESTINATION-BUNDLE-DATA {
    description
      "Destination Bundle Data";
    leaf bundle-name {
      type ncs_template_Destination-name-string;
      description
        "Bundle Name";
    }
    leaf bundle-state {
      type ncs_template_Im-state-enum;
      description
        "Bundle State";
    }
  }

  grouping ncs_template_DESTINATION-NEXT-HOP-IPV6-ADDRESS-DATA {
    description
      "Destination Next-hop IPv6 Address Data";
    leaf ipv6-address {
      type string;
      description
        "IPv6 address";
    }
    leaf vrf-name {
      type ncs_template_Destination-name-string;
      description
        "VRF name";
    }
    leaf address-is-reachable {
      type string;
      description
        "Address is reachable";
    }
  }

  grouping ncs_template_DESTINATION-NEXT-HOP-IPV4-ADDRESS-DATA {
    description
      "Destination Next-hop IPv4 Address Data";
    leaf ipv4-address {
      type string;
      description
        "IPv4 address";
    }
    leaf vrf-name {
      type ncs_template_Destination-name-string;
      description
        "VRF name";
    }
    leaf address-is-reachable {
      type string;
      description
        "Address is reachable";
    }
  }

  grouping ncs_template_DESTINATION-PSEUDOWIRE-DATA {
    description
      "Destination Pseudowire Data";
    leaf pseudowire-name {
      type ncs_template_Destination-name-string;
      description
        "Pseudowire Name";
    }
    leaf pseudowire-is-up {
      type string;
      description
        "Pseudowire State";
    }
  }

  grouping ncs_template_DESTINATION-INTERFACE-DATA {
    description
      "Destination Interface Data";
    leaf interface-name {
      type ncs_template_Destination-name-string;
      description
        "Interface Name";
    }
    leaf interface-state {
      type ncs_template_Im-state-enum;
      description
        "Interface State";
    }
  }

  grouping ncs_template_DESTINATION-STATE {
    description
      "Destination state";
    container interface-data {
      // NCS drop when statement
      description
        "Interface data";
      uses ncs_template_DESTINATION-INTERFACE-DATA;
    }
    container pseudowire-data {
      // NCS drop when statement
      description
        "Pseudowire data";
      uses ncs_template_DESTINATION-PSEUDOWIRE-DATA;
    }
    container next-hop-ipv4-data {
      // NCS drop when statement
      description
        "Next-hop IPv4 data";
      uses ncs_template_DESTINATION-NEXT-HOP-IPV4-ADDRESS-DATA;
    }
    container next-hop-ipv6-data {
      // NCS drop when statement
      description
        "Next-hop IPv6 data";
      uses ncs_template_DESTINATION-NEXT-HOP-IPV6-ADDRESS-DATA;
    }
    container file-data {
      // NCS drop when statement
      description
        "File data";
      uses ncs_template_FILE-DST-CFG-INFO;
    }
    container udp-data {
      // NCS drop when statement
      description
        "UDP data";
      uses ncs_template_UDP-DST-CFG-INFO;
    }
    container bundle-data {
      // NCS drop when statement
      description
        "Bundle data";
      uses ncs_template_DESTINATION-BUNDLE-DATA;
    }
    leaf destination-class {
      type ncs_template_Destination-class;
      description
        "DestinationClass";
    }
    leaf invalid-value {
      // NCS drop when statement
      type ncs_template_Optional-value;
      description
        "Invalid Parameter";
    }
  }

  grouping ncs_template_SPAN-MGR-SESSION-BAG {
    description
      "SPAN Manager Session Information";
    container destination-data {
      description
        "Destination data";
      uses ncs_template_DESTINATION-STATE;
    }
    container destination-id {
      description
        "Destination ID";
      uses ncs_template_DESTINATION-ID;
    }
    container rx-destination-info {
      description
        "Rx Destination Info";
      uses ncs_template_SPAN-MGR-BAG-SESS-DST-INFO;
    }
    container tx-destination-info {
      description
        "Tx Destination Info";
      uses ncs_template_SPAN-MGR-BAG-SESS-DST-INFO;
    }
    container inject-interface {
      description
        "Inject interface data";
      uses ncs_template_INJECT-INTERFACE-DATA;
    }
    container file-information {
      description
        "Extra information relating to SPAN to file";
      uses ncs_template_FILE-DST-STATE-INFO;
    }
    container cloud-span {
      description
        "Properties related to CloudSPAN";
      uses ncs_template_CLOUD-SPAN-PROPERTIES;
    }
    leaf name {
      type string;
      description
        "Session Name";
    }
    leaf session-class {
      type ncs_template_Session-class;
      description
        "Session class";
    }
    leaf id {
      type string;
      description
        "Numerical ID assigned to session";
    }
    leaf destination-error {
      type string;
      description
        "Last error observed for the destination ";
    }
    leaf separate-destinations {
      type string;
      description
        "Separate Destinations";
    }
    leaf destination-interface-name {
      type string;
      description
        "Destination interface name (deprecated by
         DestinationData, invalid for pseudowires)";
    }
    leaf destination-interface-handle {
      type xr:ncs_template_Interface-name;
      description
        "Destination interface handle (deprecated by
         DestinationID, invalid for pseudowires)";
    }
    leaf interface-error {
      type string;
      description
        "Last error observed for the destination
         interface (deprecated by DestinationError)";
    }
  }

  grouping ncs_rpc_notif_INJECT-INTERFACE-DATA {
    description
      "Inject interface data";
    leaf name {
      type string;
      description
        "Interface Name";
    }
  }

  grouping ncs_rpc_notif_SPAN-MGR-BAG-SESS-DST-INFO {
    description
      "SPAN MGR BAG SESS DST INFO";
    container destination-data {
      description
        "Destination data";
      uses ncs_rpc_notif_DESTINATION-STATE;
    }
    container destination-id {
      description
        "Destination ID";
      uses ncs_rpc_notif_DESTINATION-ID;
    }
    leaf destination-error {
      type uint32;
      description
        "Last error observed for the destination ";
    }
  }

  grouping ncs_rpc_notif_DESTINATION-BUNDLE-DATA {
    description
      "Destination Bundle Data";
    leaf bundle-name {
      type ncs_rpc_notif_Destination-name-string;
      description
        "Bundle Name";
    }
    leaf bundle-state {
      type ncs_rpc_notif_Im-state-enum;
      description
        "Bundle State";
    }
  }

  grouping ncs_rpc_notif_DESTINATION-NEXT-HOP-IPV6-ADDRESS-DATA {
    description
      "Destination Next-hop IPv6 Address Data";
    leaf ipv6-address {
      type inet:ipv6-address;
      description
        "IPv6 address";
    }
    leaf vrf-name {
      type ncs_rpc_notif_Destination-name-string;
      description
        "VRF name";
    }
    leaf address-is-reachable {
      type boolean;
      description
        "Address is reachable";
    }
  }

  grouping ncs_rpc_notif_DESTINATION-NEXT-HOP-IPV4-ADDRESS-DATA {
    description
      "Destination Next-hop IPv4 Address Data";
    leaf ipv4-address {
      type inet:ipv4-address;
      description
        "IPv4 address";
    }
    leaf vrf-name {
      type ncs_rpc_notif_Destination-name-string;
      description
        "VRF name";
    }
    leaf address-is-reachable {
      type boolean;
      description
        "Address is reachable";
    }
  }

  grouping ncs_rpc_notif_DESTINATION-PSEUDOWIRE-DATA {
    description
      "Destination Pseudowire Data";
    leaf pseudowire-name {
      type ncs_rpc_notif_Destination-name-string;
      description
        "Pseudowire Name";
    }
    leaf pseudowire-is-up {
      type boolean;
      description
        "Pseudowire State";
    }
  }

  grouping ncs_rpc_notif_DESTINATION-INTERFACE-DATA {
    description
      "Destination Interface Data";
    leaf interface-name {
      type ncs_rpc_notif_Destination-name-string;
      description
        "Interface Name";
    }
    leaf interface-state {
      type ncs_rpc_notif_Im-state-enum;
      description
        "Interface State";
    }
  }

  grouping ncs_rpc_notif_DESTINATION-STATE {
    description
      "Destination state";
    container interface-data {
      when "../destination-class = 'interface-class'" {
        tailf:xpath-root 3;
        description
          "../DestinationClass = 'InterfaceClass'";
      }
      description
        "Interface data";
      uses ncs_rpc_notif_DESTINATION-INTERFACE-DATA;
    }
    container pseudowire-data {
      when "../destination-class = 'pseudowire-class'" {
        tailf:xpath-root 3;
        description
          "../DestinationClass = 'PseudowireClass'";
      }
      description
        "Pseudowire data";
      uses ncs_rpc_notif_DESTINATION-PSEUDOWIRE-DATA;
    }
    container next-hop-ipv4-data {
      when "../destination-class = 'next-hop-ipv4-class'" {
        tailf:xpath-root 3;
        description
          "../DestinationClass = 'NextHopIPv4Class'";
      }
      description
        "Next-hop IPv4 data";
      uses ncs_rpc_notif_DESTINATION-NEXT-HOP-IPV4-ADDRESS-DATA;
    }
    container next-hop-ipv6-data {
      when "../destination-class = 'next-hop-ipv6-class'" {
        tailf:xpath-root 3;
        description
          "../DestinationClass = 'NextHopIPv6Class'";
      }
      description
        "Next-hop IPv6 data";
      uses ncs_rpc_notif_DESTINATION-NEXT-HOP-IPV6-ADDRESS-DATA;
    }
    container file-data {
      when "../destination-class = 'file-class'" {
        tailf:xpath-root 3;
        description
          "../DestinationClass = 'FileClass'";
      }
      description
        "File data";
      uses ncs_rpc_notif_FILE-DST-CFG-INFO;
    }
    container udp-data {
      when "../destination-class = 'udp-class'" {
        tailf:xpath-root 3;
        description
          "../DestinationClass = 'UDPClass'";
      }
      description
        "UDP data";
      uses ncs_rpc_notif_UDP-DST-CFG-INFO;
    }
    container bundle-data {
      when "../destination-class = 'bundle-class'" {
        tailf:xpath-root 3;
        description
          "../DestinationClass = 'BundleClass'";
      }
      description
        "Bundle data";
      uses ncs_rpc_notif_DESTINATION-BUNDLE-DATA;
    }
    leaf destination-class {
      type ncs_rpc_notif_Destination-class;
      description
        "DestinationClass";
    }
    leaf invalid-value {
      when "../destination-class != 'interface-class' and ../destination-class != 'pseudowire-class' and ../destination-class != 'next-hop-ipv4-class' and ../destination-class != 'next-hop-ipv6-class' and ../destination-class != 'file-class' and ../destination-class != 'udp-class' and ../destination-class != 'bundle-class'" {
        tailf:xpath-root 3;
        description
          "../DestinationClass != 'InterfaceClass' and .
           ./DestinationClass != 'PseudowireClass' and .
           ./DestinationClass != 'NextHopIPv4Class' and .
           ./DestinationClass != 'NextHopIPv6Class' and .
           ./DestinationClass != 'FileClass' and .
           ./DestinationClass != 'UDPClass' and .
           ./DestinationClass != 'BundleClass'";
      }
      type ncs_rpc_notif_Optional-value;
      description
        "Invalid Parameter";
    }
  }

  grouping ncs_rpc_notif_SPAN-MGR-SESSION-BAG {
    description
      "SPAN Manager Session Information";
    container destination-data {
      description
        "Destination data";
      uses ncs_rpc_notif_DESTINATION-STATE;
    }
    container destination-id {
      description
        "Destination ID";
      uses ncs_rpc_notif_DESTINATION-ID;
    }
    container rx-destination-info {
      description
        "Rx Destination Info";
      uses ncs_rpc_notif_SPAN-MGR-BAG-SESS-DST-INFO;
    }
    container tx-destination-info {
      description
        "Tx Destination Info";
      uses ncs_rpc_notif_SPAN-MGR-BAG-SESS-DST-INFO;
    }
    container inject-interface {
      description
        "Inject interface data";
      uses ncs_rpc_notif_INJECT-INTERFACE-DATA;
    }
    container file-information {
      description
        "Extra information relating to SPAN to file";
      uses ncs_rpc_notif_FILE-DST-STATE-INFO;
    }
    container cloud-span {
      description
        "Properties related to CloudSPAN";
      uses ncs_rpc_notif_CLOUD-SPAN-PROPERTIES;
    }
    leaf name {
      type string;
      description
        "Session Name";
    }
    leaf session-class {
      type ncs_rpc_notif_Session-class;
      description
        "Session class";
    }
    leaf id {
      type uint32;
      description
        "Numerical ID assigned to session";
    }
    leaf destination-error {
      type uint32;
      description
        "Last error observed for the destination ";
    }
    leaf separate-destinations {
      type boolean;
      description
        "Separate Destinations";
    }
    leaf destination-interface-name {
      type string;
      description
        "Destination interface name (deprecated by
         DestinationData, invalid for pseudowires)";
    }
    leaf destination-interface-handle {
      type xr:ncs_rpc_notif_Interface-name;
      description
        "Destination interface handle (deprecated by
         DestinationID, invalid for pseudowires)";
    }
    leaf interface-error {
      type uint32;
      description
        "Last error observed for the destination
         interface (deprecated by DestinationError)";
    }
  }

  grouping live_ncs_INJECT-INTERFACE-DATA {
    description
      "Inject interface data";
    leaf name {
      type string;
      description
        "Interface Name";
    }
  }

  grouping live_ncs_SPAN-MGR-BAG-SESS-DST-INFO {
    description
      "SPAN MGR BAG SESS DST INFO";
    container destination-data {
      description
        "Destination data";
      uses live_ncs_DESTINATION-STATE;
    }
    container destination-id {
      description
        "Destination ID";
      uses live_ncs_DESTINATION-ID;
    }
    leaf destination-error {
      type uint32;
      description
        "Last error observed for the destination ";
    }
  }

  grouping live_ncs_DESTINATION-BUNDLE-DATA {
    description
      "Destination Bundle Data";
    leaf bundle-name {
      type live_ncs_Destination-name-string;
      description
        "Bundle Name";
    }
    leaf bundle-state {
      type live_ncs_Im-state-enum;
      description
        "Bundle State";
    }
  }

  grouping live_ncs_DESTINATION-NEXT-HOP-IPV6-ADDRESS-DATA {
    description
      "Destination Next-hop IPv6 Address Data";
    leaf ipv6-address {
      type inet:ipv6-address;
      description
        "IPv6 address";
    }
    leaf vrf-name {
      type live_ncs_Destination-name-string;
      description
        "VRF name";
    }
    leaf address-is-reachable {
      type boolean;
      description
        "Address is reachable";
    }
  }

  grouping live_ncs_DESTINATION-NEXT-HOP-IPV4-ADDRESS-DATA {
    description
      "Destination Next-hop IPv4 Address Data";
    leaf ipv4-address {
      type inet:ipv4-address;
      description
        "IPv4 address";
    }
    leaf vrf-name {
      type live_ncs_Destination-name-string;
      description
        "VRF name";
    }
    leaf address-is-reachable {
      type boolean;
      description
        "Address is reachable";
    }
  }

  grouping live_ncs_DESTINATION-PSEUDOWIRE-DATA {
    description
      "Destination Pseudowire Data";
    leaf pseudowire-name {
      type live_ncs_Destination-name-string;
      description
        "Pseudowire Name";
    }
    leaf pseudowire-is-up {
      type boolean;
      description
        "Pseudowire State";
    }
  }

  grouping live_ncs_DESTINATION-INTERFACE-DATA {
    description
      "Destination Interface Data";
    leaf interface-name {
      type live_ncs_Destination-name-string;
      description
        "Interface Name";
    }
    leaf interface-state {
      type live_ncs_Im-state-enum;
      description
        "Interface State";
    }
  }

  grouping live_ncs_DESTINATION-STATE {
    description
      "Destination state";
    container interface-data {
      // NCS drop when statement
      description
        "Interface data";
      uses live_ncs_DESTINATION-INTERFACE-DATA;
    }
    container pseudowire-data {
      // NCS drop when statement
      description
        "Pseudowire data";
      uses live_ncs_DESTINATION-PSEUDOWIRE-DATA;
    }
    container next-hop-ipv4-data {
      // NCS drop when statement
      description
        "Next-hop IPv4 data";
      uses live_ncs_DESTINATION-NEXT-HOP-IPV4-ADDRESS-DATA;
    }
    container next-hop-ipv6-data {
      // NCS drop when statement
      description
        "Next-hop IPv6 data";
      uses live_ncs_DESTINATION-NEXT-HOP-IPV6-ADDRESS-DATA;
    }
    container file-data {
      // NCS drop when statement
      description
        "File data";
      uses live_ncs_FILE-DST-CFG-INFO;
    }
    container udp-data {
      // NCS drop when statement
      description
        "UDP data";
      uses live_ncs_UDP-DST-CFG-INFO;
    }
    container bundle-data {
      // NCS drop when statement
      description
        "Bundle data";
      uses live_ncs_DESTINATION-BUNDLE-DATA;
    }
    leaf destination-class {
      type live_ncs_Destination-class;
      description
        "DestinationClass";
    }
    leaf invalid-value {
      // NCS drop when statement
      type live_ncs_Optional-value;
      description
        "Invalid Parameter";
    }
  }

  grouping live_ncs_SPAN-MGR-SESSION-BAG {
    description
      "SPAN Manager Session Information";
    container destination-data {
      description
        "Destination data";
      uses live_ncs_DESTINATION-STATE;
    }
    container destination-id {
      description
        "Destination ID";
      uses live_ncs_DESTINATION-ID;
    }
    container rx-destination-info {
      description
        "Rx Destination Info";
      uses live_ncs_SPAN-MGR-BAG-SESS-DST-INFO;
    }
    container tx-destination-info {
      description
        "Tx Destination Info";
      uses live_ncs_SPAN-MGR-BAG-SESS-DST-INFO;
    }
    container inject-interface {
      description
        "Inject interface data";
      uses live_ncs_INJECT-INTERFACE-DATA;
    }
    container file-information {
      description
        "Extra information relating to SPAN to file";
      uses live_ncs_FILE-DST-STATE-INFO;
    }
    container cloud-span {
      description
        "Properties related to CloudSPAN";
      uses live_ncs_CLOUD-SPAN-PROPERTIES;
    }
    leaf name {
      type string;
      description
        "Session Name";
    }
    leaf session-class {
      type live_ncs_Session-class;
      description
        "Session class";
    }
    leaf id {
      type uint32;
      description
        "Numerical ID assigned to session";
    }
    leaf destination-error {
      type uint32;
      description
        "Last error observed for the destination ";
    }
    leaf separate-destinations {
      type boolean;
      description
        "Separate Destinations";
    }
    leaf destination-interface-name {
      type string;
      description
        "Destination interface name (deprecated by
         DestinationData, invalid for pseudowires)";
    }
    leaf destination-interface-handle {
      type xr:live_ncs_Interface-name;
      description
        "Destination interface handle (deprecated by
         DestinationID, invalid for pseudowires)";
    }
    leaf interface-error {
      type uint32;
      description
        "Last error observed for the destination
         interface (deprecated by DestinationError)";
    }
  }

  grouping INJECT-INTERFACE-DATA {
    description
      "Inject interface data";
    leaf name {
      type string;
      description
        "Interface Name";
    }
  }

  grouping SPAN-MGR-BAG-SESS-DST-INFO {
    description
      "SPAN MGR BAG SESS DST INFO";
    container destination-data {
      description
        "Destination data";
      uses DESTINATION-STATE;
    }
    container destination-id {
      description
        "Destination ID";
      uses DESTINATION-ID;
    }
    leaf destination-error {
      type uint32;
      description
        "Last error observed for the destination ";
    }
  }

  grouping DESTINATION-BUNDLE-DATA {
    description
      "Destination Bundle Data";
    leaf bundle-name {
      type Destination-name-string;
      description
        "Bundle Name";
    }
    leaf bundle-state {
      type Im-state-enum;
      description
        "Bundle State";
    }
  }

  grouping DESTINATION-NEXT-HOP-IPV6-ADDRESS-DATA {
    description
      "Destination Next-hop IPv6 Address Data";
    leaf ipv6-address {
      type inet:ipv6-address;
      description
        "IPv6 address";
    }
    leaf vrf-name {
      type Destination-name-string;
      description
        "VRF name";
    }
    leaf address-is-reachable {
      type boolean;
      description
        "Address is reachable";
    }
  }

  grouping DESTINATION-NEXT-HOP-IPV4-ADDRESS-DATA {
    description
      "Destination Next-hop IPv4 Address Data";
    leaf ipv4-address {
      type inet:ipv4-address;
      description
        "IPv4 address";
    }
    leaf vrf-name {
      type Destination-name-string;
      description
        "VRF name";
    }
    leaf address-is-reachable {
      type boolean;
      description
        "Address is reachable";
    }
  }

  grouping DESTINATION-PSEUDOWIRE-DATA {
    description
      "Destination Pseudowire Data";
    leaf pseudowire-name {
      type Destination-name-string;
      description
        "Pseudowire Name";
    }
    leaf pseudowire-is-up {
      type boolean;
      description
        "Pseudowire State";
    }
  }

  grouping DESTINATION-INTERFACE-DATA {
    description
      "Destination Interface Data";
    leaf interface-name {
      type Destination-name-string;
      description
        "Interface Name";
    }
    leaf interface-state {
      type Im-state-enum;
      description
        "Interface State";
    }
  }

  grouping DESTINATION-STATE {
    description
      "Destination state";
    container interface-data {
      when "../destination-class = 'interface-class'" {
        tailf:xpath-root 3;
        description
          "../DestinationClass = 'InterfaceClass'";
      }
      description
        "Interface data";
      uses DESTINATION-INTERFACE-DATA;
    }
    container pseudowire-data {
      when "../destination-class = 'pseudowire-class'" {
        tailf:xpath-root 3;
        description
          "../DestinationClass = 'PseudowireClass'";
      }
      description
        "Pseudowire data";
      uses DESTINATION-PSEUDOWIRE-DATA;
    }
    container next-hop-ipv4-data {
      when "../destination-class = 'next-hop-ipv4-class'" {
        tailf:xpath-root 3;
        description
          "../DestinationClass = 'NextHopIPv4Class'";
      }
      description
        "Next-hop IPv4 data";
      uses DESTINATION-NEXT-HOP-IPV4-ADDRESS-DATA;
    }
    container next-hop-ipv6-data {
      when "../destination-class = 'next-hop-ipv6-class'" {
        tailf:xpath-root 3;
        description
          "../DestinationClass = 'NextHopIPv6Class'";
      }
      description
        "Next-hop IPv6 data";
      uses DESTINATION-NEXT-HOP-IPV6-ADDRESS-DATA;
    }
    container file-data {
      when "../destination-class = 'file-class'" {
        tailf:xpath-root 3;
        description
          "../DestinationClass = 'FileClass'";
      }
      description
        "File data";
      uses FILE-DST-CFG-INFO;
    }
    container udp-data {
      when "../destination-class = 'udp-class'" {
        tailf:xpath-root 3;
        description
          "../DestinationClass = 'UDPClass'";
      }
      description
        "UDP data";
      uses UDP-DST-CFG-INFO;
    }
    container bundle-data {
      when "../destination-class = 'bundle-class'" {
        tailf:xpath-root 3;
        description
          "../DestinationClass = 'BundleClass'";
      }
      description
        "Bundle data";
      uses DESTINATION-BUNDLE-DATA;
    }
    leaf destination-class {
      type Destination-class;
      description
        "DestinationClass";
    }
    leaf invalid-value {
      when "../destination-class != 'interface-class' and ../destination-class != 'pseudowire-class' and ../destination-class != 'next-hop-ipv4-class' and ../destination-class != 'next-hop-ipv6-class' and ../destination-class != 'file-class' and ../destination-class != 'udp-class' and ../destination-class != 'bundle-class'" {
        tailf:xpath-root 3;
        description
          "../DestinationClass != 'InterfaceClass' and .
           ./DestinationClass != 'PseudowireClass' and .
           ./DestinationClass != 'NextHopIPv4Class' and .
           ./DestinationClass != 'NextHopIPv6Class' and .
           ./DestinationClass != 'FileClass' and .
           ./DestinationClass != 'UDPClass' and .
           ./DestinationClass != 'BundleClass'";
      }
      type Optional-value;
      description
        "Invalid Parameter";
    }
  }

  grouping SPAN-MGR-SESSION-BAG {
    description
      "SPAN Manager Session Information";
    container destination-data {
      description
        "Destination data";
      uses DESTINATION-STATE;
    }
    container destination-id {
      description
        "Destination ID";
      uses DESTINATION-ID;
    }
    container rx-destination-info {
      description
        "Rx Destination Info";
      uses SPAN-MGR-BAG-SESS-DST-INFO;
    }
    container tx-destination-info {
      description
        "Tx Destination Info";
      uses SPAN-MGR-BAG-SESS-DST-INFO;
    }
    container inject-interface {
      description
        "Inject interface data";
      uses INJECT-INTERFACE-DATA;
    }
    container file-information {
      description
        "Extra information relating to SPAN to file";
      uses FILE-DST-STATE-INFO;
    }
    container cloud-span {
      description
        "Properties related to CloudSPAN";
      uses CLOUD-SPAN-PROPERTIES;
    }
    leaf name {
      type string;
      description
        "Session Name";
    }
    leaf session-class {
      type Session-class;
      description
        "Session class";
    }
    leaf id {
      type uint32;
      description
        "Numerical ID assigned to session";
    }
    leaf destination-error {
      type uint32;
      description
        "Last error observed for the destination ";
    }
    leaf separate-destinations {
      type boolean;
      description
        "Separate Destinations";
    }
    leaf destination-interface-name {
      type string;
      description
        "Destination interface name (deprecated by
         DestinationData, invalid for pseudowires)";
    }
    leaf destination-interface-handle {
      type xr:Interface-name;
      description
        "Destination interface handle (deprecated by
         DestinationID, invalid for pseudowires)";
    }
    leaf interface-error {
      type uint32;
      description
        "Last error observed for the destination
         interface (deprecated by DestinationError)";
    }
  }
}

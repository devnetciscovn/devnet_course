module Cisco-IOS-XR-linux-xlnc-cfg {
  // Generated by yanger -t ncs
  tailf:mount-id "cisco-iosxr-nc-7.3:cisco-iosxr-nc-7.3";
  tailf:ncs-device-type "netconf";

  namespace "http://cisco.com/ns/yang/Cisco-IOS-XR-linux-xlnc-cfg";
  prefix linux-xlnc-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-xlnc package configuration.

     This module contains definitions
     for the following management objects:
       linux-networking: Linux Networking interface configuration

     Copyright (c) 2013-2019 by Cisco Systems, Inc.
     All rights reserved.";

  revision 2019-04-05 {
    description
      "Establish semantic version baseline.";
    semver:module-version "2.0.0";
  }
  revision 2015-11-09 {
    description
      "IOS XR 6.0 revision.";
  }

  typedef ncs_template_Addr-family {
    type string;
    description
      "Addr family";
  }

  typedef ncs_template_L4-proto-family {
    type string;
    description
      "L4 proto family";
  }

  typedef ncs_template_Statistics-sync-interval {
    type string;
    description
      "Statistics sync interval";
  }

  typedef ncs_template_Xlnc-sync-dir {
    type string;
    description
      "Xlnc sync dir";
  }

  typedef ncs_template_Xlnc-protection-action {
    type string;
    description
      "Xlnc protection action";
  }

  typedef ncs_rpc_notif_Addr-family {
    type enumeration {
      enum "ipv4" {
        value 412;
        description
          "Internet Protocol version 4, RFC 791";
      }
      enum "ipv6" {
        value 413;
        description
          "Internet Protocol version 6, RFC 8200";
      }
    }
    description
      "Addr family";
  }

  typedef ncs_rpc_notif_L4-proto-family {
    type enumeration {
      enum "tcp" {
        value 104;
        description
          "Transmission Control Protocol, RFC 793";
      }
      enum "udp" {
        value 105;
        description
          "User Datagram Protocol, RFC 768";
      }
    }
    description
      "L4 proto family";
  }

  typedef ncs_rpc_notif_Statistics-sync-interval {
    type enumeration {
      enum "5s" {
        value 2;
        description
          "5 seconds";
      }
      enum "10s" {
        value 3;
        description
          "10 seconds";
      }
      enum "30s" {
        value 4;
        description
          "30 seconds";
      }
      enum "60s" {
        value 5;
        description
          "60 seconds";
      }
    }
    description
      "Statistics sync interval";
  }

  typedef ncs_rpc_notif_Xlnc-sync-dir {
    type enumeration {
      enum "xr-to-linux" {
        value 0;
        description
          "Set direction to be from XR to Linux";
      }
      enum "linux-to-xr" {
        value 1;
        description
          "Set direction to be from Linux to XR";
      }
    }
    description
      "Xlnc sync dir";
  }

  typedef ncs_rpc_notif_Xlnc-protection-action {
    type enumeration {
      enum "permit" {
        value 7926;
        description
          "Allow traffic";
      }
      enum "deny" {
        value 7927;
        description
          "Deny traffic";
      }
    }
    description
      "Xlnc protection action";
  }

  typedef live_ncs_Addr-family {
    type enumeration {
      enum "ipv4" {
        value 412;
        description
          "Internet Protocol version 4, RFC 791";
      }
      enum "ipv6" {
        value 413;
        description
          "Internet Protocol version 6, RFC 8200";
      }
    }
    description
      "Addr family";
  }

  typedef live_ncs_L4-proto-family {
    type enumeration {
      enum "tcp" {
        value 104;
        description
          "Transmission Control Protocol, RFC 793";
      }
      enum "udp" {
        value 105;
        description
          "User Datagram Protocol, RFC 768";
      }
    }
    description
      "L4 proto family";
  }

  typedef live_ncs_Statistics-sync-interval {
    type enumeration {
      enum "5s" {
        value 2;
        description
          "5 seconds";
      }
      enum "10s" {
        value 3;
        description
          "10 seconds";
      }
      enum "30s" {
        value 4;
        description
          "30 seconds";
      }
      enum "60s" {
        value 5;
        description
          "60 seconds";
      }
    }
    description
      "Statistics sync interval";
  }

  typedef live_ncs_Xlnc-sync-dir {
    type enumeration {
      enum "xr-to-linux" {
        value 0;
        description
          "Set direction to be from XR to Linux";
      }
      enum "linux-to-xr" {
        value 1;
        description
          "Set direction to be from Linux to XR";
      }
    }
    description
      "Xlnc sync dir";
  }

  typedef live_ncs_Xlnc-protection-action {
    type enumeration {
      enum "permit" {
        value 7926;
        description
          "Allow traffic";
      }
      enum "deny" {
        value 7927;
        description
          "Deny traffic";
      }
    }
    description
      "Xlnc protection action";
  }

  typedef Addr-family {
    type enumeration {
      enum "ipv4" {
        value 412;
        description
          "Internet Protocol version 4, RFC 791";
      }
      enum "ipv6" {
        value 413;
        description
          "Internet Protocol version 6, RFC 8200";
      }
    }
    description
      "Addr family";
  }

  typedef L4-proto-family {
    type enumeration {
      enum "tcp" {
        value 104;
        description
          "Transmission Control Protocol, RFC 793";
      }
      enum "udp" {
        value 105;
        description
          "User Datagram Protocol, RFC 768";
      }
    }
    description
      "L4 proto family";
  }

  typedef Statistics-sync-interval {
    type enumeration {
      enum "5s" {
        value 2;
        description
          "5 seconds";
      }
      enum "10s" {
        value 3;
        description
          "10 seconds";
      }
      enum "30s" {
        value 4;
        description
          "30 seconds";
      }
      enum "60s" {
        value 5;
        description
          "60 seconds";
      }
    }
    description
      "Statistics sync interval";
  }

  typedef Xlnc-sync-dir {
    type enumeration {
      enum "xr-to-linux" {
        value 0;
        description
          "Set direction to be from XR to Linux";
      }
      enum "linux-to-xr" {
        value 1;
        description
          "Set direction to be from Linux to XR";
      }
    }
    description
      "Xlnc sync dir";
  }

  typedef Xlnc-protection-action {
    type enumeration {
      enum "permit" {
        value 7926;
        description
          "Allow traffic";
      }
      enum "deny" {
        value 7927;
        description
          "Deny traffic";
      }
    }
    description
      "Xlnc protection action";
  }

  augment "/ncs:devices/ncs:device/ncs:config" {
    container linux-networking {
      tailf:ncs-device-type "netconf";
      tailf:display-when "not(../../ncs:module) or ../../ncs:module[ncs:name='Cisco-IOS-XR-linux-xlnc-cfg']";
      description
        "Linux Networking interface configuration";
      container exposed-interfaces {
        description
          "Configuration for exposed interfaces";
        list exposed-interface {
          key "interface-name";
          description
            "Configuration for a single exposed interface";
          container statistics-synchronization {
            presence "Indicates a statistics-synchronization node is configured.";
            description
              "Configure synchronization of this interface's
               statistics between IOS-XR and Linux";
            leaf direction {
              type Xlnc-sync-dir;
              mandatory true;
              description
                "Specify the direction in which statistics
                 sychronization should be performed. Currently
                 the only supported value is FromXR";
            }
            leaf interval {
              type Statistics-sync-interval;
              mandatory true;
              description
                "Interval how often statistics sychronization
                 takes place";
            }
          }
          leaf exposed-interface-sync-direction {
            type Xlnc-sync-dir;
            description
              "Synchronization direction for an exposed
               interface.";
          }
          leaf interface-name {
            type xr:Interface-name;
            description
              "Interface name";
          }
        }
      }
      container statistics-synchronization {
        presence "Indicates a statistics-synchronization node is configured.";
        description
          "Configure synchronization of interface
           statistics between IOS-XR and Linux";
        leaf direction {
          type Xlnc-sync-dir;
          mandatory true;
          description
            "Specify the direction in which statistics
             sychronization should be performed. Currently
             the only supported value is FromXR";
        }
        leaf interval {
          type Statistics-sync-interval;
          mandatory true;
          description
            "Interval how often statistics sychronization
             takes place";
        }
      }
      container vrf-names {
        description
          "Table of VRF names";
        list vrf-name {
          key "vrf-name";
          description
            "VRF name";
          container address-families {
            description
              "Table of address families";
            list address-family {
              key "address-family";
              description
                "IP address family";
              container traffic-protection {
                description
                  "Traffic Protection configuration";
                container service-protocol-local-port-nums {
                  description
                    "Container for Traffic Protection Services";

                  grouping SERVICE-CONTENT {
                    description
                      "SERVICE CONTENT";
                    container rules-table {
                      description
                        "Container for Traffic Protection Rule";

                      grouping RULE-CONTENT {
                        description
                          "RULE CONTENT";
                        leaf rule-action {
                          type Xlnc-protection-action;
                          mandatory true;
                          description
                            "rule action";
                        }
                      }

                      grouping REMOTE-ADDRESS-LEAF {
                        description
                          "REMOTE ADDRESS LEAF";
                        leaf remote-address {
                          type inet:ip-prefix;
                          description
                            "remote prefix/length";
                        }
                      }

                      grouping LOCAL-ADDRESS-LEAF {
                        description
                          "LOCAL ADDRESS LEAF";
                        leaf local-address {
                          type inet:ip-prefix;
                          description
                            "local prefix/length";
                        }
                      }

                      grouping INTERFACE-NAME-LEAF {
                        description
                          "INTERFACE NAME LEAF";
                        leaf interface-name {
                          type xr:Interface-name;
                          description
                            "interface name";
                        }
                      }
                      list rule-local-address {
                        key "local-address";
                        description
                          "Represents a single Traffic Protection
                           Rule, defining an exception to the
                           parent Service's default action.";
                        uses LOCAL-ADDRESS-LEAF;
                        uses RULE-CONTENT;
                      }
                      list rule-interface-name {
                        key "interface-name";
                        description
                          "Represents a single Traffic Protection
                           Rule, defining an exception to the
                           parent Service's default action.";
                        uses INTERFACE-NAME-LEAF;
                        uses RULE-CONTENT;
                      }
                      list rule-remote-address {
                        key "remote-address";
                        description
                          "Represents a single Traffic Protection
                           Rule, defining an exception to the
                           parent Service's default action.";
                        uses REMOTE-ADDRESS-LEAF;
                        uses RULE-CONTENT;
                      }
                      list rule-remote-address-local-address {
                        key "remote-address local-address";
                        description
                          "Represents a single Traffic Protection
                           Rule, defining an exception to the
                           parent Service's default action.";
                        uses REMOTE-ADDRESS-LEAF;
                        uses LOCAL-ADDRESS-LEAF;
                        uses RULE-CONTENT;
                      }
                      list rule-remote-address-interface-name {
                        key "remote-address interface-name";
                        description
                          "Represents a single Traffic Protection
                           Rule, defining an exception to the
                           parent Service's default action.";
                        uses REMOTE-ADDRESS-LEAF;
                        uses INTERFACE-NAME-LEAF;
                        uses RULE-CONTENT;
                      }
                      list rule-local-address-interface-name {
                        key "local-address interface-name";
                        description
                          "Represents a single Traffic Protection
                           Rule, defining an exception to the
                           parent Service's default action.";
                        uses LOCAL-ADDRESS-LEAF;
                        uses INTERFACE-NAME-LEAF;
                        uses RULE-CONTENT;
                      }
                      list rule-remote-address-local-address-interface-name {
                        key "remote-address local-address interface-name";
                        description
                          "Represents a single Traffic Protection
                           Rule, defining an exception to the
                           parent Service's default action.";
                        uses REMOTE-ADDRESS-LEAF;
                        uses LOCAL-ADDRESS-LEAF;
                        uses INTERFACE-NAME-LEAF;
                        uses RULE-CONTENT;
                      }
                    }
                    leaf service-default-action {
                      type Xlnc-protection-action;
                      description
                        "Indicates the default action to be taken
                         for traffic this Traffic Protection
                         Service.";
                    }
                  }
                  list service-protocol-local-port-num {
                    key "protocol local-port-num";
                    description
                      "A single Traffic Protection Service,
                       defining a L4 protocol and local port
                       value.";
                    leaf protocol {
                      type L4-proto-family;
                      description
                        "L4 protocol";
                    }
                    leaf local-port-num {
                      type xr:Cisco-ios-xr-port-number;
                      description
                        "Local port number";
                    }
                    uses SERVICE-CONTENT;
                  }
                  list service-protocol-local-port-all {
                    key "protocol local-port-all";
                    description
                      "A single Traffic Protection Service,
                       defining a L4 protocol and local port
                       value.";
                    leaf protocol {
                      type L4-proto-family;
                      description
                        "L4 protocol";
                    }
                    leaf local-port-all {
                      type xr:Cisco-ios-xr-string;
                      description
                        "All ports";
                    }
                    uses SERVICE-CONTENT;
                  }
                }
              }
              leaf address-family {
                type Addr-family;
                description
                  "IP address family";
              }
            }
          }
          leaf vrf-name {
            type xr:Cisco-ios-xr-string {
              length "1..32";
            }
            description
              "VRF name";
          }
        }
      }
    }
  }
  augment "/ncs:devices/ncs:device/ncs:live-status" {
    container linux-networking {
      tailf:ncs-device-type "netconf";
      tailf:display-when "not(../../ncs:module) or ../../ncs:module[ncs:name='Cisco-IOS-XR-linux-xlnc-cfg'] or (../../ncs:live-status-protocol[not(ncs:capability)]) or (../../ncs:live-status-protocol/ncs:capability/ncs:module[.='Cisco-IOS-XR-linux-xlnc-cfg'])";
      description
        "Linux Networking interface configuration";
      container exposed-interfaces {
        description
          "Configuration for exposed interfaces";
        list exposed-interface {
          key "interface-name";
          description
            "Configuration for a single exposed interface";
          container statistics-synchronization {
            presence "Indicates a statistics-synchronization node is configured.";
            description
              "Configure synchronization of this interface's
               statistics between IOS-XR and Linux";
            leaf direction {
              type live_ncs_Xlnc-sync-dir;
              // NCS drop mandatory statement
              description
                "Specify the direction in which statistics
                 sychronization should be performed. Currently
                 the only supported value is FromXR";
            }
            leaf interval {
              type live_ncs_Statistics-sync-interval;
              // NCS drop mandatory statement
              description
                "Interval how often statistics sychronization
                 takes place";
            }
          }
          leaf exposed-interface-sync-direction {
            type live_ncs_Xlnc-sync-dir;
            description
              "Synchronization direction for an exposed
               interface.";
          }
          leaf interface-name {
            type xr:live_ncs_Interface-name;
            description
              "Interface name";
          }
        }
      }
      container statistics-synchronization {
        presence "Indicates a statistics-synchronization node is configured.";
        description
          "Configure synchronization of interface
           statistics between IOS-XR and Linux";
        leaf direction {
          type live_ncs_Xlnc-sync-dir;
          // NCS drop mandatory statement
          description
            "Specify the direction in which statistics
             sychronization should be performed. Currently
             the only supported value is FromXR";
        }
        leaf interval {
          type live_ncs_Statistics-sync-interval;
          // NCS drop mandatory statement
          description
            "Interval how often statistics sychronization
             takes place";
        }
      }
      container vrf-names {
        description
          "Table of VRF names";
        list vrf-name {
          key "vrf-name";
          description
            "VRF name";
          container address-families {
            description
              "Table of address families";
            list address-family {
              key "address-family";
              description
                "IP address family";
              container traffic-protection {
                description
                  "Traffic Protection configuration";
                container service-protocol-local-port-nums {
                  description
                    "Container for Traffic Protection Services";

                  grouping SERVICE-CONTENT {
                    description
                      "SERVICE CONTENT";
                    container rules-table {
                      description
                        "Container for Traffic Protection Rule";

                      grouping RULE-CONTENT {
                        description
                          "RULE CONTENT";
                        leaf rule-action {
                          type live_ncs_Xlnc-protection-action;
                          // NCS drop mandatory statement
                          description
                            "rule action";
                        }
                      }

                      grouping REMOTE-ADDRESS-LEAF {
                        description
                          "REMOTE ADDRESS LEAF";
                        leaf remote-address {
                          type inet:ip-prefix;
                          description
                            "remote prefix/length";
                        }
                      }

                      grouping LOCAL-ADDRESS-LEAF {
                        description
                          "LOCAL ADDRESS LEAF";
                        leaf local-address {
                          type inet:ip-prefix;
                          description
                            "local prefix/length";
                        }
                      }

                      grouping INTERFACE-NAME-LEAF {
                        description
                          "INTERFACE NAME LEAF";
                        leaf interface-name {
                          type xr:live_ncs_Interface-name;
                          description
                            "interface name";
                        }
                      }
                      list rule-local-address {
                        key "local-address";
                        description
                          "Represents a single Traffic Protection
                           Rule, defining an exception to the
                           parent Service's default action.";
                        uses LOCAL-ADDRESS-LEAF;
                        uses RULE-CONTENT;
                      }
                      list rule-interface-name {
                        key "interface-name";
                        description
                          "Represents a single Traffic Protection
                           Rule, defining an exception to the
                           parent Service's default action.";
                        uses INTERFACE-NAME-LEAF;
                        uses RULE-CONTENT;
                      }
                      list rule-remote-address {
                        key "remote-address";
                        description
                          "Represents a single Traffic Protection
                           Rule, defining an exception to the
                           parent Service's default action.";
                        uses REMOTE-ADDRESS-LEAF;
                        uses RULE-CONTENT;
                      }
                      list rule-remote-address-local-address {
                        key "remote-address local-address";
                        description
                          "Represents a single Traffic Protection
                           Rule, defining an exception to the
                           parent Service's default action.";
                        uses REMOTE-ADDRESS-LEAF;
                        uses LOCAL-ADDRESS-LEAF;
                        uses RULE-CONTENT;
                      }
                      list rule-remote-address-interface-name {
                        key "remote-address interface-name";
                        description
                          "Represents a single Traffic Protection
                           Rule, defining an exception to the
                           parent Service's default action.";
                        uses REMOTE-ADDRESS-LEAF;
                        uses INTERFACE-NAME-LEAF;
                        uses RULE-CONTENT;
                      }
                      list rule-local-address-interface-name {
                        key "local-address interface-name";
                        description
                          "Represents a single Traffic Protection
                           Rule, defining an exception to the
                           parent Service's default action.";
                        uses LOCAL-ADDRESS-LEAF;
                        uses INTERFACE-NAME-LEAF;
                        uses RULE-CONTENT;
                      }
                      list rule-remote-address-local-address-interface-name {
                        key "remote-address local-address interface-name";
                        description
                          "Represents a single Traffic Protection
                           Rule, defining an exception to the
                           parent Service's default action.";
                        uses REMOTE-ADDRESS-LEAF;
                        uses LOCAL-ADDRESS-LEAF;
                        uses INTERFACE-NAME-LEAF;
                        uses RULE-CONTENT;
                      }
                    }
                    leaf service-default-action {
                      type live_ncs_Xlnc-protection-action;
                      description
                        "Indicates the default action to be taken
                         for traffic this Traffic Protection
                         Service.";
                    }
                  }
                  list service-protocol-local-port-num {
                    key "protocol local-port-num";
                    description
                      "A single Traffic Protection Service,
                       defining a L4 protocol and local port
                       value.";
                    leaf protocol {
                      type live_ncs_L4-proto-family;
                      description
                        "L4 protocol";
                    }
                    leaf local-port-num {
                      type xr:live_ncs_Cisco-ios-xr-port-number;
                      description
                        "Local port number";
                    }
                    uses SERVICE-CONTENT;
                  }
                  list service-protocol-local-port-all {
                    key "protocol local-port-all";
                    description
                      "A single Traffic Protection Service,
                       defining a L4 protocol and local port
                       value.";
                    leaf protocol {
                      type live_ncs_L4-proto-family;
                      description
                        "L4 protocol";
                    }
                    leaf local-port-all {
                      type xr:live_ncs_Cisco-ios-xr-string;
                      description
                        "All ports";
                    }
                    uses SERVICE-CONTENT;
                  }
                }
              }
              leaf address-family {
                type live_ncs_Addr-family;
                description
                  "IP address family";
              }
            }
          }
          leaf vrf-name {
            type xr:live_ncs_Cisco-ios-xr-string;
            description
              "VRF name";
          }
        }
      }
    }
  }
  augment "/ncs:devices/ncs:template/ncs:ned-id/ncs:config" {
    container linux-networking {
      description
        "Linux Networking interface configuration";
      container exposed-interfaces {
        description
          "Configuration for exposed interfaces";
        list exposed-interface {
          // NCS patched for predictable order
          ordered-by user;
          key "interface-name";
          description
            "Configuration for a single exposed interface";
          container statistics-synchronization {
            presence "Indicates a statistics-synchronization node is configured.";
            description
              "Configure synchronization of this interface's
               statistics between IOS-XR and Linux";
            leaf direction {
              type ncs_template_Xlnc-sync-dir;
              // NCS drop mandatory statement
              description
                "Specify the direction in which statistics
                 sychronization should be performed. Currently
                 the only supported value is FromXR";
            }
            leaf interval {
              type ncs_template_Statistics-sync-interval;
              // NCS drop mandatory statement
              description
                "Interval how often statistics sychronization
                 takes place";
            }
          }
          leaf exposed-interface-sync-direction {
            type ncs_template_Xlnc-sync-dir;
            description
              "Synchronization direction for an exposed
               interface.";
          }
          leaf interface-name {
            type xr:ncs_template_Interface-name;
            description
              "Interface name";
          }
        }
      }
      container statistics-synchronization {
        presence "Indicates a statistics-synchronization node is configured.";
        description
          "Configure synchronization of interface
           statistics between IOS-XR and Linux";
        leaf direction {
          type ncs_template_Xlnc-sync-dir;
          // NCS drop mandatory statement
          description
            "Specify the direction in which statistics
             sychronization should be performed. Currently
             the only supported value is FromXR";
        }
        leaf interval {
          type ncs_template_Statistics-sync-interval;
          // NCS drop mandatory statement
          description
            "Interval how often statistics sychronization
             takes place";
        }
      }
      container vrf-names {
        description
          "Table of VRF names";
        list vrf-name {
          // NCS patched for predictable order
          ordered-by user;
          key "vrf-name";
          description
            "VRF name";
          container address-families {
            description
              "Table of address families";
            list address-family {
              // NCS patched for predictable order
              ordered-by user;
              key "address-family";
              description
                "IP address family";
              container traffic-protection {
                description
                  "Traffic Protection configuration";
                container service-protocol-local-port-nums {
                  description
                    "Container for Traffic Protection Services";

                  grouping SERVICE-CONTENT {
                    description
                      "SERVICE CONTENT";
                    container rules-table {
                      description
                        "Container for Traffic Protection Rule";

                      grouping RULE-CONTENT {
                        description
                          "RULE CONTENT";
                        leaf rule-action {
                          type ncs_template_Xlnc-protection-action;
                          // NCS drop mandatory statement
                          description
                            "rule action";
                        }
                      }

                      grouping REMOTE-ADDRESS-LEAF {
                        description
                          "REMOTE ADDRESS LEAF";
                        leaf remote-address {
                          type string;
                          description
                            "remote prefix/length";
                        }
                      }

                      grouping LOCAL-ADDRESS-LEAF {
                        description
                          "LOCAL ADDRESS LEAF";
                        leaf local-address {
                          type string;
                          description
                            "local prefix/length";
                        }
                      }

                      grouping INTERFACE-NAME-LEAF {
                        description
                          "INTERFACE NAME LEAF";
                        leaf interface-name {
                          type xr:ncs_template_Interface-name;
                          description
                            "interface name";
                        }
                      }
                      list rule-local-address {
                        // NCS patched for predictable order
                        ordered-by user;
                        key "local-address";
                        description
                          "Represents a single Traffic Protection
                           Rule, defining an exception to the
                           parent Service's default action.";
                        uses LOCAL-ADDRESS-LEAF;
                        uses RULE-CONTENT;
                      }
                      list rule-interface-name {
                        // NCS patched for predictable order
                        ordered-by user;
                        key "interface-name";
                        description
                          "Represents a single Traffic Protection
                           Rule, defining an exception to the
                           parent Service's default action.";
                        uses INTERFACE-NAME-LEAF;
                        uses RULE-CONTENT;
                      }
                      list rule-remote-address {
                        // NCS patched for predictable order
                        ordered-by user;
                        key "remote-address";
                        description
                          "Represents a single Traffic Protection
                           Rule, defining an exception to the
                           parent Service's default action.";
                        uses REMOTE-ADDRESS-LEAF;
                        uses RULE-CONTENT;
                      }
                      list rule-remote-address-local-address {
                        // NCS patched for predictable order
                        ordered-by user;
                        key "remote-address local-address";
                        description
                          "Represents a single Traffic Protection
                           Rule, defining an exception to the
                           parent Service's default action.";
                        uses REMOTE-ADDRESS-LEAF;
                        uses LOCAL-ADDRESS-LEAF;
                        uses RULE-CONTENT;
                      }
                      list rule-remote-address-interface-name {
                        // NCS patched for predictable order
                        ordered-by user;
                        key "remote-address interface-name";
                        description
                          "Represents a single Traffic Protection
                           Rule, defining an exception to the
                           parent Service's default action.";
                        uses REMOTE-ADDRESS-LEAF;
                        uses INTERFACE-NAME-LEAF;
                        uses RULE-CONTENT;
                      }
                      list rule-local-address-interface-name {
                        // NCS patched for predictable order
                        ordered-by user;
                        key "local-address interface-name";
                        description
                          "Represents a single Traffic Protection
                           Rule, defining an exception to the
                           parent Service's default action.";
                        uses LOCAL-ADDRESS-LEAF;
                        uses INTERFACE-NAME-LEAF;
                        uses RULE-CONTENT;
                      }
                      list rule-remote-address-local-address-interface-name {
                        // NCS patched for predictable order
                        ordered-by user;
                        key "remote-address local-address interface-name";
                        description
                          "Represents a single Traffic Protection
                           Rule, defining an exception to the
                           parent Service's default action.";
                        uses REMOTE-ADDRESS-LEAF;
                        uses LOCAL-ADDRESS-LEAF;
                        uses INTERFACE-NAME-LEAF;
                        uses RULE-CONTENT;
                      }
                    }
                    leaf service-default-action {
                      type ncs_template_Xlnc-protection-action;
                      description
                        "Indicates the default action to be taken
                         for traffic this Traffic Protection
                         Service.";
                    }
                  }
                  list service-protocol-local-port-num {
                    // NCS patched for predictable order
                    ordered-by user;
                    key "protocol local-port-num";
                    description
                      "A single Traffic Protection Service,
                       defining a L4 protocol and local port
                       value.";
                    leaf protocol {
                      type ncs_template_L4-proto-family;
                      description
                        "L4 protocol";
                    }
                    leaf local-port-num {
                      type xr:ncs_template_Cisco-ios-xr-port-number;
                      description
                        "Local port number";
                    }
                    uses SERVICE-CONTENT;
                  }
                  list service-protocol-local-port-all {
                    // NCS patched for predictable order
                    ordered-by user;
                    key "protocol local-port-all";
                    description
                      "A single Traffic Protection Service,
                       defining a L4 protocol and local port
                       value.";
                    leaf protocol {
                      type ncs_template_L4-proto-family;
                      description
                        "L4 protocol";
                    }
                    leaf local-port-all {
                      type xr:ncs_template_Cisco-ios-xr-string;
                      description
                        "All ports";
                    }
                    uses SERVICE-CONTENT;
                  }
                }
              }
              leaf address-family {
                type ncs_template_Addr-family;
                description
                  "IP address family";
              }
            }
          }
          leaf vrf-name {
            type xr:ncs_template_Cisco-ios-xr-string;
            description
              "VRF name";
          }
        }
      }
    }
  }
}

module Cisco-IOS-XR-cnbng-nal-act {
  // Generated by yanger -t ncs
  tailf:mount-id "cisco-iosxr-nc-7.3:cisco-iosxr-nc-7.3";
  tailf:ncs-device-type "netconf";

  namespace "http://cisco.com/ns/yang/Cisco-IOS-XR-cnbng-nal-act";
  prefix cnbng-nal-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2021 by Cisco Systems, Inc.
     All rights reserved.";

  revision 2021-02-11 {
    description
      "IOS XR 7.4.1 revision removing unused imports.";
    semver:module-version "1.1.0";
  }
  revision 2020-09-10 {
    description
      "IOS XR 7.3.1 revision.";
    semver:module-version "1.0.0";
  }

  augment "/ncs:devices/ncs:device/ncs:rpc" {
    container rpc-clear-cnbng-nal-subscriber-disconnect-history-location {
      tailf:ncs-device-type "netconf";
      tailf:display-when "not(../../ncs:module) or ../../ncs:module[ncs:name='Cisco-IOS-XR-cnbng-nal-act']";
      tailf:action clear-cnbng-nal-subscriber-disconnect-history-location {
        tailf:actionpoint ncsproxy {
          tailf:internal;
        }
        description
          "Clear cnBNG NAL subscriber disconnect-history entries for given node";
        input {
          leaf node-location {
            type string;
            mandatory true;
            description
              "Node location";
            csc:cli-name "*";
          }
        }
        csc:xr-task "cnbng_nal";
        csc:cli-command "clear cnbng-nal subscriber disconnect-history location <node-location>";
      }
    }
  }
  augment "/ncs:devices/ncs:device-group/ncs:ned-id/ncs:rpc" {
    container rpc-clear-cnbng-nal-subscriber-disconnect-history-location {
      tailf:ncs-device-type "netconf";
      tailf:display-when "/ncs:devices/ncs:device[ncs:name=current()/../../../ncs:member]/ncs:module[ncs:name='Cisco-IOS-XR-cnbng-nal-act']";
      tailf:action clear-cnbng-nal-subscriber-disconnect-history-location {
        tailf:actionpoint ncsproxy {
          tailf:internal;
        }
        description
          "Clear cnBNG NAL subscriber disconnect-history entries for given node";
        input {
          leaf node-location {
            type string;
            mandatory true;
            description
              "Node location";
            csc:cli-name "*";
          }
        }
        csc:xr-task "cnbng_nal";
        csc:cli-command "clear cnbng-nal subscriber disconnect-history location <node-location>";
      }
    }
  }
  augment "/ncs:devices/ncs:device/ncs:rpc" {
    container rpc-clear-cnbng-nal-subscriber-disconnect-history {
      tailf:ncs-device-type "netconf";
      tailf:display-when "not(../../ncs:module) or ../../ncs:module[ncs:name='Cisco-IOS-XR-cnbng-nal-act']";
      tailf:action clear-cnbng-nal-subscriber-disconnect-history {
        tailf:actionpoint ncsproxy {
          tailf:internal;
        }
        description
          "Clear cnBNG NAL subscriber disconnect-history entries";
        csc:xr-task "cnbng_nal";
        csc:cli-command "clear cnbng-nal subscriber disconnect-history";
      }
    }
  }
  augment "/ncs:devices/ncs:device-group/ncs:ned-id/ncs:rpc" {
    container rpc-clear-cnbng-nal-subscriber-disconnect-history {
      tailf:ncs-device-type "netconf";
      tailf:display-when "/ncs:devices/ncs:device[ncs:name=current()/../../../ncs:member]/ncs:module[ncs:name='Cisco-IOS-XR-cnbng-nal-act']";
      tailf:action clear-cnbng-nal-subscriber-disconnect-history {
        tailf:actionpoint ncsproxy {
          tailf:internal;
        }
        description
          "Clear cnBNG NAL subscriber disconnect-history entries";
        csc:xr-task "cnbng_nal";
        csc:cli-command "clear cnbng-nal subscriber disconnect-history";
      }
    }
  }
  augment "/ncs:devices/ncs:device/ncs:rpc" {
    container rpc-clear-cnbng-nal-dynamic-routes-history-location {
      tailf:ncs-device-type "netconf";
      tailf:display-when "not(../../ncs:module) or ../../ncs:module[ncs:name='Cisco-IOS-XR-cnbng-nal-act']";
      tailf:action clear-cnbng-nal-dynamic-routes-history-location {
        tailf:actionpoint ncsproxy {
          tailf:internal;
        }
        description
          "Clear cnBNG NAL Dynamic-routes history for given node";
        input {
          leaf node-location {
            type string;
            mandatory true;
            description
              "Node location";
            csc:cli-name "*";
          }
        }
        csc:xr-task "cnbng_nal";
        csc:cli-command "clear cnbng-nal dynamic-routes history location <node-location>";
      }
    }
  }
  augment "/ncs:devices/ncs:device-group/ncs:ned-id/ncs:rpc" {
    container rpc-clear-cnbng-nal-dynamic-routes-history-location {
      tailf:ncs-device-type "netconf";
      tailf:display-when "/ncs:devices/ncs:device[ncs:name=current()/../../../ncs:member]/ncs:module[ncs:name='Cisco-IOS-XR-cnbng-nal-act']";
      tailf:action clear-cnbng-nal-dynamic-routes-history-location {
        tailf:actionpoint ncsproxy {
          tailf:internal;
        }
        description
          "Clear cnBNG NAL Dynamic-routes history for given node";
        input {
          leaf node-location {
            type string;
            mandatory true;
            description
              "Node location";
            csc:cli-name "*";
          }
        }
        csc:xr-task "cnbng_nal";
        csc:cli-command "clear cnbng-nal dynamic-routes history location <node-location>";
      }
    }
  }
  augment "/ncs:devices/ncs:device/ncs:rpc" {
    container rpc-clear-cnbng-nal-dynamic-routes-history {
      tailf:ncs-device-type "netconf";
      tailf:display-when "not(../../ncs:module) or ../../ncs:module[ncs:name='Cisco-IOS-XR-cnbng-nal-act']";
      tailf:action clear-cnbng-nal-dynamic-routes-history {
        tailf:actionpoint ncsproxy {
          tailf:internal;
        }
        description
          "Clear cnBNG NAL Dynamic-routes history";
        csc:xr-task "cnbng_nal";
        csc:cli-command "clear cnbng-nal dynamic-routes history";
      }
    }
  }
  augment "/ncs:devices/ncs:device-group/ncs:ned-id/ncs:rpc" {
    container rpc-clear-cnbng-nal-dynamic-routes-history {
      tailf:ncs-device-type "netconf";
      tailf:display-when "/ncs:devices/ncs:device[ncs:name=current()/../../../ncs:member]/ncs:module[ncs:name='Cisco-IOS-XR-cnbng-nal-act']";
      tailf:action clear-cnbng-nal-dynamic-routes-history {
        tailf:actionpoint ncsproxy {
          tailf:internal;
        }
        description
          "Clear cnBNG NAL Dynamic-routes history";
        csc:xr-task "cnbng_nal";
        csc:cli-command "clear cnbng-nal dynamic-routes history";
      }
    }
  }
  augment "/ncs:devices/ncs:device/ncs:rpc" {
    container rpc-clear-cnbng-nal-dynamic-routes-afi-location {
      tailf:ncs-device-type "netconf";
      tailf:display-when "not(../../ncs:module) or ../../ncs:module[ncs:name='Cisco-IOS-XR-cnbng-nal-act']";
      tailf:action clear-cnbng-nal-dynamic-routes-afi-location {
        tailf:actionpoint ncsproxy {
          tailf:internal;
        }
        description
          "Execute clear cnBNG NAL Dynamic-routes AFI for the given node";
        input {
          leaf afi-type {
            type string;
            mandatory true;
            description
              "Address-family";
            csc:cli-name "*";
          }
          leaf node-location {
            type string;
            mandatory true;
            description
              "Node location";
            csc:cli-name "*";
          }
        }
        csc:xr-task "cnbng_nal";
        csc:cli-command "clear cnbng-nal dynamic-routes afi <afi-type> location <node-location>";
      }
    }
  }
  augment "/ncs:devices/ncs:device-group/ncs:ned-id/ncs:rpc" {
    container rpc-clear-cnbng-nal-dynamic-routes-afi-location {
      tailf:ncs-device-type "netconf";
      tailf:display-when "/ncs:devices/ncs:device[ncs:name=current()/../../../ncs:member]/ncs:module[ncs:name='Cisco-IOS-XR-cnbng-nal-act']";
      tailf:action clear-cnbng-nal-dynamic-routes-afi-location {
        tailf:actionpoint ncsproxy {
          tailf:internal;
        }
        description
          "Execute clear cnBNG NAL Dynamic-routes AFI for the given node";
        input {
          leaf afi-type {
            type string;
            mandatory true;
            description
              "Address-family";
            csc:cli-name "*";
          }
          leaf node-location {
            type string;
            mandatory true;
            description
              "Node location";
            csc:cli-name "*";
          }
        }
        csc:xr-task "cnbng_nal";
        csc:cli-command "clear cnbng-nal dynamic-routes afi <afi-type> location <node-location>";
      }
    }
  }
  augment "/ncs:devices/ncs:device/ncs:rpc" {
    container rpc-clear-cnbng-nal-dynamic-routes-afi {
      tailf:ncs-device-type "netconf";
      tailf:display-when "not(../../ncs:module) or ../../ncs:module[ncs:name='Cisco-IOS-XR-cnbng-nal-act']";
      tailf:action clear-cnbng-nal-dynamic-routes-afi {
        tailf:actionpoint ncsproxy {
          tailf:internal;
        }
        description
          "Execute clear cnBNG NAL Dynamic-routes AFI-type";
        input {
          leaf afi-type {
            type string;
            mandatory true;
            description
              "Address-family";
            csc:cli-name "*";
          }
        }
        csc:xr-task "cnbng_nal";
        csc:cli-command "clear cnbng-nal dynamic-routes afi <afi-type>";
      }
    }
  }
  augment "/ncs:devices/ncs:device-group/ncs:ned-id/ncs:rpc" {
    container rpc-clear-cnbng-nal-dynamic-routes-afi {
      tailf:ncs-device-type "netconf";
      tailf:display-when "/ncs:devices/ncs:device[ncs:name=current()/../../../ncs:member]/ncs:module[ncs:name='Cisco-IOS-XR-cnbng-nal-act']";
      tailf:action clear-cnbng-nal-dynamic-routes-afi {
        tailf:actionpoint ncsproxy {
          tailf:internal;
        }
        description
          "Execute clear cnBNG NAL Dynamic-routes AFI-type";
        input {
          leaf afi-type {
            type string;
            mandatory true;
            description
              "Address-family";
            csc:cli-name "*";
          }
        }
        csc:xr-task "cnbng_nal";
        csc:cli-command "clear cnbng-nal dynamic-routes afi <afi-type>";
      }
    }
  }
  augment "/ncs:devices/ncs:device/ncs:rpc" {
    container rpc-clear-cnbng-nal-cp-association-location {
      tailf:ncs-device-type "netconf";
      tailf:display-when "not(../../ncs:module) or ../../ncs:module[ncs:name='Cisco-IOS-XR-cnbng-nal-act']";
      tailf:action clear-cnbng-nal-cp-association-location {
        tailf:actionpoint ncsproxy {
          tailf:internal;
        }
        description
          "Clear cnBNG NAL CP server association for given node";
        input {
          leaf node-location {
            type string;
            mandatory true;
            description
              "Node location";
            csc:cli-name "*";
          }
        }
        csc:xr-task "cnbng_nal";
        csc:cli-command "clear cnbng-nal cp-association location <node-location>";
      }
    }
  }
  augment "/ncs:devices/ncs:device-group/ncs:ned-id/ncs:rpc" {
    container rpc-clear-cnbng-nal-cp-association-location {
      tailf:ncs-device-type "netconf";
      tailf:display-when "/ncs:devices/ncs:device[ncs:name=current()/../../../ncs:member]/ncs:module[ncs:name='Cisco-IOS-XR-cnbng-nal-act']";
      tailf:action clear-cnbng-nal-cp-association-location {
        tailf:actionpoint ncsproxy {
          tailf:internal;
        }
        description
          "Clear cnBNG NAL CP server association for given node";
        input {
          leaf node-location {
            type string;
            mandatory true;
            description
              "Node location";
            csc:cli-name "*";
          }
        }
        csc:xr-task "cnbng_nal";
        csc:cli-command "clear cnbng-nal cp-association location <node-location>";
      }
    }
  }
  augment "/ncs:devices/ncs:device/ncs:rpc" {
    container rpc-clear-cnbng-nal-cp-association {
      tailf:ncs-device-type "netconf";
      tailf:display-when "not(../../ncs:module) or ../../ncs:module[ncs:name='Cisco-IOS-XR-cnbng-nal-act']";
      tailf:action clear-cnbng-nal-cp-association {
        tailf:actionpoint ncsproxy {
          tailf:internal;
        }
        description
          "Clear cnBNG NAL CP server association";
        csc:xr-task "cnbng_nal";
        csc:cli-command "clear cnbng-nal cp-association";
      }
    }
  }
  augment "/ncs:devices/ncs:device-group/ncs:ned-id/ncs:rpc" {
    container rpc-clear-cnbng-nal-cp-association {
      tailf:ncs-device-type "netconf";
      tailf:display-when "/ncs:devices/ncs:device[ncs:name=current()/../../../ncs:member]/ncs:module[ncs:name='Cisco-IOS-XR-cnbng-nal-act']";
      tailf:action clear-cnbng-nal-cp-association {
        tailf:actionpoint ncsproxy {
          tailf:internal;
        }
        description
          "Clear cnBNG NAL CP server association";
        csc:xr-task "cnbng_nal";
        csc:cli-command "clear cnbng-nal cp-association";
      }
    }
  }
}

module Cisco-IOS-XR-fpmgr-cfg {
  // Generated by yanger -t ncs
  tailf:mount-id "cisco-iosxr-nc-7.3:cisco-iosxr-nc-7.3";
  tailf:ncs-device-type "netconf";

  namespace "http://cisco.com/ns/yang/Cisco-IOS-XR-fpmgr-cfg";
  prefix fpmgr-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fpmgr package configuration.

     This module contains definitions
     for the following management objects:
       fault-manager: Fault mgr

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Nsas {
    type string;
    description
      "Nsas";
  }

  typedef ncs_template_Sas {
    type string;
    description
      "Sas";
  }

  typedef ncs_rpc_notif_Nsas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Nsas";
  }

  typedef ncs_rpc_notif_Sas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Sas";
  }

  typedef live_ncs_Nsas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Nsas";
  }

  typedef live_ncs_Sas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Sas";
  }

  typedef Nsas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Nsas";
  }

  typedef Sas {
    type enumeration {
      enum "unknown" {
        value 0;
        description
          "Unkown severity";
      }
      enum "nonreported" {
        value 1;
        description
          "Non reported severity";
      }
      enum "nonfaulted" {
        value 2;
        description
          "Non faulted severity";
      }
      enum "minor" {
        value 3;
        description
          "Minor severity";
      }
      enum "major" {
        value 4;
        description
          "Major severity";
      }
      enum "critical" {
        value 5;
        description
          "Critical severity";
      }
    }
    description
      "Sas";
  }

  augment "/ncs:devices/ncs:device/ncs:config" {
    container fault-manager {
      tailf:ncs-device-type "netconf";
      tailf:display-when "not(../../ncs:module) or ../../ncs:module[ncs:name='Cisco-IOS-XR-fpmgr-cfg']";
      description
        "Fault mgr";
      list fault-profile {
        key "fault-profile-name";
        description
          "Fault profile name";
        container racks {
          description
            "Apply fault profile";
          list rack {
            key "rack";
            description
              "rack numnber";
            leaf rack {
              type xr:Cisco-ios-xr-string;
              description
                " ";
            }
            list slot {
              key "slot";
              description
                "None";
              container ports {
                description
                  "Configure a port";
                list port {
                  key "port";
                  description
                    "None";
                  leaf propagate {
                    type uint32;
                    description
                      "Propagate fault profile on child entities
                       of port";
                  }
                  leaf port {
                    type xr:Cisco-ios-xr-string;
                    description
                      " ";
                  }
                }
              }
              leaf propagate {
                type uint32;
                description
                  "Apply fault profile on child entities of
                   card";
              }
              leaf slot {
                type xr:Cisco-ios-xr-string;
                description
                  " ";
              }
            }
          }
        }
        container subsystems {
          description
            "Fault identifier";
          list subsystem {
            key "subsystem";
            description
              "Subsystem name";
            leaf subsystem {
              type xr:Cisco-ios-xr-string;
              description
                " ";
            }
            list fault-type {
              key "fault-type";
              description
                "Fault type name";
              leaf fault-type {
                type xr:Cisco-ios-xr-string;
                description
                  " ";
              }
              list fault-tag {
                key "fault-tag";
                description
                  "Fault tag name";
                leaf fault-tag {
                  type xr:Cisco-ios-xr-string;
                  description
                    " ";
                }
                leaf sas {
                  type Sas;
                  description
                    "Fault severity selection";
                }
                leaf nsas {
                  type Nsas;
                  description
                    "Fault severity selection";
                }
              }
            }
          }
        }
        leaf description {
          type string {
            length "1..128";
          }
          description
            "Fault profile description";
        }
        leaf enable {
          type empty;
          description
            "Enable Fault profile name. Deletion of this
             object also causes deletion of all associated
             objects under FaultProfile.";
        }
        leaf fault-profile-name {
          type xr:Cisco-ios-xr-string {
            length "1..32";
          }
          description
            "Fault profile";
        }
      }
    }
  }
  augment "/ncs:devices/ncs:device/ncs:live-status" {
    container fault-manager {
      tailf:ncs-device-type "netconf";
      tailf:display-when "not(../../ncs:module) or ../../ncs:module[ncs:name='Cisco-IOS-XR-fpmgr-cfg'] or (../../ncs:live-status-protocol[not(ncs:capability)]) or (../../ncs:live-status-protocol/ncs:capability/ncs:module[.='Cisco-IOS-XR-fpmgr-cfg'])";
      description
        "Fault mgr";
      list fault-profile {
        key "fault-profile-name";
        description
          "Fault profile name";
        container racks {
          description
            "Apply fault profile";
          list rack {
            key "rack";
            description
              "rack numnber";
            leaf rack {
              type xr:live_ncs_Cisco-ios-xr-string;
              description
                " ";
            }
            list slot {
              key "slot";
              description
                "None";
              container ports {
                description
                  "Configure a port";
                list port {
                  key "port";
                  description
                    "None";
                  leaf propagate {
                    type uint32;
                    description
                      "Propagate fault profile on child entities
                       of port";
                  }
                  leaf port {
                    type xr:live_ncs_Cisco-ios-xr-string;
                    description
                      " ";
                  }
                }
              }
              leaf propagate {
                type uint32;
                description
                  "Apply fault profile on child entities of
                   card";
              }
              leaf slot {
                type xr:live_ncs_Cisco-ios-xr-string;
                description
                  " ";
              }
            }
          }
        }
        container subsystems {
          description
            "Fault identifier";
          list subsystem {
            key "subsystem";
            description
              "Subsystem name";
            leaf subsystem {
              type xr:live_ncs_Cisco-ios-xr-string;
              description
                " ";
            }
            list fault-type {
              key "fault-type";
              description
                "Fault type name";
              leaf fault-type {
                type xr:live_ncs_Cisco-ios-xr-string;
                description
                  " ";
              }
              list fault-tag {
                key "fault-tag";
                description
                  "Fault tag name";
                leaf fault-tag {
                  type xr:live_ncs_Cisco-ios-xr-string;
                  description
                    " ";
                }
                leaf sas {
                  type live_ncs_Sas;
                  description
                    "Fault severity selection";
                }
                leaf nsas {
                  type live_ncs_Nsas;
                  description
                    "Fault severity selection";
                }
              }
            }
          }
        }
        leaf description {
          type string {
            length "1..128";
          }
          description
            "Fault profile description";
        }
        leaf enable {
          type empty;
          description
            "Enable Fault profile name. Deletion of this
             object also causes deletion of all associated
             objects under FaultProfile.";
        }
        leaf fault-profile-name {
          type xr:live_ncs_Cisco-ios-xr-string;
          description
            "Fault profile";
        }
      }
    }
  }
  augment "/ncs:devices/ncs:template/ncs:ned-id/ncs:config" {
    container fault-manager {
      description
        "Fault mgr";
      list fault-profile {
        // NCS patched for predictable order
        ordered-by user;
        key "fault-profile-name";
        description
          "Fault profile name";
        container racks {
          description
            "Apply fault profile";
          list rack {
            // NCS patched for predictable order
            ordered-by user;
            key "rack";
            description
              "rack numnber";
            leaf rack {
              type xr:ncs_template_Cisco-ios-xr-string;
              description
                " ";
            }
            list slot {
              // NCS patched for predictable order
              ordered-by user;
              key "slot";
              description
                "None";
              container ports {
                description
                  "Configure a port";
                list port {
                  // NCS patched for predictable order
                  ordered-by user;
                  key "port";
                  description
                    "None";
                  leaf propagate {
                    type string;
                    description
                      "Propagate fault profile on child entities
                       of port";
                  }
                  leaf port {
                    type xr:ncs_template_Cisco-ios-xr-string;
                    description
                      " ";
                  }
                }
              }
              leaf propagate {
                type string;
                description
                  "Apply fault profile on child entities of
                   card";
              }
              leaf slot {
                type xr:ncs_template_Cisco-ios-xr-string;
                description
                  " ";
              }
            }
          }
        }
        container subsystems {
          description
            "Fault identifier";
          list subsystem {
            // NCS patched for predictable order
            ordered-by user;
            key "subsystem";
            description
              "Subsystem name";
            leaf subsystem {
              type xr:ncs_template_Cisco-ios-xr-string;
              description
                " ";
            }
            list fault-type {
              // NCS patched for predictable order
              ordered-by user;
              key "fault-type";
              description
                "Fault type name";
              leaf fault-type {
                type xr:ncs_template_Cisco-ios-xr-string;
                description
                  " ";
              }
              list fault-tag {
                // NCS patched for predictable order
                ordered-by user;
                key "fault-tag";
                description
                  "Fault tag name";
                leaf fault-tag {
                  type xr:ncs_template_Cisco-ios-xr-string;
                  description
                    " ";
                }
                leaf sas {
                  type ncs_template_Sas;
                  description
                    "Fault severity selection";
                }
                leaf nsas {
                  type ncs_template_Nsas;
                  description
                    "Fault severity selection";
                }
              }
            }
          }
        }
        leaf description {
          type string;
          description
            "Fault profile description";
        }
        leaf enable {
          type empty;
          description
            "Enable Fault profile name. Deletion of this
             object also causes deletion of all associated
             objects under FaultProfile.";
        }
        leaf fault-profile-name {
          type xr:ncs_template_Cisco-ios-xr-string;
          description
            "Fault profile";
        }
      }
    }
  }
}

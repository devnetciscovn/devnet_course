submodule Cisco-IOS-XR-ifmgr-oper-sub2 {
  // Generated by yanger -t ncs
  tailf:mount-id "cisco-iosxr-nc-7.3:cisco-iosxr-nc-7.3";

  belongs-to Cisco-IOS-XR-ifmgr-oper {
    prefix Cisco-IOS-XR-ifmgr-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ifmgr package operational data.

     Copyright (c) 2013-2020 by Cisco Systems, Inc.
     All rights reserved.";

  revision 2020-10-01 {
    description
      "64-bit bandwidth changes";
    semver:module-version "2.0.0";
  }
  revision 2019-12-03 {
    description
      "Updated description.";
    semver:module-version "2.0.0";
  }
  revision 2019-07-23 {
    description
      "IosApi version change
       2019-05-30
       64 bit bandwidth changes.";
    semver:module-version "1.1.0";
  }
  revision 2019-04-05 {
    description
      "Establish semantic version baseline.";
    semver:module-version "1.0.0";
  }
  revision 2015-07-30 {
    description
      "IOS XR 5.3.2 revision.";
  }
  revision 2015-01-07 {
    description
      "IOS XR 5.3.1 revision.";
  }

  typedef ncs_template_Im-state-enum {
    type string;
    description
      "Im state enum";
  }

  typedef ncs_rpc_notif_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef live_ncs_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  grouping ncs_template_IM-SHOW-DAMP-NODE {
    description
      "Contains dampening information of capsulation and
       capsulation number of interface";
    container capsulation-dampening {
      description
        "Dampening information of capsulation";
      uses ncs_template_IM-SHOW-DAMP-NODE-INFO;
    }
    leaf capsulation-number {
      type string;
      description
        "Capsulation number of the Interface";
    }
  }

  grouping ncs_template_IM-SHOW-DAMP-NODE-INFO {
    description
      "Dampening information of interface ";
    leaf penalty {
      type string;
      description
        "Dampening penalty of the interface";
    }
    leaf is-suppressed-enabled {
      type string;
      description
        "Flag showing if state is suppressed";
    }
    leaf seconds-remaining {
      type string;
      units "second";
      description
        "Remaining period of suppression in secs";
    }
    leaf flaps {
      type string;
      description
        "Number of underlying state flaps";
    }
    leaf state {
      type ncs_template_Im-state-enum;
      description
        "Underlying state of the node";
    }
  }

  grouping ncs_template_IM-SHOW-DAMP-INFO {
    description
      "Dampening information of interface";
    container interface-dampening {
      description
        "Interface dampening configuration for an
         interface";
      uses ncs_template_IM-SHOW-DAMP-NODE-INFO;
    }
    leaf state-transition-count {
      type string;
      description
        "The number of times the state has changed";
    }
    leaf last-state-transition-time {
      type string;
      description
        "The absolute time of last state change of the
         interface";
    }
    leaf is-dampening-enabled {
      type string;
      description
        "Flag showing if dampening is enabled";
    }
    leaf half-life {
      type string;
      units "minute";
      description
        "Configured decay half life in mins";
    }
    leaf reuse-threshold {
      type string;
      description
        "Configured reuse threshold";
    }
    leaf suppress-threshold {
      type string;
      description
        "Value of suppress threshold";
    }
    leaf maximum-suppress-time {
      type string;
      units "minute";
      description
        "Maximum suppress time in mins";
    }
    leaf restart-penalty {
      type string;
      description
        "Configured restart penalty";
    }
    list capsulation {
      // NCS patched for predictable order
      ordered-by user;
      description
        "Dampening information for capsulations";
      uses ncs_template_IM-SHOW-DAMP-NODE;
    }
  }

  grouping ncs_rpc_notif_IM-SHOW-DAMP-NODE {
    description
      "Contains dampening information of capsulation and
       capsulation number of interface";
    container capsulation-dampening {
      description
        "Dampening information of capsulation";
      uses ncs_rpc_notif_IM-SHOW-DAMP-NODE-INFO;
    }
    leaf capsulation-number {
      type string;
      description
        "Capsulation number of the Interface";
    }
  }

  grouping ncs_rpc_notif_IM-SHOW-DAMP-NODE-INFO {
    description
      "Dampening information of interface ";
    leaf penalty {
      type uint32;
      description
        "Dampening penalty of the interface";
    }
    leaf is-suppressed-enabled {
      type boolean;
      description
        "Flag showing if state is suppressed";
    }
    leaf seconds-remaining {
      type uint32;
      units "second";
      description
        "Remaining period of suppression in secs";
    }
    leaf flaps {
      type uint32;
      description
        "Number of underlying state flaps";
    }
    leaf state {
      type ncs_rpc_notif_Im-state-enum;
      description
        "Underlying state of the node";
    }
  }

  grouping ncs_rpc_notif_IM-SHOW-DAMP-INFO {
    description
      "Dampening information of interface";
    container interface-dampening {
      description
        "Interface dampening configuration for an
         interface";
      uses ncs_rpc_notif_IM-SHOW-DAMP-NODE-INFO;
    }
    leaf state-transition-count {
      type uint32;
      description
        "The number of times the state has changed";
    }
    leaf last-state-transition-time {
      type uint64;
      description
        "The absolute time of last state change of the
         interface";
    }
    leaf is-dampening-enabled {
      type boolean;
      description
        "Flag showing if dampening is enabled";
    }
    leaf half-life {
      type uint32;
      units "minute";
      description
        "Configured decay half life in mins";
    }
    leaf reuse-threshold {
      type uint32;
      description
        "Configured reuse threshold";
    }
    leaf suppress-threshold {
      type uint32;
      description
        "Value of suppress threshold";
    }
    leaf maximum-suppress-time {
      type uint32;
      units "minute";
      description
        "Maximum suppress time in mins";
    }
    leaf restart-penalty {
      type uint32;
      description
        "Configured restart penalty";
    }
    list capsulation {
      description
        "Dampening information for capsulations";
      uses ncs_rpc_notif_IM-SHOW-DAMP-NODE;
    }
  }

  grouping live_ncs_IM-SHOW-DAMP-NODE {
    description
      "Contains dampening information of capsulation and
       capsulation number of interface";
    container capsulation-dampening {
      description
        "Dampening information of capsulation";
      uses live_ncs_IM-SHOW-DAMP-NODE-INFO;
    }
    leaf capsulation-number {
      type string;
      description
        "Capsulation number of the Interface";
    }
  }

  grouping live_ncs_IM-SHOW-DAMP-NODE-INFO {
    description
      "Dampening information of interface ";
    leaf penalty {
      type uint32;
      description
        "Dampening penalty of the interface";
    }
    leaf is-suppressed-enabled {
      type boolean;
      description
        "Flag showing if state is suppressed";
    }
    leaf seconds-remaining {
      type uint32;
      units "second";
      description
        "Remaining period of suppression in secs";
    }
    leaf flaps {
      type uint32;
      description
        "Number of underlying state flaps";
    }
    leaf state {
      type live_ncs_Im-state-enum;
      description
        "Underlying state of the node";
    }
  }

  grouping live_ncs_IM-SHOW-DAMP-INFO {
    description
      "Dampening information of interface";
    container interface-dampening {
      description
        "Interface dampening configuration for an
         interface";
      uses live_ncs_IM-SHOW-DAMP-NODE-INFO;
    }
    leaf state-transition-count {
      type uint32;
      description
        "The number of times the state has changed";
    }
    leaf last-state-transition-time {
      type uint64;
      description
        "The absolute time of last state change of the
         interface";
    }
    leaf is-dampening-enabled {
      type boolean;
      description
        "Flag showing if dampening is enabled";
    }
    leaf half-life {
      type uint32;
      units "minute";
      description
        "Configured decay half life in mins";
    }
    leaf reuse-threshold {
      type uint32;
      description
        "Configured reuse threshold";
    }
    leaf suppress-threshold {
      type uint32;
      description
        "Value of suppress threshold";
    }
    leaf maximum-suppress-time {
      type uint32;
      units "minute";
      description
        "Maximum suppress time in mins";
    }
    leaf restart-penalty {
      type uint32;
      description
        "Configured restart penalty";
    }
    list capsulation {
      description
        "Dampening information for capsulations";
      uses live_ncs_IM-SHOW-DAMP-NODE;
    }
  }

  grouping IM-SHOW-DAMP-NODE {
    description
      "Contains dampening information of capsulation and
       capsulation number of interface";
    container capsulation-dampening {
      description
        "Dampening information of capsulation";
      uses IM-SHOW-DAMP-NODE-INFO;
    }
    leaf capsulation-number {
      type string;
      description
        "Capsulation number of the Interface";
    }
  }

  grouping IM-SHOW-DAMP-NODE-INFO {
    description
      "Dampening information of interface ";
    leaf penalty {
      type uint32;
      description
        "Dampening penalty of the interface";
    }
    leaf is-suppressed-enabled {
      type boolean;
      description
        "Flag showing if state is suppressed";
    }
    leaf seconds-remaining {
      type uint32;
      units "second";
      description
        "Remaining period of suppression in secs";
    }
    leaf flaps {
      type uint32;
      description
        "Number of underlying state flaps";
    }
    leaf state {
      type Im-state-enum;
      description
        "Underlying state of the node";
    }
  }

  grouping IM-SHOW-DAMP-INFO {
    description
      "Dampening information of interface";
    container interface-dampening {
      description
        "Interface dampening configuration for an
         interface";
      uses IM-SHOW-DAMP-NODE-INFO;
    }
    leaf state-transition-count {
      type uint32;
      description
        "The number of times the state has changed";
    }
    leaf last-state-transition-time {
      type uint64;
      description
        "The absolute time of last state change of the
         interface";
    }
    leaf is-dampening-enabled {
      type boolean;
      description
        "Flag showing if dampening is enabled";
    }
    leaf half-life {
      type uint32;
      units "minute";
      description
        "Configured decay half life in mins";
    }
    leaf reuse-threshold {
      type uint32;
      description
        "Configured reuse threshold";
    }
    leaf suppress-threshold {
      type uint32;
      description
        "Value of suppress threshold";
    }
    leaf maximum-suppress-time {
      type uint32;
      units "minute";
      description
        "Maximum suppress time in mins";
    }
    leaf restart-penalty {
      type uint32;
      description
        "Configured restart penalty";
    }
    list capsulation {
      description
        "Dampening information for capsulations";
      uses IM-SHOW-DAMP-NODE;
    }
  }
}

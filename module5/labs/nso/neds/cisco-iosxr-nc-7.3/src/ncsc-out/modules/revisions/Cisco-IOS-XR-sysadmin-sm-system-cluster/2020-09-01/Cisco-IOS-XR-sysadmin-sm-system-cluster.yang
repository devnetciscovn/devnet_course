module Cisco-IOS-XR-sysadmin-sm-system-cluster {
  // Generated by yanger -t ncs
  tailf:mount-id "cisco-iosxr-nc-7.3:cisco-iosxr-nc-7.3";
  tailf:ncs-device-type "netconf";

  namespace "http://www.cisco.com/ns/yang/Cisco-IOS-XR-sysadmin-sm-system-cluster";
  prefix shelf_sm_system_cluster;

  import tailf-common {
    prefix tailf;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module holds Shelf Management System Cluster data.

     Copyright(c) 2020 by Cisco Systems, Inc.
     All rights reserved.

     Copyright (c) 2012-2020 by Cisco Systems, Inc.
     All rights reserved.";

  revision 2020-09-01 {
    description
      "Added version and cluster size oper fields";
    semver:module-version "1.0.0";
  }
  revision 2020-08-15 {
    description
      "Added support for mac-address-pool action";
  }
  revision 2020-07-07 {
    description
      "Enhanced support for oper and config";
  }
  revision 2020-06-10 {
    description
      "Initial revision of the partition from sm.yang";
  }

  typedef ncs_template_ClusterSizeType {
    type string;
    description
      "The List of supported Cluster Sizes";
  }

  typedef ncs_template_PortType {
    type string;
    description
      "The List of supported Port Types";
  }

  typedef ncs_rpc_notif_ClusterSizeType {
    type enumeration {
      enum "SMALL" {
        value 1;
        description
          "Small Cluster";
      }
      enum "MINI" {
        value 2;
        description
          "Mini Cluster";
      }
      enum "MEDIUM" {
        value 3;
        description
          "Medium Cluster";
      }
      enum "WARM_SPARE" {
        value 4;
        description
          "Warm-Spare Cluster";
      }
      enum "LARGE" {
        value 5;
        description
          "Large Cluster";
      }
    }
    description
      "The List of supported Cluster Sizes";
  }

  typedef ncs_rpc_notif_PortType {
    type enumeration {
      enum "ONIE" {
        value 1;
        description
          "ONIE port type";
      }
      enum "CE" {
        value 2;
        description
          "CE port type";
      }
      enum "INTER_DCM" {
        value 3;
        description
          "Inter-DCM port type";
      }
    }
    description
      "The List of supported Port Types";
  }

  typedef live_ncs_ClusterSizeType {
    type enumeration {
      enum "SMALL" {
        value 1;
        description
          "Small Cluster";
      }
      enum "MINI" {
        value 2;
        description
          "Mini Cluster";
      }
      enum "MEDIUM" {
        value 3;
        description
          "Medium Cluster";
      }
      enum "WARM_SPARE" {
        value 4;
        description
          "Warm-Spare Cluster";
      }
      enum "LARGE" {
        value 5;
        description
          "Large Cluster";
      }
    }
    description
      "The List of supported Cluster Sizes";
  }

  typedef live_ncs_PortType {
    type enumeration {
      enum "ONIE" {
        value 1;
        description
          "ONIE port type";
      }
      enum "CE" {
        value 2;
        description
          "CE port type";
      }
      enum "INTER_DCM" {
        value 3;
        description
          "Inter-DCM port type";
      }
    }
    description
      "The List of supported Port Types";
  }

  typedef ClusterSizeType {
    type enumeration {
      enum "SMALL" {
        value 1;
        description
          "Small Cluster";
      }
      enum "MINI" {
        value 2;
        description
          "Mini Cluster";
      }
      enum "MEDIUM" {
        value 3;
        description
          "Medium Cluster";
      }
      enum "WARM_SPARE" {
        value 4;
        description
          "Warm-Spare Cluster";
      }
      enum "LARGE" {
        value 5;
        description
          "Large Cluster";
      }
    }
    description
      "The List of supported Cluster Sizes";
  }

  typedef PortType {
    type enumeration {
      enum "ONIE" {
        value 1;
        description
          "ONIE port type";
      }
      enum "CE" {
        value 2;
        description
          "CE port type";
      }
      enum "INTER_DCM" {
        value 3;
        description
          "Inter-DCM port type";
      }
    }
    description
      "The List of supported Port Types";
  }

  grouping ncs_template_sm-cluster-config-group {
    container cluster-layout {
      // NCS dropped explicit config true
      uses ncs_template_system-cluster-layout-user-config-group;
      uses ncs_template_system-cluster-layout-rack-serial;
    }
  }

  grouping ncs_template_system-cluster-layout-user-config-group {
    list cluster-map-config {
      // NCS patched for predictable order
      ordered-by user;
      key "config-type";
      leaf config-type {
        type string;
        description
          "Cluster layout config type";
      }
      leaf version {
        type string;
      }
      leaf cluster-size {
        type ncs_template_ClusterSizeType;
      }
      list switch-rack-id {
        // NCS patched for predictable order
        ordered-by user;
        key "rack-id port-id";
        leaf rack-id {
          type string;
        }
        leaf port-id {
          type string;
        }
        leaf rack-type {
          type string;
        }
        leaf peer-rack-type {
          type string;
        }
        leaf peer-rack-id {
          type string;
        }
        leaf peer-port-id {
          type string;
        }
        leaf port-speed {
          type string;
        }
        leaf port-type {
          type ncs_template_PortType;
        }
      }
    }
  }

  grouping ncs_template_system-cluster-layout-rack-serial {
    list cluster-rack-serial-config {
      // NCS patched for predictable order
      ordered-by user;
      key "rack-num";
      leaf rack-num {
        type string;
      }
      leaf rack-serial {
        type string;
      }
    }
  }

  grouping ncs_template_system-cluster-action-group {
    uses ncs_template_system-cluster-layout-action-group;
  }

  grouping ncs_template_system-macpool-action-group {
    uses ncs_template_system-mac-address-pool-action-group;
  }

  grouping ncs_template_system-cluster-layout-action-group;

  grouping ncs_template_system-mac-address-pool-action-group;

  grouping ncs_template_system-cluster-layout-oper-group {
    // NCS drop config false container layout
  }

  grouping ncs_template_system-cluster-layout-rack-serial-oper-group {
    list rack-serial-config {
      // NCS patched for predictable order
      ordered-by user;
      key "rack-num";
      leaf rack-num {
        type string;
      }
      leaf rack-serial {
        type string;
      }
    }
  }

  grouping ncs_rpc_notif_sm-cluster-config-group {
    container cluster-layout {
      // NCS dropped explicit config true
      uses ncs_rpc_notif_system-cluster-layout-user-config-group;
      uses ncs_rpc_notif_system-cluster-layout-rack-serial;
    }
  }

  grouping ncs_rpc_notif_system-cluster-layout-user-config-group {
    list cluster-map-config {
      key "config-type";
      leaf config-type {
        type string;
        description
          "Cluster layout config type";
      }
      leaf version {
        type string;
      }
      leaf cluster-size {
        type ncs_rpc_notif_ClusterSizeType;
      }
      list switch-rack-id {
        key "rack-id port-id";
        leaf rack-id {
          type uint32;
        }
        leaf port-id {
          type string;
        }
        leaf rack-type {
          type uint32;
        }
        leaf peer-rack-type {
          type uint32;
        }
        leaf peer-rack-id {
          type uint32;
        }
        leaf peer-port-id {
          type string;
        }
        leaf port-speed {
          type uint32;
        }
        leaf port-type {
          type ncs_rpc_notif_PortType;
        }
      }
    }
  }

  grouping ncs_rpc_notif_system-cluster-layout-rack-serial {
    list cluster-rack-serial-config {
      key "rack-num";
      leaf rack-num {
        type uint32;
      }
      leaf rack-serial {
        type string;
      }
    }
  }

  grouping ncs_rpc_notif_system-cluster-action-group {
    uses ncs_rpc_notif_system-cluster-layout-action-group;
  }

  grouping ncs_rpc_notif_system-macpool-action-group {
    uses ncs_rpc_notif_system-mac-address-pool-action-group;
  }

  grouping ncs_rpc_notif_system-cluster-layout-action-group;

  grouping ncs_rpc_notif_system-mac-address-pool-action-group;

  grouping ncs_rpc_notif_system-cluster-layout-oper-group {
    container layout {
      config false;
      leaf version {
        type string;
      }
      leaf cluster-size {
        type string;
      }
      leaf compute-rack-count {
        type uint32;
      }
      leaf switch-rack-count {
        type uint32;
      }
      leaf fabric-rack-count {
        type uint32;
      }
      leaf line-rack-count {
        type uint32;
      }
      list switch-rack-id {
        key "rack-id port-id";
        leaf rack-id {
          type string;
        }
        leaf port-id {
          type string;
        }
        leaf switch-rack-type {
          type string;
        }
        leaf peer-rack-id {
          type string;
        }
        leaf peer-port-id {
          type string;
        }
        leaf peer-rack-type {
          type string;
        }
        leaf port-speed {
          type uint32;
        }
        leaf port-type {
          type string;
        }
      }
    }
  }

  grouping ncs_rpc_notif_system-cluster-layout-rack-serial-oper-group {
    list rack-serial-config {
      key "rack-num";
      leaf rack-num {
        type uint32;
      }
      leaf rack-serial {
        type string;
      }
    }
  }

  grouping live_ncs_sm-cluster-config-group {
    container cluster-layout {
      uses live_ncs_system-cluster-layout-user-config-group;
      uses live_ncs_system-cluster-layout-rack-serial;
    }
  }

  grouping live_ncs_system-cluster-layout-user-config-group {
    list cluster-map-config {
      key "config-type";
      leaf config-type {
        type string;
        description
          "Cluster layout config type";
      }
      leaf version {
        type string;
      }
      leaf cluster-size {
        type live_ncs_ClusterSizeType;
      }
      list switch-rack-id {
        key "rack-id port-id";
        leaf rack-id {
          type uint32;
        }
        leaf port-id {
          type string;
        }
        leaf rack-type {
          type uint32;
        }
        leaf peer-rack-type {
          type uint32;
        }
        leaf peer-rack-id {
          type uint32;
        }
        leaf peer-port-id {
          type string;
        }
        leaf port-speed {
          type uint32;
        }
        leaf port-type {
          type live_ncs_PortType;
        }
      }
    }
  }

  grouping live_ncs_system-cluster-layout-rack-serial {
    list cluster-rack-serial-config {
      key "rack-num";
      leaf rack-num {
        type uint32;
      }
      leaf rack-serial {
        type string;
      }
    }
  }

  grouping live_ncs_system-cluster-action-group {
    uses live_ncs_system-cluster-layout-action-group;
  }

  grouping live_ncs_system-macpool-action-group {
    uses live_ncs_system-mac-address-pool-action-group;
  }

  grouping live_ncs_system-cluster-layout-action-group;

  grouping live_ncs_system-mac-address-pool-action-group;

  grouping live_ncs_system-cluster-layout-oper-group {
    container layout {
      leaf version {
        type string;
      }
      leaf cluster-size {
        type string;
      }
      leaf compute-rack-count {
        type uint32;
      }
      leaf switch-rack-count {
        type uint32;
      }
      leaf fabric-rack-count {
        type uint32;
      }
      leaf line-rack-count {
        type uint32;
      }
      list switch-rack-id {
        key "rack-id port-id";
        leaf rack-id {
          type string;
        }
        leaf port-id {
          type string;
        }
        leaf switch-rack-type {
          type string;
        }
        leaf peer-rack-id {
          type string;
        }
        leaf peer-port-id {
          type string;
        }
        leaf peer-rack-type {
          type string;
        }
        leaf port-speed {
          type uint32;
        }
        leaf port-type {
          type string;
        }
      }
    }
  }

  grouping live_ncs_system-cluster-layout-rack-serial-oper-group {
    list rack-serial-config {
      key "rack-num";
      leaf rack-num {
        type uint32;
      }
      leaf rack-serial {
        type string;
      }
    }
  }

  grouping sm-cluster-config-group {
    container cluster-layout {
      // NCS dropped explicit config true
      uses system-cluster-layout-user-config-group;
      uses system-cluster-layout-rack-serial;
    }
  }

  grouping system-cluster-layout-user-config-group {
    list cluster-map-config {
      key "config-type";
      leaf config-type {
        type string;
        description
          "Cluster layout config type";
      }
      leaf version {
        type string;
      }
      leaf cluster-size {
        type ClusterSizeType;
      }
      list switch-rack-id {
        key "rack-id port-id";
        leaf rack-id {
          type uint32;
        }
        leaf port-id {
          type string;
        }
        leaf rack-type {
          type uint32;
        }
        leaf peer-rack-type {
          type uint32;
        }
        leaf peer-rack-id {
          type uint32;
        }
        leaf peer-port-id {
          type string;
        }
        leaf port-speed {
          type uint32;
        }
        leaf port-type {
          type PortType;
        }
      }
    }
  }

  grouping system-cluster-layout-rack-serial {
    list cluster-rack-serial-config {
      key "rack-num";
      leaf rack-num {
        type uint32;
      }
      leaf rack-serial {
        type string;
      }
    }
  }

  grouping system-cluster-action-group {
    uses system-cluster-layout-action-group;
  }

  grouping system-macpool-action-group {
    uses system-mac-address-pool-action-group;
  }

  grouping system-cluster-layout-action-group;

  grouping system-mac-address-pool-action-group;

  grouping system-cluster-layout-oper-group {
    // NCS drop config false container layout
  }

  grouping system-cluster-layout-rack-serial-oper-group {
    list rack-serial-config {
      key "rack-num";
      leaf rack-num {
        type uint32;
      }
      leaf rack-serial {
        type string;
      }
    }
  }

  augment "/ncs:devices/ncs:device/ncs:config" {
    uses sm-cluster-config-group {
      refine cluster-layout {
        tailf:ncs-device-type "netconf";
        tailf:display-when "not(../../ncs:module) or ../../ncs:module[ncs:name='Cisco-IOS-XR-sysadmin-sm-system-cluster']";
      }
    }
  }
  augment "/ncs:devices/ncs:device/ncs:live-status" {
    uses live_ncs_sm-cluster-config-group {
      refine cluster-layout {
        tailf:ncs-device-type "netconf";
        tailf:display-when "not(../../ncs:module) or ../../ncs:module[ncs:name='Cisco-IOS-XR-sysadmin-sm-system-cluster'] or (../../ncs:live-status-protocol[not(ncs:capability)]) or (../../ncs:live-status-protocol/ncs:capability/ncs:module[.='Cisco-IOS-XR-sysadmin-sm-system-cluster'])";
      }
    }
  }
  augment "/ncs:devices/ncs:template/ncs:ned-id/ncs:config" {
    uses ncs_template_sm-cluster-config-group;
  }
}

module Cisco-IOS-XR-ncs1001-ots-act {
  // Generated by yanger -t ncs
  tailf:mount-id "cisco-iosxr-nc-7.3:cisco-iosxr-nc-7.3";
  tailf:ncs-device-type "netconf";

  namespace "http://cisco.com/ns/yang/Cisco-IOS-XR-ncs1001-ots-act";
  prefix ncs1001-ots-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1001-ots-act package configuration.

     This module contains definitions
     for the following management objects:
       hardware-module-action: NCS1k1 HW module config

     Copyright (c) 2013-2020 by Cisco Systems, Inc.
     All rights reserved.";

  revision 2019-05-28 {
    description
      "added OTDR periodic scan and event triggered auto scan";
  }
  revision 2019-05-22 {
    description
      "added OTDR alarm support";
  }
  revision 2019-04-05 {
    description
      "Establish semantic version baseline.";
    semver:module-version "1.0.0";
  }
  revision 2018-03-12 {
    description
      "Added Otdr commands";
  }
  revision 2017-08-04 {
    description
      "IOS XR 6.3.1 revision.";
  }

  typedef ncs_template_Ots-psm-manual-switch {
    type string;
    description
      "Ots psm manual switch";
  }

  typedef ncs_template_Otdr-direction {
    type string;
    description
      "Otdr direction type";
  }

  typedef ncs_template_Otdr-scan-mode {
    type string;
    description
      "Otdr scan mode type";
  }

  typedef ncs_rpc_notif_Ots-psm-manual-switch {
    type enumeration {
      enum "working" {
        value 1;
        description
          "Working port";
      }
      enum "protected" {
        value 2;
        description
          "Protected port";
      }
    }
    description
      "Ots psm manual switch";
  }

  typedef ncs_rpc_notif_Otdr-direction {
    type enumeration {
      enum "tx" {
        value 0;
        description
          "Tx Direction";
      }
      enum "rx" {
        value 1;
        description
          "Rx Direction";
      }
    }
    description
      "Otdr direction type";
  }

  typedef ncs_rpc_notif_Otdr-scan-mode {
    type enumeration {
      enum "auto" {
        value 0;
        description
          "Automatic scan mode";
      }
      enum "expert" {
        value 1;
        description
          "Expert scan mode";
      }
    }
    description
      "Otdr scan mode type";
  }

  typedef live_ncs_Ots-psm-manual-switch {
    type enumeration {
      enum "working" {
        value 1;
        description
          "Working port";
      }
      enum "protected" {
        value 2;
        description
          "Protected port";
      }
    }
    description
      "Ots psm manual switch";
  }

  typedef live_ncs_Otdr-direction {
    type enumeration {
      enum "tx" {
        value 0;
        description
          "Tx Direction";
      }
      enum "rx" {
        value 1;
        description
          "Rx Direction";
      }
    }
    description
      "Otdr direction type";
  }

  typedef live_ncs_Otdr-scan-mode {
    type enumeration {
      enum "auto" {
        value 0;
        description
          "Automatic scan mode";
      }
      enum "expert" {
        value 1;
        description
          "Expert scan mode";
      }
    }
    description
      "Otdr scan mode type";
  }

  typedef Ots-psm-manual-switch {
    type enumeration {
      enum "working" {
        value 1;
        description
          "Working port";
      }
      enum "protected" {
        value 2;
        description
          "Protected port";
      }
    }
    description
      "Ots psm manual switch";
  }

  typedef Otdr-direction {
    type enumeration {
      enum "tx" {
        value 0;
        description
          "Tx Direction";
      }
      enum "rx" {
        value 1;
        description
          "Rx Direction";
      }
    }
    description
      "Otdr direction type";
  }

  typedef Otdr-scan-mode {
    type enumeration {
      enum "auto" {
        value 0;
        description
          "Automatic scan mode";
      }
      enum "expert" {
        value 1;
        description
          "Expert scan mode";
      }
    }
    description
      "Otdr scan mode type";
  }

  augment "/ncs:devices/ncs:device/ncs:rpc" {
    container rpc-otdr-save-baseline {
      tailf:ncs-device-type "netconf";
      tailf:display-when "not(../../ncs:module) or ../../ncs:module[ncs:name='Cisco-IOS-XR-ncs1001-ots-act']";
      tailf:action otdr-save-baseline {
        tailf:actionpoint ncsproxy {
          tailf:internal;
        }
        description
          "Otdr save baseline command";
        input {
          leaf slot-id {
            type uint32 {
              range "1..3";
            }
            mandatory true;
            description
              "Set Slot";
          }
          leaf baseline-id {
            type uint32;
            mandatory true;
            description
              "Set Baseline";
          }
        }
      }
    }
  }
  augment "/ncs:devices/ncs:device-group/ncs:ned-id/ncs:rpc" {
    container rpc-otdr-save-baseline {
      tailf:ncs-device-type "netconf";
      tailf:display-when "/ncs:devices/ncs:device[ncs:name=current()/../../../ncs:member]/ncs:module[ncs:name='Cisco-IOS-XR-ncs1001-ots-act']";
      tailf:action otdr-save-baseline {
        tailf:actionpoint ncsproxy {
          tailf:internal;
        }
        description
          "Otdr save baseline command";
        input {
          leaf slot-id {
            type uint32 {
              range "1..3";
            }
            mandatory true;
            description
              "Set Slot";
          }
          leaf baseline-id {
            type uint32;
            mandatory true;
            description
              "Set Baseline";
          }
        }
      }
    }
  }
  augment "/ncs:devices/ncs:device/ncs:rpc" {
    container rpc-otdr-scan-abort {
      tailf:ncs-device-type "netconf";
      tailf:display-when "not(../../ncs:module) or ../../ncs:module[ncs:name='Cisco-IOS-XR-ncs1001-ots-act']";
      tailf:action otdr-scan-abort {
        tailf:actionpoint ncsproxy {
          tailf:internal;
        }
        description
          "Otdr scan abort command";
        input {
          leaf slot-id {
            type uint32 {
              range "1..3";
            }
            mandatory true;
            description
              "Set Slot";
          }
          leaf port-id {
            type uint32 {
              range "1..2";
            }
            mandatory true;
            description
              "Set Port";
          }
        }
      }
    }
  }
  augment "/ncs:devices/ncs:device-group/ncs:ned-id/ncs:rpc" {
    container rpc-otdr-scan-abort {
      tailf:ncs-device-type "netconf";
      tailf:display-when "/ncs:devices/ncs:device[ncs:name=current()/../../../ncs:member]/ncs:module[ncs:name='Cisco-IOS-XR-ncs1001-ots-act']";
      tailf:action otdr-scan-abort {
        tailf:actionpoint ncsproxy {
          tailf:internal;
        }
        description
          "Otdr scan abort command";
        input {
          leaf slot-id {
            type uint32 {
              range "1..3";
            }
            mandatory true;
            description
              "Set Slot";
          }
          leaf port-id {
            type uint32 {
              range "1..2";
            }
            mandatory true;
            description
              "Set Port";
          }
        }
      }
    }
  }
  augment "/ncs:devices/ncs:device/ncs:rpc" {
    container rpc-otdr-scan {
      tailf:ncs-device-type "netconf";
      tailf:display-when "not(../../ncs:module) or ../../ncs:module[ncs:name='Cisco-IOS-XR-ncs1001-ots-act']";
      tailf:action otdr-scan {
        tailf:actionpoint ncsproxy {
          tailf:internal;
        }
        description
          "Otdr scan commands";
        input {
          leaf slot-id {
            type uint32 {
              range "1..3";
            }
            mandatory true;
            description
              "Set Slot";
          }
          leaf port-id {
            type uint32 {
              range "1..2";
            }
            mandatory true;
            description
              "Set Port";
          }
          leaf direction {
            type ncs_rpc_notif_Otdr-direction;
            mandatory true;
            description
              "Set Direction";
          }
          leaf scan-mode {
            type ncs_rpc_notif_Otdr-scan-mode;
            mandatory true;
            description
              "Otdr scan mode";
          }
        }
      }
    }
  }
  augment "/ncs:devices/ncs:device-group/ncs:ned-id/ncs:rpc" {
    container rpc-otdr-scan {
      tailf:ncs-device-type "netconf";
      tailf:display-when "/ncs:devices/ncs:device[ncs:name=current()/../../../ncs:member]/ncs:module[ncs:name='Cisco-IOS-XR-ncs1001-ots-act']";
      tailf:action otdr-scan {
        tailf:actionpoint ncsproxy {
          tailf:internal;
        }
        description
          "Otdr scan commands";
        input {
          leaf slot-id {
            type uint32 {
              range "1..3";
            }
            mandatory true;
            description
              "Set Slot";
          }
          leaf port-id {
            type uint32 {
              range "1..2";
            }
            mandatory true;
            description
              "Set Port";
          }
          leaf direction {
            type ncs_rpc_notif_Otdr-direction;
            mandatory true;
            description
              "Set Direction";
          }
          leaf scan-mode {
            type ncs_rpc_notif_Otdr-scan-mode;
            mandatory true;
            description
              "Otdr scan mode";
          }
        }
      }
    }
  }
  augment "/ncs:devices/ncs:device/ncs:rpc" {
    container rpc-psm-manual-switch-to {
      tailf:ncs-device-type "netconf";
      tailf:display-when "not(../../ncs:module) or ../../ncs:module[ncs:name='Cisco-IOS-XR-ncs1001-ots-act']";
      tailf:action psm-manual-switch-to {
        tailf:actionpoint ncsproxy {
          tailf:internal;
        }
        description
          "Psm manual switch to port";
        input {
          leaf slot-id {
            type uint32 {
              range "1..3";
            }
            mandatory true;
            description
              "Set Slot";
          }
          leaf manual-switch-to {
            type ncs_rpc_notif_Ots-psm-manual-switch;
            mandatory true;
            description
              "Switch active path to selected port";
          }
        }
      }
    }
  }
  augment "/ncs:devices/ncs:device-group/ncs:ned-id/ncs:rpc" {
    container rpc-psm-manual-switch-to {
      tailf:ncs-device-type "netconf";
      tailf:display-when "/ncs:devices/ncs:device[ncs:name=current()/../../../ncs:member]/ncs:module[ncs:name='Cisco-IOS-XR-ncs1001-ots-act']";
      tailf:action psm-manual-switch-to {
        tailf:actionpoint ncsproxy {
          tailf:internal;
        }
        description
          "Psm manual switch to port";
        input {
          leaf slot-id {
            type uint32 {
              range "1..3";
            }
            mandatory true;
            description
              "Set Slot";
          }
          leaf manual-switch-to {
            type ncs_rpc_notif_Ots-psm-manual-switch;
            mandatory true;
            description
              "Switch active path to selected port";
          }
        }
      }
    }
  }
}

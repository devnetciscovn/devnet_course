module Cisco-IOS-XR-crypto-macsec-pl-oper {
  // Generated by yanger -t ncs
  tailf:mount-id "cisco-iosxr-nc-7.3:cisco-iosxr-nc-7.3";
  tailf:ncs-device-type "netconf";

  namespace "http://cisco.com/ns/yang/Cisco-IOS-XR-crypto-macsec-pl-oper";
  prefix crypto-macsec-pl-oper;

  import Cisco-IOS-XR-types {
    prefix xr;
  }
  import cisco-semver {
    prefix semver;
  }
  include Cisco-IOS-XR-crypto-macsec-pl-oper-sub1 {
    revision-date 2020-11-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-macsec-pl package operational data.

     This module contains definitions
     for the following management objects:
       macsec-platform: MACSec operational data

     Copyright (c) 2013-2020 by Cisco Systems, Inc.
     All rights reserved.";

  revision 2020-11-05 {
    description
      "Revison Update doe macsec pl oper";
    semver:module-version "2.0.0";
  }
  revision 2019-12-05 {
    description
      "Revison Update doe macsec pl oper";
    semver:module-version "1.2.0";
  }
  revision 2019-04-05 {
    description
      "Establish semantic version baseline.";
    semver:module-version "1.1.0";
  }
  revision 2015-11-09 {
    description
      "IOS XR 6.0 revision.";
  }

  augment "/ncs:devices/ncs:device/ncs:config" {
    // NCS drop config false container 'macsec-platform'
  }
  augment "/ncs:devices/ncs:device/ncs:live-status" {
    container macsec-platform {
      tailf:ncs-device-type "netconf";
      tailf:display-when "not(../../ncs:module) or ../../ncs:module[ncs:name='Cisco-IOS-XR-crypto-macsec-pl-oper'] or (../../ncs:live-status-protocol[not(ncs:capability)]) or (../../ncs:live-status-protocol/ncs:capability/ncs:module[.='Cisco-IOS-XR-crypto-macsec-pl-oper'])";
      description
        "MACSec operational data";
      container nodes {
        description
          "NodeTable for all the nodes";
        list node {
          key "node-name";
          description
            "Node where macsec interfaces exist";
          container interfaces {
            description
              "Table of Interfaces";
            list interface {
              key "name";
              description
                "Interface Where Macsec is configured";
              container hw-statistics {
                description
                  "The Hardware Statistics";
                uses live_ncs_PL-MACSEC-STATS;
              }
              container hw-sas {
                description
                  "Table of Hardware SAs";
                list hw-sa {
                  key "sa-id";
                  description
                    "Hardware Security Association";
                  leaf sa-id {
                    type uint32;
                    description
                      "SA ID";
                  }
                  uses live_ncs_PL-MACSEC-SA;
                }
              }
              container hw-flow-s {
                description
                  "Table of Hardware Flows";
                list hw-flow {
                  key "flow-id";
                  description
                    "Hardware Flow";
                  leaf flow-id {
                    type uint32;
                    description
                      "FLOW ID";
                  }
                  uses live_ncs_PL-MACSEC-FLOW;
                }
              }
              container sw-statistics {
                description
                  "The Software Statistics";
                uses live_ncs_PL-MACSEC-STATS;
              }
              leaf name {
                type xr:live_ncs_Interface-name;
                description
                  "Value";
              }
            }
          }
          leaf node-name {
            type xr:live_ncs_Node-id;
            description
              "Node";
          }
        }
      }
    }
  }
  augment "/ncs:devices/ncs:template/ncs:ned-id/ncs:config" {
    // NCS drop config false container 'macsec-platform'
  }
}

module Cisco-IOS-XR-hwmod-mpa-reload-act {
  // Generated by yanger -t ncs
  tailf:mount-id "cisco-iosxr-nc-7.3:cisco-iosxr-nc-7.3";
  tailf:ncs-device-type "netconf";

  namespace "http://cisco.com/ns/yang/Cisco-IOS-XR-hwmod-mpa-reload-act";
  prefix hwmod-mpa-reload-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR MPA reload action package configuration.

     Copyright (c) 2016-2019 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2016-06-30 {
    description
      "IOS XR 6.2.1 revision.";
  }

  augment "/ncs:devices/ncs:device/ncs:rpc" {
    container rpc-hw-module-subslot {
      tailf:ncs-device-type "netconf";
      tailf:display-when "not(../../ncs:module) or ../../ncs:module[ncs:name='Cisco-IOS-XR-hwmod-mpa-reload-act']";
      tailf:action hw-module-subslot {
        tailf:actionpoint ncsproxy {
          tailf:internal;
        }
        description
          "Execute subslot h/w module operations";
        input {
          leaf subslot {
            type string;
            description
              "Fully qualified location specification";
          }
          leaf reload {
            type empty;
            description
              "Cycle subslot h/w reset";
          }
        }
      }
    }
  }
  augment "/ncs:devices/ncs:device-group/ncs:ned-id/ncs:rpc" {
    container rpc-hw-module-subslot {
      tailf:ncs-device-type "netconf";
      tailf:display-when "/ncs:devices/ncs:device[ncs:name=current()/../../../ncs:member]/ncs:module[ncs:name='Cisco-IOS-XR-hwmod-mpa-reload-act']";
      tailf:action hw-module-subslot {
        tailf:actionpoint ncsproxy {
          tailf:internal;
        }
        description
          "Execute subslot h/w module operations";
        input {
          leaf subslot {
            type string;
            description
              "Fully qualified location specification";
          }
          leaf reload {
            type empty;
            description
              "Cycle subslot h/w reset";
          }
        }
      }
    }
  }
}

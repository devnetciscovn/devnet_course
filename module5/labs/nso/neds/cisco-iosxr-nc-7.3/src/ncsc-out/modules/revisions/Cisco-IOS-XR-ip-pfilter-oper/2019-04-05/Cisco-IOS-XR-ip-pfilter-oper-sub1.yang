submodule Cisco-IOS-XR-ip-pfilter-oper-sub1 {
  // Generated by yanger -t ncs
  tailf:mount-id "cisco-iosxr-nc-7.3:cisco-iosxr-nc-7.3";

  belongs-to Cisco-IOS-XR-ip-pfilter-oper {
    prefix Cisco-IOS-XR-ip-pfilter-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-pfilter package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_PFILTER-INTF-ACL-INFO {
    description
      "Pfilter interface ACL details";
    leaf acl-info {
      type string;
      description
        "acl information";
    }
  }

  grouping ncs_rpc_notif_PFILTER-INTF-ACL-INFO {
    description
      "Pfilter interface ACL details";
    leaf acl-info {
      type string;
      description
        "acl information";
    }
  }

  grouping live_ncs_PFILTER-INTF-ACL-INFO {
    description
      "Pfilter interface ACL details";
    leaf acl-info {
      type string;
      description
        "acl information";
    }
  }

  grouping PFILTER-INTF-ACL-INFO {
    description
      "Pfilter interface ACL details";
    leaf acl-info {
      type string;
      description
        "acl information";
    }
  }
}

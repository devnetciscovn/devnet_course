module Cisco-IOS-XR-pbr-vservice-mgr-oper {
  // Generated by yanger -t ncs
  tailf:mount-id "cisco-iosxr-nc-7.3:cisco-iosxr-nc-7.3";
  tailf:ncs-device-type "netconf";

  namespace "http://cisco.com/ns/yang/Cisco-IOS-XR-pbr-vservice-mgr-oper";
  prefix pbr-vservice-mgr-oper;

  import Cisco-IOS-XR-types {
    prefix xr;
  }
  import cisco-semver {
    prefix semver;
  }
  import Cisco-IOS-XR-pbr-datatypes {
    prefix dt1;
  }
  include Cisco-IOS-XR-pbr-vservice-mgr-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr-vservice-mgr package operational data.

     This module contains definitions
     for the following management objects:
       global-service-function-chaining: NSH Service Function
         Chaining global operational data

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-11-09 {
    description
      "IOS XR 6.0 revision.";
  }

  augment "/ncs:devices/ncs:device/ncs:config" {
    // NCS drop config false container 'global-service-function-chaining'
  }
  augment "/ncs:devices/ncs:device/ncs:live-status" {
    container global-service-function-chaining {
      tailf:ncs-device-type "netconf";
      tailf:display-when "not(../../ncs:module) or ../../ncs:module[ncs:name='Cisco-IOS-XR-pbr-vservice-mgr-oper'] or (../../ncs:live-status-protocol[not(ncs:capability)]) or (../../ncs:live-status-protocol/ncs:capability/ncs:module[.='Cisco-IOS-XR-pbr-vservice-mgr-oper'])";
      description
        "NSH Service Function Chaining global operational
         data";
      container service-function-path {
        description
          "Service Function Path operational data";
        container path-ids {
          description
            "Service Function Path Id ";
          list path-id {
            key "id";
            description
              "Specific Service-Function-Path identifier ";
            container stats {
              description
                "SFP Statistics";
              container detail {
                description
                  "Detail statistics per service index ";
                uses live_ncs_VSERVICE-EDM-NSH-STATS-INFO;
              }
              container summarized {
                description
                  "Combined statistics of all service index in
                   service functionpath";
                uses live_ncs_VSERVICE-EDM-NSH-STATS-INFO;
              }
            }
            container service-indexes {
              description
                "Service Index Belonging to Path";
              list service-index {
                key "index";
                description
                  "Service index operational data belonging to
                   this path";
                leaf index {
                  type dt1:live_ncs_Vservice-nsh-service-index-range;
                  description
                    "Service Index";
                }
                uses live_ncs_VSERVICE-EDM-NSH-STATS-INFO;
              }
            }
            leaf id {
              type dt1:live_ncs_Vservice-nsh-path-id-range;
              description
                "Specific Service-Function-Path identifier";
            }
          }
        }
      }
      container service-function {
        description
          "Service Function operational data";
        container sf-names {
          description
            "List of Service Function Names";
          list sf-name {
            key "name";
            description
              "Name of Service Function";
            leaf name {
              type xr:live_ncs_Cisco-ios-xr-string;
              description
                "Name";
            }
            uses live_ncs_VSERVICE-EDM-NSH-STATS-INFO;
          }
        }
      }
      container service-function-forwarder {
        description
          "Service Function Forwarder operational data";
        container sff-names {
          description
            "List of Service Function Forwarder Names";
          list sff-name {
            key "name";
            description
              "Name of Service Function Forwarder";
            leaf name {
              type xr:live_ncs_Cisco-ios-xr-string;
              description
                "Name";
            }
            uses live_ncs_VSERVICE-EDM-NSH-STATS-INFO;
          }
        }
        container local {
          description
            "Local Service Function Forwarder operational
             data";
          container error {
            description
              "Error Statistics for local service function
               forwarder";
            uses live_ncs_VSERVICE-EDM-NSH-STATS-INFO;
          }
        }
      }
    }
  }
  augment "/ncs:devices/ncs:template/ncs:ned-id/ncs:config" {
    // NCS drop config false container 'global-service-function-chaining'
  }
}

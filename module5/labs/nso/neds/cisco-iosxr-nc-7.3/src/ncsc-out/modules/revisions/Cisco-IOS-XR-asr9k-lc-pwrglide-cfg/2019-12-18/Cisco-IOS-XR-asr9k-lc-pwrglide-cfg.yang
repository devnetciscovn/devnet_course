module Cisco-IOS-XR-asr9k-lc-pwrglide-cfg {
  // Generated by yanger -t ncs
  tailf:mount-id "cisco-iosxr-nc-7.3:cisco-iosxr-nc-7.3";
  tailf:ncs-device-type "netconf";

  namespace "http://cisco.com/ns/yang/Cisco-IOS-XR-asr9k-lc-pwrglide-cfg";
  prefix asr9k-lc-pwrglide-cfg;

  import cisco-semver {
    prefix semver;
  }
  import Cisco-IOS-XR-config-mda-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-lc-pwrglide package configuration.

     This YANG module augments the
       Cisco-IOS-XR-config-mda-cfg
     module with configuration data.

     Copyright (c) 2013-2019 by Cisco Systems, Inc.
     All rights reserved.";

  revision 2019-12-18 {
    description
      "Added/modified to support port mode config through yang model.";
    semver:module-version "1.0.0";
  }
  revision 2019-04-05 {
    description
      "Establish semantic version baseline.";
  }
  revision 2015-11-09 {
    description
      "IOS XR 6.0 revision.";
  }

  grouping ncs_template_HARDWARE-MODULE-PORT-MODE {
    description
      "Common node of active-node, preconfigured-node";
    container hardware-module-port-mode {
      description
        "HW module port-mode config";
      leaf if-port-mode {
        type string;
        description
          "Linecard interface port-mode";
      }
    }
  }

  grouping ncs_rpc_notif_HARDWARE-MODULE-PORT-MODE {
    description
      "Common node of active-node, preconfigured-node";
    container hardware-module-port-mode {
      description
        "HW module port-mode config";
      leaf if-port-mode {
        type string;
        description
          "Linecard interface port-mode";
      }
    }
  }

  grouping live_ncs_HARDWARE-MODULE-PORT-MODE {
    description
      "Common node of active-node, preconfigured-node";
    container hardware-module-port-mode {
      description
        "HW module port-mode config";
      leaf if-port-mode {
        type string;
        description
          "Linecard interface port-mode";
      }
    }
  }

  grouping HARDWARE-MODULE-PORT-MODE {
    description
      "Common node of active-node, preconfigured-node";
    container hardware-module-port-mode {
      description
        "HW module port-mode config";
      leaf if-port-mode {
        type string;
        description
          "Linecard interface port-mode";
      }
    }
  }

  augment "/ncs:devices/ncs:template/ncs:ned-id/ncs:config/a1:preconfigured-nodes/a1:preconfigured-node" {
    description
      "This augment extends the configuration data of
       'Cisco-IOS-XR-config-mda-cfg'";
    uses ncs_template_HARDWARE-MODULE-PORT-MODE;
  }
  augment "/ncs:devices/ncs:device/ncs:live-status/a1:preconfigured-nodes/a1:preconfigured-node" {
    description
      "This augment extends the configuration data of
       'Cisco-IOS-XR-config-mda-cfg'";
    uses live_ncs_HARDWARE-MODULE-PORT-MODE {
      refine hardware-module-port-mode {
        tailf:ncs-device-type "netconf";
        tailf:display-when "not(../../../../ncs:module) or ../../../../ncs:module[ncs:name='Cisco-IOS-XR-asr9k-lc-pwrglide-cfg'] or (../../../../ncs:live-status-protocol[not(ncs:capability)]) or (../../../../ncs:live-status-protocol/ncs:capability/ncs:module[.='Cisco-IOS-XR-asr9k-lc-pwrglide-cfg'])";
      }
    }
  }
  augment "/ncs:devices/ncs:device/ncs:config/a1:preconfigured-nodes/a1:preconfigured-node" {
    description
      "This augment extends the configuration data of
       'Cisco-IOS-XR-config-mda-cfg'";
    uses HARDWARE-MODULE-PORT-MODE {
      refine hardware-module-port-mode {
        tailf:ncs-device-type "netconf";
        tailf:display-when "not(../../../../ncs:module) or ../../../../ncs:module[ncs:name='Cisco-IOS-XR-asr9k-lc-pwrglide-cfg']";
      }
    }
  }
  augment "/ncs:devices/ncs:template/ncs:ned-id/ncs:config/a1:active-nodes/a1:active-node" {
    description
      "This augment extends the configuration data of
       'Cisco-IOS-XR-config-mda-cfg'";
    uses ncs_template_HARDWARE-MODULE-PORT-MODE;
  }
  augment "/ncs:devices/ncs:device/ncs:live-status/a1:active-nodes/a1:active-node" {
    description
      "This augment extends the configuration data of
       'Cisco-IOS-XR-config-mda-cfg'";
    uses live_ncs_HARDWARE-MODULE-PORT-MODE {
      refine hardware-module-port-mode {
        tailf:ncs-device-type "netconf";
        tailf:display-when "not(../../../../ncs:module) or ../../../../ncs:module[ncs:name='Cisco-IOS-XR-asr9k-lc-pwrglide-cfg'] or (../../../../ncs:live-status-protocol[not(ncs:capability)]) or (../../../../ncs:live-status-protocol/ncs:capability/ncs:module[.='Cisco-IOS-XR-asr9k-lc-pwrglide-cfg'])";
      }
    }
  }
  augment "/ncs:devices/ncs:device/ncs:config/a1:active-nodes/a1:active-node" {
    description
      "This augment extends the configuration data of
       'Cisco-IOS-XR-config-mda-cfg'";
    uses HARDWARE-MODULE-PORT-MODE {
      refine hardware-module-port-mode {
        tailf:ncs-device-type "netconf";
        tailf:display-when "not(../../../../ncs:module) or ../../../../ncs:module[ncs:name='Cisco-IOS-XR-asr9k-lc-pwrglide-cfg']";
      }
    }
  }
}

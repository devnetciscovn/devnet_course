module Cisco-IOS-XR-ipv6-smiap-cfg {
  // Generated by yanger -t ncs
  tailf:mount-id "cisco-iosxr-nc-7.3:cisco-iosxr-nc-7.3";
  tailf:ncs-device-type "netconf";

  namespace "http://cisco.com/ns/yang/Cisco-IOS-XR-ipv6-smiap-cfg";
  prefix ipv6-smiap-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv6-smiap package configuration.

     This module contains definitions
     for the following management objects:
       ipv6-virtual: IPv6 virtual address for management interfaces

     Copyright (c) 2013-2019 by Cisco Systems, Inc.
     All rights reserved.";

  revision 2019-04-05 {
    description
      "Establish semantic version baseline.";
    semver:module-version "1.0.1";
  }
  revision 2016-07-04 {
    description
      "this schema file has all the latest changes.";
  }
  revision 2015-11-09 {
    description
      "IOS XR 6.0 revision.";
  }

  augment "/ncs:devices/ncs:device/ncs:config" {
    container ipv6-virtual {
      tailf:ncs-device-type "netconf";
      tailf:display-when "not(../../ncs:module) or ../../ncs:module[ncs:name='Cisco-IOS-XR-ipv6-smiap-cfg']";
      description
        "IPv6 virtual address for management interfaces";
      container vrfs {
        description
          "VRFs for the virtual IPv6 addresses";
        list vrf {
          key "vrf-name";
          description
            "A VRF for a virtual IPv6 address.  Specify
             'default' for VRF default";
          container address {
            presence "Indicates a address node is configured.";
            description
              "IPv6 address and mask";
            leaf address {
              type inet:ipv6-address-no-zone;
              mandatory true;
              description
                "IPv6 address";
            }
            leaf prefix-length {
              type xr:Ipv6-prefix-length;
              mandatory true;
              description
                "IPv6 address prefix length";
            }
          }
          leaf vrf-name {
            type xr:Cisco-ios-xr-string;
            description
              "Name of VRF";
          }
        }
      }
      leaf use-as-source-address {
        type empty;
        description
          "Enable use as default source address on sourced
           packets";
      }
    }
  }
  augment "/ncs:devices/ncs:device/ncs:live-status" {
    container ipv6-virtual {
      tailf:ncs-device-type "netconf";
      tailf:display-when "not(../../ncs:module) or ../../ncs:module[ncs:name='Cisco-IOS-XR-ipv6-smiap-cfg'] or (../../ncs:live-status-protocol[not(ncs:capability)]) or (../../ncs:live-status-protocol/ncs:capability/ncs:module[.='Cisco-IOS-XR-ipv6-smiap-cfg'])";
      description
        "IPv6 virtual address for management interfaces";
      container vrfs {
        description
          "VRFs for the virtual IPv6 addresses";
        list vrf {
          key "vrf-name";
          description
            "A VRF for a virtual IPv6 address.  Specify
             'default' for VRF default";
          container address {
            presence "Indicates a address node is configured.";
            description
              "IPv6 address and mask";
            leaf address {
              type inet:ipv6-address-no-zone;
              // NCS drop mandatory statement
              description
                "IPv6 address";
            }
            leaf prefix-length {
              type xr:live_ncs_Ipv6-prefix-length;
              // NCS drop mandatory statement
              description
                "IPv6 address prefix length";
            }
          }
          leaf vrf-name {
            type xr:live_ncs_Cisco-ios-xr-string;
            description
              "Name of VRF";
          }
        }
      }
      leaf use-as-source-address {
        type empty;
        description
          "Enable use as default source address on sourced
           packets";
      }
    }
  }
  augment "/ncs:devices/ncs:template/ncs:ned-id/ncs:config" {
    container ipv6-virtual {
      description
        "IPv6 virtual address for management interfaces";
      container vrfs {
        description
          "VRFs for the virtual IPv6 addresses";
        list vrf {
          // NCS patched for predictable order
          ordered-by user;
          key "vrf-name";
          description
            "A VRF for a virtual IPv6 address.  Specify
             'default' for VRF default";
          container address {
            presence "Indicates a address node is configured.";
            description
              "IPv6 address and mask";
            leaf address {
              type string;
              // NCS drop mandatory statement
              description
                "IPv6 address";
            }
            leaf prefix-length {
              type xr:ncs_template_Ipv6-prefix-length;
              // NCS drop mandatory statement
              description
                "IPv6 address prefix length";
            }
          }
          leaf vrf-name {
            type xr:ncs_template_Cisco-ios-xr-string;
            description
              "Name of VRF";
          }
        }
      }
      leaf use-as-source-address {
        type empty;
        description
          "Enable use as default source address on sourced
           packets";
      }
    }
  }
}

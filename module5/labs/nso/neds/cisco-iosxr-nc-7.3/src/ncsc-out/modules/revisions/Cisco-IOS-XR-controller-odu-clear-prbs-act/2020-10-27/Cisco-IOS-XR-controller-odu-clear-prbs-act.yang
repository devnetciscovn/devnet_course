module Cisco-IOS-XR-controller-odu-clear-prbs-act {
  // Generated by yanger -t ncs
  tailf:mount-id "cisco-iosxr-nc-7.3:cisco-iosxr-nc-7.3";
  tailf:ncs-device-type "netconf";

  namespace "http://cisco.com/ns/yang/Cisco-IOS-XR-controller-odu-clear-prbs-act";
  prefix controller-odu-clear-prbs-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR clear prbs bit-errrs statistics for controller-odu module.

     Copyright (c) 2018-2020 by Cisco Systems, Inc.
     All rights reserved.";

  revision 2020-10-27 {
    description
      "Clear prbs bit-errors support for odu controllers";
    semver:module-version "1.0.0";
  }

  augment "/ncs:devices/ncs:device/ncs:rpc" {
    container rpc-clear-controller-prbsdetails {
      tailf:ncs-device-type "netconf";
      tailf:display-when "not(../../ncs:module) or ../../ncs:module[ncs:name='Cisco-IOS-XR-controller-odu-clear-prbs-act']";
      tailf:action clear-controller-prbsdetails {
        tailf:actionpoint ncsproxy {
          tailf:internal;
        }
        description
          "Clear prbs bit-errors statistics";
        input {
          leaf controller {
            type string;
            description
              "Controller name in R/S/I/P format";
          }
          leaf prbsdetails {
            type empty;
            description
              "clear prbs bit-errors counter";
          }
        }
      }
    }
  }
  augment "/ncs:devices/ncs:device-group/ncs:ned-id/ncs:rpc" {
    container rpc-clear-controller-prbsdetails {
      tailf:ncs-device-type "netconf";
      tailf:display-when "/ncs:devices/ncs:device[ncs:name=current()/../../../ncs:member]/ncs:module[ncs:name='Cisco-IOS-XR-controller-odu-clear-prbs-act']";
      tailf:action clear-controller-prbsdetails {
        tailf:actionpoint ncsproxy {
          tailf:internal;
        }
        description
          "Clear prbs bit-errors statistics";
        input {
          leaf controller {
            type string;
            description
              "Controller name in R/S/I/P format";
          }
          leaf prbsdetails {
            type empty;
            description
              "clear prbs bit-errors counter";
          }
        }
      }
    }
  }
}

module Cisco-IOS-XR-ethernet-sat-act {
  // Generated by yanger -t ncs
  tailf:mount-id "cisco-iosxr-nc-7.3:cisco-iosxr-nc-7.3";
  tailf:ncs-device-type "netconf";

  namespace "http://cisco.com/ns/yang/Cisco-IOS-XR-ethernet-sat-act";
  prefix ethernet-sat-act;

  import Cisco-IOS-XR-types {
    prefix xr;
  }
  import Cisco-IOS-XR-ethernet-sat-datatypes {
    prefix dt1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet service activation test actions.

     Copyright (c) 2013-2018 by Cisco Systems, Inc.
     All rights reserved.";

  revision 2018-07-10 {
    description
      "IOS XR 7.1.1 revision.";
  }

  typedef ncs_template_sat-mac-address-type {
    type string;
    description
      "MAC address";
  }

  typedef ncs_rpc_notif_sat-mac-address-type {
    type string {
      pattern '[0-9a-fA-F]{4}(\.[0-9a-fA-F]{4}){2}';
    }
    description
      "MAC address";
  }

  typedef live_ncs_sat-mac-address-type {
    type string {
      pattern '[0-9a-fA-F]{4}(\.[0-9a-fA-F]{4}){2}';
    }
    description
      "MAC address";
  }

  typedef sat-mac-address-type {
    type string {
      pattern '[0-9a-fA-F]{4}(\.[0-9a-fA-F]{4}){2}';
    }
    description
      "MAC address";
  }

  augment "/ncs:devices/ncs:device/ncs:rpc" {
    container rpc-service-activation-test-clear-all {
      tailf:ncs-device-type "netconf";
      tailf:display-when "not(../../ncs:module) or ../../ncs:module[ncs:name='Cisco-IOS-XR-ethernet-sat-act']";
      tailf:action service-activation-test-clear-all {
        tailf:actionpoint ncsproxy {
          tailf:internal;
        }
        description
          "Clear stored SAT results on all interfaces";
        xr:xr-task "ethernet-services";
        xr:cli-command "clear ethernet service-activation-test results all";
      }
    }
  }
  augment "/ncs:devices/ncs:device-group/ncs:ned-id/ncs:rpc" {
    container rpc-service-activation-test-clear-all {
      tailf:ncs-device-type "netconf";
      tailf:display-when "/ncs:devices/ncs:device[ncs:name=current()/../../../ncs:member]/ncs:module[ncs:name='Cisco-IOS-XR-ethernet-sat-act']";
      tailf:action service-activation-test-clear-all {
        tailf:actionpoint ncsproxy {
          tailf:internal;
        }
        description
          "Clear stored SAT results on all interfaces";
        xr:xr-task "ethernet-services";
        xr:cli-command "clear ethernet service-activation-test results all";
      }
    }
  }
  augment "/ncs:devices/ncs:device/ncs:rpc" {
    container rpc-service-activation-test-clear {
      tailf:ncs-device-type "netconf";
      tailf:display-when "not(../../ncs:module) or ../../ncs:module[ncs:name='Cisco-IOS-XR-ethernet-sat-act']";
      tailf:action service-activation-test-clear {
        tailf:actionpoint ncsproxy {
          tailf:internal;
        }
        description
          "Clear stored SAT results on the specified interface";
        input {
          leaf interface {
            type xr:ncs_rpc_notif_Interface-name;
            mandatory true;
            description
              "Interface name";
          }
        }
        xr:xr-task "ethernet-services";
        xr:cli-command "clear ethernet service-activation-test results interface <interface>";
      }
    }
  }
  augment "/ncs:devices/ncs:device-group/ncs:ned-id/ncs:rpc" {
    container rpc-service-activation-test-clear {
      tailf:ncs-device-type "netconf";
      tailf:display-when "/ncs:devices/ncs:device[ncs:name=current()/../../../ncs:member]/ncs:module[ncs:name='Cisco-IOS-XR-ethernet-sat-act']";
      tailf:action service-activation-test-clear {
        tailf:actionpoint ncsproxy {
          tailf:internal;
        }
        description
          "Clear stored SAT results on the specified interface";
        input {
          leaf interface {
            type xr:ncs_rpc_notif_Interface-name;
            mandatory true;
            description
              "Interface name";
          }
        }
        xr:xr-task "ethernet-services";
        xr:cli-command "clear ethernet service-activation-test results interface <interface>";
      }
    }
  }
  augment "/ncs:devices/ncs:device/ncs:rpc" {
    container rpc-service-activation-test-stop-all {
      tailf:ncs-device-type "netconf";
      tailf:display-when "not(../../ncs:module) or ../../ncs:module[ncs:name='Cisco-IOS-XR-ethernet-sat-act']";
      tailf:action service-activation-test-stop-all {
        tailf:actionpoint ncsproxy {
          tailf:internal;
        }
        description
          "Stop running SAT on all interfaces";
        xr:xr-task "ethernet-services";
        xr:cli-command "ethernet service-activation-test stop all";
      }
    }
  }
  augment "/ncs:devices/ncs:device-group/ncs:ned-id/ncs:rpc" {
    container rpc-service-activation-test-stop-all {
      tailf:ncs-device-type "netconf";
      tailf:display-when "/ncs:devices/ncs:device[ncs:name=current()/../../../ncs:member]/ncs:module[ncs:name='Cisco-IOS-XR-ethernet-sat-act']";
      tailf:action service-activation-test-stop-all {
        tailf:actionpoint ncsproxy {
          tailf:internal;
        }
        description
          "Stop running SAT on all interfaces";
        xr:xr-task "ethernet-services";
        xr:cli-command "ethernet service-activation-test stop all";
      }
    }
  }
  augment "/ncs:devices/ncs:device/ncs:rpc" {
    container rpc-service-activation-test-stop {
      tailf:ncs-device-type "netconf";
      tailf:display-when "not(../../ncs:module) or ../../ncs:module[ncs:name='Cisco-IOS-XR-ethernet-sat-act']";
      tailf:action service-activation-test-stop {
        tailf:actionpoint ncsproxy {
          tailf:internal;
        }
        description
          "Stop running SAT on the specified interface";
        input {
          leaf interface {
            type xr:ncs_rpc_notif_Interface-name;
            mandatory true;
            description
              "Interface name";
          }
        }
        xr:xr-task "ethernet-services";
        xr:cli-command "ethernet service-activation-test stop interface <interface>";
      }
    }
  }
  augment "/ncs:devices/ncs:device-group/ncs:ned-id/ncs:rpc" {
    container rpc-service-activation-test-stop {
      tailf:ncs-device-type "netconf";
      tailf:display-when "/ncs:devices/ncs:device[ncs:name=current()/../../../ncs:member]/ncs:module[ncs:name='Cisco-IOS-XR-ethernet-sat-act']";
      tailf:action service-activation-test-stop {
        tailf:actionpoint ncsproxy {
          tailf:internal;
        }
        description
          "Stop running SAT on the specified interface";
        input {
          leaf interface {
            type xr:ncs_rpc_notif_Interface-name;
            mandatory true;
            description
              "Interface name";
          }
        }
        xr:xr-task "ethernet-services";
        xr:cli-command "ethernet service-activation-test stop interface <interface>";
      }
    }
  }
  augment "/ncs:devices/ncs:device/ncs:rpc" {
    container rpc-service-activation-test-start {
      tailf:ncs-device-type "netconf";
      tailf:display-when "not(../../ncs:module) or ../../ncs:module[ncs:name='Cisco-IOS-XR-ethernet-sat-act']";
      tailf:action service-activation-test-start {
        tailf:actionpoint ncsproxy {
          tailf:internal;
        }
        description
          "Start a SAT on the specified interface";
        input {
          leaf interface {
            type xr:ncs_rpc_notif_Interface-name;
            mandatory true;
            description
              "Interface name";
          }
          leaf profile {
            type xr:ncs_rpc_notif_Cisco-ios-xr-string;
            mandatory true;
            description
              "Profile name";
          }
          leaf destination {
            type ncs_rpc_notif_sat-mac-address-type;
            mandatory true;
            description
              "Destination MAC address";
          }
          leaf direction {
            type dt1:ncs_rpc_notif_Sat-direction;
            mandatory true;
            description
              "Test direction";
          }
        }
        xr:xr-task "ethernet-services";
        xr:cli-command "ethernet service-activation-test start interface <interface> profile <profile> destination <destination> direction <direction>";
      }
    }
  }
  augment "/ncs:devices/ncs:device-group/ncs:ned-id/ncs:rpc" {
    container rpc-service-activation-test-start {
      tailf:ncs-device-type "netconf";
      tailf:display-when "/ncs:devices/ncs:device[ncs:name=current()/../../../ncs:member]/ncs:module[ncs:name='Cisco-IOS-XR-ethernet-sat-act']";
      tailf:action service-activation-test-start {
        tailf:actionpoint ncsproxy {
          tailf:internal;
        }
        description
          "Start a SAT on the specified interface";
        input {
          leaf interface {
            type xr:ncs_rpc_notif_Interface-name;
            mandatory true;
            description
              "Interface name";
          }
          leaf profile {
            type xr:ncs_rpc_notif_Cisco-ios-xr-string;
            mandatory true;
            description
              "Profile name";
          }
          leaf destination {
            type ncs_rpc_notif_sat-mac-address-type;
            mandatory true;
            description
              "Destination MAC address";
          }
          leaf direction {
            type dt1:ncs_rpc_notif_Sat-direction;
            mandatory true;
            description
              "Test direction";
          }
        }
        xr:xr-task "ethernet-services";
        xr:cli-command "ethernet service-activation-test start interface <interface> profile <profile> destination <destination> direction <direction>";
      }
    }
  }
}

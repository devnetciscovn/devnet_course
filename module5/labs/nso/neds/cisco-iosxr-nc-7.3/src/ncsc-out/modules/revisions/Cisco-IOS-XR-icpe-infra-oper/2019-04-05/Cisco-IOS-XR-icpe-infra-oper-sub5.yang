submodule Cisco-IOS-XR-icpe-infra-oper-sub5 {
  // Generated by yanger -t ncs
  tailf:mount-id "cisco-iosxr-nc-7.3:cisco-iosxr-nc-7.3";

  belongs-to Cisco-IOS-XR-icpe-infra-oper {
    prefix Cisco-IOS-XR-icpe-infra-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR icpe-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_ICPE-INSTALL-PROGRESS {
    description
      "Current percentage of install";
    leaf operation-id-xr {
      type string;
      description
        "Operation ID";
    }
    leaf progress-percentage {
      type string;
      units "percentage";
      description
        "Progress percentage";
    }
    leaf satellite-count {
      type string;
      description
        "Satellite count";
    }
  }

  grouping ncs_rpc_notif_ICPE-INSTALL-PROGRESS {
    description
      "Current percentage of install";
    leaf operation-id-xr {
      type uint32;
      description
        "Operation ID";
    }
    leaf progress-percentage {
      type uint16;
      units "percentage";
      description
        "Progress percentage";
    }
    leaf satellite-count {
      type uint32;
      description
        "Satellite count";
    }
  }

  grouping live_ncs_ICPE-INSTALL-PROGRESS {
    description
      "Current percentage of install";
    leaf operation-id-xr {
      type uint32;
      description
        "Operation ID";
    }
    leaf progress-percentage {
      type uint16;
      units "percentage";
      description
        "Progress percentage";
    }
    leaf satellite-count {
      type uint32;
      description
        "Satellite count";
    }
  }

  grouping ICPE-INSTALL-PROGRESS {
    description
      "Current percentage of install";
    leaf operation-id-xr {
      type uint32;
      description
        "Operation ID";
    }
    leaf progress-percentage {
      type uint16;
      units "percentage";
      description
        "Progress percentage";
    }
    leaf satellite-count {
      type uint32;
      description
        "Satellite count";
    }
  }
}

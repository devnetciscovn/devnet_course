module Cisco-IOS-XR-um-router-pim-cfg {
  // Generated by yanger -t ncs
  tailf:mount-id "cisco-iosxr-nc-7.3:cisco-iosxr-nc-7.3";
  tailf:ncs-device-type "netconf";

  namespace "http://cisco.com/ns/yang/Cisco-IOS-XR-um-router-pim-cfg";
  prefix um-router-pim-cfg;

  import cisco-semver {
    prefix semver;
  }
  import Cisco-IOS-XR-types {
    prefix xr;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR router pim configuration.

     Copyright (c) 2019-2021 by Cisco Systems, Inc.
     All rights reserved.";

  revision 2021-01-28 {
    description
      "Added cisco-support task yang nodes";
    semver:module-version "1.1.0";
  }
  revision 2020-12-09 {
    description
      "Removed cisco-support task nodes";
    semver:module-version "1.0.0";
  }
  revision 2020-10-15 {
    description
      "Adjusted must statement under bsr candidate-rp";
  }
  revision 2019-08-20 {
    description
      "Initial release";
    semver:module-version "1.0.0";
  }

  augment "/ncs:devices/ncs:device/ncs:config" {
    container router {
      tailf:ncs-device-type "netconf";
      tailf:display-when "not(../../ncs:module) or ../../ncs:module[ncs:name='Cisco-IOS-XR-um-router-pim-cfg']";
      description
        "Enable a routing process";
      container pim {
        presence "Indicates a pim node is configured.";
        description
          "PIM configuration subcommands";
        container vrfs {
          description
            "VRF configs";
          list vrf {
            key "vrf-name";
            description
              "VRF configs";
            leaf vrf-name {
              type xr:Cisco-ios-xr-string {
                length "1..32" {
                  description
                    "Enter VRF name";
                }
              }
              description
                "VRF configs";
            }
            container address-family {
              description
                "Enter Address Family command mode";
              container ipv4 {
                description
                  "IPv4 Address Family";
                container rp-addresses {
                  description
                    "Configure Rendezvous Point";
                  list rp-address {
                    key "address";
                    description
                      "Configure Rendezvous Point";
                    leaf address {
                      type inet:ipv4-address-no-zone;
                      description
                        "Configure Rendezvous Point";
                    }
                    leaf access-list {
                      type xr:Cisco-ios-xr-string {
                        length "1..32" {
                          description
                            "Access list of groups that should map to given RP";
                        }
                      }
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      key "address";
                      description
                        "Configure Rendezvous Point";
                      leaf address {
                        type inet:ipv4-address-no-zone;
                        description
                          "Configure Rendezvous Point";
                      }
                      leaf access-list {
                        type xr:Cisco-ios-xr-string {
                          length "1..32" {
                            description
                              "Access list of groups that should map to given RP";
                          }
                        }
                        description
                          "Access list of groups that should map to given RP";
                      }
                      container override {
                        presence "Indicates a override node is configured.";
                        description
                          "Static RP config overrides auto-rp and BSR";
                      }
                    }
                  }
                }
                leaf rp-static-deny {
                  type xr:Cisco-ios-xr-string {
                    length "1..32" {
                      description
                        "IP named access list";
                    }
                  }
                  description
                    "Configure static RP deny range";
                }
                leaf accept-register {
                  type xr:Cisco-ios-xr-string {
                    length "1..32" {
                      description
                        "IP named access list";
                    }
                  }
                  description
                    "Registers accept filter";
                }
                container suppress-data-registers {
                  presence "Indicates a suppress-data-registers node is configured.";
                  description
                    "Suppress data registers after initial state setup";
                }
                leaf register-source {
                  type xr:Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:Cisco-ios-xr-string {
                    length "1..32" {
                      description
                        "IP named access list";
                    }
                  }
                  description
                    "Neighbor filter";
                }
                container convergence {
                  description
                    "Convergence related parameters";
                  leaf rpf-conflict-join-delay {
                    type uint32 {
                      range "0..15" {
                        description
                          "Delay in seconds";
                      }
                    }
                    description
                      "Delay in sending first join if RPF points to any downstream neighbor";
                  }
                  leaf link-down-prune-delay {
                    type uint32 {
                      range "0..60" {
                        description
                          "Delay in seconds";
                      }
                    }
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:Cisco-ios-xr-string {
                        length "1..32" {
                          description
                            "Access-list of threshold limited groups";
                        }
                      }
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type uint32 {
                    range "1..3600" {
                      description
                        "Hello interval in seconds";
                    }
                  }
                  description
                    "Inherited by all interfaces : Hello interval in seconds";
                }
                leaf dr-priority {
                  type uint32 {
                    range "0..4294967295" {
                      description
                        "Hello DR priority, preference given to larger value";
                    }
                  }
                  description
                    "Inherited by all interfaces : PIM Hello DR priority";
                }
                leaf join-prune-interval {
                  type uint32 {
                    range "10..600" {
                      description
                        "Join-Prune interval in seconds";
                    }
                  }
                  description
                    "Inherited by all interfaces : Join-Prune interval";
                }
                leaf join-prune-mtu {
                  type uint32 {
                    range "576..65535" {
                      description
                        "Join-Prune MTU in bytes";
                    }
                  }
                  description
                    "Inherited by all interfaces : Join-Prune MTU";
                }
                leaf propagation-delay {
                  type uint32 {
                    range "100..32767" {
                      description
                        "Propagatoin delay in milliseconds";
                    }
                  }
                  description
                    "Inherited by all interfaces : PIM Hello Propagation delay";
                }
                leaf override-interval {
                  type uint32 {
                    range "400..65535" {
                      description
                        "Override interval in milliseconds";
                    }
                  }
                  description
                    "Inherited by all interfaces : PIM Hello override interval";
                }
                container maximum {
                  description
                    "Maximum state limits";
                  container routes {
                    presence "Indicates a routes node is configured.";
                    description
                      "PIM routes";
                    leaf maximum-routes {
                      type uint32 {
                        range "1..200000" {
                          description
                            "Maximum PIM routes";
                        }
                      }
                      mandatory true;
                      description
                        "PIM routes";
                    }
                    leaf threshold {
                      type uint32 {
                        range "1..200000" {
                          description
                            "Threshold value";
                        }
                      }
                      must '. <= ../maximum-routes' {
                        tailf:xpath-root 3;
                      }
                      description
                        "Set threshold to print warning";
                    }
                  }
                  container route-interfaces {
                    presence "Indicates a route-interfaces node is configured.";
                    description
                      "PIM total number of interfaces on all routes";
                    leaf maximum-route-interfaces {
                      type uint32 {
                        range "1..1100000" {
                          description
                            "Maximum PIM route-interfaces";
                        }
                      }
                      mandatory true;
                      description
                        "PIM total number of interfaces on all routes";
                    }
                    leaf threshold {
                      type uint32 {
                        range "1..1100000" {
                          description
                            "Threshold value";
                        }
                      }
                      must '. <= ../maximum-route-interfaces' {
                        tailf:xpath-root 3;
                      }
                      description
                        "Set threshold to print warning";
                    }
                  }
                  container register-states {
                    presence "Indicates a register-states node is configured.";
                    description
                      "PIM source register states";
                    leaf maximum-register-states {
                      type uint32 {
                        range "0..75000" {
                          description
                            "Maximum PIM sparse-mode source register states";
                        }
                      }
                      mandatory true;
                      description
                        "PIM source register states";
                    }
                    leaf threshold {
                      type uint32 {
                        range "0..75000" {
                          description
                            "Threshold value";
                        }
                      }
                      must '. <= ../maximum-register-states' {
                        tailf:xpath-root 3;
                      }
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type uint32 {
                          range "1..10000" {
                            description
                              "Maximum PIM group mappings from elected BSR";
                          }
                        }
                        mandatory true;
                        description
                          "Learned through the BSR distribution mechanism";
                      }
                      leaf threshold {
                        type uint32 {
                          range "1..10000" {
                            description
                              "Threshold value";
                          }
                        }
                        must '. <= ../maximum-bsr' {
                          tailf:xpath-root 3;
                        }
                        description
                          "Set threshold to print warning";
                      }
                    }
                    container autorp {
                      presence "Indicates a autorp node is configured.";
                      description
                        "Learned through the Auto-RP distribution mechanism";
                      leaf maximum-autorp {
                        type uint32 {
                          range "1..10000" {
                            description
                              "Maximum PIM group mappings from Auto-RP mapping agent";
                          }
                        }
                        mandatory true;
                        description
                          "Learned through the Auto-RP distribution mechanism";
                      }
                      leaf threshold {
                        type uint32 {
                          range "1..10000" {
                            description
                              "Threshold value";
                          }
                        }
                        must '. <= ../maximum-autorp' {
                          tailf:xpath-root 3;
                        }
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type uint32 {
                          range "1..10000" {
                            description
                              "Maximum number of C-RP cache";
                          }
                        }
                        mandatory true;
                        description
                          "Set maximum number of C-RP cache in BSR";
                      }
                      leaf threshold {
                        type uint32 {
                          range "1..10000" {
                            description
                              "Threshold value";
                          }
                        }
                        must '. <= ../maximum-crp-cache' {
                          tailf:xpath-root 3;
                        }
                        description
                          "Set threshold to print warning";
                      }
                    }
                  }
                }
                leaf convergence-timeout {
                  type uint32 {
                    range "1800..2400" {
                      description
                        "Unicast convergence fallback timer in seconds";
                    }
                  }
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf-vector-injects {
                  description
                    "inject RPF vector";
                  list inject {
                    must 'rpf-vector' {
                      tailf:xpath-root 3;
                    }
                    key "source-address masklen";
                    description
                      "inject RPF vector";
                    leaf source-address {
                      type inet:ipv4-address-no-zone;
                      description
                        "inject RPF vector";
                    }
                    leaf masklen {
                      type uint32 {
                        range "0..32" {
                          description
                            "masklen";
                        }
                      }
                      description
                        "masklen";
                    }
                    leaf-list rpf-vector {
                      type inet:ipv4-address-no-zone;
                      max-elements 22;
                      description
                        "configure this node";
                    }
                  }
                }
                container explicit-rpf-vector {
                  description
                    "Enable Explicit PIM RPF Vector";
                  container injects {
                    description
                      "inject Explicit RPF vector";
                    list inject {
                      must 'rpf-vector' {
                        tailf:xpath-root 3;
                      }
                      key "source-address masklen";
                      description
                        "inject Explicit RPF vector";
                      leaf source-address {
                        type inet:ipv4-address-no-zone;
                        description
                          "inject Explicit RPF vector";
                      }
                      leaf masklen {
                        type uint32 {
                          range "0..32" {
                            description
                              "masklen";
                          }
                        }
                        description
                          "masklen";
                      }
                      leaf-list rpf-vector {
                        type inet:ipv4-address-no-zone;
                        max-elements 22;
                        description
                          "configure this node";
                      }
                    }
                  }
                }
                container rpf {
                  description
                    "RPF commands";
                  container topology {
                    description
                      "Select RPF topology";
                    leaf route-policy {
                      type xr:Route-policy-name;
                      description
                        "Route policy to select RPF topology";
                    }
                  }
                }
                container mdt {
                  description
                    "Multicast Distribution Tree commands";
                  leaf neighbor-filter {
                    type xr:Cisco-ios-xr-string {
                      length "1..32" {
                        description
                          "IP named access list";
                      }
                    }
                    description
                      "Neighbor filter";
                  }
                  container data {
                    description
                      "Data MDT Options";
                    leaf switchover-interval {
                      type uint32 {
                        range "3..60" {
                          description
                            "Interval value in seconds";
                        }
                      }
                      description
                        "Data MDT switchover interval";
                    }
                    leaf announce-interval {
                      type uint32 {
                        range "3..120" {
                          description
                            "Interval value in seconds";
                        }
                      }
                      description
                        "Periodic Data MDT Join TLV interval";
                    }
                    leaf max-aggregation {
                      type uint32 {
                        range "1..16777215" {
                          description
                            "Aggregation value";
                        }
                      }
                      description
                        "Data MDT max-aggregation";
                    }
                  }
                  container c-multicast-routing {
                    presence "Indicates a c-multicast-routing node is configured.";
                    description
                      "MVPN customer routing commands";
                    leaf type {
                      type enumeration {
                        enum "pim" {
                          value 1;
                          description
                            "PIM customer multicast routing";
                        }
                        enum "bgp" {
                          value 2;
                          description
                            "BGP customer multicast routing";
                        }
                      }
                      mandatory true;
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      when "../type != 'pim'" {
                        tailf:xpath-root 3;
                      }
                      description
                        "PIM Hellos over MDT";
                      container enable {
                        presence "Indicates a enable node is configured.";
                        description
                          "Enable PIM Hellos over MDT";
                      }
                    }
                    leaf shared-tree-prune-delay {
                      type uint32 {
                        range "0..1800" {
                          description
                            "Delay in seconds.";
                        }
                      }
                      description
                        "Delay before pruning I-S PMSI from S,G when SA received";
                    }
                    leaf source-tree-prune-delay {
                      type uint32 {
                        range "0..300" {
                          description
                            "Delay in seconds.";
                        }
                      }
                      description
                        "Delay before removing PMSI from olist after BGP withdrawal";
                    }
                    container migration {
                      presence "Indicates a migration node is configured.";
                      description
                        "customer routing migration";
                      leaf route-policy {
                        type xr:Route-policy-name;
                        description
                          "Route policy to select customer routing";
                      }
                    }
                    container unicast-reachability {
                      description
                        "Control addition of Extended Communities to Unicast VPN-IP routes";
                      container connector {
                        description
                          "Enable/Disable Connector";
                        container disable {
                          must 'not(../enable)' {
                            tailf:xpath-root 3;
                          }
                          presence "Indicates a disable node is configured.";
                          description
                            "Disable Connector Attribute";
                        }
                        container enable {
                          must 'not(../disable)' {
                            tailf:xpath-root 3;
                          }
                          presence "Indicates a enable node is configured.";
                          description
                            "Enable Connector Attribute";
                        }
                      }
                      container source-as {
                        description
                          "Enable/Disable Source AS";
                        container disable {
                          must 'not(../enable)' {
                            tailf:xpath-root 3;
                          }
                          presence "Indicates a disable node is configured.";
                          description
                            "Disable Source-AS Attribute";
                        }
                        container enable {
                          must 'not(../disable)' {
                            tailf:xpath-root 3;
                          }
                          presence "Indicates a enable node is configured.";
                          description
                            "Enable Source-AS Attribute";
                        }
                      }
                      container vrf-route-import {
                        description
                          "Enable/Disable VRF Route Import";
                        container disable {
                          must 'not(../enable)' {
                            tailf:xpath-root 3;
                          }
                          presence "Indicates a disable node is configured.";
                          description
                            "Disable VRF Route Import Attribute";
                        }
                        container enable {
                          must 'not(../disable)' {
                            tailf:xpath-root 3;
                          }
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:Cisco-ios-xr-string {
                      length "1..32" {
                        description
                          "ACL Name for rp-list";
                      }
                    }
                    description
                      "Access-list for allowed RP addresses";
                  }
                  leaf group-list {
                    type xr:Cisco-ios-xr-string {
                      length "1..32" {
                        description
                          "Access name for group-list";
                      }
                    }
                    description
                      "Access-list for allowed group ranges";
                  }
                }
                container sg-expiry-timer {
                  presence "Indicates a sg-expiry-timer node is configured.";
                  description
                    "Configure SG expiry timer";
                  leaf sg-expiry-timer-value {
                    type uint32 {
                      range "40..57600" {
                        description
                          "Duration of the expiry timer interval, in seconds";
                      }
                    }
                    mandatory true;
                    description
                      "Configure SG expiry timer";
                  }
                  leaf sg-list {
                    type xr:Cisco-ios-xr-string {
                      length "1..32" {
                        description
                          "IP named access list";
                      }
                    }
                    description
                      "Access-list of (S,G) routes for which expiry timer is applicable";
                  }
                }
                container ssm {
                  description
                    "Configure a group range for Source-Specific use";
                  leaf range {
                    type xr:Cisco-ios-xr-string {
                      length "1..32" {
                        description
                          "Access list specifying SSM group range";
                      }
                    }
                    must 'not(../disable)' {
                      tailf:xpath-root 3;
                    }
                    description
                      "Provide ACL that specifies non-standard SSM range";
                  }
                  container disable {
                    must 'not(../range)' {
                      tailf:xpath-root 3;
                    }
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    must 'source or source-nexthop or source-group' {
                      tailf:xpath-root 3;
                    }
                    presence "Indicates a hash node is configured.";
                    description
                      "Enter a hashing algorithm";
                    container source {
                      must 'not(../source-nexthop) and not(../source-group)' {
                        tailf:xpath-root 3;
                      }
                      presence "Indicates a source node is configured.";
                      description
                        "Enable source based multipath hashing (Compatible with IOS versions)";
                    }
                    container source-nexthop {
                      must 'not(../source) and not(../source-group)' {
                        tailf:xpath-root 3;
                      }
                      presence "Indicates a source-nexthop node is configured.";
                      description
                        "Enable source with next-hop multipath hashing (better distribution)";
                    }
                    container source-group {
                      must 'not(../source-nexthop) and not(../source)' {
                        tailf:xpath-root 3;
                      }
                      presence "Indicates a source-group node is configured.";
                      description
                        "Enable source, group based multipath hashing (Compatible with IOS versions)";
                    }
                  }
                }
                container auto-rp {
                  description
                    "Auto-RP Commands";
                  container listen {
                    description
                      "RP discovery through AUTORP protocol";
                    container disable {
                      presence "Indicates a disable node is configured.";
                      description
                        "Disable RP discovery through the AUTORP protocol";
                    }
                  }
                  container relay {
                    description
                      "relay";
                    container vrfs {
                      description
                        "vrf";
                      list vrf {
                        key "vrf-name";
                        description
                          "vrf";
                        leaf vrf-name {
                          type xr:Cisco-ios-xr-string {
                            length "1..32" {
                              description
                                "vrf-name";
                            }
                          }
                          description
                            "vrf";
                        }
                        container listen {
                          presence "Indicates a listen node is configured.";
                          description
                            "Enable RP relay in listen mode";
                        }
                      }
                    }
                  }
                }
                container interfaces {
                  description
                    "PIM interface configuration subcommands";
                  list interface {
                    key "interface-name";
                    description
                      "Select an interface to configure";
                    leaf interface-name {
                      type xr:Interface-name;
                      description
                        "Select an interface to configure";
                    }
                    leaf dr-priority {
                      type uint32 {
                        range "0..4294967295" {
                          description
                            "Hello DR priority, preference given to larger value";
                        }
                      }
                      description
                        "PIM Hello DR priority";
                    }
                    leaf hello-interval {
                      type uint32 {
                        range "1..3600" {
                          description
                            "Hello interval in seconds";
                        }
                      }
                      description
                        "PIM neighbor Hello announcement interval";
                    }
                    leaf join-prune-interval {
                      type uint32 {
                        range "10..600" {
                          description
                            "Join-Prune interval in seconds";
                        }
                      }
                      description
                        "PIM periodic Join-Prune announcement interval";
                    }
                    leaf join-prune-mtu {
                      type uint32 {
                        range "576..65535" {
                          description
                            "MTU to use in bytes";
                        }
                      }
                      description
                        "MTU to use when sending PIM J/P packets";
                    }
                    leaf propagation-delay {
                      type uint32 {
                        range "100..32767" {
                          description
                            "Propagatoin delay in milliseconds";
                        }
                      }
                      description
                        "PIM Hello propagation delay";
                    }
                    leaf override-interval {
                      type uint32 {
                        range "400..65535" {
                          description
                            "Override interval in milliseconds";
                        }
                      }
                      description
                        "PIM Hello override interval";
                    }
                    container bsr-border {
                      presence "Indicates a bsr-border node is configured.";
                      description
                        "Do not fwd BSR messages on this interface";
                    }
                    container enable {
                      must 'not(../disable)' {
                        tailf:xpath-root 3;
                      }
                      presence "Indicates a enable node is configured.";
                      description
                        "Enable PIM processing on this interface";
                    }
                    container disable {
                      must 'not(../enable)' {
                        tailf:xpath-root 3;
                      }
                      presence "Indicates a disable node is configured.";
                      description
                        "Disable PIM processing on this interface";
                    }
                    leaf neighbor-filter {
                      type xr:Cisco-ios-xr-string {
                        length "1..1024" {
                          description
                            "Access list specifying neighbor address";
                        }
                      }
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type uint32 {
                            range "1..1100000" {
                              description
                                "Maximum number of allowed routes for this interface";
                            }
                          }
                          mandatory true;
                          description
                            "PIM downstream joined interfaces";
                        }
                        leaf threshold {
                          type uint32 {
                            range "1..1100000" {
                              description
                                "Threshold warning";
                            }
                          }
                          must '. <= ../maximum-route-interfaces' {
                            tailf:xpath-root 3;
                          }
                          description
                            "Threshold warning";
                        }
                        leaf access-list {
                          type xr:Cisco-ios-xr-string {
                            length "1..64" {
                              description
                                "Name of ACL that specifies to which routes to apply the maximum limit";
                            }
                          }
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type uint32 {
                          range "3..30000" {
                            description
                              "hello interval in milli-seconds";
                          }
                        }
                        description
                          "Hello interval";
                      }
                      leaf multiplier {
                        type uint32 {
                          range "2..50" {
                            description
                              "Detect multiplier";
                          }
                        }
                        description
                          "Detect multiplier";
                      }
                    }
                  }
                }
                container bsr {
                  description
                    "BSR Configurations";
                  container candidate-bsr {
                    presence "Indicates a candidate-bsr node is configured.";
                    description
                      "configure candidate BSR";
                    leaf address {
                      type inet:ipv4-address-no-zone;
                      mandatory true;
                      description
                        "IP address of configured BSR";
                    }
                    leaf hash-mask-len {
                      type uint32 {
                        range "0..32" {
                          description
                            "mask length";
                        }
                      }
                      mandatory true;
                      description
                        "BSR Hash Mask Length";
                    }
                    leaf priority {
                      type uint32 {
                        range "1..255" {
                          description
                            "priority";
                        }
                      }
                      mandatory true;
                      description
                        "BSR Priority";
                    }
                  }
                  container candidate-rps {
                    description
                      "BSR Candidate RP Configurations";
                    list candidate-rp {
                      must '(priority and interval) or (bidir/priority and bidir/interval)' {
                        tailf:xpath-root 3;
                      }
                      key "address";
                      description
                        "BSR Candidate RP Configurations";
                      leaf address {
                        type inet:ipv4-address-no-zone;
                        description
                          "BSR Candidate RP Configurations";
                      }
                      leaf group-list {
                        type xr:Cisco-ios-xr-string {
                          length "1..64" {
                            description
                              "access-list";
                          }
                        }
                        description
                          "Group List access-list";
                      }
                      leaf priority {
                        type uint32 {
                          range "1..255" {
                            description
                              "priority";
                          }
                        }
                        description
                          "C-RP Priority";
                      }
                      leaf interval {
                        type uint32 {
                          range "30..600" {
                            description
                              "interval in second";
                          }
                        }
                        description
                          "C-RP Advertisement interval";
                      }
                      container bidir {
                        description
                          "To specify group ranges as Bidir";
                        leaf group-list {
                          type xr:Cisco-ios-xr-string {
                            length "1..64" {
                              description
                                "access-list";
                            }
                          }
                          description
                            "Group List access-list";
                        }
                        leaf priority {
                          type uint32 {
                            range "1..255" {
                              description
                                "priority";
                            }
                          }
                          description
                            "C-RP Priority";
                        }
                        leaf interval {
                          type uint32 {
                            range "30..600" {
                              description
                                "interval in second";
                            }
                          }
                          description
                            "C-RP Advertisement interval";
                        }
                      }
                    }
                  }
                  container relay {
                    description
                      "BSR RP relay config";
                    container vrfs {
                      description
                        "vrf";
                      list vrf {
                        key "vrf-name";
                        description
                          "vrf";
                        leaf vrf-name {
                          type xr:Cisco-ios-xr-string {
                            length "1..1024" {
                              description
                                "vrf-name";
                            }
                          }
                          description
                            "vrf";
                        }
                        container listen {
                          presence "Indicates a listen node is configured.";
                          description
                            "Enable RP relay in listen mode";
                        }
                      }
                    }
                  }
                }
                container mofrr {
                  presence "Indicates a mofrr node is configured.";
                  description
                    "PIM Mofrr";
                  leaf flow {
                    type xr:Cisco-ios-xr-string {
                      length "1..1024" {
                        description
                          "Access list specifying SGs that should do MOFRR with hardware switchover triggers";
                      }
                    }
                    description
                      "Multicast Only FRR";
                  }
                  leaf rib {
                    type string {
                      length "1..1024" {
                        description
                          "Access list specifying SGs that should do MOFRR with RIB events as switchover triggers";
                      }
                    }
                    description
                      "Use the rib keyword to restrict switchover triggers to RIB events";
                  }
                  container non-revertive {
                    presence "Indicates a non-revertive node is configured.";
                    description
                      "Non-revertive MoFRR";
                  }
                  container clone {
                    description
                      "Use the clone keyword to clone";
                    container joins {
                      description
                        "Use the join keyword to clone S,G as S1,G joins as S2,G joins";
                      list join {
                        must 'to' {
                          tailf:xpath-root 3;
                        }
                        key "address";
                        description
                          "Use the join keyword to clone S,G as S1,G joins as S2,G joins";
                        leaf address {
                          type inet:ipv4-address-no-zone;
                          description
                            "Source S";
                        }
                        list to {
                          must 'and' {
                            tailf:xpath-root 3;
                          }
                          key "address";
                          description
                            "to";
                          leaf address {
                            type inet:ipv4-address-no-zone;
                            description
                              "Source S1";
                          }
                          list and {
                            must 'masklen' {
                              tailf:xpath-root 3;
                            }
                            key "address";
                            description
                              "and";
                            leaf address {
                              type inet:ipv4-address-no-zone;
                              description
                                "Source S2";
                            }
                            list masklen {
                              key "mask-length";
                              description
                                "masklen";
                              leaf mask-length {
                                type uint32 {
                                  range "0..32" {
                                    description
                                      "masklen";
                                  }
                                }
                                description
                                  "masklen";
                              }
                            }
                          }
                        }
                      }
                    }
                    container sources {
                      description
                        "Use the source keyword to clone S,G as S1,G traffic and S2,G traffic";
                      list source {
                        must 'to' {
                          tailf:xpath-root 3;
                        }
                        key "address";
                        description
                          "Use the source keyword to clone S,G as S1,G traffic and S2,G traffic";
                        leaf address {
                          type inet:ipv4-address-no-zone;
                          description
                            "Source S";
                        }
                        list to {
                          must 'and' {
                            tailf:xpath-root 3;
                          }
                          key "address";
                          description
                            "to";
                          leaf address {
                            type inet:ipv4-address-no-zone;
                            description
                              "Source S1";
                          }
                          list and {
                            must 'masklen' {
                              tailf:xpath-root 3;
                            }
                            key "address";
                            description
                              "and";
                            leaf address {
                              type inet:ipv4-address-no-zone;
                              description
                                "Source S2";
                            }
                            list masklen {
                              key "mask-length";
                              description
                                "masklen";
                              leaf mask-length {
                                type uint32 {
                                  range "0..32" {
                                    description
                                      "masklen";
                                  }
                                }
                                description
                                  "masklen";
                              }
                            }
                          }
                        }
                      }
                    }
                  }
                }
                container sr-p2mp-policies {
                  description
                    "Segment-routing P2MP policy";
                  list sr-p2mp-policy {
                    key "policy-name";
                    description
                      "Segment-routing P2MP policy";
                    leaf policy-name {
                      type xr:Cisco-ios-xr-string {
                        length "1..1024" {
                          description
                            "Name of the P2MP policy";
                        }
                      }
                      description
                        "Segment-routing P2MP policy";
                    }
                    container static-group {
                      description
                        "ipv4 static multicast group";
                      list group-address {
                        key "group-address";
                        description
                          "ipv4 static multicast group";
                        leaf group-address {
                          type inet:ipv4-address-no-zone;
                          description
                            "ipv4 static multicast group";
                        }
                        container group-address-only {
                          presence "Indicates a group-address-only node is configured.";
                          description
                            "Group-address without increment mask/source-address";
                        }
                        container group-address-inc-masks {
                          description
                            "Group-address with increment mask for group address";
                          list inc-mask {
                            key "group-mask-address";
                            description
                              "Increment mask for group address";
                            leaf group-mask-address {
                              type inet:ipv4-address-no-zone;
                              description
                                "Increment mask for group address";
                            }
                            leaf group-address-count {
                              type uint32 {
                                range "1..512" {
                                  description
                                    "No. of group addresses to join";
                                }
                              }
                              mandatory true;
                              description
                                "No. of group addresses to join";
                            }
                          }
                        }
                        container group-address-source-address {
                          description
                            "Group-address with source-address";
                          list source-address {
                            key "source-address";
                            description
                              "Source address to join";
                            leaf source-address {
                              type inet:ipv4-address-no-zone;
                              description
                                "Source address to join";
                            }
                          }
                        }
                        container group-address-inc-mask-source-address {
                          description
                            "Group-address with increment-mask and source-address";
                          list inc-mask {
                            key "group-mask-address source-address";
                            description
                              "Increment mask for group address";
                            leaf group-mask-address {
                              type inet:ipv4-address-no-zone;
                              description
                                "Increment mask for group address";
                            }
                            leaf source-address {
                              type inet:ipv4-address-no-zone;
                              description
                                "Source address to join";
                            }
                            leaf group-address-count {
                              type uint32 {
                                range "1..512" {
                                  description
                                    "No. of group addresses to join";
                                }
                              }
                              mandatory true;
                              description
                                "No. of group addresses to join";
                            }
                          }
                        }
                        container group-address-source-address-inc-mask {
                          description
                            "Group-address and source-address with increment-mask";
                          list inc-mask {
                            key "source-address source-mask-address";
                            description
                              "Increment mask for group address";
                            leaf source-address {
                              type inet:ipv4-address-no-zone;
                              description
                                "Source address to join";
                            }
                            leaf source-mask-address {
                              type inet:ipv4-address-no-zone;
                              description
                                "Increment mask for source address";
                            }
                            leaf source-address-count {
                              type uint32 {
                                range "1..512" {
                                  description
                                    "No. of source addresses to join";
                                }
                              }
                              mandatory true;
                              description
                                "No. of source addresses to join";
                            }
                          }
                        }
                        container group-inc-mask-source-inc-mask {
                          description
                            "Group-address with increment-mask and source-address with increment-mask";
                          list inc-mask {
                            key "group-mask-address source-address source-mask-address";
                            leaf group-mask-address {
                              type inet:ipv4-address-no-zone;
                              description
                                "Increment mask for group address";
                            }
                            leaf source-address {
                              type inet:ipv4-address-no-zone;
                              description
                                "Source address to join";
                            }
                            leaf source-mask-address {
                              type inet:ipv4-address-no-zone;
                              description
                                "Increment mask for source address";
                            }
                            leaf group-address-count {
                              type uint32 {
                                range "1..512" {
                                  description
                                    "No. of group addresses to join";
                                }
                              }
                              mandatory true;
                              description
                                "No. of group addresses to join";
                            }
                            leaf source-address-count {
                              type uint32 {
                                range "1..512" {
                                  description
                                    "No. of source addresses to join";
                                }
                              }
                              mandatory true;
                              description
                                "No. of source addresses to join";
                            }
                          }
                        }
                      }
                    }
                  }
                }
              }
              container ipv6 {
                description
                  "IPv6 Address Family";
                container rp-addresses {
                  description
                    "Configure Rendezvous Point";
                  list rp-address {
                    key "address";
                    description
                      "Configure Rendezvous Point";
                    leaf address {
                      type inet:ipv6-address-no-zone;
                      description
                        "Configure Rendezvous Point";
                    }
                    leaf access-list {
                      type xr:Cisco-ios-xr-string {
                        length "1..32" {
                          description
                            "Access list of groups that should map to given RP";
                        }
                      }
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      key "address";
                      description
                        "Configure Rendezvous Point";
                      leaf address {
                        type inet:ipv6-address-no-zone;
                        description
                          "Configure Rendezvous Point";
                      }
                      leaf access-list {
                        type xr:Cisco-ios-xr-string {
                          length "1..32" {
                            description
                              "Access list of groups that should map to given RP";
                          }
                        }
                        description
                          "Access list of groups that should map to given RP";
                      }
                      container override {
                        presence "Indicates a override node is configured.";
                        description
                          "Static RP config overrides auto-rp and BSR";
                      }
                    }
                  }
                }
                leaf rp-static-deny {
                  type xr:Cisco-ios-xr-string {
                    length "1..32" {
                      description
                        "IP named access list";
                    }
                  }
                  description
                    "Configure static RP deny range";
                }
                leaf accept-register {
                  type xr:Cisco-ios-xr-string {
                    length "1..32" {
                      description
                        "IP named access list";
                    }
                  }
                  description
                    "Registers accept filter";
                }
                container suppress-data-registers {
                  presence "Indicates a suppress-data-registers node is configured.";
                  description
                    "Suppress data registers after initial state setup";
                }
                leaf register-source {
                  type xr:Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:Cisco-ios-xr-string {
                    length "1..32" {
                      description
                        "IP named access list";
                    }
                  }
                  description
                    "Neighbor filter";
                }
                container convergence {
                  description
                    "Convergence related parameters";
                  leaf rpf-conflict-join-delay {
                    type uint32 {
                      range "0..15" {
                        description
                          "Delay in seconds";
                      }
                    }
                    description
                      "Delay in sending first join if RPF points to any downstream neighbor";
                  }
                  leaf link-down-prune-delay {
                    type uint32 {
                      range "0..60" {
                        description
                          "Delay in seconds";
                      }
                    }
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:Cisco-ios-xr-string {
                        length "1..32" {
                          description
                            "Access-list of threshold limited groups";
                        }
                      }
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type uint32 {
                    range "1..3600" {
                      description
                        "Hello interval in seconds";
                    }
                  }
                  description
                    "Inherited by all interfaces : Hello interval in seconds";
                }
                leaf dr-priority {
                  type uint32 {
                    range "0..4294967295" {
                      description
                        "Hello DR priority, preference given to larger value";
                    }
                  }
                  description
                    "Inherited by all interfaces : PIM Hello DR priority";
                }
                leaf join-prune-interval {
                  type uint32 {
                    range "10..600" {
                      description
                        "Join-Prune interval in seconds";
                    }
                  }
                  description
                    "Inherited by all interfaces : Join-Prune interval";
                }
                leaf join-prune-mtu {
                  type uint32 {
                    range "576..65535" {
                      description
                        "Join-Prune MTU in bytes";
                    }
                  }
                  description
                    "Inherited by all interfaces : Join-Prune MTU";
                }
                leaf propagation-delay {
                  type uint32 {
                    range "100..32767" {
                      description
                        "Propagatoin delay in milliseconds";
                    }
                  }
                  description
                    "Inherited by all interfaces : PIM Hello Propagation delay";
                }
                leaf override-interval {
                  type uint32 {
                    range "400..65535" {
                      description
                        "Override interval in milliseconds";
                    }
                  }
                  description
                    "Inherited by all interfaces : PIM Hello override interval";
                }
                container maximum {
                  description
                    "Maximum state limits";
                  container routes {
                    presence "Indicates a routes node is configured.";
                    description
                      "PIM routes";
                    leaf maximum-routes {
                      type uint32 {
                        range "1..200000" {
                          description
                            "Maximum PIM routes";
                        }
                      }
                      mandatory true;
                      description
                        "PIM routes";
                    }
                    leaf threshold {
                      type uint32 {
                        range "1..200000" {
                          description
                            "Threshold value";
                        }
                      }
                      must '. <= ../maximum-routes' {
                        tailf:xpath-root 3;
                      }
                      description
                        "Set threshold to print warning";
                    }
                  }
                  container route-interfaces {
                    presence "Indicates a route-interfaces node is configured.";
                    description
                      "PIM total number of interfaces on all routes";
                    leaf maximum-route-interfaces {
                      type uint32 {
                        range "1..1100000" {
                          description
                            "Maximum PIM route-interfaces";
                        }
                      }
                      mandatory true;
                      description
                        "PIM total number of interfaces on all routes";
                    }
                    leaf threshold {
                      type uint32 {
                        range "1..1100000" {
                          description
                            "Threshold value";
                        }
                      }
                      must '. <= ../maximum-route-interfaces' {
                        tailf:xpath-root 3;
                      }
                      description
                        "Set threshold to print warning";
                    }
                  }
                  container register-states {
                    presence "Indicates a register-states node is configured.";
                    description
                      "PIM source register states";
                    leaf maximum-register-states {
                      type uint32 {
                        range "0..75000" {
                          description
                            "Maximum PIM sparse-mode source register states";
                        }
                      }
                      mandatory true;
                      description
                        "PIM source register states";
                    }
                    leaf threshold {
                      type uint32 {
                        range "0..75000" {
                          description
                            "Threshold value";
                        }
                      }
                      must '. <= ../maximum-register-states' {
                        tailf:xpath-root 3;
                      }
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type uint32 {
                          range "1..10000" {
                            description
                              "Maximum PIM group mappings from elected BSR";
                          }
                        }
                        mandatory true;
                        description
                          "Learned through the BSR distribution mechanism";
                      }
                      leaf threshold {
                        type uint32 {
                          range "1..10000" {
                            description
                              "Threshold value";
                          }
                        }
                        must '. <= ../maximum-bsr' {
                          tailf:xpath-root 3;
                        }
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type uint32 {
                          range "1..10000" {
                            description
                              "Maximum number of C-RP cache";
                          }
                        }
                        mandatory true;
                        description
                          "Set maximum number of C-RP cache in BSR";
                      }
                      leaf threshold {
                        type uint32 {
                          range "1..10000" {
                            description
                              "Threshold value";
                          }
                        }
                        must '. <= ../maximum-crp-cache' {
                          tailf:xpath-root 3;
                        }
                        description
                          "Set threshold to print warning";
                      }
                    }
                  }
                }
                leaf convergence-timeout {
                  type uint32 {
                    range "1800..2400" {
                      description
                        "Unicast convergence fallback timer in seconds";
                    }
                  }
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf {
                  description
                    "RPF commands";
                  container topology {
                    description
                      "Select RPF topology";
                    leaf route-policy {
                      type xr:Route-policy-name;
                      description
                        "Route policy to select RPF topology";
                    }
                  }
                }
                container mdt {
                  description
                    "Multicast Distribution Tree commands";
                  leaf neighbor-filter {
                    type xr:Cisco-ios-xr-string {
                      length "1..32" {
                        description
                          "IP named access list";
                      }
                    }
                    description
                      "Neighbor filter";
                  }
                  container data {
                    description
                      "Data MDT Options";
                    leaf switchover-interval {
                      type uint32 {
                        range "3..60" {
                          description
                            "Interval value in seconds";
                        }
                      }
                      description
                        "Data MDT switchover interval";
                    }
                    leaf announce-interval {
                      type uint32 {
                        range "3..120" {
                          description
                            "Interval value in seconds";
                        }
                      }
                      description
                        "Periodic Data MDT Join TLV interval";
                    }
                    leaf max-aggregation {
                      type uint32 {
                        range "1..16777215" {
                          description
                            "Aggregation value";
                        }
                      }
                      description
                        "Data MDT max-aggregation";
                    }
                  }
                  container c-multicast-routing {
                    presence "Indicates a c-multicast-routing node is configured.";
                    description
                      "MVPN customer routing commands";
                    leaf type {
                      type enumeration {
                        enum "pim" {
                          value 1;
                          description
                            "PIM customer multicast routing";
                        }
                        enum "bgp" {
                          value 2;
                          description
                            "BGP customer multicast routing";
                        }
                      }
                      mandatory true;
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      when "../type != 'pim'" {
                        tailf:xpath-root 3;
                      }
                      description
                        "PIM Hellos over MDT";
                      container enable {
                        presence "Indicates a enable node is configured.";
                        description
                          "Enable PIM Hellos over MDT";
                      }
                    }
                    leaf shared-tree-prune-delay {
                      type uint32 {
                        range "0..1800" {
                          description
                            "Delay in seconds.";
                        }
                      }
                      description
                        "Delay before pruning I-S PMSI from S,G when SA received";
                    }
                    leaf source-tree-prune-delay {
                      type uint32 {
                        range "0..300" {
                          description
                            "Delay in seconds.";
                        }
                      }
                      description
                        "Delay before removing PMSI from olist after BGP withdrawal";
                    }
                    container migration {
                      presence "Indicates a migration node is configured.";
                      description
                        "customer routing migration";
                      leaf route-policy {
                        type xr:Route-policy-name;
                        description
                          "Route policy to select customer routing";
                      }
                    }
                    container unicast-reachability {
                      description
                        "Control addition of Extended Communities to Unicast VPN-IP routes";
                      container connector {
                        description
                          "Enable/Disable Connector";
                        container disable {
                          must 'not(../enable)' {
                            tailf:xpath-root 3;
                          }
                          presence "Indicates a disable node is configured.";
                          description
                            "Disable Connector Attribute";
                        }
                        container enable {
                          must 'not(../disable)' {
                            tailf:xpath-root 3;
                          }
                          presence "Indicates a enable node is configured.";
                          description
                            "Enable Connector Attribute";
                        }
                      }
                      container source-as {
                        description
                          "Enable/Disable Source AS";
                        container disable {
                          must 'not(../enable)' {
                            tailf:xpath-root 3;
                          }
                          presence "Indicates a disable node is configured.";
                          description
                            "Disable Source-AS Attribute";
                        }
                        container enable {
                          must 'not(../disable)' {
                            tailf:xpath-root 3;
                          }
                          presence "Indicates a enable node is configured.";
                          description
                            "Enable Source-AS Attribute";
                        }
                      }
                      container vrf-route-import {
                        description
                          "Enable/Disable VRF Route Import";
                        container disable {
                          must 'not(../enable)' {
                            tailf:xpath-root 3;
                          }
                          presence "Indicates a disable node is configured.";
                          description
                            "Disable VRF Route Import Attribute";
                        }
                        container enable {
                          must 'not(../disable)' {
                            tailf:xpath-root 3;
                          }
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:Cisco-ios-xr-string {
                      length "1..32" {
                        description
                          "ACL Name for rp-list";
                      }
                    }
                    description
                      "Access-list for allowed RP addresses";
                  }
                  leaf group-list {
                    type xr:Cisco-ios-xr-string {
                      length "1..32" {
                        description
                          "Access name for group-list";
                      }
                    }
                    description
                      "Access-list for allowed group ranges";
                  }
                }
                container sg-expiry-timer {
                  presence "Indicates a sg-expiry-timer node is configured.";
                  description
                    "Configure SG expiry timer";
                  leaf sg-expiry-timer-value {
                    type uint32 {
                      range "40..57600" {
                        description
                          "Duration of the expiry timer interval, in seconds";
                      }
                    }
                    mandatory true;
                    description
                      "Configure SG expiry timer";
                  }
                  leaf sg-list {
                    type xr:Cisco-ios-xr-string {
                      length "1..32" {
                        description
                          "IP named access list";
                      }
                    }
                    description
                      "Access-list of (S,G) routes for which expiry timer is applicable";
                  }
                }
                container ssm {
                  description
                    "Configure a group range for Source-Specific use";
                  leaf range {
                    type xr:Cisco-ios-xr-string {
                      length "1..32" {
                        description
                          "Access list specifying SSM group range";
                      }
                    }
                    must 'not(../disable)' {
                      tailf:xpath-root 3;
                    }
                    description
                      "Provide ACL that specifies non-standard SSM range";
                  }
                  container disable {
                    must 'not(../range)' {
                      tailf:xpath-root 3;
                    }
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    must 'interface-extended or source-nexthop or source-group' {
                      tailf:xpath-root 3;
                    }
                    presence "Indicates a hash node is configured.";
                    description
                      "Enter a hashing algorithm";
                    container interface-extended {
                      must 'not(../source-nexthop) and not(../source-group)' {
                        tailf:xpath-root 3;
                      }
                      presence "Indicates a interface-extended node is configured.";
                      description
                        "Enable interface extensions for non-unique next-hop addrs";
                    }
                    container source-nexthop {
                      must 'not(../interface-extended) and not(../source-group)' {
                        tailf:xpath-root 3;
                      }
                      presence "Indicates a source-nexthop node is configured.";
                      description
                        "Enable source with next-hop multipath hashing (better distribution)";
                    }
                    container source-group {
                      must 'not(../source-nexthop) and not(../interface-extended)' {
                        tailf:xpath-root 3;
                      }
                      presence "Indicates a source-group node is configured.";
                      description
                        "Enable source, group based multipath hashing (Compatible with IOS versions)";
                    }
                  }
                }
                container interfaces {
                  description
                    "PIM interface configuration subcommands";
                  list interface {
                    key "interface-name";
                    description
                      "Select an interface to configure";
                    leaf interface-name {
                      type xr:Interface-name;
                      description
                        "Select an interface to configure";
                    }
                    leaf dr-priority {
                      type uint32 {
                        range "0..4294967295" {
                          description
                            "Hello DR priority, preference given to larger value";
                        }
                      }
                      description
                        "PIM Hello DR priority";
                    }
                    leaf hello-interval {
                      type uint32 {
                        range "1..3600" {
                          description
                            "Hello interval in seconds";
                        }
                      }
                      description
                        "PIM neighbor Hello announcement interval";
                    }
                    leaf join-prune-interval {
                      type uint32 {
                        range "10..600" {
                          description
                            "Join-Prune interval in seconds";
                        }
                      }
                      description
                        "PIM periodic Join-Prune announcement interval";
                    }
                    leaf join-prune-mtu {
                      type uint32 {
                        range "576..65535" {
                          description
                            "MTU to use in bytes";
                        }
                      }
                      description
                        "MTU to use when sending PIM J/P packets";
                    }
                    leaf propagation-delay {
                      type uint32 {
                        range "100..32767" {
                          description
                            "Propagatoin delay in milliseconds";
                        }
                      }
                      description
                        "PIM Hello propagation delay";
                    }
                    leaf override-interval {
                      type uint32 {
                        range "400..65535" {
                          description
                            "Override interval in milliseconds";
                        }
                      }
                      description
                        "PIM Hello override interval";
                    }
                    container bsr-border {
                      presence "Indicates a bsr-border node is configured.";
                      description
                        "Do not fwd BSR messages on this interface";
                    }
                    container enable {
                      must 'not(../disable)' {
                        tailf:xpath-root 3;
                      }
                      presence "Indicates a enable node is configured.";
                      description
                        "Enable PIM processing on this interface";
                    }
                    container disable {
                      must 'not(../enable)' {
                        tailf:xpath-root 3;
                      }
                      presence "Indicates a disable node is configured.";
                      description
                        "Disable PIM processing on this interface";
                    }
                    leaf neighbor-filter {
                      type xr:Cisco-ios-xr-string {
                        length "1..1024" {
                          description
                            "Access list specifying neighbor address";
                        }
                      }
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type uint32 {
                            range "1..1100000" {
                              description
                                "Maximum number of allowed routes for this interface";
                            }
                          }
                          mandatory true;
                          description
                            "PIM downstream joined interfaces";
                        }
                        leaf threshold {
                          type uint32 {
                            range "1..1100000" {
                              description
                                "Threshold warning";
                            }
                          }
                          must '. <= ../maximum-route-interfaces' {
                            tailf:xpath-root 3;
                          }
                          description
                            "Threshold warning";
                        }
                        leaf access-list {
                          type xr:Cisco-ios-xr-string {
                            length "1..64" {
                              description
                                "Name of ACL that specifies to which routes to apply the maximum limit";
                            }
                          }
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type uint32 {
                          range "3..30000" {
                            description
                              "hello interval in milli-seconds";
                          }
                        }
                        description
                          "Hello interval";
                      }
                      leaf multiplier {
                        type uint32 {
                          range "2..50" {
                            description
                              "Detect multiplier";
                          }
                        }
                        description
                          "Detect multiplier";
                      }
                    }
                  }
                }
                container bsr {
                  description
                    "BSR Configurations";
                  container candidate-bsr {
                    presence "Indicates a candidate-bsr node is configured.";
                    description
                      "configure candidate BSR";
                    leaf address {
                      type inet:ipv6-address-no-zone;
                      mandatory true;
                      description
                        "IP address of configured BSR";
                    }
                    leaf hash-mask-len {
                      type uint32 {
                        range "0..128" {
                          description
                            "mask length";
                        }
                      }
                      mandatory true;
                      description
                        "BSR Hash Mask Length";
                    }
                    leaf priority {
                      type uint32 {
                        range "1..255" {
                          description
                            "priority";
                        }
                      }
                      mandatory true;
                      description
                        "BSR Priority";
                    }
                  }
                  container candidate-rps {
                    description
                      "BSR Candidate RP Configurations";
                    list candidate-rp {
                      must '(priority and interval) or (bidir/priority and bidir/interval)' {
                        tailf:xpath-root 3;
                      }
                      key "address";
                      description
                        "BSR Candidate RP Configurations";
                      leaf address {
                        type inet:ipv6-address-no-zone;
                        description
                          "BSR Candidate RP Configurations";
                      }
                      leaf group-list {
                        type xr:Cisco-ios-xr-string {
                          length "1..64" {
                            description
                              "access-list";
                          }
                        }
                        description
                          "Group List access-list";
                      }
                      leaf priority {
                        type uint32 {
                          range "1..255" {
                            description
                              "priority";
                          }
                        }
                        description
                          "C-RP Priority";
                      }
                      leaf interval {
                        type uint32 {
                          range "30..600" {
                            description
                              "interval in second";
                          }
                        }
                        description
                          "C-RP Advertisement interval";
                      }
                      container bidir {
                        description
                          "To specify group ranges as Bidir";
                        leaf group-list {
                          type xr:Cisco-ios-xr-string {
                            length "1..64" {
                              description
                                "access-list";
                            }
                          }
                          description
                            "Group List access-list";
                        }
                        leaf priority {
                          type uint32 {
                            range "1..255" {
                              description
                                "priority";
                            }
                          }
                          description
                            "C-RP Priority";
                        }
                        leaf interval {
                          type uint32 {
                            range "30..600" {
                              description
                                "interval in second";
                            }
                          }
                          description
                            "C-RP Advertisement interval";
                        }
                      }
                    }
                  }
                  container relay {
                    description
                      "BSR RP relay config";
                    container vrfs {
                      description
                        "vrf";
                      list vrf {
                        key "vrf-name";
                        description
                          "vrf";
                        leaf vrf-name {
                          type xr:Cisco-ios-xr-string {
                            length "1..1024" {
                              description
                                "vrf-name";
                            }
                          }
                          description
                            "vrf";
                        }
                        container listen {
                          presence "Indicates a listen node is configured.";
                          description
                            "Enable RP relay in listen mode";
                        }
                      }
                    }
                  }
                }
                container sr-p2mp-policies {
                  description
                    "Segment-routing P2MP policy";
                  list sr-p2mp-policy {
                    key "policy-name";
                    description
                      "Segment-routing P2MP policy";
                    leaf policy-name {
                      type xr:Cisco-ios-xr-string {
                        length "1..1024" {
                          description
                            "Name of the P2MP policy";
                        }
                      }
                      description
                        "Segment-routing P2MP policy";
                    }
                    container static-group {
                      description
                        "ipv6 static multicast group";
                      list group-address {
                        key "group-address";
                        description
                          "ipv6 static multicast group";
                        leaf group-address {
                          type inet:ipv6-address-no-zone;
                          description
                            "ipv6 static multicast group";
                        }
                        container group-address-only {
                          presence "Indicates a group-address-only node is configured.";
                          description
                            "Group-address without increment mask/source-address";
                        }
                        container group-address-inc-masks {
                          description
                            "Group-address with increment mask for group address";
                          list inc-mask {
                            key "group-mask-address";
                            description
                              "Increment mask for group address";
                            leaf group-mask-address {
                              type inet:ipv6-address-no-zone;
                              description
                                "Increment mask for group address";
                            }
                            leaf group-address-count {
                              type uint32 {
                                range "1..512" {
                                  description
                                    "No. of group addresses to join";
                                }
                              }
                              mandatory true;
                              description
                                "No. of group addresses to join";
                            }
                          }
                        }
                        container group-address-source-address {
                          description
                            "Group-address with source-address";
                          list source-address {
                            key "source-address";
                            description
                              "Source address to join";
                            leaf source-address {
                              type inet:ipv6-address-no-zone;
                              description
                                "Source address to join";
                            }
                          }
                        }
                        container group-address-inc-mask-source-address {
                          description
                            "Group-address with increment-mask and source-address";
                          list inc-mask {
                            key "group-mask-address source-address";
                            description
                              "Increment mask for group address";
                            leaf group-mask-address {
                              type inet:ipv6-address-no-zone;
                              description
                                "Increment mask for group address";
                            }
                            leaf source-address {
                              type inet:ipv6-address-no-zone;
                              description
                                "Source address to join";
                            }
                            leaf group-address-count {
                              type uint32 {
                                range "1..512" {
                                  description
                                    "No. of group addresses to join";
                                }
                              }
                              mandatory true;
                              description
                                "No. of group addresses to join";
                            }
                          }
                        }
                        container group-address-source-address-inc-mask {
                          description
                            "Group-address and source-address with increment-mask";
                          list inc-mask {
                            key "source-address source-mask-address";
                            description
                              "Increment mask for group address";
                            leaf source-address {
                              type inet:ipv6-address-no-zone;
                              description
                                "Source address to join";
                            }
                            leaf source-mask-address {
                              type inet:ipv6-address-no-zone;
                              description
                                "Increment mask for source address";
                            }
                            leaf source-address-count {
                              type uint32 {
                                range "1..512" {
                                  description
                                    "No. of source addresses to join";
                                }
                              }
                              mandatory true;
                              description
                                "No. of source addresses to join";
                            }
                          }
                        }
                        container group-inc-mask-source-inc-mask {
                          description
                            "Group-address with increment-mask and source-address with increment-mask";
                          list inc-mask {
                            key "group-mask-address source-address source-mask-address";
                            leaf group-mask-address {
                              type inet:ipv6-address-no-zone;
                              description
                                "Increment mask for group address";
                            }
                            leaf source-address {
                              type inet:ipv6-address-no-zone;
                              description
                                "Source address to join";
                            }
                            leaf source-mask-address {
                              type inet:ipv6-address-no-zone;
                              description
                                "Increment mask for source address";
                            }
                            leaf group-address-count {
                              type uint32 {
                                range "1..512" {
                                  description
                                    "No. of group addresses to join";
                                }
                              }
                              mandatory true;
                              description
                                "No. of group addresses to join";
                            }
                            leaf source-address-count {
                              type uint32 {
                                range "1..512" {
                                  description
                                    "No. of source addresses to join";
                                }
                              }
                              mandatory true;
                              description
                                "No. of source addresses to join";
                            }
                          }
                        }
                      }
                    }
                  }
                }
                container embedded-rp {
                  description
                    "Set Embedded RP processing support";
                  list ip-addresses {
                    key "ip-address";
                    description
                      "IP name or address of Rendezvous Point";
                    leaf ip-address {
                      type inet:ipv6-address-no-zone;
                      description
                        "IP name or address of Rendezvous Point";
                    }
                    leaf access-list-name {
                      type xr:Cisco-ios-xr-string {
                        length "1..1024" {
                          description
                            "Access list of groups that should map to given RP";
                        }
                      }
                      mandatory true;
                      description
                        "Access list of groups that should map to given RP";
                    }
                  }
                  container disable {
                    presence "Indicates a disable node is configured.";
                    description
                      "Disable Embedded RP processing";
                  }
                }
              }
            }
          }
        }
        container address-family {
          description
            "Enter Address Family command mode";
          container ipv4 {
            description
              "IPv4 Address Family";
            container rp-addresses {
              description
                "Configure Rendezvous Point";
              list rp-address {
                key "address";
                description
                  "Configure Rendezvous Point";
                leaf address {
                  type inet:ipv4-address-no-zone;
                  description
                    "Configure Rendezvous Point";
                }
                leaf access-list {
                  type xr:Cisco-ios-xr-string {
                    length "1..32" {
                      description
                        "Access list of groups that should map to given RP";
                    }
                  }
                  description
                    "Access list of groups that should map to given RP";
                }
                container override {
                  presence "Indicates a override node is configured.";
                  description
                    "Static RP config overrides auto-rp and BSR";
                }
              }
              container bidir {
                description
                  "Specify keyword bidir to configure a bidir RP";
                list rp-address {
                  key "address";
                  description
                    "Configure Rendezvous Point";
                  leaf address {
                    type inet:ipv4-address-no-zone;
                    description
                      "Configure Rendezvous Point";
                  }
                  leaf access-list {
                    type xr:Cisco-ios-xr-string {
                      length "1..32" {
                        description
                          "Access list of groups that should map to given RP";
                      }
                    }
                    description
                      "Access list of groups that should map to given RP";
                  }
                  container override {
                    presence "Indicates a override node is configured.";
                    description
                      "Static RP config overrides auto-rp and BSR";
                  }
                }
              }
            }
            leaf rp-static-deny {
              type xr:Cisco-ios-xr-string {
                length "1..32" {
                  description
                    "IP named access list";
                }
              }
              description
                "Configure static RP deny range";
            }
            leaf accept-register {
              type xr:Cisco-ios-xr-string {
                length "1..32" {
                  description
                    "IP named access list";
                }
              }
              description
                "Registers accept filter";
            }
            container suppress-data-registers {
              presence "Indicates a suppress-data-registers node is configured.";
              description
                "Suppress data registers after initial state setup";
            }
            leaf register-source {
              type xr:Interface-name;
              description
                "Source address to use for register messages";
            }
            container suppress-rpf-change-prunes {
              presence "Indicates a suppress-rpf-change-prunes node is configured.";
              description
                "Suppress prunes triggered as a result of RPF changes";
            }
            leaf neighbor-filter {
              type xr:Cisco-ios-xr-string {
                length "1..32" {
                  description
                    "IP named access list";
                }
              }
              description
                "Neighbor filter";
            }
            container convergence {
              description
                "Convergence related parameters";
              leaf rpf-conflict-join-delay {
                type uint32 {
                  range "0..15" {
                    description
                      "Delay in seconds";
                  }
                }
                description
                  "Delay in sending first join if RPF points to any downstream neighbor";
              }
              leaf link-down-prune-delay {
                type uint32 {
                  range "0..60" {
                    description
                      "Delay in seconds";
                  }
                }
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:Cisco-ios-xr-string {
                    length "1..32" {
                      description
                        "Access-list of threshold limited groups";
                    }
                  }
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type uint32 {
                  range "10..600" {
                    description
                      "Maximum time for PIM NSF mode in seconds";
                  }
                }
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type uint32 {
                range "1..3600" {
                  description
                    "Hello interval in seconds";
                }
              }
              description
                "Inherited by all interfaces : Hello interval in seconds";
            }
            leaf mdt-hello-interval {
              type uint32 {
                range "1..3600" {
                  description
                    "Hello interval in seconds";
                }
              }
              description
                "Hello interval for all MDT interfaces (seconds)";
            }
            leaf dr-priority {
              type uint32 {
                range "0..4294967295" {
                  description
                    "Hello DR priority, preference given to larger value";
                }
              }
              description
                "Inherited by all interfaces : PIM Hello DR priority";
            }
            leaf join-prune-interval {
              type uint32 {
                range "10..600" {
                  description
                    "Join-Prune interval in seconds";
                }
              }
              description
                "Inherited by all interfaces : Join-Prune interval";
            }
            leaf join-prune-mtu {
              type uint32 {
                range "576..65535" {
                  description
                    "Join-Prune MTU in bytes";
                }
              }
              description
                "Inherited by all interfaces : Join-Prune MTU";
            }
            leaf propagation-delay {
              type uint32 {
                range "100..32767" {
                  description
                    "Propagatoin delay in milliseconds";
                }
              }
              description
                "Inherited by all interfaces : PIM Hello Propagation delay";
            }
            leaf override-interval {
              type uint32 {
                range "400..65535" {
                  description
                    "Override interval in milliseconds";
                }
              }
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type uint32 {
                      range "1..200000" {
                        description
                          "Maximum PIM routes";
                      }
                    }
                    mandatory true;
                    description
                      "PIM routes for all VRFs";
                  }
                  leaf threshold {
                    type uint32 {
                      range "1..200000" {
                        description
                          "Threshold value";
                      }
                    }
                    must '. <= ../maximum-routes' {
                      tailf:xpath-root 3;
                    }
                    description
                      "Set threshold to print warning";
                  }
                }
                container route-interfaces {
                  presence "Indicates a route-interfaces node is configured.";
                  description
                    "PIM total interfaces on routes for all VRFs";
                  leaf maximum-route-interfaces {
                    type uint32 {
                      range "1..1100000" {
                        description
                          "Maximum PIM route-interfaces";
                      }
                    }
                    mandatory true;
                    description
                      "PIM total interfaces on routes for all VRFs";
                  }
                  leaf threshold {
                    type uint32 {
                      range "1..1100000" {
                        description
                          "Threshold value";
                      }
                    }
                    must '. <= ../maximum-route-interfaces' {
                      tailf:xpath-root 3;
                    }
                    description
                      "Set threshold to print warning";
                  }
                }
                container register-states {
                  presence "Indicates a register-states node is configured.";
                  description
                    "PIM source register states for all VRFs";
                  leaf maximum-register-states {
                    type uint32 {
                      range "0..75000" {
                        description
                          "Maximum PIM sparse-mode source register states";
                      }
                    }
                    mandatory true;
                    description
                      "PIM source register states for all VRFs";
                  }
                  leaf threshold {
                    type uint32 {
                      range "0..75000" {
                        description
                          "Threshold value";
                      }
                    }
                    must '. <= ../maximum-register-states' {
                      tailf:xpath-root 3;
                    }
                    description
                      "Set threshold to print warning";
                  }
                }
                container packet-queue {
                  description
                    "PIM Packet queue size in bytes";
                  leaf high-priority {
                    type uint32 {
                      range "0..2147483648" {
                        description
                          "Maximum PIM routes";
                      }
                    }
                    description
                      "PIM high priority packet queue size in bytes";
                  }
                  leaf low-priority {
                    type uint32 {
                      range "0..2147483648" {
                        description
                          "Maximum PIM routes";
                      }
                    }
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type uint32 {
                        range "1..10000" {
                          description
                            "Maximum PIM group-mapping learnt from BSR";
                        }
                      }
                      mandatory true;
                    }
                    leaf threshold {
                      type uint32 {
                        range "1..10000" {
                          description
                            "Threshold value";
                        }
                      }
                      must '. <= ../maximum-bsr' {
                        tailf:xpath-root 3;
                      }
                      description
                        "Set threshold to print warning";
                    }
                  }
                  container autorp {
                    presence "Indicates a autorp node is configured.";
                    description
                      "Learned through the Auto-RP distribution mechanism";
                    leaf maximum-autorp {
                      type uint32 {
                        range "1..10000" {
                          description
                            "Maximum PIM group mappings from Auto-RP mapping agent";
                        }
                      }
                      mandatory true;
                      description
                        "Learned through the Auto-RP distribution mechanism";
                    }
                    leaf threshold {
                      type uint32 {
                        range "1..10000" {
                          description
                            "Threshold value";
                        }
                      }
                      must '. <= ../maximum-autorp' {
                        tailf:xpath-root 3;
                      }
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type uint32 {
                        range "1..10000" {
                          description
                            "Maximum PIM BSR C-RP cache";
                        }
                      }
                      mandatory true;
                      description
                        "Set maximum number of C-RP cache in BSR";
                    }
                    leaf threshold {
                      type uint32 {
                        range "1..10000" {
                          description
                            "Threshold value";
                        }
                      }
                      must '. <= ../maximum-crp-cache' {
                        tailf:xpath-root 3;
                      }
                      description
                        "Set threshold to print warning";
                    }
                  }
                }
              }
            }
            container maximum {
              description
                "Maximum state limits";
              container routes {
                presence "Indicates a routes node is configured.";
                description
                  "PIM routes";
                leaf maximum-routes {
                  type uint32 {
                    range "1..200000" {
                      description
                        "Maximum PIM routes";
                    }
                  }
                  mandatory true;
                  description
                    "PIM routes";
                }
                leaf threshold {
                  type uint32 {
                    range "1..200000" {
                      description
                        "Threshold value";
                    }
                  }
                  must '. <= ../maximum-routes' {
                    tailf:xpath-root 3;
                  }
                  description
                    "Set threshold to print warning";
                }
              }
              container route-interfaces {
                presence "Indicates a route-interfaces node is configured.";
                description
                  "PIM total number of interfaces on all routes";
                leaf maximum-route-interfaces {
                  type uint32 {
                    range "1..1100000" {
                      description
                        "Maximum PIM route-interfaces";
                    }
                  }
                  mandatory true;
                  description
                    "PIM total number of interfaces on all routes";
                }
                leaf threshold {
                  type uint32 {
                    range "1..1100000" {
                      description
                        "Threshold value";
                    }
                  }
                  must '. <= ../maximum-route-interfaces' {
                    tailf:xpath-root 3;
                  }
                  description
                    "Set threshold to print warning";
                }
              }
              container register-states {
                presence "Indicates a register-states node is configured.";
                description
                  "PIM source register states";
                leaf maximum-register-states {
                  type uint32 {
                    range "0..75000" {
                      description
                        "Maximum PIM sparse-mode source register states";
                    }
                  }
                  mandatory true;
                  description
                    "PIM source register states";
                }
                leaf threshold {
                  type uint32 {
                    range "0..75000" {
                      description
                        "Threshold value";
                    }
                  }
                  must '. <= ../maximum-register-states' {
                    tailf:xpath-root 3;
                  }
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type uint32 {
                      range "1..10000" {
                        description
                          "Maximum PIM group mappings from elected BSR";
                      }
                    }
                    mandatory true;
                    description
                      "Learned through the BSR distribution mechanism";
                  }
                  leaf threshold {
                    type uint32 {
                      range "1..10000" {
                        description
                          "Threshold value";
                      }
                    }
                    must '. <= ../maximum-bsr' {
                      tailf:xpath-root 3;
                    }
                    description
                      "Set threshold to print warning";
                  }
                }
                container autorp {
                  presence "Indicates a autorp node is configured.";
                  description
                    "Learned through the Auto-RP distribution mechanism";
                  leaf maximum-autorp {
                    type uint32 {
                      range "1..10000" {
                        description
                          "Maximum PIM group mappings from Auto-RP mapping agent";
                      }
                    }
                    mandatory true;
                    description
                      "Learned through the Auto-RP distribution mechanism";
                  }
                  leaf threshold {
                    type uint32 {
                      range "1..10000" {
                        description
                          "Threshold value";
                      }
                    }
                    must '. <= ../maximum-autorp' {
                      tailf:xpath-root 3;
                    }
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type uint32 {
                      range "1..10000" {
                        description
                          "Maximum number of C-RP cache";
                      }
                    }
                    mandatory true;
                    description
                      "Set maximum number of C-RP cache in BSR";
                  }
                  leaf threshold {
                    type uint32 {
                      range "1..10000" {
                        description
                          "Threshold value";
                      }
                    }
                    must '. <= ../maximum-crp-cache' {
                      tailf:xpath-root 3;
                    }
                    description
                      "Set threshold to print warning";
                  }
                }
              }
            }
            leaf convergence-timeout {
              type uint32 {
                range "1800..2400" {
                  description
                    "Unicast convergence fallback timer in seconds";
                }
              }
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf-vector-injects {
              description
                "inject RPF vector";
              list inject {
                must 'rpf-vector' {
                  tailf:xpath-root 3;
                }
                key "source-address masklen";
                description
                  "inject RPF vector";
                leaf source-address {
                  type inet:ipv4-address-no-zone;
                  description
                    "inject RPF vector";
                }
                leaf masklen {
                  type uint32 {
                    range "0..32" {
                      description
                        "masklen";
                    }
                  }
                  description
                    "masklen";
                }
                leaf-list rpf-vector {
                  type inet:ipv4-address-no-zone;
                  max-elements 22;
                  description
                    "configure this node";
                }
              }
            }
            container explicit-rpf-vector {
              description
                "Enable Explicit PIM RPF Vector";
              container injects {
                description
                  "inject Explicit RPF vector";
                list inject {
                  must 'rpf-vector' {
                    tailf:xpath-root 3;
                  }
                  key "source-address masklen";
                  description
                    "inject Explicit RPF vector";
                  leaf source-address {
                    type inet:ipv4-address-no-zone;
                    description
                      "inject Explicit RPF vector";
                  }
                  leaf masklen {
                    type uint32 {
                      range "0..32" {
                        description
                          "masklen";
                      }
                    }
                    description
                      "masklen";
                  }
                  leaf-list rpf-vector {
                    type inet:ipv4-address-no-zone;
                    max-elements 22;
                    description
                      "configure this node";
                  }
                }
              }
            }
            container rpf {
              description
                "RPF commands";
              container topology {
                description
                  "Select RPF topology";
                leaf route-policy {
                  type xr:Route-policy-name;
                  description
                    "Route policy to select RPF topology";
                }
              }
            }
            container mdt {
              description
                "Multicast Distribution Tree commands";
              leaf neighbor-filter {
                type xr:Cisco-ios-xr-string {
                  length "1..32" {
                    description
                      "IP named access list";
                  }
                }
                description
                  "Neighbor filter";
              }
              container data {
                description
                  "Data MDT Options";
                leaf switchover-interval {
                  type uint32 {
                    range "3..60" {
                      description
                        "Interval value in seconds";
                    }
                  }
                  description
                    "Data MDT switchover interval";
                }
                leaf announce-interval {
                  type uint32 {
                    range "3..120" {
                      description
                        "Interval value in seconds";
                    }
                  }
                  description
                    "Periodic Data MDT Join TLV interval";
                }
                leaf max-aggregation {
                  type uint32 {
                    range "1..16777215" {
                      description
                        "Aggregation value";
                    }
                  }
                  description
                    "Data MDT max-aggregation";
                }
              }
              container c-multicast-routing {
                presence "Indicates a c-multicast-routing node is configured.";
                description
                  "MVPN customer routing commands";
                leaf type {
                  type enumeration {
                    enum "pim" {
                      value 1;
                      description
                        "PIM customer multicast routing";
                    }
                    enum "bgp" {
                      value 2;
                      description
                        "BGP customer multicast routing";
                    }
                  }
                  mandatory true;
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  when "../type != 'pim'" {
                    tailf:xpath-root 3;
                  }
                  description
                    "PIM Hellos over MDT";
                  container enable {
                    presence "Indicates a enable node is configured.";
                    description
                      "Enable PIM Hellos over MDT";
                  }
                }
                leaf shared-tree-prune-delay {
                  type uint32 {
                    range "0..1800" {
                      description
                        "Delay in seconds.";
                    }
                  }
                  description
                    "Delay before pruning I-S PMSI from S,G when SA received";
                }
                leaf source-tree-prune-delay {
                  type uint32 {
                    range "0..300" {
                      description
                        "Delay in seconds.";
                    }
                  }
                  description
                    "Delay before removing PMSI from olist after BGP withdrawal";
                }
                container migration {
                  presence "Indicates a migration node is configured.";
                  description
                    "customer routing migration";
                  leaf route-policy {
                    type xr:Route-policy-name;
                    description
                      "Route policy to select customer routing";
                  }
                }
                container unicast-reachability {
                  description
                    "Control addition of Extended Communities to Unicast VPN-IP routes";
                  container connector {
                    description
                      "Enable/Disable Connector";
                    container disable {
                      must 'not(../enable)' {
                        tailf:xpath-root 3;
                      }
                      presence "Indicates a disable node is configured.";
                      description
                        "Disable Connector Attribute";
                    }
                    container enable {
                      must 'not(../disable)' {
                        tailf:xpath-root 3;
                      }
                      presence "Indicates a enable node is configured.";
                      description
                        "Enable Connector Attribute";
                    }
                  }
                  container source-as {
                    description
                      "Enable/Disable Source AS";
                    container disable {
                      must 'not(../enable)' {
                        tailf:xpath-root 3;
                      }
                      presence "Indicates a disable node is configured.";
                      description
                        "Disable Source-AS Attribute";
                    }
                    container enable {
                      must 'not(../disable)' {
                        tailf:xpath-root 3;
                      }
                      presence "Indicates a enable node is configured.";
                      description
                        "Enable Source-AS Attribute";
                    }
                  }
                  container vrf-route-import {
                    description
                      "Enable/Disable VRF Route Import";
                    container disable {
                      must 'not(../enable)' {
                        tailf:xpath-root 3;
                      }
                      presence "Indicates a disable node is configured.";
                      description
                        "Disable VRF Route Import Attribute";
                    }
                    container enable {
                      must 'not(../disable)' {
                        tailf:xpath-root 3;
                      }
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:Cisco-ios-xr-string {
                  length "1..32" {
                    description
                      "ACL Name for rp-list";
                  }
                }
                description
                  "Access-list for allowed RP addresses";
              }
              leaf group-list {
                type xr:Cisco-ios-xr-string {
                  length "1..32" {
                    description
                      "Access name for group-list";
                  }
                }
                description
                  "Access-list for allowed group ranges";
              }
            }
            container sg-expiry-timer {
              presence "Indicates a sg-expiry-timer node is configured.";
              description
                "Configure SG expiry timer";
              leaf sg-expiry-timer-value {
                type uint32 {
                  range "40..57600" {
                    description
                      "Duration of the expiry timer interval, in seconds";
                  }
                }
                mandatory true;
                description
                  "Configure SG expiry timer";
              }
              leaf sg-list {
                type xr:Cisco-ios-xr-string {
                  length "1..32" {
                    description
                      "IP named access list";
                  }
                }
                description
                  "Access-list of (S,G) routes for which expiry timer is applicable";
              }
            }
            container ssm {
              description
                "Configure a group range for Source-Specific use";
              leaf range {
                type xr:Cisco-ios-xr-string {
                  length "1..32" {
                    description
                      "Access list specifying SSM group range";
                  }
                }
                must 'not(../disable)' {
                  tailf:xpath-root 3;
                }
                description
                  "Provide ACL that specifies non-standard SSM range";
              }
              container disable {
                must 'not(../range)' {
                  tailf:xpath-root 3;
                }
                presence "Indicates a disable node is configured.";
                description
                  "Disable use of all SSM group ranges";
              }
              container allow-override {
                presence "Indicates a allow-override node is configured.";
                description
                  "Allow SSM ranges to be overridden by more specific ranges";
              }
            }
            container rpf-redirect {
              description
                "Route policy for rpf-redirect bundles";
              leaf route-policy {
                type xr:Route-policy-name;
                description
                  "Bandwidth assigment (kbps) for SG routes";
              }
            }
            container multipath {
              presence "Indicates a multipath node is configured.";
              description
                "Enable equal-cost multipath routing";
              container hash {
                must 'source or source-nexthop or source-group' {
                  tailf:xpath-root 3;
                }
                presence "Indicates a hash node is configured.";
                description
                  "Enter a hashing algorithm";
                container source {
                  must 'not(../source-nexthop) and not(../source-group)' {
                    tailf:xpath-root 3;
                  }
                  presence "Indicates a source node is configured.";
                  description
                    "Enable source based multipath hashing (Compatible with IOS versions)";
                }
                container source-nexthop {
                  must 'not(../source) and not(../source-group)' {
                    tailf:xpath-root 3;
                  }
                  presence "Indicates a source-nexthop node is configured.";
                  description
                    "Enable source with next-hop multipath hashing (better distribution)";
                }
                container source-group {
                  must 'not(../source-nexthop) and not(../source)' {
                    tailf:xpath-root 3;
                  }
                  presence "Indicates a source-group node is configured.";
                  description
                    "Enable source, group based multipath hashing (Compatible with IOS versions)";
                }
              }
            }
            container auto-rp {
              description
                "Auto-RP Commands";
              container candidate-rps {
                description
                  "Configure as a Candidate RP";
                list candidate-rp {
                  must 'scope or bidir/scope' {
                    tailf:xpath-root 3;
                  }
                  key "interface-name";
                  description
                    "Candidate RP Configurations";
                  leaf interface-name {
                    type xr:Interface-name;
                    description
                      "Candidate RP Configurations";
                  }
                  leaf scope {
                    type uint32 {
                      range "1..255" {
                        description
                          "TTL in hops";
                      }
                    }
                    must '../group-list and ../interval' {
                      tailf:xpath-root 3;
                    }
                    description
                      "TTL for the announcement";
                  }
                  leaf group-list {
                    type xr:Cisco-ios-xr-string {
                      length "1..64" {
                        description
                          "Access-list of groups to be RP for";
                      }
                    }
                    description
                      "Be a candidate RP for groups specified by the acl";
                  }
                  leaf interval {
                    type uint32 {
                      range "1..600" {
                        description
                          "interval in second";
                      }
                    }
                    description
                      "time between announcements <in seconds>";
                  }
                  container bidir {
                    description
                      "to specify group ranges as bidir, default is pim-sm";
                    leaf scope {
                      type uint32 {
                        range "1..255" {
                          description
                            "TTL in hops";
                        }
                      }
                      must '../group-list and ../interval' {
                        tailf:xpath-root 3;
                      }
                      description
                        "TTL for the announcement";
                    }
                    leaf group-list {
                      type xr:Cisco-ios-xr-string {
                        length "1..64" {
                          description
                            "Access-list of groups to be RP for";
                        }
                      }
                      description
                        "Be a candidate RP for groups specified by the acl";
                    }
                    leaf interval {
                      type uint32 {
                        range "1..600" {
                          description
                            "interval in second";
                        }
                      }
                      description
                        "time between announcements <in seconds>";
                    }
                  }
                }
              }
              container mapping-agent {
                presence "Indicates a mapping-agent node is configured.";
                description
                  "Configure as a Mapping Agent";
                leaf interface-name {
                  type xr:Interface-name;
                  mandatory true;
                  description
                    "Candidate RP Configurations";
                }
                leaf scope {
                  type uint32 {
                    range "1..255" {
                      description
                        "TTL in hops";
                    }
                  }
                  mandatory true;
                  description
                    "TTL for the announcement";
                }
                leaf interval {
                  type uint32 {
                    range "1..600" {
                      description
                        "interval in second";
                    }
                  }
                  mandatory true;
                  description
                    "number of seconds between discovery messages";
                }
              }
              container listen {
                description
                  "RP discovery through AUTORP protocol";
                container disable {
                  presence "Indicates a disable node is configured.";
                  description
                    "Disable RP discovery through the AUTORP protocol";
                }
              }
              container relay {
                description
                  "relay";
                container vrfs {
                  description
                    "vrf";
                  list vrf {
                    key "vrf-name";
                    description
                      "vrf";
                    leaf vrf-name {
                      type xr:Cisco-ios-xr-string {
                        length "1..32" {
                          description
                            "vrf-name";
                        }
                      }
                      description
                        "vrf";
                    }
                    container listen {
                      presence "Indicates a listen node is configured.";
                      description
                        "Enable RP relay in listen mode";
                    }
                  }
                }
              }
            }
            container interface {
              description
                "PIM interface configuration subcommands";
              container interfaces {
                description
                  "Select an interface to configure";
                list interface {
                  key "interface-name";
                  description
                    "Select an interface to configure";
                  leaf interface-name {
                    type xr:Interface-name;
                    description
                      "Select an interface to configure";
                  }
                  leaf dr-priority {
                    type uint32 {
                      range "0..4294967295" {
                        description
                          "Hello DR priority, preference given to larger value";
                      }
                    }
                    description
                      "PIM Hello DR priority";
                  }
                  leaf hello-interval {
                    type uint32 {
                      range "1..3600" {
                        description
                          "Hello interval in seconds";
                      }
                    }
                    description
                      "PIM neighbor Hello announcement interval";
                  }
                  leaf join-prune-interval {
                    type uint32 {
                      range "10..600" {
                        description
                          "Join-Prune interval in seconds";
                      }
                    }
                    description
                      "PIM periodic Join-Prune announcement interval";
                  }
                  leaf join-prune-mtu {
                    type uint32 {
                      range "576..65535" {
                        description
                          "MTU to use in bytes";
                      }
                    }
                    description
                      "MTU to use when sending PIM J/P packets";
                  }
                  leaf propagation-delay {
                    type uint32 {
                      range "100..32767" {
                        description
                          "Propagatoin delay in milliseconds";
                      }
                    }
                    description
                      "PIM Hello propagation delay";
                  }
                  leaf override-interval {
                    type uint32 {
                      range "400..65535" {
                        description
                          "Override interval in milliseconds";
                      }
                    }
                    description
                      "PIM Hello override interval";
                  }
                  container bsr-border {
                    presence "Indicates a bsr-border node is configured.";
                    description
                      "Do not fwd BSR messages on this interface";
                  }
                  container enable {
                    must 'not(../disable)' {
                      tailf:xpath-root 3;
                    }
                    presence "Indicates a enable node is configured.";
                    description
                      "Enable PIM processing on this interface";
                  }
                  container disable {
                    must 'not(../enable)' {
                      tailf:xpath-root 3;
                    }
                    presence "Indicates a disable node is configured.";
                    description
                      "Disable PIM processing on this interface";
                  }
                  leaf neighbor-filter {
                    type xr:Cisco-ios-xr-string {
                      length "1..1024" {
                        description
                          "Access list specifying neighbor address";
                      }
                    }
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type uint32 {
                          range "1..1100000" {
                            description
                              "Maximum number of allowed routes for this interface";
                          }
                        }
                        mandatory true;
                        description
                          "PIM downstream joined interfaces";
                      }
                      leaf threshold {
                        type uint32 {
                          range "1..1100000" {
                            description
                              "Threshold warning";
                          }
                        }
                        must '. <= ../maximum-route-interfaces' {
                          tailf:xpath-root 3;
                        }
                        description
                          "Threshold warning";
                      }
                      leaf access-list {
                        type xr:Cisco-ios-xr-string {
                          length "1..64" {
                            description
                              "Name of ACL that specifies to which routes to apply the maximum limit";
                          }
                        }
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type uint32 {
                        range "3..30000" {
                          description
                            "hello interval in milli-seconds";
                        }
                      }
                      description
                        "Hello interval";
                    }
                    leaf multiplier {
                      type uint32 {
                        range "2..50" {
                          description
                            "Detect multiplier";
                        }
                      }
                      description
                        "Detect multiplier";
                    }
                  }
                  container rpf-redirect {
                    presence "Indicates a rpf-redirect node is configured.";
                    description
                      "RPF redirect bundle configuration";
                    leaf bundle {
                      type xr:Cisco-ios-xr-string {
                        length "1..32" {
                          description
                            "Bundle name";
                        }
                      }
                      mandatory true;
                      description
                        "Bundle name";
                    }
                    leaf bandwidth {
                      type uint32 {
                        range "0..100000000" {
                          description
                            "Interface bandwidth in Kbps";
                        }
                      }
                      description
                        "Interface bandwidth in Kbps";
                    }
                    leaf threshold {
                      type uint32 {
                        range "0..100000000" {
                          description
                            "Bandwidth threshold in Kbps";
                        }
                      }
                      must '../bandwidth' {
                        tailf:xpath-root 3;
                      }
                      description
                        "Bandwidth threshold in Kbps";
                    }
                  }
                }
              }
            }
            container bsr {
              description
                "BSR Configurations";
              container candidate-bsr {
                presence "Indicates a candidate-bsr node is configured.";
                description
                  "configure candidate BSR";
                leaf address {
                  type inet:ipv4-address-no-zone;
                  mandatory true;
                  description
                    "IP address of configured BSR";
                }
                leaf hash-mask-len {
                  type uint32 {
                    range "0..32" {
                      description
                        "mask length";
                    }
                  }
                  mandatory true;
                  description
                    "BSR Hash Mask Length";
                }
                leaf priority {
                  type uint32 {
                    range "1..255" {
                      description
                        "priority";
                    }
                  }
                  mandatory true;
                  description
                    "BSR Priority";
                }
              }
              container candidate-rps {
                description
                  "BSR Candidate RP Configurations";
                list candidate-rp {
                  must '(priority and interval) or (bidir/priority and bidir/interval)' {
                    tailf:xpath-root 3;
                  }
                  key "address";
                  description
                    "BSR Candidate RP Configurations";
                  leaf address {
                    type inet:ipv4-address-no-zone;
                    description
                      "BSR Candidate RP Configurations";
                  }
                  leaf group-list {
                    type xr:Cisco-ios-xr-string {
                      length "1..64" {
                        description
                          "access-list";
                      }
                    }
                    description
                      "Group List access-list";
                  }
                  leaf priority {
                    type uint32 {
                      range "1..255" {
                        description
                          "priority";
                      }
                    }
                    description
                      "C-RP Priority";
                  }
                  leaf interval {
                    type uint32 {
                      range "30..600" {
                        description
                          "interval in second";
                      }
                    }
                    description
                      "C-RP Advertisement interval";
                  }
                  container bidir {
                    description
                      "To specify group ranges as Bidir";
                    leaf group-list {
                      type xr:Cisco-ios-xr-string {
                        length "1..64" {
                          description
                            "access-list";
                        }
                      }
                      description
                        "Group List access-list";
                    }
                    leaf priority {
                      type uint32 {
                        range "1..255" {
                          description
                            "priority";
                        }
                      }
                      description
                        "C-RP Priority";
                    }
                    leaf interval {
                      type uint32 {
                        range "30..600" {
                          description
                            "interval in second";
                        }
                      }
                      description
                        "C-RP Advertisement interval";
                    }
                  }
                }
              }
              container relay {
                description
                  "BSR RP relay config";
                container vrfs {
                  description
                    "vrf";
                  list vrf {
                    key "vrf-name";
                    description
                      "vrf";
                    leaf vrf-name {
                      type xr:Cisco-ios-xr-string {
                        length "1..1024" {
                          description
                            "vrf-name";
                        }
                      }
                      description
                        "vrf";
                    }
                    container listen {
                      presence "Indicates a listen node is configured.";
                      description
                        "Enable RP relay in listen mode";
                    }
                  }
                }
              }
            }
            container mofrr {
              presence "Indicates a mofrr node is configured.";
              description
                "PIM Mofrr";
              leaf flow {
                type string {
                  length "1..1024" {
                    description
                      "Access list specifying SGs that should do MOFRR with hardware switchover triggers";
                  }
                }
                description
                  "Multicast Only FRR";
              }
              leaf rib {
                type string {
                  length "1..1024" {
                    description
                      "Access list specifying SGs that should do MOFRR with RIB events as switchover triggers";
                  }
                }
                description
                  "Use the rib keyword to restrict switchover triggers to RIB events";
              }
              container non-revertive {
                presence "Indicates a non-revertive node is configured.";
                description
                  "Non-revertive MoFRR";
              }
              container clone {
                description
                  "Use the clone keyword to clone";
                container joins {
                  description
                    "Use the join keyword to clone S,G as S1,G joins and S2,G joins";
                  list join {
                    must 'to' {
                      tailf:xpath-root 3;
                    }
                    key "address";
                    description
                      "Use the join keyword to clone S,G as S1,G joins as S2,G joins";
                    leaf address {
                      type inet:ipv4-address-no-zone;
                      description
                        "Source S";
                    }
                    list to {
                      must 'and' {
                        tailf:xpath-root 3;
                      }
                      key "address";
                      description
                        "to";
                      leaf address {
                        type inet:ipv4-address-no-zone;
                        description
                          "Source S1";
                      }
                      list and {
                        must 'masklen' {
                          tailf:xpath-root 3;
                        }
                        key "address";
                        description
                          "and";
                        leaf address {
                          type inet:ipv4-address-no-zone;
                          description
                            "Source S2";
                        }
                        list masklen {
                          key "mask-length";
                          description
                            "masklen";
                          leaf mask-length {
                            type uint32 {
                              range "0..32" {
                                description
                                  "masklen";
                              }
                            }
                            description
                              "masklen";
                          }
                        }
                      }
                    }
                  }
                }
                container sources {
                  description
                    "Use the source keyword to clone S,G as S1,G traffic and S2,G traffic";
                  list source {
                    must 'to' {
                      tailf:xpath-root 3;
                    }
                    key "address";
                    description
                      "Use the source keyword to clone S,G as S1,G traffic and S2,G traffic";
                    leaf address {
                      type inet:ipv4-address-no-zone;
                      description
                        "Source S";
                    }
                    list to {
                      must 'and' {
                        tailf:xpath-root 3;
                      }
                      key "address";
                      description
                        "to";
                      leaf address {
                        type inet:ipv4-address-no-zone;
                        description
                          "Source S1";
                      }
                      list and {
                        must 'masklen' {
                          tailf:xpath-root 3;
                        }
                        key "address";
                        description
                          "and";
                        leaf address {
                          type inet:ipv4-address-no-zone;
                          description
                            "Source S2";
                        }
                        list masklen {
                          key "mask-length";
                          description
                            "masklen";
                          leaf mask-length {
                            type uint32 {
                              range "0..32" {
                                description
                                  "masklen";
                              }
                            }
                            description
                              "masklen";
                          }
                        }
                      }
                    }
                  }
                }
              }
            }
            container sr-p2mp-policies {
              description
                "Segment-routing P2MP policy";
              list sr-p2mp-policy {
                key "sr-p2mp-policy-id";
                description
                  "Segment-routing P2MP policy";
                leaf sr-p2mp-policy-id {
                  type xr:Cisco-ios-xr-string {
                    length "1..1024" {
                      description
                        "Name of the P2MP policy";
                    }
                  }
                  description
                    "Segment-routing P2MP policy";
                }
                container static-group {
                  description
                    "ipv4 static multicast group";
                  list group-address {
                    key "group-address";
                    description
                      "ipv4 static multicast group";
                    leaf group-address {
                      type inet:ipv4-address-no-zone;
                      description
                        "ipv4 static multicast group";
                    }
                    container group-address-only {
                      presence "Indicates a group-address-only node is configured.";
                      description
                        "Group-address without increment mask/source-address";
                    }
                    container group-address-inc-masks {
                      description
                        "Group-address with increment mask for group address";
                      list inc-mask {
                        key "group-mask-address";
                        description
                          "Increment mask for group address";
                        leaf group-mask-address {
                          type inet:ipv4-address-no-zone;
                          description
                            "Increment mask for group address";
                        }
                        leaf group-address-count {
                          type uint32 {
                            range "1..512" {
                              description
                                "No. of group addresses to join";
                            }
                          }
                          mandatory true;
                          description
                            "No. of group addresses to join";
                        }
                      }
                    }
                    container group-address-source-address {
                      description
                        "Group-address with source-address";
                      list source-address {
                        key "source-address";
                        description
                          "Source address to join";
                        leaf source-address {
                          type inet:ipv4-address-no-zone;
                          description
                            "Source address to join";
                        }
                      }
                    }
                    container group-address-inc-mask-source-address {
                      description
                        "Group-address with increment-mask and source-address";
                      list inc-mask {
                        key "group-mask-address source-address";
                        description
                          "Increment mask for group address";
                        leaf group-mask-address {
                          type inet:ipv4-address-no-zone;
                          description
                            "Increment mask for group address";
                        }
                        leaf source-address {
                          type inet:ipv4-address-no-zone;
                          description
                            "Source address to join";
                        }
                        leaf group-address-count {
                          type uint32 {
                            range "1..512" {
                              description
                                "No. of group addresses to join";
                            }
                          }
                          mandatory true;
                          description
                            "No. of group addresses to join";
                        }
                      }
                    }
                    container group-address-source-address-inc-mask {
                      description
                        "Group-address and source-address with increment-mask";
                      list inc-mask {
                        key "source-address source-mask-address";
                        description
                          "Increment mask for group address";
                        leaf source-address {
                          type inet:ipv4-address-no-zone;
                          description
                            "Source address to join";
                        }
                        leaf source-mask-address {
                          type inet:ipv4-address-no-zone;
                          description
                            "Increment mask for source address";
                        }
                        leaf source-address-count {
                          type uint32 {
                            range "1..512" {
                              description
                                "No. of source addresses to join";
                            }
                          }
                          mandatory true;
                          description
                            "No. of source addresses to join";
                        }
                      }
                    }
                    container group-inc-mask-source-inc-mask {
                      description
                        "Group-address with increment-mask and source-address with increment-mask";
                      list inc-mask {
                        key "group-mask-address source-address source-mask-address";
                        leaf group-mask-address {
                          type inet:ipv4-address-no-zone;
                          description
                            "Increment mask for group address";
                        }
                        leaf source-address {
                          type inet:ipv4-address-no-zone;
                          description
                            "Source address to join";
                        }
                        leaf source-mask-address {
                          type inet:ipv4-address-no-zone;
                          description
                            "Increment mask for source address";
                        }
                        leaf group-address-count {
                          type uint32 {
                            range "1..512" {
                              description
                                "No. of group addresses to join";
                            }
                          }
                          mandatory true;
                          description
                            "No. of group addresses to join";
                        }
                        leaf source-address-count {
                          type uint32 {
                            range "1..512" {
                              description
                                "No. of source addresses to join";
                            }
                          }
                          mandatory true;
                          description
                            "No. of source addresses to join";
                        }
                      }
                    }
                  }
                }
              }
            }
          }
          container ipv6 {
            description
              "IPv6 Address Family";
            container rp-addresses {
              description
                "Configure Rendezvous Point";
              list rp-address {
                key "address";
                description
                  "Configure Rendezvous Point";
                leaf address {
                  type inet:ipv6-address-no-zone;
                  description
                    "Configure Rendezvous Point";
                }
                leaf access-list {
                  type xr:Cisco-ios-xr-string {
                    length "1..32" {
                      description
                        "Access list of groups that should map to given RP";
                    }
                  }
                  description
                    "Access list of groups that should map to given RP";
                }
                container override {
                  presence "Indicates a override node is configured.";
                  description
                    "Static RP config overrides auto-rp and BSR";
                }
              }
              container bidir {
                description
                  "Specify keyword bidir to configure a bidir RP";
                list rp-address {
                  key "address";
                  description
                    "Configure Rendezvous Point";
                  leaf address {
                    type inet:ipv6-address-no-zone;
                    description
                      "Configure Rendezvous Point";
                  }
                  leaf access-list {
                    type xr:Cisco-ios-xr-string {
                      length "1..32" {
                        description
                          "Access list of groups that should map to given RP";
                      }
                    }
                    description
                      "Access list of groups that should map to given RP";
                  }
                  container override {
                    presence "Indicates a override node is configured.";
                    description
                      "Static RP config overrides auto-rp and BSR";
                  }
                }
              }
            }
            leaf rp-static-deny {
              type xr:Cisco-ios-xr-string {
                length "1..32" {
                  description
                    "IP named access list";
                }
              }
              description
                "Configure static RP deny range";
            }
            leaf accept-register {
              type xr:Cisco-ios-xr-string {
                length "1..32" {
                  description
                    "IP named access list";
                }
              }
              description
                "Registers accept filter";
            }
            container suppress-data-registers {
              presence "Indicates a suppress-data-registers node is configured.";
              description
                "Suppress data registers after initial state setup";
            }
            leaf register-source {
              type xr:Interface-name;
              description
                "Source address to use for register messages";
            }
            container suppress-rpf-change-prunes {
              presence "Indicates a suppress-rpf-change-prunes node is configured.";
              description
                "Suppress prunes triggered as a result of RPF changes";
            }
            leaf neighbor-filter {
              type xr:Cisco-ios-xr-string {
                length "1..32" {
                  description
                    "IP named access list";
                }
              }
              description
                "Neighbor filter";
            }
            container convergence {
              description
                "Convergence related parameters";
              leaf rpf-conflict-join-delay {
                type uint32 {
                  range "0..15" {
                    description
                      "Delay in seconds";
                  }
                }
                description
                  "Delay in sending first join if RPF points to any downstream neighbor";
              }
              leaf link-down-prune-delay {
                type uint32 {
                  range "0..60" {
                    description
                      "Delay in seconds";
                  }
                }
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:Cisco-ios-xr-string {
                    length "1..32" {
                      description
                        "Access-list of threshold limited groups";
                    }
                  }
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type uint32 {
                  range "10..600" {
                    description
                      "Maximum time for PIM NSF mode in seconds";
                  }
                }
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type uint32 {
                range "1..3600" {
                  description
                    "Hello interval in seconds";
                }
              }
              description
                "Inherited by all interfaces : Hello interval in seconds";
            }
            leaf mdt-hello-interval {
              type uint32 {
                range "1..3600" {
                  description
                    "Hello interval in seconds";
                }
              }
              description
                "Hello interval for all MDT interfaces (seconds)";
            }
            leaf dr-priority {
              type uint32 {
                range "0..4294967295" {
                  description
                    "Hello DR priority, preference given to larger value";
                }
              }
              description
                "Inherited by all interfaces : PIM Hello DR priority";
            }
            leaf join-prune-interval {
              type uint32 {
                range "10..600" {
                  description
                    "Join-Prune interval in seconds";
                }
              }
              description
                "Inherited by all interfaces : Join-Prune interval";
            }
            leaf join-prune-mtu {
              type uint32 {
                range "576..65535" {
                  description
                    "Join-Prune MTU in bytes";
                }
              }
              description
                "Inherited by all interfaces : Join-Prune MTU";
            }
            leaf propagation-delay {
              type uint32 {
                range "100..32767" {
                  description
                    "Propagatoin delay in milliseconds";
                }
              }
              description
                "Inherited by all interfaces : PIM Hello Propagation delay";
            }
            leaf override-interval {
              type uint32 {
                range "400..65535" {
                  description
                    "Override interval in milliseconds";
                }
              }
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type uint32 {
                      range "1..200000" {
                        description
                          "Maximum PIM routes";
                      }
                    }
                    mandatory true;
                    description
                      "PIM routes for all VRFs";
                  }
                  leaf threshold {
                    type uint32 {
                      range "1..200000" {
                        description
                          "Threshold value";
                      }
                    }
                    must '. <= ../maximum-routes' {
                      tailf:xpath-root 3;
                    }
                    description
                      "Set threshold to print warning";
                  }
                }
                container route-interfaces {
                  presence "Indicates a route-interfaces node is configured.";
                  description
                    "PIM total interfaces on routes for all VRFs";
                  leaf maximum-route-interfaces {
                    type uint32 {
                      range "1..1100000" {
                        description
                          "Maximum PIM route-interfaces";
                      }
                    }
                    mandatory true;
                    description
                      "PIM total interfaces on routes for all VRFs";
                  }
                  leaf threshold {
                    type uint32 {
                      range "1..1100000" {
                        description
                          "Threshold value";
                      }
                    }
                    must '. <= ../maximum-route-interfaces' {
                      tailf:xpath-root 3;
                    }
                    description
                      "Set threshold to print warning";
                  }
                }
                container register-states {
                  presence "Indicates a register-states node is configured.";
                  description
                    "PIM source register states for all VRFs";
                  leaf maximum-register-states {
                    type uint32 {
                      range "0..75000" {
                        description
                          "Maximum PIM sparse-mode source register states";
                      }
                    }
                    mandatory true;
                    description
                      "PIM source register states for all VRFs";
                  }
                  leaf threshold {
                    type uint32 {
                      range "0..75000" {
                        description
                          "Threshold value";
                      }
                    }
                    must '. <= ../maximum-register-states' {
                      tailf:xpath-root 3;
                    }
                    description
                      "Set threshold to print warning";
                  }
                }
                container packet-queue {
                  description
                    "PIM Packet queue size in bytes";
                  leaf high-priority {
                    type uint32 {
                      range "0..2147483648" {
                        description
                          "Maximum PIM routes";
                      }
                    }
                    description
                      "PIM high priority packet queue size in bytes";
                  }
                  leaf low-priority {
                    type uint32 {
                      range "0..2147483648" {
                        description
                          "Maximum PIM routes";
                      }
                    }
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type uint32 {
                        range "1..10000" {
                          description
                            "Maximum PIM group-mapping learnt from BSR";
                        }
                      }
                      mandatory true;
                    }
                    leaf threshold {
                      type uint32 {
                        range "1..10000" {
                          description
                            "Threshold value";
                        }
                      }
                      must '. <= ../maximum-bsr' {
                        tailf:xpath-root 3;
                      }
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type uint32 {
                        range "1..10000" {
                          description
                            "Maximum PIM BSR C-RP cache";
                        }
                      }
                      mandatory true;
                      description
                        "Set maximum number of C-RP cache in BSR";
                    }
                    leaf threshold {
                      type uint32 {
                        range "1..10000" {
                          description
                            "Threshold value";
                        }
                      }
                      must '. <= ../maximum-crp-cache' {
                        tailf:xpath-root 3;
                      }
                      description
                        "Set threshold to print warning";
                    }
                  }
                }
              }
            }
            container maximum {
              description
                "Maximum state limits";
              container routes {
                presence "Indicates a routes node is configured.";
                description
                  "PIM routes";
                leaf maximum-routes {
                  type uint32 {
                    range "1..200000" {
                      description
                        "Maximum PIM routes";
                    }
                  }
                  mandatory true;
                  description
                    "PIM routes";
                }
                leaf threshold {
                  type uint32 {
                    range "1..200000" {
                      description
                        "Threshold value";
                    }
                  }
                  must '. <= ../maximum-routes' {
                    tailf:xpath-root 3;
                  }
                  description
                    "Set threshold to print warning";
                }
              }
              container route-interfaces {
                presence "Indicates a route-interfaces node is configured.";
                description
                  "PIM total number of interfaces on all routes";
                leaf maximum-route-interfaces {
                  type uint32 {
                    range "1..1100000" {
                      description
                        "Maximum PIM route-interfaces";
                    }
                  }
                  mandatory true;
                  description
                    "PIM total number of interfaces on all routes";
                }
                leaf threshold {
                  type uint32 {
                    range "1..1100000" {
                      description
                        "Threshold value";
                    }
                  }
                  must '. <= ../maximum-route-interfaces' {
                    tailf:xpath-root 3;
                  }
                  description
                    "Set threshold to print warning";
                }
              }
              container register-states {
                presence "Indicates a register-states node is configured.";
                description
                  "PIM source register states";
                leaf maximum-register-states {
                  type uint32 {
                    range "0..75000" {
                      description
                        "Maximum PIM sparse-mode source register states";
                    }
                  }
                  mandatory true;
                  description
                    "PIM source register states";
                }
                leaf threshold {
                  type uint32 {
                    range "0..75000" {
                      description
                        "Threshold value";
                    }
                  }
                  must '. <= ../maximum-register-states' {
                    tailf:xpath-root 3;
                  }
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type uint32 {
                      range "1..10000" {
                        description
                          "Maximum PIM group mappings from elected BSR";
                      }
                    }
                    mandatory true;
                    description
                      "Learned through the BSR distribution mechanism";
                  }
                  leaf threshold {
                    type uint32 {
                      range "1..10000" {
                        description
                          "Threshold value";
                      }
                    }
                    must '. <= ../maximum-bsr' {
                      tailf:xpath-root 3;
                    }
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type uint32 {
                      range "1..10000" {
                        description
                          "Maximum number of C-RP cache";
                      }
                    }
                    mandatory true;
                    description
                      "Set maximum number of C-RP cache in BSR";
                  }
                  leaf threshold {
                    type uint32 {
                      range "1..10000" {
                        description
                          "Threshold value";
                      }
                    }
                    must '. <= ../maximum-crp-cache' {
                      tailf:xpath-root 3;
                    }
                    description
                      "Set threshold to print warning";
                  }
                }
              }
            }
            leaf convergence-timeout {
              type uint32 {
                range "1800..2400" {
                  description
                    "Unicast convergence fallback timer in seconds";
                }
              }
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf {
              description
                "RPF commands";
              container topology {
                description
                  "Select RPF topology";
                leaf route-policy {
                  type xr:Route-policy-name;
                  description
                    "Route policy to select RPF topology";
                }
              }
            }
            container mdt {
              description
                "Multicast Distribution Tree commands";
              leaf neighbor-filter {
                type xr:Cisco-ios-xr-string {
                  length "1..32" {
                    description
                      "IP named access list";
                  }
                }
                description
                  "Neighbor filter";
              }
              container data {
                description
                  "Data MDT Options";
                leaf switchover-interval {
                  type uint32 {
                    range "3..60" {
                      description
                        "Interval value in seconds";
                    }
                  }
                  description
                    "Data MDT switchover interval";
                }
                leaf announce-interval {
                  type uint32 {
                    range "3..120" {
                      description
                        "Interval value in seconds";
                    }
                  }
                  description
                    "Periodic Data MDT Join TLV interval";
                }
                leaf max-aggregation {
                  type uint32 {
                    range "1..16777215" {
                      description
                        "Aggregation value";
                    }
                  }
                  description
                    "Data MDT max-aggregation";
                }
              }
              container c-multicast-routing {
                presence "Indicates a c-multicast-routing node is configured.";
                description
                  "MVPN customer routing commands";
                leaf type {
                  type enumeration {
                    enum "pim" {
                      value 1;
                      description
                        "PIM customer multicast routing";
                    }
                    enum "bgp" {
                      value 2;
                      description
                        "BGP customer multicast routing";
                    }
                  }
                  mandatory true;
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  when "../type != 'pim'" {
                    tailf:xpath-root 3;
                  }
                  description
                    "PIM Hellos over MDT";
                  container enable {
                    presence "Indicates a enable node is configured.";
                    description
                      "Enable PIM Hellos over MDT";
                  }
                }
                leaf shared-tree-prune-delay {
                  type uint32 {
                    range "0..1800" {
                      description
                        "Delay in seconds.";
                    }
                  }
                  description
                    "Delay before pruning I-S PMSI from S,G when SA received";
                }
                leaf source-tree-prune-delay {
                  type uint32 {
                    range "0..300" {
                      description
                        "Delay in seconds.";
                    }
                  }
                  description
                    "Delay before removing PMSI from olist after BGP withdrawal";
                }
                container migration {
                  presence "Indicates a migration node is configured.";
                  description
                    "customer routing migration";
                  leaf route-policy {
                    type xr:Route-policy-name;
                    description
                      "Route policy to select customer routing";
                  }
                }
                container unicast-reachability {
                  description
                    "Control addition of Extended Communities to Unicast VPN-IP routes";
                  container connector {
                    description
                      "Enable/Disable Connector";
                    container disable {
                      must 'not(../enable)' {
                        tailf:xpath-root 3;
                      }
                      presence "Indicates a disable node is configured.";
                      description
                        "Disable Connector Attribute";
                    }
                    container enable {
                      must 'not(../disable)' {
                        tailf:xpath-root 3;
                      }
                      presence "Indicates a enable node is configured.";
                      description
                        "Enable Connector Attribute";
                    }
                  }
                  container source-as {
                    description
                      "Enable/Disable Source AS";
                    container disable {
                      must 'not(../enable)' {
                        tailf:xpath-root 3;
                      }
                      presence "Indicates a disable node is configured.";
                      description
                        "Disable Source-AS Attribute";
                    }
                    container enable {
                      must 'not(../disable)' {
                        tailf:xpath-root 3;
                      }
                      presence "Indicates a enable node is configured.";
                      description
                        "Enable Source-AS Attribute";
                    }
                  }
                  container vrf-route-import {
                    description
                      "Enable/Disable VRF Route Import";
                    container disable {
                      must 'not(../enable)' {
                        tailf:xpath-root 3;
                      }
                      presence "Indicates a disable node is configured.";
                      description
                        "Disable VRF Route Import Attribute";
                    }
                    container enable {
                      must 'not(../disable)' {
                        tailf:xpath-root 3;
                      }
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:Cisco-ios-xr-string {
                  length "1..32" {
                    description
                      "ACL Name for rp-list";
                  }
                }
                description
                  "Access-list for allowed RP addresses";
              }
              leaf group-list {
                type xr:Cisco-ios-xr-string {
                  length "1..32" {
                    description
                      "Access name for group-list";
                  }
                }
                description
                  "Access-list for allowed group ranges";
              }
            }
            container sg-expiry-timer {
              presence "Indicates a sg-expiry-timer node is configured.";
              description
                "Configure SG expiry timer";
              leaf sg-expiry-timer-value {
                type uint32 {
                  range "40..57600" {
                    description
                      "Duration of the expiry timer interval, in seconds";
                  }
                }
                mandatory true;
                description
                  "Configure SG expiry timer";
              }
              leaf sg-list {
                type xr:Cisco-ios-xr-string {
                  length "1..32" {
                    description
                      "IP named access list";
                  }
                }
                description
                  "Access-list of (S,G) routes for which expiry timer is applicable";
              }
            }
            container ssm {
              description
                "Configure a group range for Source-Specific use";
              leaf range {
                type xr:Cisco-ios-xr-string {
                  length "1..32" {
                    description
                      "Access list specifying SSM group range";
                  }
                }
                must 'not(../disable)' {
                  tailf:xpath-root 3;
                }
                description
                  "Provide ACL that specifies non-standard SSM range";
              }
              container disable {
                must 'not(../range)' {
                  tailf:xpath-root 3;
                }
                presence "Indicates a disable node is configured.";
                description
                  "Disable use of all SSM group ranges";
              }
              container allow-override {
                presence "Indicates a allow-override node is configured.";
                description
                  "Allow SSM ranges to be overridden by more specific ranges";
              }
            }
            container multipath {
              presence "Indicates a multipath node is configured.";
              description
                "Enable equal-cost multipath routing";
              container hash {
                must 'interface-extended or source-nexthop or source-group' {
                  tailf:xpath-root 3;
                }
                presence "Indicates a hash node is configured.";
                description
                  "Enter a hashing algorithm";
                container interface-extended {
                  must 'not(../source-nexthop) and not(../source-group)' {
                    tailf:xpath-root 3;
                  }
                  presence "Indicates a interface-extended node is configured.";
                  description
                    "Enable interface extensions for non-unique next-hop addrs";
                }
                container source-nexthop {
                  must 'not(../interface-extended) and not(../source-group)' {
                    tailf:xpath-root 3;
                  }
                  presence "Indicates a source-nexthop node is configured.";
                  description
                    "Enable source with next-hop multipath hashing (better distribution)";
                }
                container source-group {
                  must 'not(../source-nexthop) and not(../interface-extended)' {
                    tailf:xpath-root 3;
                  }
                  presence "Indicates a source-group node is configured.";
                  description
                    "Enable source, group based multipath hashing (Compatible with IOS versions)";
                }
              }
            }
            container interface {
              description
                "PIM interface configuration subcommands";
              container interfaces {
                description
                  "Select an interface to configure";
                list interface {
                  key "interface-name";
                  description
                    "Select an interface to configure";
                  leaf interface-name {
                    type xr:Interface-name;
                    description
                      "Select an interface to configure";
                  }
                  leaf dr-priority {
                    type uint32 {
                      range "0..4294967295" {
                        description
                          "Hello DR priority, preference given to larger value";
                      }
                    }
                    description
                      "PIM Hello DR priority";
                  }
                  leaf hello-interval {
                    type uint32 {
                      range "1..3600" {
                        description
                          "Hello interval in seconds";
                      }
                    }
                    description
                      "PIM neighbor Hello announcement interval";
                  }
                  leaf join-prune-interval {
                    type uint32 {
                      range "10..600" {
                        description
                          "Join-Prune interval in seconds";
                      }
                    }
                    description
                      "PIM periodic Join-Prune announcement interval";
                  }
                  leaf join-prune-mtu {
                    type uint32 {
                      range "576..65535" {
                        description
                          "MTU to use in bytes";
                      }
                    }
                    description
                      "MTU to use when sending PIM J/P packets";
                  }
                  leaf propagation-delay {
                    type uint32 {
                      range "100..32767" {
                        description
                          "Propagatoin delay in milliseconds";
                      }
                    }
                    description
                      "PIM Hello propagation delay";
                  }
                  leaf override-interval {
                    type uint32 {
                      range "400..65535" {
                        description
                          "Override interval in milliseconds";
                      }
                    }
                    description
                      "PIM Hello override interval";
                  }
                  container bsr-border {
                    presence "Indicates a bsr-border node is configured.";
                    description
                      "Do not fwd BSR messages on this interface";
                  }
                  container enable {
                    must 'not(../disable)' {
                      tailf:xpath-root 3;
                    }
                    presence "Indicates a enable node is configured.";
                    description
                      "Enable PIM processing on this interface";
                  }
                  container disable {
                    must 'not(../enable)' {
                      tailf:xpath-root 3;
                    }
                    presence "Indicates a disable node is configured.";
                    description
                      "Disable PIM processing on this interface";
                  }
                  leaf neighbor-filter {
                    type xr:Cisco-ios-xr-string {
                      length "1..1024" {
                        description
                          "Access list specifying neighbor address";
                      }
                    }
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type uint32 {
                          range "1..1100000" {
                            description
                              "Maximum number of allowed routes for this interface";
                          }
                        }
                        mandatory true;
                        description
                          "PIM downstream joined interfaces";
                      }
                      leaf threshold {
                        type uint32 {
                          range "1..1100000" {
                            description
                              "Threshold warning";
                          }
                        }
                        must '. <= ../maximum-route-interfaces' {
                          tailf:xpath-root 3;
                        }
                        description
                          "Threshold warning";
                      }
                      leaf access-list {
                        type xr:Cisco-ios-xr-string {
                          length "1..64" {
                            description
                              "Name of ACL that specifies to which routes to apply the maximum limit";
                          }
                        }
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type uint32 {
                        range "3..30000" {
                          description
                            "hello interval in milli-seconds";
                        }
                      }
                      description
                        "Hello interval";
                    }
                    leaf multiplier {
                      type uint32 {
                        range "2..50" {
                          description
                            "Detect multiplier";
                        }
                      }
                      description
                        "Detect multiplier";
                    }
                  }
                }
              }
            }
            container bsr {
              description
                "BSR Configurations";
              container candidate-bsr {
                presence "Indicates a candidate-bsr node is configured.";
                description
                  "configure candidate BSR";
                leaf address {
                  type inet:ipv6-address-no-zone;
                  mandatory true;
                  description
                    "IP address of configured BSR";
                }
                leaf hash-mask-len {
                  type uint32 {
                    range "0..128" {
                      description
                        "mask length";
                    }
                  }
                  mandatory true;
                  description
                    "BSR Hash Mask Length";
                }
                leaf priority {
                  type uint32 {
                    range "1..255" {
                      description
                        "priority";
                    }
                  }
                  mandatory true;
                  description
                    "BSR Priority";
                }
              }
              container candidate-rps {
                description
                  "BSR Candidate RP Configurations";
                list candidate-rp {
                  must '(priority and interval) or (bidir/priority and bidir/interval)' {
                    tailf:xpath-root 3;
                  }
                  key "address";
                  description
                    "BSR Candidate RP Configurations";
                  leaf address {
                    type inet:ipv6-address-no-zone;
                    description
                      "BSR Candidate RP Configurations";
                  }
                  leaf group-list {
                    type xr:Cisco-ios-xr-string {
                      length "1..64" {
                        description
                          "access-list";
                      }
                    }
                    description
                      "Group List access-list";
                  }
                  leaf priority {
                    type uint32 {
                      range "1..255" {
                        description
                          "priority";
                      }
                    }
                    description
                      "C-RP Priority";
                  }
                  leaf interval {
                    type uint32 {
                      range "30..600" {
                        description
                          "interval in second";
                      }
                    }
                    description
                      "C-RP Advertisement interval";
                  }
                  container bidir {
                    description
                      "To specify group ranges as Bidir";
                    leaf group-list {
                      type xr:Cisco-ios-xr-string {
                        length "1..64" {
                          description
                            "access-list";
                        }
                      }
                      description
                        "Group List access-list";
                    }
                    leaf priority {
                      type uint32 {
                        range "1..255" {
                          description
                            "priority";
                        }
                      }
                      description
                        "C-RP Priority";
                    }
                    leaf interval {
                      type uint32 {
                        range "30..600" {
                          description
                            "interval in second";
                        }
                      }
                      description
                        "C-RP Advertisement interval";
                    }
                  }
                }
              }
              container relay {
                description
                  "BSR RP relay config";
                container vrfs {
                  description
                    "vrf";
                  list vrf {
                    key "vrf-name";
                    description
                      "vrf";
                    leaf vrf-name {
                      type xr:Cisco-ios-xr-string {
                        length "1..1024" {
                          description
                            "vrf-name";
                        }
                      }
                      description
                        "vrf";
                    }
                    container listen {
                      presence "Indicates a listen node is configured.";
                      description
                        "Enable RP relay in listen mode";
                    }
                  }
                }
              }
            }
            container sr-p2mp-policies {
              description
                "Segment-routing P2MP policy";
              list sr-p2mp-policy {
                key "sr-p2mp-policy-id";
                description
                  "Segment-routing P2MP policy";
                leaf sr-p2mp-policy-id {
                  type xr:Cisco-ios-xr-string {
                    length "1..1024" {
                      description
                        "Name of the P2MP policy";
                    }
                  }
                  description
                    "Segment-routing P2MP policy";
                }
                container static-group {
                  description
                    "ipv6 static multicast group";
                  list group-address {
                    key "group-address";
                    description
                      "ipv6 static multicast group";
                    leaf group-address {
                      type inet:ipv6-address-no-zone;
                      description
                        "ipv6 static multicast group";
                    }
                    container group-address-only {
                      presence "Indicates a group-address-only node is configured.";
                      description
                        "Group-address without increment mask/source-address";
                    }
                    container group-address-inc-masks {
                      description
                        "Group-address with increment mask for group address";
                      list inc-mask {
                        key "group-mask-address";
                        description
                          "Increment mask for group address";
                        leaf group-mask-address {
                          type inet:ipv6-address-no-zone;
                          description
                            "Increment mask for group address";
                        }
                        leaf group-address-count {
                          type uint32 {
                            range "1..512" {
                              description
                                "No. of group addresses to join";
                            }
                          }
                          mandatory true;
                          description
                            "No. of group addresses to join";
                        }
                      }
                    }
                    container group-address-source-address {
                      description
                        "Group-address with source-address";
                      list source-address {
                        key "source-address";
                        description
                          "Source address to join";
                        leaf source-address {
                          type inet:ipv6-address-no-zone;
                          description
                            "Source address to join";
                        }
                      }
                    }
                    container group-address-inc-mask-source-address {
                      description
                        "Group-address with increment-mask and source-address";
                      list inc-mask {
                        key "group-mask-address source-address";
                        description
                          "Increment mask for group address";
                        leaf group-mask-address {
                          type inet:ipv6-address-no-zone;
                          description
                            "Increment mask for group address";
                        }
                        leaf source-address {
                          type inet:ipv6-address-no-zone;
                          description
                            "Source address to join";
                        }
                        leaf group-address-count {
                          type uint32 {
                            range "1..512" {
                              description
                                "No. of group addresses to join";
                            }
                          }
                          mandatory true;
                          description
                            "No. of group addresses to join";
                        }
                      }
                    }
                    container group-address-source-address-inc-mask {
                      description
                        "Group-address and source-address with increment-mask";
                      list inc-mask {
                        key "source-address source-mask-address";
                        description
                          "Increment mask for group address";
                        leaf source-address {
                          type inet:ipv6-address-no-zone;
                          description
                            "Source address to join";
                        }
                        leaf source-mask-address {
                          type inet:ipv6-address-no-zone;
                          description
                            "Increment mask for source address";
                        }
                        leaf source-address-count {
                          type uint32 {
                            range "1..512" {
                              description
                                "No. of source addresses to join";
                            }
                          }
                          mandatory true;
                          description
                            "No. of source addresses to join";
                        }
                      }
                    }
                    container group-inc-mask-source-inc-mask {
                      description
                        "Group-address with increment-mask and source-address with increment-mask";
                      list inc-mask {
                        key "group-mask-address source-address source-mask-address";
                        leaf group-mask-address {
                          type inet:ipv6-address-no-zone;
                          description
                            "Increment mask for group address";
                        }
                        leaf source-address {
                          type inet:ipv6-address-no-zone;
                          description
                            "Source address to join";
                        }
                        leaf source-mask-address {
                          type inet:ipv6-address-no-zone;
                          description
                            "Increment mask for source address";
                        }
                        leaf group-address-count {
                          type uint32 {
                            range "1..512" {
                              description
                                "No. of group addresses to join";
                            }
                          }
                          mandatory true;
                          description
                            "No. of group addresses to join";
                        }
                        leaf source-address-count {
                          type uint32 {
                            range "1..512" {
                              description
                                "No. of source addresses to join";
                            }
                          }
                          mandatory true;
                          description
                            "No. of source addresses to join";
                        }
                      }
                    }
                  }
                }
              }
            }
            container embedded-rp {
              description
                "Set Embedded RP processing support";
              list ip-addresses {
                key "ip-address";
                description
                  "IP name or address of Rendezvous Point";
                leaf ip-address {
                  type inet:ipv6-address-no-zone;
                  description
                    "IP name or address of Rendezvous Point";
                }
                leaf access-list-name {
                  type xr:Cisco-ios-xr-string {
                    length "1..1024" {
                      description
                        "Access list of groups that should map to given RP";
                    }
                  }
                  mandatory true;
                  description
                    "Access list of groups that should map to given RP";
                }
              }
              container disable {
                presence "Indicates a disable node is configured.";
                description
                  "Disable Embedded RP processing";
              }
            }
          }
        }
      }
    }
  }
  augment "/ncs:devices/ncs:device/ncs:live-status" {
    container router {
      tailf:ncs-device-type "netconf";
      tailf:display-when "not(../../ncs:module) or ../../ncs:module[ncs:name='Cisco-IOS-XR-um-router-pim-cfg'] or (../../ncs:live-status-protocol[not(ncs:capability)]) or (../../ncs:live-status-protocol/ncs:capability/ncs:module[.='Cisco-IOS-XR-um-router-pim-cfg'])";
      description
        "Enable a routing process";
      container pim {
        presence "Indicates a pim node is configured.";
        description
          "PIM configuration subcommands";
        container vrfs {
          description
            "VRF configs";
          list vrf {
            key "vrf-name";
            description
              "VRF configs";
            leaf vrf-name {
              type xr:live_ncs_Cisco-ios-xr-string;
              description
                "VRF configs";
            }
            container address-family {
              description
                "Enter Address Family command mode";
              container ipv4 {
                description
                  "IPv4 Address Family";
                container rp-addresses {
                  description
                    "Configure Rendezvous Point";
                  list rp-address {
                    key "address";
                    description
                      "Configure Rendezvous Point";
                    leaf address {
                      type inet:ipv4-address-no-zone;
                      description
                        "Configure Rendezvous Point";
                    }
                    leaf access-list {
                      type xr:live_ncs_Cisco-ios-xr-string;
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      key "address";
                      description
                        "Configure Rendezvous Point";
                      leaf address {
                        type inet:ipv4-address-no-zone;
                        description
                          "Configure Rendezvous Point";
                      }
                      leaf access-list {
                        type xr:live_ncs_Cisco-ios-xr-string;
                        description
                          "Access list of groups that should map to given RP";
                      }
                      container override {
                        presence "Indicates a override node is configured.";
                        description
                          "Static RP config overrides auto-rp and BSR";
                      }
                    }
                  }
                }
                leaf rp-static-deny {
                  type xr:live_ncs_Cisco-ios-xr-string;
                  description
                    "Configure static RP deny range";
                }
                leaf accept-register {
                  type xr:live_ncs_Cisco-ios-xr-string;
                  description
                    "Registers accept filter";
                }
                container suppress-data-registers {
                  presence "Indicates a suppress-data-registers node is configured.";
                  description
                    "Suppress data registers after initial state setup";
                }
                leaf register-source {
                  type xr:live_ncs_Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:live_ncs_Cisco-ios-xr-string;
                  description
                    "Neighbor filter";
                }
                container convergence {
                  description
                    "Convergence related parameters";
                  leaf rpf-conflict-join-delay {
                    type uint32 {
                      range "0..15" {
                        description
                          "Delay in seconds";
                      }
                    }
                    description
                      "Delay in sending first join if RPF points to any downstream neighbor";
                  }
                  leaf link-down-prune-delay {
                    type uint32 {
                      range "0..60" {
                        description
                          "Delay in seconds";
                      }
                    }
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:live_ncs_Cisco-ios-xr-string;
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type uint32 {
                    range "1..3600" {
                      description
                        "Hello interval in seconds";
                    }
                  }
                  description
                    "Inherited by all interfaces : Hello interval in seconds";
                }
                leaf dr-priority {
                  type uint32 {
                    range "0..4294967295" {
                      description
                        "Hello DR priority, preference given to larger value";
                    }
                  }
                  description
                    "Inherited by all interfaces : PIM Hello DR priority";
                }
                leaf join-prune-interval {
                  type uint32 {
                    range "10..600" {
                      description
                        "Join-Prune interval in seconds";
                    }
                  }
                  description
                    "Inherited by all interfaces : Join-Prune interval";
                }
                leaf join-prune-mtu {
                  type uint32 {
                    range "576..65535" {
                      description
                        "Join-Prune MTU in bytes";
                    }
                  }
                  description
                    "Inherited by all interfaces : Join-Prune MTU";
                }
                leaf propagation-delay {
                  type uint32 {
                    range "100..32767" {
                      description
                        "Propagatoin delay in milliseconds";
                    }
                  }
                  description
                    "Inherited by all interfaces : PIM Hello Propagation delay";
                }
                leaf override-interval {
                  type uint32 {
                    range "400..65535" {
                      description
                        "Override interval in milliseconds";
                    }
                  }
                  description
                    "Inherited by all interfaces : PIM Hello override interval";
                }
                container maximum {
                  description
                    "Maximum state limits";
                  container routes {
                    presence "Indicates a routes node is configured.";
                    description
                      "PIM routes";
                    leaf maximum-routes {
                      type uint32 {
                        range "1..200000" {
                          description
                            "Maximum PIM routes";
                        }
                      }
                      // NCS drop mandatory statement
                      description
                        "PIM routes";
                    }
                    leaf threshold {
                      type uint32 {
                        range "1..200000" {
                          description
                            "Threshold value";
                        }
                      }
                      // NCS drop must statement
                      description
                        "Set threshold to print warning";
                    }
                  }
                  container route-interfaces {
                    presence "Indicates a route-interfaces node is configured.";
                    description
                      "PIM total number of interfaces on all routes";
                    leaf maximum-route-interfaces {
                      type uint32 {
                        range "1..1100000" {
                          description
                            "Maximum PIM route-interfaces";
                        }
                      }
                      // NCS drop mandatory statement
                      description
                        "PIM total number of interfaces on all routes";
                    }
                    leaf threshold {
                      type uint32 {
                        range "1..1100000" {
                          description
                            "Threshold value";
                        }
                      }
                      // NCS drop must statement
                      description
                        "Set threshold to print warning";
                    }
                  }
                  container register-states {
                    presence "Indicates a register-states node is configured.";
                    description
                      "PIM source register states";
                    leaf maximum-register-states {
                      type uint32 {
                        range "0..75000" {
                          description
                            "Maximum PIM sparse-mode source register states";
                        }
                      }
                      // NCS drop mandatory statement
                      description
                        "PIM source register states";
                    }
                    leaf threshold {
                      type uint32 {
                        range "0..75000" {
                          description
                            "Threshold value";
                        }
                      }
                      // NCS drop must statement
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type uint32 {
                          range "1..10000" {
                            description
                              "Maximum PIM group mappings from elected BSR";
                          }
                        }
                        // NCS drop mandatory statement
                        description
                          "Learned through the BSR distribution mechanism";
                      }
                      leaf threshold {
                        type uint32 {
                          range "1..10000" {
                            description
                              "Threshold value";
                          }
                        }
                        // NCS drop must statement
                        description
                          "Set threshold to print warning";
                      }
                    }
                    container autorp {
                      presence "Indicates a autorp node is configured.";
                      description
                        "Learned through the Auto-RP distribution mechanism";
                      leaf maximum-autorp {
                        type uint32 {
                          range "1..10000" {
                            description
                              "Maximum PIM group mappings from Auto-RP mapping agent";
                          }
                        }
                        // NCS drop mandatory statement
                        description
                          "Learned through the Auto-RP distribution mechanism";
                      }
                      leaf threshold {
                        type uint32 {
                          range "1..10000" {
                            description
                              "Threshold value";
                          }
                        }
                        // NCS drop must statement
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type uint32 {
                          range "1..10000" {
                            description
                              "Maximum number of C-RP cache";
                          }
                        }
                        // NCS drop mandatory statement
                        description
                          "Set maximum number of C-RP cache in BSR";
                      }
                      leaf threshold {
                        type uint32 {
                          range "1..10000" {
                            description
                              "Threshold value";
                          }
                        }
                        // NCS drop must statement
                        description
                          "Set threshold to print warning";
                      }
                    }
                  }
                }
                leaf convergence-timeout {
                  type uint32 {
                    range "1800..2400" {
                      description
                        "Unicast convergence fallback timer in seconds";
                    }
                  }
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf-vector-injects {
                  description
                    "inject RPF vector";
                  list inject {
                    // NCS drop must statement
                    key "source-address masklen";
                    description
                      "inject RPF vector";
                    leaf source-address {
                      type inet:ipv4-address-no-zone;
                      description
                        "inject RPF vector";
                    }
                    leaf masklen {
                      type uint32 {
                        range "0..32" {
                          description
                            "masklen";
                        }
                      }
                      description
                        "masklen";
                    }
                    leaf-list rpf-vector {
                      type inet:ipv4-address-no-zone;
                      // NCS drop max-elements statement
                      description
                        "configure this node";
                    }
                  }
                }
                container explicit-rpf-vector {
                  description
                    "Enable Explicit PIM RPF Vector";
                  container injects {
                    description
                      "inject Explicit RPF vector";
                    list inject {
                      // NCS drop must statement
                      key "source-address masklen";
                      description
                        "inject Explicit RPF vector";
                      leaf source-address {
                        type inet:ipv4-address-no-zone;
                        description
                          "inject Explicit RPF vector";
                      }
                      leaf masklen {
                        type uint32 {
                          range "0..32" {
                            description
                              "masklen";
                          }
                        }
                        description
                          "masklen";
                      }
                      leaf-list rpf-vector {
                        type inet:ipv4-address-no-zone;
                        // NCS drop max-elements statement
                        description
                          "configure this node";
                      }
                    }
                  }
                }
                container rpf {
                  description
                    "RPF commands";
                  container topology {
                    description
                      "Select RPF topology";
                    leaf route-policy {
                      type xr:live_ncs_Route-policy-name;
                      description
                        "Route policy to select RPF topology";
                    }
                  }
                }
                container mdt {
                  description
                    "Multicast Distribution Tree commands";
                  leaf neighbor-filter {
                    type xr:live_ncs_Cisco-ios-xr-string;
                    description
                      "Neighbor filter";
                  }
                  container data {
                    description
                      "Data MDT Options";
                    leaf switchover-interval {
                      type uint32 {
                        range "3..60" {
                          description
                            "Interval value in seconds";
                        }
                      }
                      description
                        "Data MDT switchover interval";
                    }
                    leaf announce-interval {
                      type uint32 {
                        range "3..120" {
                          description
                            "Interval value in seconds";
                        }
                      }
                      description
                        "Periodic Data MDT Join TLV interval";
                    }
                    leaf max-aggregation {
                      type uint32 {
                        range "1..16777215" {
                          description
                            "Aggregation value";
                        }
                      }
                      description
                        "Data MDT max-aggregation";
                    }
                  }
                  container c-multicast-routing {
                    presence "Indicates a c-multicast-routing node is configured.";
                    description
                      "MVPN customer routing commands";
                    leaf type {
                      type enumeration {
                        enum "pim" {
                          value 1;
                          description
                            "PIM customer multicast routing";
                        }
                        enum "bgp" {
                          value 2;
                          description
                            "BGP customer multicast routing";
                        }
                      }
                      // NCS drop mandatory statement
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      // NCS drop when statement
                      description
                        "PIM Hellos over MDT";
                      container enable {
                        presence "Indicates a enable node is configured.";
                        description
                          "Enable PIM Hellos over MDT";
                      }
                    }
                    leaf shared-tree-prune-delay {
                      type uint32 {
                        range "0..1800" {
                          description
                            "Delay in seconds.";
                        }
                      }
                      description
                        "Delay before pruning I-S PMSI from S,G when SA received";
                    }
                    leaf source-tree-prune-delay {
                      type uint32 {
                        range "0..300" {
                          description
                            "Delay in seconds.";
                        }
                      }
                      description
                        "Delay before removing PMSI from olist after BGP withdrawal";
                    }
                    container migration {
                      presence "Indicates a migration node is configured.";
                      description
                        "customer routing migration";
                      leaf route-policy {
                        type xr:live_ncs_Route-policy-name;
                        description
                          "Route policy to select customer routing";
                      }
                    }
                    container unicast-reachability {
                      description
                        "Control addition of Extended Communities to Unicast VPN-IP routes";
                      container connector {
                        description
                          "Enable/Disable Connector";
                        container disable {
                          // NCS drop must statement
                          presence "Indicates a disable node is configured.";
                          description
                            "Disable Connector Attribute";
                        }
                        container enable {
                          // NCS drop must statement
                          presence "Indicates a enable node is configured.";
                          description
                            "Enable Connector Attribute";
                        }
                      }
                      container source-as {
                        description
                          "Enable/Disable Source AS";
                        container disable {
                          // NCS drop must statement
                          presence "Indicates a disable node is configured.";
                          description
                            "Disable Source-AS Attribute";
                        }
                        container enable {
                          // NCS drop must statement
                          presence "Indicates a enable node is configured.";
                          description
                            "Enable Source-AS Attribute";
                        }
                      }
                      container vrf-route-import {
                        description
                          "Enable/Disable VRF Route Import";
                        container disable {
                          // NCS drop must statement
                          presence "Indicates a disable node is configured.";
                          description
                            "Disable VRF Route Import Attribute";
                        }
                        container enable {
                          // NCS drop must statement
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:live_ncs_Cisco-ios-xr-string;
                    description
                      "Access-list for allowed RP addresses";
                  }
                  leaf group-list {
                    type xr:live_ncs_Cisco-ios-xr-string;
                    description
                      "Access-list for allowed group ranges";
                  }
                }
                container sg-expiry-timer {
                  presence "Indicates a sg-expiry-timer node is configured.";
                  description
                    "Configure SG expiry timer";
                  leaf sg-expiry-timer-value {
                    type uint32 {
                      range "40..57600" {
                        description
                          "Duration of the expiry timer interval, in seconds";
                      }
                    }
                    // NCS drop mandatory statement
                    description
                      "Configure SG expiry timer";
                  }
                  leaf sg-list {
                    type xr:live_ncs_Cisco-ios-xr-string;
                    description
                      "Access-list of (S,G) routes for which expiry timer is applicable";
                  }
                }
                container ssm {
                  description
                    "Configure a group range for Source-Specific use";
                  leaf range {
                    type xr:live_ncs_Cisco-ios-xr-string;
                    // NCS drop must statement
                    description
                      "Provide ACL that specifies non-standard SSM range";
                  }
                  container disable {
                    // NCS drop must statement
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    // NCS drop must statement
                    presence "Indicates a hash node is configured.";
                    description
                      "Enter a hashing algorithm";
                    container source {
                      // NCS drop must statement
                      presence "Indicates a source node is configured.";
                      description
                        "Enable source based multipath hashing (Compatible with IOS versions)";
                    }
                    container source-nexthop {
                      // NCS drop must statement
                      presence "Indicates a source-nexthop node is configured.";
                      description
                        "Enable source with next-hop multipath hashing (better distribution)";
                    }
                    container source-group {
                      // NCS drop must statement
                      presence "Indicates a source-group node is configured.";
                      description
                        "Enable source, group based multipath hashing (Compatible with IOS versions)";
                    }
                  }
                }
                container auto-rp {
                  description
                    "Auto-RP Commands";
                  container listen {
                    description
                      "RP discovery through AUTORP protocol";
                    container disable {
                      presence "Indicates a disable node is configured.";
                      description
                        "Disable RP discovery through the AUTORP protocol";
                    }
                  }
                  container relay {
                    description
                      "relay";
                    container vrfs {
                      description
                        "vrf";
                      list vrf {
                        key "vrf-name";
                        description
                          "vrf";
                        leaf vrf-name {
                          type xr:live_ncs_Cisco-ios-xr-string;
                          description
                            "vrf";
                        }
                        container listen {
                          presence "Indicates a listen node is configured.";
                          description
                            "Enable RP relay in listen mode";
                        }
                      }
                    }
                  }
                }
                container interfaces {
                  description
                    "PIM interface configuration subcommands";
                  list interface {
                    key "interface-name";
                    description
                      "Select an interface to configure";
                    leaf interface-name {
                      type xr:live_ncs_Interface-name;
                      description
                        "Select an interface to configure";
                    }
                    leaf dr-priority {
                      type uint32 {
                        range "0..4294967295" {
                          description
                            "Hello DR priority, preference given to larger value";
                        }
                      }
                      description
                        "PIM Hello DR priority";
                    }
                    leaf hello-interval {
                      type uint32 {
                        range "1..3600" {
                          description
                            "Hello interval in seconds";
                        }
                      }
                      description
                        "PIM neighbor Hello announcement interval";
                    }
                    leaf join-prune-interval {
                      type uint32 {
                        range "10..600" {
                          description
                            "Join-Prune interval in seconds";
                        }
                      }
                      description
                        "PIM periodic Join-Prune announcement interval";
                    }
                    leaf join-prune-mtu {
                      type uint32 {
                        range "576..65535" {
                          description
                            "MTU to use in bytes";
                        }
                      }
                      description
                        "MTU to use when sending PIM J/P packets";
                    }
                    leaf propagation-delay {
                      type uint32 {
                        range "100..32767" {
                          description
                            "Propagatoin delay in milliseconds";
                        }
                      }
                      description
                        "PIM Hello propagation delay";
                    }
                    leaf override-interval {
                      type uint32 {
                        range "400..65535" {
                          description
                            "Override interval in milliseconds";
                        }
                      }
                      description
                        "PIM Hello override interval";
                    }
                    container bsr-border {
                      presence "Indicates a bsr-border node is configured.";
                      description
                        "Do not fwd BSR messages on this interface";
                    }
                    container enable {
                      // NCS drop must statement
                      presence "Indicates a enable node is configured.";
                      description
                        "Enable PIM processing on this interface";
                    }
                    container disable {
                      // NCS drop must statement
                      presence "Indicates a disable node is configured.";
                      description
                        "Disable PIM processing on this interface";
                    }
                    leaf neighbor-filter {
                      type xr:live_ncs_Cisco-ios-xr-string;
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type uint32 {
                            range "1..1100000" {
                              description
                                "Maximum number of allowed routes for this interface";
                            }
                          }
                          // NCS drop mandatory statement
                          description
                            "PIM downstream joined interfaces";
                        }
                        leaf threshold {
                          type uint32 {
                            range "1..1100000" {
                              description
                                "Threshold warning";
                            }
                          }
                          // NCS drop must statement
                          description
                            "Threshold warning";
                        }
                        leaf access-list {
                          type xr:live_ncs_Cisco-ios-xr-string;
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type uint32 {
                          range "3..30000" {
                            description
                              "hello interval in milli-seconds";
                          }
                        }
                        description
                          "Hello interval";
                      }
                      leaf multiplier {
                        type uint32 {
                          range "2..50" {
                            description
                              "Detect multiplier";
                          }
                        }
                        description
                          "Detect multiplier";
                      }
                    }
                  }
                }
                container bsr {
                  description
                    "BSR Configurations";
                  container candidate-bsr {
                    presence "Indicates a candidate-bsr node is configured.";
                    description
                      "configure candidate BSR";
                    leaf address {
                      type inet:ipv4-address-no-zone;
                      // NCS drop mandatory statement
                      description
                        "IP address of configured BSR";
                    }
                    leaf hash-mask-len {
                      type uint32 {
                        range "0..32" {
                          description
                            "mask length";
                        }
                      }
                      // NCS drop mandatory statement
                      description
                        "BSR Hash Mask Length";
                    }
                    leaf priority {
                      type uint32 {
                        range "1..255" {
                          description
                            "priority";
                        }
                      }
                      // NCS drop mandatory statement
                      description
                        "BSR Priority";
                    }
                  }
                  container candidate-rps {
                    description
                      "BSR Candidate RP Configurations";
                    list candidate-rp {
                      // NCS drop must statement
                      key "address";
                      description
                        "BSR Candidate RP Configurations";
                      leaf address {
                        type inet:ipv4-address-no-zone;
                        description
                          "BSR Candidate RP Configurations";
                      }
                      leaf group-list {
                        type xr:live_ncs_Cisco-ios-xr-string;
                        description
                          "Group List access-list";
                      }
                      leaf priority {
                        type uint32 {
                          range "1..255" {
                            description
                              "priority";
                          }
                        }
                        description
                          "C-RP Priority";
                      }
                      leaf interval {
                        type uint32 {
                          range "30..600" {
                            description
                              "interval in second";
                          }
                        }
                        description
                          "C-RP Advertisement interval";
                      }
                      container bidir {
                        description
                          "To specify group ranges as Bidir";
                        leaf group-list {
                          type xr:live_ncs_Cisco-ios-xr-string;
                          description
                            "Group List access-list";
                        }
                        leaf priority {
                          type uint32 {
                            range "1..255" {
                              description
                                "priority";
                            }
                          }
                          description
                            "C-RP Priority";
                        }
                        leaf interval {
                          type uint32 {
                            range "30..600" {
                              description
                                "interval in second";
                            }
                          }
                          description
                            "C-RP Advertisement interval";
                        }
                      }
                    }
                  }
                  container relay {
                    description
                      "BSR RP relay config";
                    container vrfs {
                      description
                        "vrf";
                      list vrf {
                        key "vrf-name";
                        description
                          "vrf";
                        leaf vrf-name {
                          type xr:live_ncs_Cisco-ios-xr-string;
                          description
                            "vrf";
                        }
                        container listen {
                          presence "Indicates a listen node is configured.";
                          description
                            "Enable RP relay in listen mode";
                        }
                      }
                    }
                  }
                }
                container mofrr {
                  presence "Indicates a mofrr node is configured.";
                  description
                    "PIM Mofrr";
                  leaf flow {
                    type xr:live_ncs_Cisco-ios-xr-string;
                    description
                      "Multicast Only FRR";
                  }
                  leaf rib {
                    type string {
                      length "1..1024" {
                        description
                          "Access list specifying SGs that should do MOFRR with RIB events as switchover triggers";
                      }
                    }
                    description
                      "Use the rib keyword to restrict switchover triggers to RIB events";
                  }
                  container non-revertive {
                    presence "Indicates a non-revertive node is configured.";
                    description
                      "Non-revertive MoFRR";
                  }
                  container clone {
                    description
                      "Use the clone keyword to clone";
                    container joins {
                      description
                        "Use the join keyword to clone S,G as S1,G joins as S2,G joins";
                      list join {
                        // NCS drop must statement
                        key "address";
                        description
                          "Use the join keyword to clone S,G as S1,G joins as S2,G joins";
                        leaf address {
                          type inet:ipv4-address-no-zone;
                          description
                            "Source S";
                        }
                        list to {
                          // NCS drop must statement
                          key "address";
                          description
                            "to";
                          leaf address {
                            type inet:ipv4-address-no-zone;
                            description
                              "Source S1";
                          }
                          list and {
                            // NCS drop must statement
                            key "address";
                            description
                              "and";
                            leaf address {
                              type inet:ipv4-address-no-zone;
                              description
                                "Source S2";
                            }
                            list masklen {
                              key "mask-length";
                              description
                                "masklen";
                              leaf mask-length {
                                type uint32 {
                                  range "0..32" {
                                    description
                                      "masklen";
                                  }
                                }
                                description
                                  "masklen";
                              }
                            }
                          }
                        }
                      }
                    }
                    container sources {
                      description
                        "Use the source keyword to clone S,G as S1,G traffic and S2,G traffic";
                      list source {
                        // NCS drop must statement
                        key "address";
                        description
                          "Use the source keyword to clone S,G as S1,G traffic and S2,G traffic";
                        leaf address {
                          type inet:ipv4-address-no-zone;
                          description
                            "Source S";
                        }
                        list to {
                          // NCS drop must statement
                          key "address";
                          description
                            "to";
                          leaf address {
                            type inet:ipv4-address-no-zone;
                            description
                              "Source S1";
                          }
                          list and {
                            // NCS drop must statement
                            key "address";
                            description
                              "and";
                            leaf address {
                              type inet:ipv4-address-no-zone;
                              description
                                "Source S2";
                            }
                            list masklen {
                              key "mask-length";
                              description
                                "masklen";
                              leaf mask-length {
                                type uint32 {
                                  range "0..32" {
                                    description
                                      "masklen";
                                  }
                                }
                                description
                                  "masklen";
                              }
                            }
                          }
                        }
                      }
                    }
                  }
                }
                container sr-p2mp-policies {
                  description
                    "Segment-routing P2MP policy";
                  list sr-p2mp-policy {
                    key "policy-name";
                    description
                      "Segment-routing P2MP policy";
                    leaf policy-name {
                      type xr:live_ncs_Cisco-ios-xr-string;
                      description
                        "Segment-routing P2MP policy";
                    }
                    container static-group {
                      description
                        "ipv4 static multicast group";
                      list group-address {
                        key "group-address";
                        description
                          "ipv4 static multicast group";
                        leaf group-address {
                          type inet:ipv4-address-no-zone;
                          description
                            "ipv4 static multicast group";
                        }
                        container group-address-only {
                          presence "Indicates a group-address-only node is configured.";
                          description
                            "Group-address without increment mask/source-address";
                        }
                        container group-address-inc-masks {
                          description
                            "Group-address with increment mask for group address";
                          list inc-mask {
                            key "group-mask-address";
                            description
                              "Increment mask for group address";
                            leaf group-mask-address {
                              type inet:ipv4-address-no-zone;
                              description
                                "Increment mask for group address";
                            }
                            leaf group-address-count {
                              type uint32 {
                                range "1..512" {
                                  description
                                    "No. of group addresses to join";
                                }
                              }
                              // NCS drop mandatory statement
                              description
                                "No. of group addresses to join";
                            }
                          }
                        }
                        container group-address-source-address {
                          description
                            "Group-address with source-address";
                          list source-address {
                            key "source-address";
                            description
                              "Source address to join";
                            leaf source-address {
                              type inet:ipv4-address-no-zone;
                              description
                                "Source address to join";
                            }
                          }
                        }
                        container group-address-inc-mask-source-address {
                          description
                            "Group-address with increment-mask and source-address";
                          list inc-mask {
                            key "group-mask-address source-address";
                            description
                              "Increment mask for group address";
                            leaf group-mask-address {
                              type inet:ipv4-address-no-zone;
                              description
                                "Increment mask for group address";
                            }
                            leaf source-address {
                              type inet:ipv4-address-no-zone;
                              description
                                "Source address to join";
                            }
                            leaf group-address-count {
                              type uint32 {
                                range "1..512" {
                                  description
                                    "No. of group addresses to join";
                                }
                              }
                              // NCS drop mandatory statement
                              description
                                "No. of group addresses to join";
                            }
                          }
                        }
                        container group-address-source-address-inc-mask {
                          description
                            "Group-address and source-address with increment-mask";
                          list inc-mask {
                            key "source-address source-mask-address";
                            description
                              "Increment mask for group address";
                            leaf source-address {
                              type inet:ipv4-address-no-zone;
                              description
                                "Source address to join";
                            }
                            leaf source-mask-address {
                              type inet:ipv4-address-no-zone;
                              description
                                "Increment mask for source address";
                            }
                            leaf source-address-count {
                              type uint32 {
                                range "1..512" {
                                  description
                                    "No. of source addresses to join";
                                }
                              }
                              // NCS drop mandatory statement
                              description
                                "No. of source addresses to join";
                            }
                          }
                        }
                        container group-inc-mask-source-inc-mask {
                          description
                            "Group-address with increment-mask and source-address with increment-mask";
                          list inc-mask {
                            key "group-mask-address source-address source-mask-address";
                            leaf group-mask-address {
                              type inet:ipv4-address-no-zone;
                              description
                                "Increment mask for group address";
                            }
                            leaf source-address {
                              type inet:ipv4-address-no-zone;
                              description
                                "Source address to join";
                            }
                            leaf source-mask-address {
                              type inet:ipv4-address-no-zone;
                              description
                                "Increment mask for source address";
                            }
                            leaf group-address-count {
                              type uint32 {
                                range "1..512" {
                                  description
                                    "No. of group addresses to join";
                                }
                              }
                              // NCS drop mandatory statement
                              description
                                "No. of group addresses to join";
                            }
                            leaf source-address-count {
                              type uint32 {
                                range "1..512" {
                                  description
                                    "No. of source addresses to join";
                                }
                              }
                              // NCS drop mandatory statement
                              description
                                "No. of source addresses to join";
                            }
                          }
                        }
                      }
                    }
                  }
                }
              }
              container ipv6 {
                description
                  "IPv6 Address Family";
                container rp-addresses {
                  description
                    "Configure Rendezvous Point";
                  list rp-address {
                    key "address";
                    description
                      "Configure Rendezvous Point";
                    leaf address {
                      type inet:ipv6-address-no-zone;
                      description
                        "Configure Rendezvous Point";
                    }
                    leaf access-list {
                      type xr:live_ncs_Cisco-ios-xr-string;
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      key "address";
                      description
                        "Configure Rendezvous Point";
                      leaf address {
                        type inet:ipv6-address-no-zone;
                        description
                          "Configure Rendezvous Point";
                      }
                      leaf access-list {
                        type xr:live_ncs_Cisco-ios-xr-string;
                        description
                          "Access list of groups that should map to given RP";
                      }
                      container override {
                        presence "Indicates a override node is configured.";
                        description
                          "Static RP config overrides auto-rp and BSR";
                      }
                    }
                  }
                }
                leaf rp-static-deny {
                  type xr:live_ncs_Cisco-ios-xr-string;
                  description
                    "Configure static RP deny range";
                }
                leaf accept-register {
                  type xr:live_ncs_Cisco-ios-xr-string;
                  description
                    "Registers accept filter";
                }
                container suppress-data-registers {
                  presence "Indicates a suppress-data-registers node is configured.";
                  description
                    "Suppress data registers after initial state setup";
                }
                leaf register-source {
                  type xr:live_ncs_Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:live_ncs_Cisco-ios-xr-string;
                  description
                    "Neighbor filter";
                }
                container convergence {
                  description
                    "Convergence related parameters";
                  leaf rpf-conflict-join-delay {
                    type uint32 {
                      range "0..15" {
                        description
                          "Delay in seconds";
                      }
                    }
                    description
                      "Delay in sending first join if RPF points to any downstream neighbor";
                  }
                  leaf link-down-prune-delay {
                    type uint32 {
                      range "0..60" {
                        description
                          "Delay in seconds";
                      }
                    }
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:live_ncs_Cisco-ios-xr-string;
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type uint32 {
                    range "1..3600" {
                      description
                        "Hello interval in seconds";
                    }
                  }
                  description
                    "Inherited by all interfaces : Hello interval in seconds";
                }
                leaf dr-priority {
                  type uint32 {
                    range "0..4294967295" {
                      description
                        "Hello DR priority, preference given to larger value";
                    }
                  }
                  description
                    "Inherited by all interfaces : PIM Hello DR priority";
                }
                leaf join-prune-interval {
                  type uint32 {
                    range "10..600" {
                      description
                        "Join-Prune interval in seconds";
                    }
                  }
                  description
                    "Inherited by all interfaces : Join-Prune interval";
                }
                leaf join-prune-mtu {
                  type uint32 {
                    range "576..65535" {
                      description
                        "Join-Prune MTU in bytes";
                    }
                  }
                  description
                    "Inherited by all interfaces : Join-Prune MTU";
                }
                leaf propagation-delay {
                  type uint32 {
                    range "100..32767" {
                      description
                        "Propagatoin delay in milliseconds";
                    }
                  }
                  description
                    "Inherited by all interfaces : PIM Hello Propagation delay";
                }
                leaf override-interval {
                  type uint32 {
                    range "400..65535" {
                      description
                        "Override interval in milliseconds";
                    }
                  }
                  description
                    "Inherited by all interfaces : PIM Hello override interval";
                }
                container maximum {
                  description
                    "Maximum state limits";
                  container routes {
                    presence "Indicates a routes node is configured.";
                    description
                      "PIM routes";
                    leaf maximum-routes {
                      type uint32 {
                        range "1..200000" {
                          description
                            "Maximum PIM routes";
                        }
                      }
                      // NCS drop mandatory statement
                      description
                        "PIM routes";
                    }
                    leaf threshold {
                      type uint32 {
                        range "1..200000" {
                          description
                            "Threshold value";
                        }
                      }
                      // NCS drop must statement
                      description
                        "Set threshold to print warning";
                    }
                  }
                  container route-interfaces {
                    presence "Indicates a route-interfaces node is configured.";
                    description
                      "PIM total number of interfaces on all routes";
                    leaf maximum-route-interfaces {
                      type uint32 {
                        range "1..1100000" {
                          description
                            "Maximum PIM route-interfaces";
                        }
                      }
                      // NCS drop mandatory statement
                      description
                        "PIM total number of interfaces on all routes";
                    }
                    leaf threshold {
                      type uint32 {
                        range "1..1100000" {
                          description
                            "Threshold value";
                        }
                      }
                      // NCS drop must statement
                      description
                        "Set threshold to print warning";
                    }
                  }
                  container register-states {
                    presence "Indicates a register-states node is configured.";
                    description
                      "PIM source register states";
                    leaf maximum-register-states {
                      type uint32 {
                        range "0..75000" {
                          description
                            "Maximum PIM sparse-mode source register states";
                        }
                      }
                      // NCS drop mandatory statement
                      description
                        "PIM source register states";
                    }
                    leaf threshold {
                      type uint32 {
                        range "0..75000" {
                          description
                            "Threshold value";
                        }
                      }
                      // NCS drop must statement
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type uint32 {
                          range "1..10000" {
                            description
                              "Maximum PIM group mappings from elected BSR";
                          }
                        }
                        // NCS drop mandatory statement
                        description
                          "Learned through the BSR distribution mechanism";
                      }
                      leaf threshold {
                        type uint32 {
                          range "1..10000" {
                            description
                              "Threshold value";
                          }
                        }
                        // NCS drop must statement
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type uint32 {
                          range "1..10000" {
                            description
                              "Maximum number of C-RP cache";
                          }
                        }
                        // NCS drop mandatory statement
                        description
                          "Set maximum number of C-RP cache in BSR";
                      }
                      leaf threshold {
                        type uint32 {
                          range "1..10000" {
                            description
                              "Threshold value";
                          }
                        }
                        // NCS drop must statement
                        description
                          "Set threshold to print warning";
                      }
                    }
                  }
                }
                leaf convergence-timeout {
                  type uint32 {
                    range "1800..2400" {
                      description
                        "Unicast convergence fallback timer in seconds";
                    }
                  }
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf {
                  description
                    "RPF commands";
                  container topology {
                    description
                      "Select RPF topology";
                    leaf route-policy {
                      type xr:live_ncs_Route-policy-name;
                      description
                        "Route policy to select RPF topology";
                    }
                  }
                }
                container mdt {
                  description
                    "Multicast Distribution Tree commands";
                  leaf neighbor-filter {
                    type xr:live_ncs_Cisco-ios-xr-string;
                    description
                      "Neighbor filter";
                  }
                  container data {
                    description
                      "Data MDT Options";
                    leaf switchover-interval {
                      type uint32 {
                        range "3..60" {
                          description
                            "Interval value in seconds";
                        }
                      }
                      description
                        "Data MDT switchover interval";
                    }
                    leaf announce-interval {
                      type uint32 {
                        range "3..120" {
                          description
                            "Interval value in seconds";
                        }
                      }
                      description
                        "Periodic Data MDT Join TLV interval";
                    }
                    leaf max-aggregation {
                      type uint32 {
                        range "1..16777215" {
                          description
                            "Aggregation value";
                        }
                      }
                      description
                        "Data MDT max-aggregation";
                    }
                  }
                  container c-multicast-routing {
                    presence "Indicates a c-multicast-routing node is configured.";
                    description
                      "MVPN customer routing commands";
                    leaf type {
                      type enumeration {
                        enum "pim" {
                          value 1;
                          description
                            "PIM customer multicast routing";
                        }
                        enum "bgp" {
                          value 2;
                          description
                            "BGP customer multicast routing";
                        }
                      }
                      // NCS drop mandatory statement
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      // NCS drop when statement
                      description
                        "PIM Hellos over MDT";
                      container enable {
                        presence "Indicates a enable node is configured.";
                        description
                          "Enable PIM Hellos over MDT";
                      }
                    }
                    leaf shared-tree-prune-delay {
                      type uint32 {
                        range "0..1800" {
                          description
                            "Delay in seconds.";
                        }
                      }
                      description
                        "Delay before pruning I-S PMSI from S,G when SA received";
                    }
                    leaf source-tree-prune-delay {
                      type uint32 {
                        range "0..300" {
                          description
                            "Delay in seconds.";
                        }
                      }
                      description
                        "Delay before removing PMSI from olist after BGP withdrawal";
                    }
                    container migration {
                      presence "Indicates a migration node is configured.";
                      description
                        "customer routing migration";
                      leaf route-policy {
                        type xr:live_ncs_Route-policy-name;
                        description
                          "Route policy to select customer routing";
                      }
                    }
                    container unicast-reachability {
                      description
                        "Control addition of Extended Communities to Unicast VPN-IP routes";
                      container connector {
                        description
                          "Enable/Disable Connector";
                        container disable {
                          // NCS drop must statement
                          presence "Indicates a disable node is configured.";
                          description
                            "Disable Connector Attribute";
                        }
                        container enable {
                          // NCS drop must statement
                          presence "Indicates a enable node is configured.";
                          description
                            "Enable Connector Attribute";
                        }
                      }
                      container source-as {
                        description
                          "Enable/Disable Source AS";
                        container disable {
                          // NCS drop must statement
                          presence "Indicates a disable node is configured.";
                          description
                            "Disable Source-AS Attribute";
                        }
                        container enable {
                          // NCS drop must statement
                          presence "Indicates a enable node is configured.";
                          description
                            "Enable Source-AS Attribute";
                        }
                      }
                      container vrf-route-import {
                        description
                          "Enable/Disable VRF Route Import";
                        container disable {
                          // NCS drop must statement
                          presence "Indicates a disable node is configured.";
                          description
                            "Disable VRF Route Import Attribute";
                        }
                        container enable {
                          // NCS drop must statement
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:live_ncs_Cisco-ios-xr-string;
                    description
                      "Access-list for allowed RP addresses";
                  }
                  leaf group-list {
                    type xr:live_ncs_Cisco-ios-xr-string;
                    description
                      "Access-list for allowed group ranges";
                  }
                }
                container sg-expiry-timer {
                  presence "Indicates a sg-expiry-timer node is configured.";
                  description
                    "Configure SG expiry timer";
                  leaf sg-expiry-timer-value {
                    type uint32 {
                      range "40..57600" {
                        description
                          "Duration of the expiry timer interval, in seconds";
                      }
                    }
                    // NCS drop mandatory statement
                    description
                      "Configure SG expiry timer";
                  }
                  leaf sg-list {
                    type xr:live_ncs_Cisco-ios-xr-string;
                    description
                      "Access-list of (S,G) routes for which expiry timer is applicable";
                  }
                }
                container ssm {
                  description
                    "Configure a group range for Source-Specific use";
                  leaf range {
                    type xr:live_ncs_Cisco-ios-xr-string;
                    // NCS drop must statement
                    description
                      "Provide ACL that specifies non-standard SSM range";
                  }
                  container disable {
                    // NCS drop must statement
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    // NCS drop must statement
                    presence "Indicates a hash node is configured.";
                    description
                      "Enter a hashing algorithm";
                    container interface-extended {
                      // NCS drop must statement
                      presence "Indicates a interface-extended node is configured.";
                      description
                        "Enable interface extensions for non-unique next-hop addrs";
                    }
                    container source-nexthop {
                      // NCS drop must statement
                      presence "Indicates a source-nexthop node is configured.";
                      description
                        "Enable source with next-hop multipath hashing (better distribution)";
                    }
                    container source-group {
                      // NCS drop must statement
                      presence "Indicates a source-group node is configured.";
                      description
                        "Enable source, group based multipath hashing (Compatible with IOS versions)";
                    }
                  }
                }
                container interfaces {
                  description
                    "PIM interface configuration subcommands";
                  list interface {
                    key "interface-name";
                    description
                      "Select an interface to configure";
                    leaf interface-name {
                      type xr:live_ncs_Interface-name;
                      description
                        "Select an interface to configure";
                    }
                    leaf dr-priority {
                      type uint32 {
                        range "0..4294967295" {
                          description
                            "Hello DR priority, preference given to larger value";
                        }
                      }
                      description
                        "PIM Hello DR priority";
                    }
                    leaf hello-interval {
                      type uint32 {
                        range "1..3600" {
                          description
                            "Hello interval in seconds";
                        }
                      }
                      description
                        "PIM neighbor Hello announcement interval";
                    }
                    leaf join-prune-interval {
                      type uint32 {
                        range "10..600" {
                          description
                            "Join-Prune interval in seconds";
                        }
                      }
                      description
                        "PIM periodic Join-Prune announcement interval";
                    }
                    leaf join-prune-mtu {
                      type uint32 {
                        range "576..65535" {
                          description
                            "MTU to use in bytes";
                        }
                      }
                      description
                        "MTU to use when sending PIM J/P packets";
                    }
                    leaf propagation-delay {
                      type uint32 {
                        range "100..32767" {
                          description
                            "Propagatoin delay in milliseconds";
                        }
                      }
                      description
                        "PIM Hello propagation delay";
                    }
                    leaf override-interval {
                      type uint32 {
                        range "400..65535" {
                          description
                            "Override interval in milliseconds";
                        }
                      }
                      description
                        "PIM Hello override interval";
                    }
                    container bsr-border {
                      presence "Indicates a bsr-border node is configured.";
                      description
                        "Do not fwd BSR messages on this interface";
                    }
                    container enable {
                      // NCS drop must statement
                      presence "Indicates a enable node is configured.";
                      description
                        "Enable PIM processing on this interface";
                    }
                    container disable {
                      // NCS drop must statement
                      presence "Indicates a disable node is configured.";
                      description
                        "Disable PIM processing on this interface";
                    }
                    leaf neighbor-filter {
                      type xr:live_ncs_Cisco-ios-xr-string;
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type uint32 {
                            range "1..1100000" {
                              description
                                "Maximum number of allowed routes for this interface";
                            }
                          }
                          // NCS drop mandatory statement
                          description
                            "PIM downstream joined interfaces";
                        }
                        leaf threshold {
                          type uint32 {
                            range "1..1100000" {
                              description
                                "Threshold warning";
                            }
                          }
                          // NCS drop must statement
                          description
                            "Threshold warning";
                        }
                        leaf access-list {
                          type xr:live_ncs_Cisco-ios-xr-string;
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type uint32 {
                          range "3..30000" {
                            description
                              "hello interval in milli-seconds";
                          }
                        }
                        description
                          "Hello interval";
                      }
                      leaf multiplier {
                        type uint32 {
                          range "2..50" {
                            description
                              "Detect multiplier";
                          }
                        }
                        description
                          "Detect multiplier";
                      }
                    }
                  }
                }
                container bsr {
                  description
                    "BSR Configurations";
                  container candidate-bsr {
                    presence "Indicates a candidate-bsr node is configured.";
                    description
                      "configure candidate BSR";
                    leaf address {
                      type inet:ipv6-address-no-zone;
                      // NCS drop mandatory statement
                      description
                        "IP address of configured BSR";
                    }
                    leaf hash-mask-len {
                      type uint32 {
                        range "0..128" {
                          description
                            "mask length";
                        }
                      }
                      // NCS drop mandatory statement
                      description
                        "BSR Hash Mask Length";
                    }
                    leaf priority {
                      type uint32 {
                        range "1..255" {
                          description
                            "priority";
                        }
                      }
                      // NCS drop mandatory statement
                      description
                        "BSR Priority";
                    }
                  }
                  container candidate-rps {
                    description
                      "BSR Candidate RP Configurations";
                    list candidate-rp {
                      // NCS drop must statement
                      key "address";
                      description
                        "BSR Candidate RP Configurations";
                      leaf address {
                        type inet:ipv6-address-no-zone;
                        description
                          "BSR Candidate RP Configurations";
                      }
                      leaf group-list {
                        type xr:live_ncs_Cisco-ios-xr-string;
                        description
                          "Group List access-list";
                      }
                      leaf priority {
                        type uint32 {
                          range "1..255" {
                            description
                              "priority";
                          }
                        }
                        description
                          "C-RP Priority";
                      }
                      leaf interval {
                        type uint32 {
                          range "30..600" {
                            description
                              "interval in second";
                          }
                        }
                        description
                          "C-RP Advertisement interval";
                      }
                      container bidir {
                        description
                          "To specify group ranges as Bidir";
                        leaf group-list {
                          type xr:live_ncs_Cisco-ios-xr-string;
                          description
                            "Group List access-list";
                        }
                        leaf priority {
                          type uint32 {
                            range "1..255" {
                              description
                                "priority";
                            }
                          }
                          description
                            "C-RP Priority";
                        }
                        leaf interval {
                          type uint32 {
                            range "30..600" {
                              description
                                "interval in second";
                            }
                          }
                          description
                            "C-RP Advertisement interval";
                        }
                      }
                    }
                  }
                  container relay {
                    description
                      "BSR RP relay config";
                    container vrfs {
                      description
                        "vrf";
                      list vrf {
                        key "vrf-name";
                        description
                          "vrf";
                        leaf vrf-name {
                          type xr:live_ncs_Cisco-ios-xr-string;
                          description
                            "vrf";
                        }
                        container listen {
                          presence "Indicates a listen node is configured.";
                          description
                            "Enable RP relay in listen mode";
                        }
                      }
                    }
                  }
                }
                container sr-p2mp-policies {
                  description
                    "Segment-routing P2MP policy";
                  list sr-p2mp-policy {
                    key "policy-name";
                    description
                      "Segment-routing P2MP policy";
                    leaf policy-name {
                      type xr:live_ncs_Cisco-ios-xr-string;
                      description
                        "Segment-routing P2MP policy";
                    }
                    container static-group {
                      description
                        "ipv6 static multicast group";
                      list group-address {
                        key "group-address";
                        description
                          "ipv6 static multicast group";
                        leaf group-address {
                          type inet:ipv6-address-no-zone;
                          description
                            "ipv6 static multicast group";
                        }
                        container group-address-only {
                          presence "Indicates a group-address-only node is configured.";
                          description
                            "Group-address without increment mask/source-address";
                        }
                        container group-address-inc-masks {
                          description
                            "Group-address with increment mask for group address";
                          list inc-mask {
                            key "group-mask-address";
                            description
                              "Increment mask for group address";
                            leaf group-mask-address {
                              type inet:ipv6-address-no-zone;
                              description
                                "Increment mask for group address";
                            }
                            leaf group-address-count {
                              type uint32 {
                                range "1..512" {
                                  description
                                    "No. of group addresses to join";
                                }
                              }
                              // NCS drop mandatory statement
                              description
                                "No. of group addresses to join";
                            }
                          }
                        }
                        container group-address-source-address {
                          description
                            "Group-address with source-address";
                          list source-address {
                            key "source-address";
                            description
                              "Source address to join";
                            leaf source-address {
                              type inet:ipv6-address-no-zone;
                              description
                                "Source address to join";
                            }
                          }
                        }
                        container group-address-inc-mask-source-address {
                          description
                            "Group-address with increment-mask and source-address";
                          list inc-mask {
                            key "group-mask-address source-address";
                            description
                              "Increment mask for group address";
                            leaf group-mask-address {
                              type inet:ipv6-address-no-zone;
                              description
                                "Increment mask for group address";
                            }
                            leaf source-address {
                              type inet:ipv6-address-no-zone;
                              description
                                "Source address to join";
                            }
                            leaf group-address-count {
                              type uint32 {
                                range "1..512" {
                                  description
                                    "No. of group addresses to join";
                                }
                              }
                              // NCS drop mandatory statement
                              description
                                "No. of group addresses to join";
                            }
                          }
                        }
                        container group-address-source-address-inc-mask {
                          description
                            "Group-address and source-address with increment-mask";
                          list inc-mask {
                            key "source-address source-mask-address";
                            description
                              "Increment mask for group address";
                            leaf source-address {
                              type inet:ipv6-address-no-zone;
                              description
                                "Source address to join";
                            }
                            leaf source-mask-address {
                              type inet:ipv6-address-no-zone;
                              description
                                "Increment mask for source address";
                            }
                            leaf source-address-count {
                              type uint32 {
                                range "1..512" {
                                  description
                                    "No. of source addresses to join";
                                }
                              }
                              // NCS drop mandatory statement
                              description
                                "No. of source addresses to join";
                            }
                          }
                        }
                        container group-inc-mask-source-inc-mask {
                          description
                            "Group-address with increment-mask and source-address with increment-mask";
                          list inc-mask {
                            key "group-mask-address source-address source-mask-address";
                            leaf group-mask-address {
                              type inet:ipv6-address-no-zone;
                              description
                                "Increment mask for group address";
                            }
                            leaf source-address {
                              type inet:ipv6-address-no-zone;
                              description
                                "Source address to join";
                            }
                            leaf source-mask-address {
                              type inet:ipv6-address-no-zone;
                              description
                                "Increment mask for source address";
                            }
                            leaf group-address-count {
                              type uint32 {
                                range "1..512" {
                                  description
                                    "No. of group addresses to join";
                                }
                              }
                              // NCS drop mandatory statement
                              description
                                "No. of group addresses to join";
                            }
                            leaf source-address-count {
                              type uint32 {
                                range "1..512" {
                                  description
                                    "No. of source addresses to join";
                                }
                              }
                              // NCS drop mandatory statement
                              description
                                "No. of source addresses to join";
                            }
                          }
                        }
                      }
                    }
                  }
                }
                container embedded-rp {
                  description
                    "Set Embedded RP processing support";
                  list ip-addresses {
                    key "ip-address";
                    description
                      "IP name or address of Rendezvous Point";
                    leaf ip-address {
                      type inet:ipv6-address-no-zone;
                      description
                        "IP name or address of Rendezvous Point";
                    }
                    leaf access-list-name {
                      type xr:live_ncs_Cisco-ios-xr-string;
                      // NCS drop mandatory statement
                      description
                        "Access list of groups that should map to given RP";
                    }
                  }
                  container disable {
                    presence "Indicates a disable node is configured.";
                    description
                      "Disable Embedded RP processing";
                  }
                }
              }
            }
          }
        }
        container address-family {
          description
            "Enter Address Family command mode";
          container ipv4 {
            description
              "IPv4 Address Family";
            container rp-addresses {
              description
                "Configure Rendezvous Point";
              list rp-address {
                key "address";
                description
                  "Configure Rendezvous Point";
                leaf address {
                  type inet:ipv4-address-no-zone;
                  description
                    "Configure Rendezvous Point";
                }
                leaf access-list {
                  type xr:live_ncs_Cisco-ios-xr-string;
                  description
                    "Access list of groups that should map to given RP";
                }
                container override {
                  presence "Indicates a override node is configured.";
                  description
                    "Static RP config overrides auto-rp and BSR";
                }
              }
              container bidir {
                description
                  "Specify keyword bidir to configure a bidir RP";
                list rp-address {
                  key "address";
                  description
                    "Configure Rendezvous Point";
                  leaf address {
                    type inet:ipv4-address-no-zone;
                    description
                      "Configure Rendezvous Point";
                  }
                  leaf access-list {
                    type xr:live_ncs_Cisco-ios-xr-string;
                    description
                      "Access list of groups that should map to given RP";
                  }
                  container override {
                    presence "Indicates a override node is configured.";
                    description
                      "Static RP config overrides auto-rp and BSR";
                  }
                }
              }
            }
            leaf rp-static-deny {
              type xr:live_ncs_Cisco-ios-xr-string;
              description
                "Configure static RP deny range";
            }
            leaf accept-register {
              type xr:live_ncs_Cisco-ios-xr-string;
              description
                "Registers accept filter";
            }
            container suppress-data-registers {
              presence "Indicates a suppress-data-registers node is configured.";
              description
                "Suppress data registers after initial state setup";
            }
            leaf register-source {
              type xr:live_ncs_Interface-name;
              description
                "Source address to use for register messages";
            }
            container suppress-rpf-change-prunes {
              presence "Indicates a suppress-rpf-change-prunes node is configured.";
              description
                "Suppress prunes triggered as a result of RPF changes";
            }
            leaf neighbor-filter {
              type xr:live_ncs_Cisco-ios-xr-string;
              description
                "Neighbor filter";
            }
            container convergence {
              description
                "Convergence related parameters";
              leaf rpf-conflict-join-delay {
                type uint32 {
                  range "0..15" {
                    description
                      "Delay in seconds";
                  }
                }
                description
                  "Delay in sending first join if RPF points to any downstream neighbor";
              }
              leaf link-down-prune-delay {
                type uint32 {
                  range "0..60" {
                    description
                      "Delay in seconds";
                  }
                }
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:live_ncs_Cisco-ios-xr-string;
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type uint32 {
                  range "10..600" {
                    description
                      "Maximum time for PIM NSF mode in seconds";
                  }
                }
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type uint32 {
                range "1..3600" {
                  description
                    "Hello interval in seconds";
                }
              }
              description
                "Inherited by all interfaces : Hello interval in seconds";
            }
            leaf mdt-hello-interval {
              type uint32 {
                range "1..3600" {
                  description
                    "Hello interval in seconds";
                }
              }
              description
                "Hello interval for all MDT interfaces (seconds)";
            }
            leaf dr-priority {
              type uint32 {
                range "0..4294967295" {
                  description
                    "Hello DR priority, preference given to larger value";
                }
              }
              description
                "Inherited by all interfaces : PIM Hello DR priority";
            }
            leaf join-prune-interval {
              type uint32 {
                range "10..600" {
                  description
                    "Join-Prune interval in seconds";
                }
              }
              description
                "Inherited by all interfaces : Join-Prune interval";
            }
            leaf join-prune-mtu {
              type uint32 {
                range "576..65535" {
                  description
                    "Join-Prune MTU in bytes";
                }
              }
              description
                "Inherited by all interfaces : Join-Prune MTU";
            }
            leaf propagation-delay {
              type uint32 {
                range "100..32767" {
                  description
                    "Propagatoin delay in milliseconds";
                }
              }
              description
                "Inherited by all interfaces : PIM Hello Propagation delay";
            }
            leaf override-interval {
              type uint32 {
                range "400..65535" {
                  description
                    "Override interval in milliseconds";
                }
              }
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type uint32 {
                      range "1..200000" {
                        description
                          "Maximum PIM routes";
                      }
                    }
                    // NCS drop mandatory statement
                    description
                      "PIM routes for all VRFs";
                  }
                  leaf threshold {
                    type uint32 {
                      range "1..200000" {
                        description
                          "Threshold value";
                      }
                    }
                    // NCS drop must statement
                    description
                      "Set threshold to print warning";
                  }
                }
                container route-interfaces {
                  presence "Indicates a route-interfaces node is configured.";
                  description
                    "PIM total interfaces on routes for all VRFs";
                  leaf maximum-route-interfaces {
                    type uint32 {
                      range "1..1100000" {
                        description
                          "Maximum PIM route-interfaces";
                      }
                    }
                    // NCS drop mandatory statement
                    description
                      "PIM total interfaces on routes for all VRFs";
                  }
                  leaf threshold {
                    type uint32 {
                      range "1..1100000" {
                        description
                          "Threshold value";
                      }
                    }
                    // NCS drop must statement
                    description
                      "Set threshold to print warning";
                  }
                }
                container register-states {
                  presence "Indicates a register-states node is configured.";
                  description
                    "PIM source register states for all VRFs";
                  leaf maximum-register-states {
                    type uint32 {
                      range "0..75000" {
                        description
                          "Maximum PIM sparse-mode source register states";
                      }
                    }
                    // NCS drop mandatory statement
                    description
                      "PIM source register states for all VRFs";
                  }
                  leaf threshold {
                    type uint32 {
                      range "0..75000" {
                        description
                          "Threshold value";
                      }
                    }
                    // NCS drop must statement
                    description
                      "Set threshold to print warning";
                  }
                }
                container packet-queue {
                  description
                    "PIM Packet queue size in bytes";
                  leaf high-priority {
                    type uint32 {
                      range "0..2147483648" {
                        description
                          "Maximum PIM routes";
                      }
                    }
                    description
                      "PIM high priority packet queue size in bytes";
                  }
                  leaf low-priority {
                    type uint32 {
                      range "0..2147483648" {
                        description
                          "Maximum PIM routes";
                      }
                    }
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type uint32 {
                        range "1..10000" {
                          description
                            "Maximum PIM group-mapping learnt from BSR";
                        }
                      }
                      // NCS drop mandatory statement
                    }
                    leaf threshold {
                      type uint32 {
                        range "1..10000" {
                          description
                            "Threshold value";
                        }
                      }
                      // NCS drop must statement
                      description
                        "Set threshold to print warning";
                    }
                  }
                  container autorp {
                    presence "Indicates a autorp node is configured.";
                    description
                      "Learned through the Auto-RP distribution mechanism";
                    leaf maximum-autorp {
                      type uint32 {
                        range "1..10000" {
                          description
                            "Maximum PIM group mappings from Auto-RP mapping agent";
                        }
                      }
                      // NCS drop mandatory statement
                      description
                        "Learned through the Auto-RP distribution mechanism";
                    }
                    leaf threshold {
                      type uint32 {
                        range "1..10000" {
                          description
                            "Threshold value";
                        }
                      }
                      // NCS drop must statement
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type uint32 {
                        range "1..10000" {
                          description
                            "Maximum PIM BSR C-RP cache";
                        }
                      }
                      // NCS drop mandatory statement
                      description
                        "Set maximum number of C-RP cache in BSR";
                    }
                    leaf threshold {
                      type uint32 {
                        range "1..10000" {
                          description
                            "Threshold value";
                        }
                      }
                      // NCS drop must statement
                      description
                        "Set threshold to print warning";
                    }
                  }
                }
              }
            }
            container maximum {
              description
                "Maximum state limits";
              container routes {
                presence "Indicates a routes node is configured.";
                description
                  "PIM routes";
                leaf maximum-routes {
                  type uint32 {
                    range "1..200000" {
                      description
                        "Maximum PIM routes";
                    }
                  }
                  // NCS drop mandatory statement
                  description
                    "PIM routes";
                }
                leaf threshold {
                  type uint32 {
                    range "1..200000" {
                      description
                        "Threshold value";
                    }
                  }
                  // NCS drop must statement
                  description
                    "Set threshold to print warning";
                }
              }
              container route-interfaces {
                presence "Indicates a route-interfaces node is configured.";
                description
                  "PIM total number of interfaces on all routes";
                leaf maximum-route-interfaces {
                  type uint32 {
                    range "1..1100000" {
                      description
                        "Maximum PIM route-interfaces";
                    }
                  }
                  // NCS drop mandatory statement
                  description
                    "PIM total number of interfaces on all routes";
                }
                leaf threshold {
                  type uint32 {
                    range "1..1100000" {
                      description
                        "Threshold value";
                    }
                  }
                  // NCS drop must statement
                  description
                    "Set threshold to print warning";
                }
              }
              container register-states {
                presence "Indicates a register-states node is configured.";
                description
                  "PIM source register states";
                leaf maximum-register-states {
                  type uint32 {
                    range "0..75000" {
                      description
                        "Maximum PIM sparse-mode source register states";
                    }
                  }
                  // NCS drop mandatory statement
                  description
                    "PIM source register states";
                }
                leaf threshold {
                  type uint32 {
                    range "0..75000" {
                      description
                        "Threshold value";
                    }
                  }
                  // NCS drop must statement
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type uint32 {
                      range "1..10000" {
                        description
                          "Maximum PIM group mappings from elected BSR";
                      }
                    }
                    // NCS drop mandatory statement
                    description
                      "Learned through the BSR distribution mechanism";
                  }
                  leaf threshold {
                    type uint32 {
                      range "1..10000" {
                        description
                          "Threshold value";
                      }
                    }
                    // NCS drop must statement
                    description
                      "Set threshold to print warning";
                  }
                }
                container autorp {
                  presence "Indicates a autorp node is configured.";
                  description
                    "Learned through the Auto-RP distribution mechanism";
                  leaf maximum-autorp {
                    type uint32 {
                      range "1..10000" {
                        description
                          "Maximum PIM group mappings from Auto-RP mapping agent";
                      }
                    }
                    // NCS drop mandatory statement
                    description
                      "Learned through the Auto-RP distribution mechanism";
                  }
                  leaf threshold {
                    type uint32 {
                      range "1..10000" {
                        description
                          "Threshold value";
                      }
                    }
                    // NCS drop must statement
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type uint32 {
                      range "1..10000" {
                        description
                          "Maximum number of C-RP cache";
                      }
                    }
                    // NCS drop mandatory statement
                    description
                      "Set maximum number of C-RP cache in BSR";
                  }
                  leaf threshold {
                    type uint32 {
                      range "1..10000" {
                        description
                          "Threshold value";
                      }
                    }
                    // NCS drop must statement
                    description
                      "Set threshold to print warning";
                  }
                }
              }
            }
            leaf convergence-timeout {
              type uint32 {
                range "1800..2400" {
                  description
                    "Unicast convergence fallback timer in seconds";
                }
              }
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf-vector-injects {
              description
                "inject RPF vector";
              list inject {
                // NCS drop must statement
                key "source-address masklen";
                description
                  "inject RPF vector";
                leaf source-address {
                  type inet:ipv4-address-no-zone;
                  description
                    "inject RPF vector";
                }
                leaf masklen {
                  type uint32 {
                    range "0..32" {
                      description
                        "masklen";
                    }
                  }
                  description
                    "masklen";
                }
                leaf-list rpf-vector {
                  type inet:ipv4-address-no-zone;
                  // NCS drop max-elements statement
                  description
                    "configure this node";
                }
              }
            }
            container explicit-rpf-vector {
              description
                "Enable Explicit PIM RPF Vector";
              container injects {
                description
                  "inject Explicit RPF vector";
                list inject {
                  // NCS drop must statement
                  key "source-address masklen";
                  description
                    "inject Explicit RPF vector";
                  leaf source-address {
                    type inet:ipv4-address-no-zone;
                    description
                      "inject Explicit RPF vector";
                  }
                  leaf masklen {
                    type uint32 {
                      range "0..32" {
                        description
                          "masklen";
                      }
                    }
                    description
                      "masklen";
                  }
                  leaf-list rpf-vector {
                    type inet:ipv4-address-no-zone;
                    // NCS drop max-elements statement
                    description
                      "configure this node";
                  }
                }
              }
            }
            container rpf {
              description
                "RPF commands";
              container topology {
                description
                  "Select RPF topology";
                leaf route-policy {
                  type xr:live_ncs_Route-policy-name;
                  description
                    "Route policy to select RPF topology";
                }
              }
            }
            container mdt {
              description
                "Multicast Distribution Tree commands";
              leaf neighbor-filter {
                type xr:live_ncs_Cisco-ios-xr-string;
                description
                  "Neighbor filter";
              }
              container data {
                description
                  "Data MDT Options";
                leaf switchover-interval {
                  type uint32 {
                    range "3..60" {
                      description
                        "Interval value in seconds";
                    }
                  }
                  description
                    "Data MDT switchover interval";
                }
                leaf announce-interval {
                  type uint32 {
                    range "3..120" {
                      description
                        "Interval value in seconds";
                    }
                  }
                  description
                    "Periodic Data MDT Join TLV interval";
                }
                leaf max-aggregation {
                  type uint32 {
                    range "1..16777215" {
                      description
                        "Aggregation value";
                    }
                  }
                  description
                    "Data MDT max-aggregation";
                }
              }
              container c-multicast-routing {
                presence "Indicates a c-multicast-routing node is configured.";
                description
                  "MVPN customer routing commands";
                leaf type {
                  type enumeration {
                    enum "pim" {
                      value 1;
                      description
                        "PIM customer multicast routing";
                    }
                    enum "bgp" {
                      value 2;
                      description
                        "BGP customer multicast routing";
                    }
                  }
                  // NCS drop mandatory statement
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  // NCS drop when statement
                  description
                    "PIM Hellos over MDT";
                  container enable {
                    presence "Indicates a enable node is configured.";
                    description
                      "Enable PIM Hellos over MDT";
                  }
                }
                leaf shared-tree-prune-delay {
                  type uint32 {
                    range "0..1800" {
                      description
                        "Delay in seconds.";
                    }
                  }
                  description
                    "Delay before pruning I-S PMSI from S,G when SA received";
                }
                leaf source-tree-prune-delay {
                  type uint32 {
                    range "0..300" {
                      description
                        "Delay in seconds.";
                    }
                  }
                  description
                    "Delay before removing PMSI from olist after BGP withdrawal";
                }
                container migration {
                  presence "Indicates a migration node is configured.";
                  description
                    "customer routing migration";
                  leaf route-policy {
                    type xr:live_ncs_Route-policy-name;
                    description
                      "Route policy to select customer routing";
                  }
                }
                container unicast-reachability {
                  description
                    "Control addition of Extended Communities to Unicast VPN-IP routes";
                  container connector {
                    description
                      "Enable/Disable Connector";
                    container disable {
                      // NCS drop must statement
                      presence "Indicates a disable node is configured.";
                      description
                        "Disable Connector Attribute";
                    }
                    container enable {
                      // NCS drop must statement
                      presence "Indicates a enable node is configured.";
                      description
                        "Enable Connector Attribute";
                    }
                  }
                  container source-as {
                    description
                      "Enable/Disable Source AS";
                    container disable {
                      // NCS drop must statement
                      presence "Indicates a disable node is configured.";
                      description
                        "Disable Source-AS Attribute";
                    }
                    container enable {
                      // NCS drop must statement
                      presence "Indicates a enable node is configured.";
                      description
                        "Enable Source-AS Attribute";
                    }
                  }
                  container vrf-route-import {
                    description
                      "Enable/Disable VRF Route Import";
                    container disable {
                      // NCS drop must statement
                      presence "Indicates a disable node is configured.";
                      description
                        "Disable VRF Route Import Attribute";
                    }
                    container enable {
                      // NCS drop must statement
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:live_ncs_Cisco-ios-xr-string;
                description
                  "Access-list for allowed RP addresses";
              }
              leaf group-list {
                type xr:live_ncs_Cisco-ios-xr-string;
                description
                  "Access-list for allowed group ranges";
              }
            }
            container sg-expiry-timer {
              presence "Indicates a sg-expiry-timer node is configured.";
              description
                "Configure SG expiry timer";
              leaf sg-expiry-timer-value {
                type uint32 {
                  range "40..57600" {
                    description
                      "Duration of the expiry timer interval, in seconds";
                  }
                }
                // NCS drop mandatory statement
                description
                  "Configure SG expiry timer";
              }
              leaf sg-list {
                type xr:live_ncs_Cisco-ios-xr-string;
                description
                  "Access-list of (S,G) routes for which expiry timer is applicable";
              }
            }
            container ssm {
              description
                "Configure a group range for Source-Specific use";
              leaf range {
                type xr:live_ncs_Cisco-ios-xr-string;
                // NCS drop must statement
                description
                  "Provide ACL that specifies non-standard SSM range";
              }
              container disable {
                // NCS drop must statement
                presence "Indicates a disable node is configured.";
                description
                  "Disable use of all SSM group ranges";
              }
              container allow-override {
                presence "Indicates a allow-override node is configured.";
                description
                  "Allow SSM ranges to be overridden by more specific ranges";
              }
            }
            container rpf-redirect {
              description
                "Route policy for rpf-redirect bundles";
              leaf route-policy {
                type xr:live_ncs_Route-policy-name;
                description
                  "Bandwidth assigment (kbps) for SG routes";
              }
            }
            container multipath {
              presence "Indicates a multipath node is configured.";
              description
                "Enable equal-cost multipath routing";
              container hash {
                // NCS drop must statement
                presence "Indicates a hash node is configured.";
                description
                  "Enter a hashing algorithm";
                container source {
                  // NCS drop must statement
                  presence "Indicates a source node is configured.";
                  description
                    "Enable source based multipath hashing (Compatible with IOS versions)";
                }
                container source-nexthop {
                  // NCS drop must statement
                  presence "Indicates a source-nexthop node is configured.";
                  description
                    "Enable source with next-hop multipath hashing (better distribution)";
                }
                container source-group {
                  // NCS drop must statement
                  presence "Indicates a source-group node is configured.";
                  description
                    "Enable source, group based multipath hashing (Compatible with IOS versions)";
                }
              }
            }
            container auto-rp {
              description
                "Auto-RP Commands";
              container candidate-rps {
                description
                  "Configure as a Candidate RP";
                list candidate-rp {
                  // NCS drop must statement
                  key "interface-name";
                  description
                    "Candidate RP Configurations";
                  leaf interface-name {
                    type xr:live_ncs_Interface-name;
                    description
                      "Candidate RP Configurations";
                  }
                  leaf scope {
                    type uint32 {
                      range "1..255" {
                        description
                          "TTL in hops";
                      }
                    }
                    // NCS drop must statement
                    description
                      "TTL for the announcement";
                  }
                  leaf group-list {
                    type xr:live_ncs_Cisco-ios-xr-string;
                    description
                      "Be a candidate RP for groups specified by the acl";
                  }
                  leaf interval {
                    type uint32 {
                      range "1..600" {
                        description
                          "interval in second";
                      }
                    }
                    description
                      "time between announcements <in seconds>";
                  }
                  container bidir {
                    description
                      "to specify group ranges as bidir, default is pim-sm";
                    leaf scope {
                      type uint32 {
                        range "1..255" {
                          description
                            "TTL in hops";
                        }
                      }
                      // NCS drop must statement
                      description
                        "TTL for the announcement";
                    }
                    leaf group-list {
                      type xr:live_ncs_Cisco-ios-xr-string;
                      description
                        "Be a candidate RP for groups specified by the acl";
                    }
                    leaf interval {
                      type uint32 {
                        range "1..600" {
                          description
                            "interval in second";
                        }
                      }
                      description
                        "time between announcements <in seconds>";
                    }
                  }
                }
              }
              container mapping-agent {
                presence "Indicates a mapping-agent node is configured.";
                description
                  "Configure as a Mapping Agent";
                leaf interface-name {
                  type xr:live_ncs_Interface-name;
                  // NCS drop mandatory statement
                  description
                    "Candidate RP Configurations";
                }
                leaf scope {
                  type uint32 {
                    range "1..255" {
                      description
                        "TTL in hops";
                    }
                  }
                  // NCS drop mandatory statement
                  description
                    "TTL for the announcement";
                }
                leaf interval {
                  type uint32 {
                    range "1..600" {
                      description
                        "interval in second";
                    }
                  }
                  // NCS drop mandatory statement
                  description
                    "number of seconds between discovery messages";
                }
              }
              container listen {
                description
                  "RP discovery through AUTORP protocol";
                container disable {
                  presence "Indicates a disable node is configured.";
                  description
                    "Disable RP discovery through the AUTORP protocol";
                }
              }
              container relay {
                description
                  "relay";
                container vrfs {
                  description
                    "vrf";
                  list vrf {
                    key "vrf-name";
                    description
                      "vrf";
                    leaf vrf-name {
                      type xr:live_ncs_Cisco-ios-xr-string;
                      description
                        "vrf";
                    }
                    container listen {
                      presence "Indicates a listen node is configured.";
                      description
                        "Enable RP relay in listen mode";
                    }
                  }
                }
              }
            }
            container interface {
              description
                "PIM interface configuration subcommands";
              container interfaces {
                description
                  "Select an interface to configure";
                list interface {
                  key "interface-name";
                  description
                    "Select an interface to configure";
                  leaf interface-name {
                    type xr:live_ncs_Interface-name;
                    description
                      "Select an interface to configure";
                  }
                  leaf dr-priority {
                    type uint32 {
                      range "0..4294967295" {
                        description
                          "Hello DR priority, preference given to larger value";
                      }
                    }
                    description
                      "PIM Hello DR priority";
                  }
                  leaf hello-interval {
                    type uint32 {
                      range "1..3600" {
                        description
                          "Hello interval in seconds";
                      }
                    }
                    description
                      "PIM neighbor Hello announcement interval";
                  }
                  leaf join-prune-interval {
                    type uint32 {
                      range "10..600" {
                        description
                          "Join-Prune interval in seconds";
                      }
                    }
                    description
                      "PIM periodic Join-Prune announcement interval";
                  }
                  leaf join-prune-mtu {
                    type uint32 {
                      range "576..65535" {
                        description
                          "MTU to use in bytes";
                      }
                    }
                    description
                      "MTU to use when sending PIM J/P packets";
                  }
                  leaf propagation-delay {
                    type uint32 {
                      range "100..32767" {
                        description
                          "Propagatoin delay in milliseconds";
                      }
                    }
                    description
                      "PIM Hello propagation delay";
                  }
                  leaf override-interval {
                    type uint32 {
                      range "400..65535" {
                        description
                          "Override interval in milliseconds";
                      }
                    }
                    description
                      "PIM Hello override interval";
                  }
                  container bsr-border {
                    presence "Indicates a bsr-border node is configured.";
                    description
                      "Do not fwd BSR messages on this interface";
                  }
                  container enable {
                    // NCS drop must statement
                    presence "Indicates a enable node is configured.";
                    description
                      "Enable PIM processing on this interface";
                  }
                  container disable {
                    // NCS drop must statement
                    presence "Indicates a disable node is configured.";
                    description
                      "Disable PIM processing on this interface";
                  }
                  leaf neighbor-filter {
                    type xr:live_ncs_Cisco-ios-xr-string;
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type uint32 {
                          range "1..1100000" {
                            description
                              "Maximum number of allowed routes for this interface";
                          }
                        }
                        // NCS drop mandatory statement
                        description
                          "PIM downstream joined interfaces";
                      }
                      leaf threshold {
                        type uint32 {
                          range "1..1100000" {
                            description
                              "Threshold warning";
                          }
                        }
                        // NCS drop must statement
                        description
                          "Threshold warning";
                      }
                      leaf access-list {
                        type xr:live_ncs_Cisco-ios-xr-string;
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type uint32 {
                        range "3..30000" {
                          description
                            "hello interval in milli-seconds";
                        }
                      }
                      description
                        "Hello interval";
                    }
                    leaf multiplier {
                      type uint32 {
                        range "2..50" {
                          description
                            "Detect multiplier";
                        }
                      }
                      description
                        "Detect multiplier";
                    }
                  }
                  container rpf-redirect {
                    presence "Indicates a rpf-redirect node is configured.";
                    description
                      "RPF redirect bundle configuration";
                    leaf bundle {
                      type xr:live_ncs_Cisco-ios-xr-string;
                      // NCS drop mandatory statement
                      description
                        "Bundle name";
                    }
                    leaf bandwidth {
                      type uint32 {
                        range "0..100000000" {
                          description
                            "Interface bandwidth in Kbps";
                        }
                      }
                      description
                        "Interface bandwidth in Kbps";
                    }
                    leaf threshold {
                      type uint32 {
                        range "0..100000000" {
                          description
                            "Bandwidth threshold in Kbps";
                        }
                      }
                      // NCS drop must statement
                      description
                        "Bandwidth threshold in Kbps";
                    }
                  }
                }
              }
            }
            container bsr {
              description
                "BSR Configurations";
              container candidate-bsr {
                presence "Indicates a candidate-bsr node is configured.";
                description
                  "configure candidate BSR";
                leaf address {
                  type inet:ipv4-address-no-zone;
                  // NCS drop mandatory statement
                  description
                    "IP address of configured BSR";
                }
                leaf hash-mask-len {
                  type uint32 {
                    range "0..32" {
                      description
                        "mask length";
                    }
                  }
                  // NCS drop mandatory statement
                  description
                    "BSR Hash Mask Length";
                }
                leaf priority {
                  type uint32 {
                    range "1..255" {
                      description
                        "priority";
                    }
                  }
                  // NCS drop mandatory statement
                  description
                    "BSR Priority";
                }
              }
              container candidate-rps {
                description
                  "BSR Candidate RP Configurations";
                list candidate-rp {
                  // NCS drop must statement
                  key "address";
                  description
                    "BSR Candidate RP Configurations";
                  leaf address {
                    type inet:ipv4-address-no-zone;
                    description
                      "BSR Candidate RP Configurations";
                  }
                  leaf group-list {
                    type xr:live_ncs_Cisco-ios-xr-string;
                    description
                      "Group List access-list";
                  }
                  leaf priority {
                    type uint32 {
                      range "1..255" {
                        description
                          "priority";
                      }
                    }
                    description
                      "C-RP Priority";
                  }
                  leaf interval {
                    type uint32 {
                      range "30..600" {
                        description
                          "interval in second";
                      }
                    }
                    description
                      "C-RP Advertisement interval";
                  }
                  container bidir {
                    description
                      "To specify group ranges as Bidir";
                    leaf group-list {
                      type xr:live_ncs_Cisco-ios-xr-string;
                      description
                        "Group List access-list";
                    }
                    leaf priority {
                      type uint32 {
                        range "1..255" {
                          description
                            "priority";
                        }
                      }
                      description
                        "C-RP Priority";
                    }
                    leaf interval {
                      type uint32 {
                        range "30..600" {
                          description
                            "interval in second";
                        }
                      }
                      description
                        "C-RP Advertisement interval";
                    }
                  }
                }
              }
              container relay {
                description
                  "BSR RP relay config";
                container vrfs {
                  description
                    "vrf";
                  list vrf {
                    key "vrf-name";
                    description
                      "vrf";
                    leaf vrf-name {
                      type xr:live_ncs_Cisco-ios-xr-string;
                      description
                        "vrf";
                    }
                    container listen {
                      presence "Indicates a listen node is configured.";
                      description
                        "Enable RP relay in listen mode";
                    }
                  }
                }
              }
            }
            container mofrr {
              presence "Indicates a mofrr node is configured.";
              description
                "PIM Mofrr";
              leaf flow {
                type string {
                  length "1..1024" {
                    description
                      "Access list specifying SGs that should do MOFRR with hardware switchover triggers";
                  }
                }
                description
                  "Multicast Only FRR";
              }
              leaf rib {
                type string {
                  length "1..1024" {
                    description
                      "Access list specifying SGs that should do MOFRR with RIB events as switchover triggers";
                  }
                }
                description
                  "Use the rib keyword to restrict switchover triggers to RIB events";
              }
              container non-revertive {
                presence "Indicates a non-revertive node is configured.";
                description
                  "Non-revertive MoFRR";
              }
              container clone {
                description
                  "Use the clone keyword to clone";
                container joins {
                  description
                    "Use the join keyword to clone S,G as S1,G joins and S2,G joins";
                  list join {
                    // NCS drop must statement
                    key "address";
                    description
                      "Use the join keyword to clone S,G as S1,G joins as S2,G joins";
                    leaf address {
                      type inet:ipv4-address-no-zone;
                      description
                        "Source S";
                    }
                    list to {
                      // NCS drop must statement
                      key "address";
                      description
                        "to";
                      leaf address {
                        type inet:ipv4-address-no-zone;
                        description
                          "Source S1";
                      }
                      list and {
                        // NCS drop must statement
                        key "address";
                        description
                          "and";
                        leaf address {
                          type inet:ipv4-address-no-zone;
                          description
                            "Source S2";
                        }
                        list masklen {
                          key "mask-length";
                          description
                            "masklen";
                          leaf mask-length {
                            type uint32 {
                              range "0..32" {
                                description
                                  "masklen";
                              }
                            }
                            description
                              "masklen";
                          }
                        }
                      }
                    }
                  }
                }
                container sources {
                  description
                    "Use the source keyword to clone S,G as S1,G traffic and S2,G traffic";
                  list source {
                    // NCS drop must statement
                    key "address";
                    description
                      "Use the source keyword to clone S,G as S1,G traffic and S2,G traffic";
                    leaf address {
                      type inet:ipv4-address-no-zone;
                      description
                        "Source S";
                    }
                    list to {
                      // NCS drop must statement
                      key "address";
                      description
                        "to";
                      leaf address {
                        type inet:ipv4-address-no-zone;
                        description
                          "Source S1";
                      }
                      list and {
                        // NCS drop must statement
                        key "address";
                        description
                          "and";
                        leaf address {
                          type inet:ipv4-address-no-zone;
                          description
                            "Source S2";
                        }
                        list masklen {
                          key "mask-length";
                          description
                            "masklen";
                          leaf mask-length {
                            type uint32 {
                              range "0..32" {
                                description
                                  "masklen";
                              }
                            }
                            description
                              "masklen";
                          }
                        }
                      }
                    }
                  }
                }
              }
            }
            container sr-p2mp-policies {
              description
                "Segment-routing P2MP policy";
              list sr-p2mp-policy {
                key "sr-p2mp-policy-id";
                description
                  "Segment-routing P2MP policy";
                leaf sr-p2mp-policy-id {
                  type xr:live_ncs_Cisco-ios-xr-string;
                  description
                    "Segment-routing P2MP policy";
                }
                container static-group {
                  description
                    "ipv4 static multicast group";
                  list group-address {
                    key "group-address";
                    description
                      "ipv4 static multicast group";
                    leaf group-address {
                      type inet:ipv4-address-no-zone;
                      description
                        "ipv4 static multicast group";
                    }
                    container group-address-only {
                      presence "Indicates a group-address-only node is configured.";
                      description
                        "Group-address without increment mask/source-address";
                    }
                    container group-address-inc-masks {
                      description
                        "Group-address with increment mask for group address";
                      list inc-mask {
                        key "group-mask-address";
                        description
                          "Increment mask for group address";
                        leaf group-mask-address {
                          type inet:ipv4-address-no-zone;
                          description
                            "Increment mask for group address";
                        }
                        leaf group-address-count {
                          type uint32 {
                            range "1..512" {
                              description
                                "No. of group addresses to join";
                            }
                          }
                          // NCS drop mandatory statement
                          description
                            "No. of group addresses to join";
                        }
                      }
                    }
                    container group-address-source-address {
                      description
                        "Group-address with source-address";
                      list source-address {
                        key "source-address";
                        description
                          "Source address to join";
                        leaf source-address {
                          type inet:ipv4-address-no-zone;
                          description
                            "Source address to join";
                        }
                      }
                    }
                    container group-address-inc-mask-source-address {
                      description
                        "Group-address with increment-mask and source-address";
                      list inc-mask {
                        key "group-mask-address source-address";
                        description
                          "Increment mask for group address";
                        leaf group-mask-address {
                          type inet:ipv4-address-no-zone;
                          description
                            "Increment mask for group address";
                        }
                        leaf source-address {
                          type inet:ipv4-address-no-zone;
                          description
                            "Source address to join";
                        }
                        leaf group-address-count {
                          type uint32 {
                            range "1..512" {
                              description
                                "No. of group addresses to join";
                            }
                          }
                          // NCS drop mandatory statement
                          description
                            "No. of group addresses to join";
                        }
                      }
                    }
                    container group-address-source-address-inc-mask {
                      description
                        "Group-address and source-address with increment-mask";
                      list inc-mask {
                        key "source-address source-mask-address";
                        description
                          "Increment mask for group address";
                        leaf source-address {
                          type inet:ipv4-address-no-zone;
                          description
                            "Source address to join";
                        }
                        leaf source-mask-address {
                          type inet:ipv4-address-no-zone;
                          description
                            "Increment mask for source address";
                        }
                        leaf source-address-count {
                          type uint32 {
                            range "1..512" {
                              description
                                "No. of source addresses to join";
                            }
                          }
                          // NCS drop mandatory statement
                          description
                            "No. of source addresses to join";
                        }
                      }
                    }
                    container group-inc-mask-source-inc-mask {
                      description
                        "Group-address with increment-mask and source-address with increment-mask";
                      list inc-mask {
                        key "group-mask-address source-address source-mask-address";
                        leaf group-mask-address {
                          type inet:ipv4-address-no-zone;
                          description
                            "Increment mask for group address";
                        }
                        leaf source-address {
                          type inet:ipv4-address-no-zone;
                          description
                            "Source address to join";
                        }
                        leaf source-mask-address {
                          type inet:ipv4-address-no-zone;
                          description
                            "Increment mask for source address";
                        }
                        leaf group-address-count {
                          type uint32 {
                            range "1..512" {
                              description
                                "No. of group addresses to join";
                            }
                          }
                          // NCS drop mandatory statement
                          description
                            "No. of group addresses to join";
                        }
                        leaf source-address-count {
                          type uint32 {
                            range "1..512" {
                              description
                                "No. of source addresses to join";
                            }
                          }
                          // NCS drop mandatory statement
                          description
                            "No. of source addresses to join";
                        }
                      }
                    }
                  }
                }
              }
            }
          }
          container ipv6 {
            description
              "IPv6 Address Family";
            container rp-addresses {
              description
                "Configure Rendezvous Point";
              list rp-address {
                key "address";
                description
                  "Configure Rendezvous Point";
                leaf address {
                  type inet:ipv6-address-no-zone;
                  description
                    "Configure Rendezvous Point";
                }
                leaf access-list {
                  type xr:live_ncs_Cisco-ios-xr-string;
                  description
                    "Access list of groups that should map to given RP";
                }
                container override {
                  presence "Indicates a override node is configured.";
                  description
                    "Static RP config overrides auto-rp and BSR";
                }
              }
              container bidir {
                description
                  "Specify keyword bidir to configure a bidir RP";
                list rp-address {
                  key "address";
                  description
                    "Configure Rendezvous Point";
                  leaf address {
                    type inet:ipv6-address-no-zone;
                    description
                      "Configure Rendezvous Point";
                  }
                  leaf access-list {
                    type xr:live_ncs_Cisco-ios-xr-string;
                    description
                      "Access list of groups that should map to given RP";
                  }
                  container override {
                    presence "Indicates a override node is configured.";
                    description
                      "Static RP config overrides auto-rp and BSR";
                  }
                }
              }
            }
            leaf rp-static-deny {
              type xr:live_ncs_Cisco-ios-xr-string;
              description
                "Configure static RP deny range";
            }
            leaf accept-register {
              type xr:live_ncs_Cisco-ios-xr-string;
              description
                "Registers accept filter";
            }
            container suppress-data-registers {
              presence "Indicates a suppress-data-registers node is configured.";
              description
                "Suppress data registers after initial state setup";
            }
            leaf register-source {
              type xr:live_ncs_Interface-name;
              description
                "Source address to use for register messages";
            }
            container suppress-rpf-change-prunes {
              presence "Indicates a suppress-rpf-change-prunes node is configured.";
              description
                "Suppress prunes triggered as a result of RPF changes";
            }
            leaf neighbor-filter {
              type xr:live_ncs_Cisco-ios-xr-string;
              description
                "Neighbor filter";
            }
            container convergence {
              description
                "Convergence related parameters";
              leaf rpf-conflict-join-delay {
                type uint32 {
                  range "0..15" {
                    description
                      "Delay in seconds";
                  }
                }
                description
                  "Delay in sending first join if RPF points to any downstream neighbor";
              }
              leaf link-down-prune-delay {
                type uint32 {
                  range "0..60" {
                    description
                      "Delay in seconds";
                  }
                }
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:live_ncs_Cisco-ios-xr-string;
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type uint32 {
                  range "10..600" {
                    description
                      "Maximum time for PIM NSF mode in seconds";
                  }
                }
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type uint32 {
                range "1..3600" {
                  description
                    "Hello interval in seconds";
                }
              }
              description
                "Inherited by all interfaces : Hello interval in seconds";
            }
            leaf mdt-hello-interval {
              type uint32 {
                range "1..3600" {
                  description
                    "Hello interval in seconds";
                }
              }
              description
                "Hello interval for all MDT interfaces (seconds)";
            }
            leaf dr-priority {
              type uint32 {
                range "0..4294967295" {
                  description
                    "Hello DR priority, preference given to larger value";
                }
              }
              description
                "Inherited by all interfaces : PIM Hello DR priority";
            }
            leaf join-prune-interval {
              type uint32 {
                range "10..600" {
                  description
                    "Join-Prune interval in seconds";
                }
              }
              description
                "Inherited by all interfaces : Join-Prune interval";
            }
            leaf join-prune-mtu {
              type uint32 {
                range "576..65535" {
                  description
                    "Join-Prune MTU in bytes";
                }
              }
              description
                "Inherited by all interfaces : Join-Prune MTU";
            }
            leaf propagation-delay {
              type uint32 {
                range "100..32767" {
                  description
                    "Propagatoin delay in milliseconds";
                }
              }
              description
                "Inherited by all interfaces : PIM Hello Propagation delay";
            }
            leaf override-interval {
              type uint32 {
                range "400..65535" {
                  description
                    "Override interval in milliseconds";
                }
              }
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type uint32 {
                      range "1..200000" {
                        description
                          "Maximum PIM routes";
                      }
                    }
                    // NCS drop mandatory statement
                    description
                      "PIM routes for all VRFs";
                  }
                  leaf threshold {
                    type uint32 {
                      range "1..200000" {
                        description
                          "Threshold value";
                      }
                    }
                    // NCS drop must statement
                    description
                      "Set threshold to print warning";
                  }
                }
                container route-interfaces {
                  presence "Indicates a route-interfaces node is configured.";
                  description
                    "PIM total interfaces on routes for all VRFs";
                  leaf maximum-route-interfaces {
                    type uint32 {
                      range "1..1100000" {
                        description
                          "Maximum PIM route-interfaces";
                      }
                    }
                    // NCS drop mandatory statement
                    description
                      "PIM total interfaces on routes for all VRFs";
                  }
                  leaf threshold {
                    type uint32 {
                      range "1..1100000" {
                        description
                          "Threshold value";
                      }
                    }
                    // NCS drop must statement
                    description
                      "Set threshold to print warning";
                  }
                }
                container register-states {
                  presence "Indicates a register-states node is configured.";
                  description
                    "PIM source register states for all VRFs";
                  leaf maximum-register-states {
                    type uint32 {
                      range "0..75000" {
                        description
                          "Maximum PIM sparse-mode source register states";
                      }
                    }
                    // NCS drop mandatory statement
                    description
                      "PIM source register states for all VRFs";
                  }
                  leaf threshold {
                    type uint32 {
                      range "0..75000" {
                        description
                          "Threshold value";
                      }
                    }
                    // NCS drop must statement
                    description
                      "Set threshold to print warning";
                  }
                }
                container packet-queue {
                  description
                    "PIM Packet queue size in bytes";
                  leaf high-priority {
                    type uint32 {
                      range "0..2147483648" {
                        description
                          "Maximum PIM routes";
                      }
                    }
                    description
                      "PIM high priority packet queue size in bytes";
                  }
                  leaf low-priority {
                    type uint32 {
                      range "0..2147483648" {
                        description
                          "Maximum PIM routes";
                      }
                    }
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type uint32 {
                        range "1..10000" {
                          description
                            "Maximum PIM group-mapping learnt from BSR";
                        }
                      }
                      // NCS drop mandatory statement
                    }
                    leaf threshold {
                      type uint32 {
                        range "1..10000" {
                          description
                            "Threshold value";
                        }
                      }
                      // NCS drop must statement
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type uint32 {
                        range "1..10000" {
                          description
                            "Maximum PIM BSR C-RP cache";
                        }
                      }
                      // NCS drop mandatory statement
                      description
                        "Set maximum number of C-RP cache in BSR";
                    }
                    leaf threshold {
                      type uint32 {
                        range "1..10000" {
                          description
                            "Threshold value";
                        }
                      }
                      // NCS drop must statement
                      description
                        "Set threshold to print warning";
                    }
                  }
                }
              }
            }
            container maximum {
              description
                "Maximum state limits";
              container routes {
                presence "Indicates a routes node is configured.";
                description
                  "PIM routes";
                leaf maximum-routes {
                  type uint32 {
                    range "1..200000" {
                      description
                        "Maximum PIM routes";
                    }
                  }
                  // NCS drop mandatory statement
                  description
                    "PIM routes";
                }
                leaf threshold {
                  type uint32 {
                    range "1..200000" {
                      description
                        "Threshold value";
                    }
                  }
                  // NCS drop must statement
                  description
                    "Set threshold to print warning";
                }
              }
              container route-interfaces {
                presence "Indicates a route-interfaces node is configured.";
                description
                  "PIM total number of interfaces on all routes";
                leaf maximum-route-interfaces {
                  type uint32 {
                    range "1..1100000" {
                      description
                        "Maximum PIM route-interfaces";
                    }
                  }
                  // NCS drop mandatory statement
                  description
                    "PIM total number of interfaces on all routes";
                }
                leaf threshold {
                  type uint32 {
                    range "1..1100000" {
                      description
                        "Threshold value";
                    }
                  }
                  // NCS drop must statement
                  description
                    "Set threshold to print warning";
                }
              }
              container register-states {
                presence "Indicates a register-states node is configured.";
                description
                  "PIM source register states";
                leaf maximum-register-states {
                  type uint32 {
                    range "0..75000" {
                      description
                        "Maximum PIM sparse-mode source register states";
                    }
                  }
                  // NCS drop mandatory statement
                  description
                    "PIM source register states";
                }
                leaf threshold {
                  type uint32 {
                    range "0..75000" {
                      description
                        "Threshold value";
                    }
                  }
                  // NCS drop must statement
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type uint32 {
                      range "1..10000" {
                        description
                          "Maximum PIM group mappings from elected BSR";
                      }
                    }
                    // NCS drop mandatory statement
                    description
                      "Learned through the BSR distribution mechanism";
                  }
                  leaf threshold {
                    type uint32 {
                      range "1..10000" {
                        description
                          "Threshold value";
                      }
                    }
                    // NCS drop must statement
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type uint32 {
                      range "1..10000" {
                        description
                          "Maximum number of C-RP cache";
                      }
                    }
                    // NCS drop mandatory statement
                    description
                      "Set maximum number of C-RP cache in BSR";
                  }
                  leaf threshold {
                    type uint32 {
                      range "1..10000" {
                        description
                          "Threshold value";
                      }
                    }
                    // NCS drop must statement
                    description
                      "Set threshold to print warning";
                  }
                }
              }
            }
            leaf convergence-timeout {
              type uint32 {
                range "1800..2400" {
                  description
                    "Unicast convergence fallback timer in seconds";
                }
              }
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf {
              description
                "RPF commands";
              container topology {
                description
                  "Select RPF topology";
                leaf route-policy {
                  type xr:live_ncs_Route-policy-name;
                  description
                    "Route policy to select RPF topology";
                }
              }
            }
            container mdt {
              description
                "Multicast Distribution Tree commands";
              leaf neighbor-filter {
                type xr:live_ncs_Cisco-ios-xr-string;
                description
                  "Neighbor filter";
              }
              container data {
                description
                  "Data MDT Options";
                leaf switchover-interval {
                  type uint32 {
                    range "3..60" {
                      description
                        "Interval value in seconds";
                    }
                  }
                  description
                    "Data MDT switchover interval";
                }
                leaf announce-interval {
                  type uint32 {
                    range "3..120" {
                      description
                        "Interval value in seconds";
                    }
                  }
                  description
                    "Periodic Data MDT Join TLV interval";
                }
                leaf max-aggregation {
                  type uint32 {
                    range "1..16777215" {
                      description
                        "Aggregation value";
                    }
                  }
                  description
                    "Data MDT max-aggregation";
                }
              }
              container c-multicast-routing {
                presence "Indicates a c-multicast-routing node is configured.";
                description
                  "MVPN customer routing commands";
                leaf type {
                  type enumeration {
                    enum "pim" {
                      value 1;
                      description
                        "PIM customer multicast routing";
                    }
                    enum "bgp" {
                      value 2;
                      description
                        "BGP customer multicast routing";
                    }
                  }
                  // NCS drop mandatory statement
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  // NCS drop when statement
                  description
                    "PIM Hellos over MDT";
                  container enable {
                    presence "Indicates a enable node is configured.";
                    description
                      "Enable PIM Hellos over MDT";
                  }
                }
                leaf shared-tree-prune-delay {
                  type uint32 {
                    range "0..1800" {
                      description
                        "Delay in seconds.";
                    }
                  }
                  description
                    "Delay before pruning I-S PMSI from S,G when SA received";
                }
                leaf source-tree-prune-delay {
                  type uint32 {
                    range "0..300" {
                      description
                        "Delay in seconds.";
                    }
                  }
                  description
                    "Delay before removing PMSI from olist after BGP withdrawal";
                }
                container migration {
                  presence "Indicates a migration node is configured.";
                  description
                    "customer routing migration";
                  leaf route-policy {
                    type xr:live_ncs_Route-policy-name;
                    description
                      "Route policy to select customer routing";
                  }
                }
                container unicast-reachability {
                  description
                    "Control addition of Extended Communities to Unicast VPN-IP routes";
                  container connector {
                    description
                      "Enable/Disable Connector";
                    container disable {
                      // NCS drop must statement
                      presence "Indicates a disable node is configured.";
                      description
                        "Disable Connector Attribute";
                    }
                    container enable {
                      // NCS drop must statement
                      presence "Indicates a enable node is configured.";
                      description
                        "Enable Connector Attribute";
                    }
                  }
                  container source-as {
                    description
                      "Enable/Disable Source AS";
                    container disable {
                      // NCS drop must statement
                      presence "Indicates a disable node is configured.";
                      description
                        "Disable Source-AS Attribute";
                    }
                    container enable {
                      // NCS drop must statement
                      presence "Indicates a enable node is configured.";
                      description
                        "Enable Source-AS Attribute";
                    }
                  }
                  container vrf-route-import {
                    description
                      "Enable/Disable VRF Route Import";
                    container disable {
                      // NCS drop must statement
                      presence "Indicates a disable node is configured.";
                      description
                        "Disable VRF Route Import Attribute";
                    }
                    container enable {
                      // NCS drop must statement
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:live_ncs_Cisco-ios-xr-string;
                description
                  "Access-list for allowed RP addresses";
              }
              leaf group-list {
                type xr:live_ncs_Cisco-ios-xr-string;
                description
                  "Access-list for allowed group ranges";
              }
            }
            container sg-expiry-timer {
              presence "Indicates a sg-expiry-timer node is configured.";
              description
                "Configure SG expiry timer";
              leaf sg-expiry-timer-value {
                type uint32 {
                  range "40..57600" {
                    description
                      "Duration of the expiry timer interval, in seconds";
                  }
                }
                // NCS drop mandatory statement
                description
                  "Configure SG expiry timer";
              }
              leaf sg-list {
                type xr:live_ncs_Cisco-ios-xr-string;
                description
                  "Access-list of (S,G) routes for which expiry timer is applicable";
              }
            }
            container ssm {
              description
                "Configure a group range for Source-Specific use";
              leaf range {
                type xr:live_ncs_Cisco-ios-xr-string;
                // NCS drop must statement
                description
                  "Provide ACL that specifies non-standard SSM range";
              }
              container disable {
                // NCS drop must statement
                presence "Indicates a disable node is configured.";
                description
                  "Disable use of all SSM group ranges";
              }
              container allow-override {
                presence "Indicates a allow-override node is configured.";
                description
                  "Allow SSM ranges to be overridden by more specific ranges";
              }
            }
            container multipath {
              presence "Indicates a multipath node is configured.";
              description
                "Enable equal-cost multipath routing";
              container hash {
                // NCS drop must statement
                presence "Indicates a hash node is configured.";
                description
                  "Enter a hashing algorithm";
                container interface-extended {
                  // NCS drop must statement
                  presence "Indicates a interface-extended node is configured.";
                  description
                    "Enable interface extensions for non-unique next-hop addrs";
                }
                container source-nexthop {
                  // NCS drop must statement
                  presence "Indicates a source-nexthop node is configured.";
                  description
                    "Enable source with next-hop multipath hashing (better distribution)";
                }
                container source-group {
                  // NCS drop must statement
                  presence "Indicates a source-group node is configured.";
                  description
                    "Enable source, group based multipath hashing (Compatible with IOS versions)";
                }
              }
            }
            container interface {
              description
                "PIM interface configuration subcommands";
              container interfaces {
                description
                  "Select an interface to configure";
                list interface {
                  key "interface-name";
                  description
                    "Select an interface to configure";
                  leaf interface-name {
                    type xr:live_ncs_Interface-name;
                    description
                      "Select an interface to configure";
                  }
                  leaf dr-priority {
                    type uint32 {
                      range "0..4294967295" {
                        description
                          "Hello DR priority, preference given to larger value";
                      }
                    }
                    description
                      "PIM Hello DR priority";
                  }
                  leaf hello-interval {
                    type uint32 {
                      range "1..3600" {
                        description
                          "Hello interval in seconds";
                      }
                    }
                    description
                      "PIM neighbor Hello announcement interval";
                  }
                  leaf join-prune-interval {
                    type uint32 {
                      range "10..600" {
                        description
                          "Join-Prune interval in seconds";
                      }
                    }
                    description
                      "PIM periodic Join-Prune announcement interval";
                  }
                  leaf join-prune-mtu {
                    type uint32 {
                      range "576..65535" {
                        description
                          "MTU to use in bytes";
                      }
                    }
                    description
                      "MTU to use when sending PIM J/P packets";
                  }
                  leaf propagation-delay {
                    type uint32 {
                      range "100..32767" {
                        description
                          "Propagatoin delay in milliseconds";
                      }
                    }
                    description
                      "PIM Hello propagation delay";
                  }
                  leaf override-interval {
                    type uint32 {
                      range "400..65535" {
                        description
                          "Override interval in milliseconds";
                      }
                    }
                    description
                      "PIM Hello override interval";
                  }
                  container bsr-border {
                    presence "Indicates a bsr-border node is configured.";
                    description
                      "Do not fwd BSR messages on this interface";
                  }
                  container enable {
                    // NCS drop must statement
                    presence "Indicates a enable node is configured.";
                    description
                      "Enable PIM processing on this interface";
                  }
                  container disable {
                    // NCS drop must statement
                    presence "Indicates a disable node is configured.";
                    description
                      "Disable PIM processing on this interface";
                  }
                  leaf neighbor-filter {
                    type xr:live_ncs_Cisco-ios-xr-string;
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type uint32 {
                          range "1..1100000" {
                            description
                              "Maximum number of allowed routes for this interface";
                          }
                        }
                        // NCS drop mandatory statement
                        description
                          "PIM downstream joined interfaces";
                      }
                      leaf threshold {
                        type uint32 {
                          range "1..1100000" {
                            description
                              "Threshold warning";
                          }
                        }
                        // NCS drop must statement
                        description
                          "Threshold warning";
                      }
                      leaf access-list {
                        type xr:live_ncs_Cisco-ios-xr-string;
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type uint32 {
                        range "3..30000" {
                          description
                            "hello interval in milli-seconds";
                        }
                      }
                      description
                        "Hello interval";
                    }
                    leaf multiplier {
                      type uint32 {
                        range "2..50" {
                          description
                            "Detect multiplier";
                        }
                      }
                      description
                        "Detect multiplier";
                    }
                  }
                }
              }
            }
            container bsr {
              description
                "BSR Configurations";
              container candidate-bsr {
                presence "Indicates a candidate-bsr node is configured.";
                description
                  "configure candidate BSR";
                leaf address {
                  type inet:ipv6-address-no-zone;
                  // NCS drop mandatory statement
                  description
                    "IP address of configured BSR";
                }
                leaf hash-mask-len {
                  type uint32 {
                    range "0..128" {
                      description
                        "mask length";
                    }
                  }
                  // NCS drop mandatory statement
                  description
                    "BSR Hash Mask Length";
                }
                leaf priority {
                  type uint32 {
                    range "1..255" {
                      description
                        "priority";
                    }
                  }
                  // NCS drop mandatory statement
                  description
                    "BSR Priority";
                }
              }
              container candidate-rps {
                description
                  "BSR Candidate RP Configurations";
                list candidate-rp {
                  // NCS drop must statement
                  key "address";
                  description
                    "BSR Candidate RP Configurations";
                  leaf address {
                    type inet:ipv6-address-no-zone;
                    description
                      "BSR Candidate RP Configurations";
                  }
                  leaf group-list {
                    type xr:live_ncs_Cisco-ios-xr-string;
                    description
                      "Group List access-list";
                  }
                  leaf priority {
                    type uint32 {
                      range "1..255" {
                        description
                          "priority";
                      }
                    }
                    description
                      "C-RP Priority";
                  }
                  leaf interval {
                    type uint32 {
                      range "30..600" {
                        description
                          "interval in second";
                      }
                    }
                    description
                      "C-RP Advertisement interval";
                  }
                  container bidir {
                    description
                      "To specify group ranges as Bidir";
                    leaf group-list {
                      type xr:live_ncs_Cisco-ios-xr-string;
                      description
                        "Group List access-list";
                    }
                    leaf priority {
                      type uint32 {
                        range "1..255" {
                          description
                            "priority";
                        }
                      }
                      description
                        "C-RP Priority";
                    }
                    leaf interval {
                      type uint32 {
                        range "30..600" {
                          description
                            "interval in second";
                        }
                      }
                      description
                        "C-RP Advertisement interval";
                    }
                  }
                }
              }
              container relay {
                description
                  "BSR RP relay config";
                container vrfs {
                  description
                    "vrf";
                  list vrf {
                    key "vrf-name";
                    description
                      "vrf";
                    leaf vrf-name {
                      type xr:live_ncs_Cisco-ios-xr-string;
                      description
                        "vrf";
                    }
                    container listen {
                      presence "Indicates a listen node is configured.";
                      description
                        "Enable RP relay in listen mode";
                    }
                  }
                }
              }
            }
            container sr-p2mp-policies {
              description
                "Segment-routing P2MP policy";
              list sr-p2mp-policy {
                key "sr-p2mp-policy-id";
                description
                  "Segment-routing P2MP policy";
                leaf sr-p2mp-policy-id {
                  type xr:live_ncs_Cisco-ios-xr-string;
                  description
                    "Segment-routing P2MP policy";
                }
                container static-group {
                  description
                    "ipv6 static multicast group";
                  list group-address {
                    key "group-address";
                    description
                      "ipv6 static multicast group";
                    leaf group-address {
                      type inet:ipv6-address-no-zone;
                      description
                        "ipv6 static multicast group";
                    }
                    container group-address-only {
                      presence "Indicates a group-address-only node is configured.";
                      description
                        "Group-address without increment mask/source-address";
                    }
                    container group-address-inc-masks {
                      description
                        "Group-address with increment mask for group address";
                      list inc-mask {
                        key "group-mask-address";
                        description
                          "Increment mask for group address";
                        leaf group-mask-address {
                          type inet:ipv6-address-no-zone;
                          description
                            "Increment mask for group address";
                        }
                        leaf group-address-count {
                          type uint32 {
                            range "1..512" {
                              description
                                "No. of group addresses to join";
                            }
                          }
                          // NCS drop mandatory statement
                          description
                            "No. of group addresses to join";
                        }
                      }
                    }
                    container group-address-source-address {
                      description
                        "Group-address with source-address";
                      list source-address {
                        key "source-address";
                        description
                          "Source address to join";
                        leaf source-address {
                          type inet:ipv6-address-no-zone;
                          description
                            "Source address to join";
                        }
                      }
                    }
                    container group-address-inc-mask-source-address {
                      description
                        "Group-address with increment-mask and source-address";
                      list inc-mask {
                        key "group-mask-address source-address";
                        description
                          "Increment mask for group address";
                        leaf group-mask-address {
                          type inet:ipv6-address-no-zone;
                          description
                            "Increment mask for group address";
                        }
                        leaf source-address {
                          type inet:ipv6-address-no-zone;
                          description
                            "Source address to join";
                        }
                        leaf group-address-count {
                          type uint32 {
                            range "1..512" {
                              description
                                "No. of group addresses to join";
                            }
                          }
                          // NCS drop mandatory statement
                          description
                            "No. of group addresses to join";
                        }
                      }
                    }
                    container group-address-source-address-inc-mask {
                      description
                        "Group-address and source-address with increment-mask";
                      list inc-mask {
                        key "source-address source-mask-address";
                        description
                          "Increment mask for group address";
                        leaf source-address {
                          type inet:ipv6-address-no-zone;
                          description
                            "Source address to join";
                        }
                        leaf source-mask-address {
                          type inet:ipv6-address-no-zone;
                          description
                            "Increment mask for source address";
                        }
                        leaf source-address-count {
                          type uint32 {
                            range "1..512" {
                              description
                                "No. of source addresses to join";
                            }
                          }
                          // NCS drop mandatory statement
                          description
                            "No. of source addresses to join";
                        }
                      }
                    }
                    container group-inc-mask-source-inc-mask {
                      description
                        "Group-address with increment-mask and source-address with increment-mask";
                      list inc-mask {
                        key "group-mask-address source-address source-mask-address";
                        leaf group-mask-address {
                          type inet:ipv6-address-no-zone;
                          description
                            "Increment mask for group address";
                        }
                        leaf source-address {
                          type inet:ipv6-address-no-zone;
                          description
                            "Source address to join";
                        }
                        leaf source-mask-address {
                          type inet:ipv6-address-no-zone;
                          description
                            "Increment mask for source address";
                        }
                        leaf group-address-count {
                          type uint32 {
                            range "1..512" {
                              description
                                "No. of group addresses to join";
                            }
                          }
                          // NCS drop mandatory statement
                          description
                            "No. of group addresses to join";
                        }
                        leaf source-address-count {
                          type uint32 {
                            range "1..512" {
                              description
                                "No. of source addresses to join";
                            }
                          }
                          // NCS drop mandatory statement
                          description
                            "No. of source addresses to join";
                        }
                      }
                    }
                  }
                }
              }
            }
            container embedded-rp {
              description
                "Set Embedded RP processing support";
              list ip-addresses {
                key "ip-address";
                description
                  "IP name or address of Rendezvous Point";
                leaf ip-address {
                  type inet:ipv6-address-no-zone;
                  description
                    "IP name or address of Rendezvous Point";
                }
                leaf access-list-name {
                  type xr:live_ncs_Cisco-ios-xr-string;
                  // NCS drop mandatory statement
                  description
                    "Access list of groups that should map to given RP";
                }
              }
              container disable {
                presence "Indicates a disable node is configured.";
                description
                  "Disable Embedded RP processing";
              }
            }
          }
        }
      }
    }
  }
  augment "/ncs:devices/ncs:template/ncs:ned-id/ncs:config" {
    container router {
      description
        "Enable a routing process";
      container pim {
        presence "Indicates a pim node is configured.";
        description
          "PIM configuration subcommands";
        container vrfs {
          description
            "VRF configs";
          list vrf {
            // NCS patched for predictable order
            ordered-by user;
            key "vrf-name";
            description
              "VRF configs";
            leaf vrf-name {
              type xr:ncs_template_Cisco-ios-xr-string;
              description
                "VRF configs";
            }
            container address-family {
              description
                "Enter Address Family command mode";
              container ipv4 {
                description
                  "IPv4 Address Family";
                container rp-addresses {
                  description
                    "Configure Rendezvous Point";
                  list rp-address {
                    // NCS patched for predictable order
                    ordered-by user;
                    key "address";
                    description
                      "Configure Rendezvous Point";
                    leaf address {
                      type string;
                      description
                        "Configure Rendezvous Point";
                    }
                    leaf access-list {
                      type xr:ncs_template_Cisco-ios-xr-string;
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      // NCS patched for predictable order
                      ordered-by user;
                      key "address";
                      description
                        "Configure Rendezvous Point";
                      leaf address {
                        type string;
                        description
                          "Configure Rendezvous Point";
                      }
                      leaf access-list {
                        type xr:ncs_template_Cisco-ios-xr-string;
                        description
                          "Access list of groups that should map to given RP";
                      }
                      container override {
                        presence "Indicates a override node is configured.";
                        description
                          "Static RP config overrides auto-rp and BSR";
                      }
                    }
                  }
                }
                leaf rp-static-deny {
                  type xr:ncs_template_Cisco-ios-xr-string;
                  description
                    "Configure static RP deny range";
                }
                leaf accept-register {
                  type xr:ncs_template_Cisco-ios-xr-string;
                  description
                    "Registers accept filter";
                }
                container suppress-data-registers {
                  presence "Indicates a suppress-data-registers node is configured.";
                  description
                    "Suppress data registers after initial state setup";
                }
                leaf register-source {
                  type xr:ncs_template_Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:ncs_template_Cisco-ios-xr-string;
                  description
                    "Neighbor filter";
                }
                container convergence {
                  description
                    "Convergence related parameters";
                  leaf rpf-conflict-join-delay {
                    type string;
                    description
                      "Delay in sending first join if RPF points to any downstream neighbor";
                  }
                  leaf link-down-prune-delay {
                    type string;
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:ncs_template_Cisco-ios-xr-string;
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type string;
                  description
                    "Inherited by all interfaces : Hello interval in seconds";
                }
                leaf dr-priority {
                  type string;
                  description
                    "Inherited by all interfaces : PIM Hello DR priority";
                }
                leaf join-prune-interval {
                  type string;
                  description
                    "Inherited by all interfaces : Join-Prune interval";
                }
                leaf join-prune-mtu {
                  type string;
                  description
                    "Inherited by all interfaces : Join-Prune MTU";
                }
                leaf propagation-delay {
                  type string;
                  description
                    "Inherited by all interfaces : PIM Hello Propagation delay";
                }
                leaf override-interval {
                  type string;
                  description
                    "Inherited by all interfaces : PIM Hello override interval";
                }
                container maximum {
                  description
                    "Maximum state limits";
                  container routes {
                    presence "Indicates a routes node is configured.";
                    description
                      "PIM routes";
                    leaf maximum-routes {
                      type string;
                      // NCS drop mandatory statement
                      description
                        "PIM routes";
                    }
                    leaf threshold {
                      type string;
                      // NCS drop must statement
                      description
                        "Set threshold to print warning";
                    }
                  }
                  container route-interfaces {
                    presence "Indicates a route-interfaces node is configured.";
                    description
                      "PIM total number of interfaces on all routes";
                    leaf maximum-route-interfaces {
                      type string;
                      // NCS drop mandatory statement
                      description
                        "PIM total number of interfaces on all routes";
                    }
                    leaf threshold {
                      type string;
                      // NCS drop must statement
                      description
                        "Set threshold to print warning";
                    }
                  }
                  container register-states {
                    presence "Indicates a register-states node is configured.";
                    description
                      "PIM source register states";
                    leaf maximum-register-states {
                      type string;
                      // NCS drop mandatory statement
                      description
                        "PIM source register states";
                    }
                    leaf threshold {
                      type string;
                      // NCS drop must statement
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type string;
                        // NCS drop mandatory statement
                        description
                          "Learned through the BSR distribution mechanism";
                      }
                      leaf threshold {
                        type string;
                        // NCS drop must statement
                        description
                          "Set threshold to print warning";
                      }
                    }
                    container autorp {
                      presence "Indicates a autorp node is configured.";
                      description
                        "Learned through the Auto-RP distribution mechanism";
                      leaf maximum-autorp {
                        type string;
                        // NCS drop mandatory statement
                        description
                          "Learned through the Auto-RP distribution mechanism";
                      }
                      leaf threshold {
                        type string;
                        // NCS drop must statement
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type string;
                        // NCS drop mandatory statement
                        description
                          "Set maximum number of C-RP cache in BSR";
                      }
                      leaf threshold {
                        type string;
                        // NCS drop must statement
                        description
                          "Set threshold to print warning";
                      }
                    }
                  }
                }
                leaf convergence-timeout {
                  type string;
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf-vector-injects {
                  description
                    "inject RPF vector";
                  list inject {
                    // NCS patched for predictable order
                    ordered-by user;
                    // NCS drop must statement
                    key "source-address masklen";
                    description
                      "inject RPF vector";
                    leaf source-address {
                      type string;
                      description
                        "inject RPF vector";
                    }
                    leaf masklen {
                      type string;
                      description
                        "masklen";
                    }
                    leaf-list rpf-vector {
                      // NCS patched for predictable order
                      ordered-by user;
                      type string;
                      // NCS drop max-elements statement
                      description
                        "configure this node";
                    }
                  }
                }
                container explicit-rpf-vector {
                  description
                    "Enable Explicit PIM RPF Vector";
                  container injects {
                    description
                      "inject Explicit RPF vector";
                    list inject {
                      // NCS patched for predictable order
                      ordered-by user;
                      // NCS drop must statement
                      key "source-address masklen";
                      description
                        "inject Explicit RPF vector";
                      leaf source-address {
                        type string;
                        description
                          "inject Explicit RPF vector";
                      }
                      leaf masklen {
                        type string;
                        description
                          "masklen";
                      }
                      leaf-list rpf-vector {
                        // NCS patched for predictable order
                        ordered-by user;
                        type string;
                        // NCS drop max-elements statement
                        description
                          "configure this node";
                      }
                    }
                  }
                }
                container rpf {
                  description
                    "RPF commands";
                  container topology {
                    description
                      "Select RPF topology";
                    leaf route-policy {
                      type xr:ncs_template_Route-policy-name;
                      description
                        "Route policy to select RPF topology";
                    }
                  }
                }
                container mdt {
                  description
                    "Multicast Distribution Tree commands";
                  leaf neighbor-filter {
                    type xr:ncs_template_Cisco-ios-xr-string;
                    description
                      "Neighbor filter";
                  }
                  container data {
                    description
                      "Data MDT Options";
                    leaf switchover-interval {
                      type string;
                      description
                        "Data MDT switchover interval";
                    }
                    leaf announce-interval {
                      type string;
                      description
                        "Periodic Data MDT Join TLV interval";
                    }
                    leaf max-aggregation {
                      type string;
                      description
                        "Data MDT max-aggregation";
                    }
                  }
                  container c-multicast-routing {
                    presence "Indicates a c-multicast-routing node is configured.";
                    description
                      "MVPN customer routing commands";
                    leaf type {
                      type string;
                      // NCS drop mandatory statement
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      // NCS drop when statement
                      description
                        "PIM Hellos over MDT";
                      container enable {
                        presence "Indicates a enable node is configured.";
                        description
                          "Enable PIM Hellos over MDT";
                      }
                    }
                    leaf shared-tree-prune-delay {
                      type string;
                      description
                        "Delay before pruning I-S PMSI from S,G when SA received";
                    }
                    leaf source-tree-prune-delay {
                      type string;
                      description
                        "Delay before removing PMSI from olist after BGP withdrawal";
                    }
                    container migration {
                      presence "Indicates a migration node is configured.";
                      description
                        "customer routing migration";
                      leaf route-policy {
                        type xr:ncs_template_Route-policy-name;
                        description
                          "Route policy to select customer routing";
                      }
                    }
                    container unicast-reachability {
                      description
                        "Control addition of Extended Communities to Unicast VPN-IP routes";
                      container connector {
                        description
                          "Enable/Disable Connector";
                        container disable {
                          // NCS drop must statement
                          presence "Indicates a disable node is configured.";
                          description
                            "Disable Connector Attribute";
                        }
                        container enable {
                          // NCS drop must statement
                          presence "Indicates a enable node is configured.";
                          description
                            "Enable Connector Attribute";
                        }
                      }
                      container source-as {
                        description
                          "Enable/Disable Source AS";
                        container disable {
                          // NCS drop must statement
                          presence "Indicates a disable node is configured.";
                          description
                            "Disable Source-AS Attribute";
                        }
                        container enable {
                          // NCS drop must statement
                          presence "Indicates a enable node is configured.";
                          description
                            "Enable Source-AS Attribute";
                        }
                      }
                      container vrf-route-import {
                        description
                          "Enable/Disable VRF Route Import";
                        container disable {
                          // NCS drop must statement
                          presence "Indicates a disable node is configured.";
                          description
                            "Disable VRF Route Import Attribute";
                        }
                        container enable {
                          // NCS drop must statement
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:ncs_template_Cisco-ios-xr-string;
                    description
                      "Access-list for allowed RP addresses";
                  }
                  leaf group-list {
                    type xr:ncs_template_Cisco-ios-xr-string;
                    description
                      "Access-list for allowed group ranges";
                  }
                }
                container sg-expiry-timer {
                  presence "Indicates a sg-expiry-timer node is configured.";
                  description
                    "Configure SG expiry timer";
                  leaf sg-expiry-timer-value {
                    type string;
                    // NCS drop mandatory statement
                    description
                      "Configure SG expiry timer";
                  }
                  leaf sg-list {
                    type xr:ncs_template_Cisco-ios-xr-string;
                    description
                      "Access-list of (S,G) routes for which expiry timer is applicable";
                  }
                }
                container ssm {
                  description
                    "Configure a group range for Source-Specific use";
                  leaf range {
                    type xr:ncs_template_Cisco-ios-xr-string;
                    // NCS drop must statement
                    description
                      "Provide ACL that specifies non-standard SSM range";
                  }
                  container disable {
                    // NCS drop must statement
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    // NCS drop must statement
                    presence "Indicates a hash node is configured.";
                    description
                      "Enter a hashing algorithm";
                    container source {
                      // NCS drop must statement
                      presence "Indicates a source node is configured.";
                      description
                        "Enable source based multipath hashing (Compatible with IOS versions)";
                    }
                    container source-nexthop {
                      // NCS drop must statement
                      presence "Indicates a source-nexthop node is configured.";
                      description
                        "Enable source with next-hop multipath hashing (better distribution)";
                    }
                    container source-group {
                      // NCS drop must statement
                      presence "Indicates a source-group node is configured.";
                      description
                        "Enable source, group based multipath hashing (Compatible with IOS versions)";
                    }
                  }
                }
                container auto-rp {
                  description
                    "Auto-RP Commands";
                  container listen {
                    description
                      "RP discovery through AUTORP protocol";
                    container disable {
                      presence "Indicates a disable node is configured.";
                      description
                        "Disable RP discovery through the AUTORP protocol";
                    }
                  }
                  container relay {
                    description
                      "relay";
                    container vrfs {
                      description
                        "vrf";
                      list vrf {
                        // NCS patched for predictable order
                        ordered-by user;
                        key "vrf-name";
                        description
                          "vrf";
                        leaf vrf-name {
                          type xr:ncs_template_Cisco-ios-xr-string;
                          description
                            "vrf";
                        }
                        container listen {
                          presence "Indicates a listen node is configured.";
                          description
                            "Enable RP relay in listen mode";
                        }
                      }
                    }
                  }
                }
                container interfaces {
                  description
                    "PIM interface configuration subcommands";
                  list interface {
                    // NCS patched for predictable order
                    ordered-by user;
                    key "interface-name";
                    description
                      "Select an interface to configure";
                    leaf interface-name {
                      type xr:ncs_template_Interface-name;
                      description
                        "Select an interface to configure";
                    }
                    leaf dr-priority {
                      type string;
                      description
                        "PIM Hello DR priority";
                    }
                    leaf hello-interval {
                      type string;
                      description
                        "PIM neighbor Hello announcement interval";
                    }
                    leaf join-prune-interval {
                      type string;
                      description
                        "PIM periodic Join-Prune announcement interval";
                    }
                    leaf join-prune-mtu {
                      type string;
                      description
                        "MTU to use when sending PIM J/P packets";
                    }
                    leaf propagation-delay {
                      type string;
                      description
                        "PIM Hello propagation delay";
                    }
                    leaf override-interval {
                      type string;
                      description
                        "PIM Hello override interval";
                    }
                    container bsr-border {
                      presence "Indicates a bsr-border node is configured.";
                      description
                        "Do not fwd BSR messages on this interface";
                    }
                    container enable {
                      // NCS drop must statement
                      presence "Indicates a enable node is configured.";
                      description
                        "Enable PIM processing on this interface";
                    }
                    container disable {
                      // NCS drop must statement
                      presence "Indicates a disable node is configured.";
                      description
                        "Disable PIM processing on this interface";
                    }
                    leaf neighbor-filter {
                      type xr:ncs_template_Cisco-ios-xr-string;
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type string;
                          // NCS drop mandatory statement
                          description
                            "PIM downstream joined interfaces";
                        }
                        leaf threshold {
                          type string;
                          // NCS drop must statement
                          description
                            "Threshold warning";
                        }
                        leaf access-list {
                          type xr:ncs_template_Cisco-ios-xr-string;
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type string;
                        description
                          "Hello interval";
                      }
                      leaf multiplier {
                        type string;
                        description
                          "Detect multiplier";
                      }
                    }
                  }
                }
                container bsr {
                  description
                    "BSR Configurations";
                  container candidate-bsr {
                    presence "Indicates a candidate-bsr node is configured.";
                    description
                      "configure candidate BSR";
                    leaf address {
                      type string;
                      // NCS drop mandatory statement
                      description
                        "IP address of configured BSR";
                    }
                    leaf hash-mask-len {
                      type string;
                      // NCS drop mandatory statement
                      description
                        "BSR Hash Mask Length";
                    }
                    leaf priority {
                      type string;
                      // NCS drop mandatory statement
                      description
                        "BSR Priority";
                    }
                  }
                  container candidate-rps {
                    description
                      "BSR Candidate RP Configurations";
                    list candidate-rp {
                      // NCS patched for predictable order
                      ordered-by user;
                      // NCS drop must statement
                      key "address";
                      description
                        "BSR Candidate RP Configurations";
                      leaf address {
                        type string;
                        description
                          "BSR Candidate RP Configurations";
                      }
                      leaf group-list {
                        type xr:ncs_template_Cisco-ios-xr-string;
                        description
                          "Group List access-list";
                      }
                      leaf priority {
                        type string;
                        description
                          "C-RP Priority";
                      }
                      leaf interval {
                        type string;
                        description
                          "C-RP Advertisement interval";
                      }
                      container bidir {
                        description
                          "To specify group ranges as Bidir";
                        leaf group-list {
                          type xr:ncs_template_Cisco-ios-xr-string;
                          description
                            "Group List access-list";
                        }
                        leaf priority {
                          type string;
                          description
                            "C-RP Priority";
                        }
                        leaf interval {
                          type string;
                          description
                            "C-RP Advertisement interval";
                        }
                      }
                    }
                  }
                  container relay {
                    description
                      "BSR RP relay config";
                    container vrfs {
                      description
                        "vrf";
                      list vrf {
                        // NCS patched for predictable order
                        ordered-by user;
                        key "vrf-name";
                        description
                          "vrf";
                        leaf vrf-name {
                          type xr:ncs_template_Cisco-ios-xr-string;
                          description
                            "vrf";
                        }
                        container listen {
                          presence "Indicates a listen node is configured.";
                          description
                            "Enable RP relay in listen mode";
                        }
                      }
                    }
                  }
                }
                container mofrr {
                  presence "Indicates a mofrr node is configured.";
                  description
                    "PIM Mofrr";
                  leaf flow {
                    type xr:ncs_template_Cisco-ios-xr-string;
                    description
                      "Multicast Only FRR";
                  }
                  leaf rib {
                    type string;
                    description
                      "Use the rib keyword to restrict switchover triggers to RIB events";
                  }
                  container non-revertive {
                    presence "Indicates a non-revertive node is configured.";
                    description
                      "Non-revertive MoFRR";
                  }
                  container clone {
                    description
                      "Use the clone keyword to clone";
                    container joins {
                      description
                        "Use the join keyword to clone S,G as S1,G joins as S2,G joins";
                      list join {
                        // NCS patched for predictable order
                        ordered-by user;
                        // NCS drop must statement
                        key "address";
                        description
                          "Use the join keyword to clone S,G as S1,G joins as S2,G joins";
                        leaf address {
                          type string;
                          description
                            "Source S";
                        }
                        list to {
                          // NCS patched for predictable order
                          ordered-by user;
                          // NCS drop must statement
                          key "address";
                          description
                            "to";
                          leaf address {
                            type string;
                            description
                              "Source S1";
                          }
                          list and {
                            // NCS patched for predictable order
                            ordered-by user;
                            // NCS drop must statement
                            key "address";
                            description
                              "and";
                            leaf address {
                              type string;
                              description
                                "Source S2";
                            }
                            list masklen {
                              // NCS patched for predictable order
                              ordered-by user;
                              key "mask-length";
                              description
                                "masklen";
                              leaf mask-length {
                                type string;
                                description
                                  "masklen";
                              }
                            }
                          }
                        }
                      }
                    }
                    container sources {
                      description
                        "Use the source keyword to clone S,G as S1,G traffic and S2,G traffic";
                      list source {
                        // NCS patched for predictable order
                        ordered-by user;
                        // NCS drop must statement
                        key "address";
                        description
                          "Use the source keyword to clone S,G as S1,G traffic and S2,G traffic";
                        leaf address {
                          type string;
                          description
                            "Source S";
                        }
                        list to {
                          // NCS patched for predictable order
                          ordered-by user;
                          // NCS drop must statement
                          key "address";
                          description
                            "to";
                          leaf address {
                            type string;
                            description
                              "Source S1";
                          }
                          list and {
                            // NCS patched for predictable order
                            ordered-by user;
                            // NCS drop must statement
                            key "address";
                            description
                              "and";
                            leaf address {
                              type string;
                              description
                                "Source S2";
                            }
                            list masklen {
                              // NCS patched for predictable order
                              ordered-by user;
                              key "mask-length";
                              description
                                "masklen";
                              leaf mask-length {
                                type string;
                                description
                                  "masklen";
                              }
                            }
                          }
                        }
                      }
                    }
                  }
                }
                container sr-p2mp-policies {
                  description
                    "Segment-routing P2MP policy";
                  list sr-p2mp-policy {
                    // NCS patched for predictable order
                    ordered-by user;
                    key "policy-name";
                    description
                      "Segment-routing P2MP policy";
                    leaf policy-name {
                      type xr:ncs_template_Cisco-ios-xr-string;
                      description
                        "Segment-routing P2MP policy";
                    }
                    container static-group {
                      description
                        "ipv4 static multicast group";
                      list group-address {
                        // NCS patched for predictable order
                        ordered-by user;
                        key "group-address";
                        description
                          "ipv4 static multicast group";
                        leaf group-address {
                          type string;
                          description
                            "ipv4 static multicast group";
                        }
                        container group-address-only {
                          presence "Indicates a group-address-only node is configured.";
                          description
                            "Group-address without increment mask/source-address";
                        }
                        container group-address-inc-masks {
                          description
                            "Group-address with increment mask for group address";
                          list inc-mask {
                            // NCS patched for predictable order
                            ordered-by user;
                            key "group-mask-address";
                            description
                              "Increment mask for group address";
                            leaf group-mask-address {
                              type string;
                              description
                                "Increment mask for group address";
                            }
                            leaf group-address-count {
                              type string;
                              // NCS drop mandatory statement
                              description
                                "No. of group addresses to join";
                            }
                          }
                        }
                        container group-address-source-address {
                          description
                            "Group-address with source-address";
                          list source-address {
                            // NCS patched for predictable order
                            ordered-by user;
                            key "source-address";
                            description
                              "Source address to join";
                            leaf source-address {
                              type string;
                              description
                                "Source address to join";
                            }
                          }
                        }
                        container group-address-inc-mask-source-address {
                          description
                            "Group-address with increment-mask and source-address";
                          list inc-mask {
                            // NCS patched for predictable order
                            ordered-by user;
                            key "group-mask-address source-address";
                            description
                              "Increment mask for group address";
                            leaf group-mask-address {
                              type string;
                              description
                                "Increment mask for group address";
                            }
                            leaf source-address {
                              type string;
                              description
                                "Source address to join";
                            }
                            leaf group-address-count {
                              type string;
                              // NCS drop mandatory statement
                              description
                                "No. of group addresses to join";
                            }
                          }
                        }
                        container group-address-source-address-inc-mask {
                          description
                            "Group-address and source-address with increment-mask";
                          list inc-mask {
                            // NCS patched for predictable order
                            ordered-by user;
                            key "source-address source-mask-address";
                            description
                              "Increment mask for group address";
                            leaf source-address {
                              type string;
                              description
                                "Source address to join";
                            }
                            leaf source-mask-address {
                              type string;
                              description
                                "Increment mask for source address";
                            }
                            leaf source-address-count {
                              type string;
                              // NCS drop mandatory statement
                              description
                                "No. of source addresses to join";
                            }
                          }
                        }
                        container group-inc-mask-source-inc-mask {
                          description
                            "Group-address with increment-mask and source-address with increment-mask";
                          list inc-mask {
                            // NCS patched for predictable order
                            ordered-by user;
                            key "group-mask-address source-address source-mask-address";
                            leaf group-mask-address {
                              type string;
                              description
                                "Increment mask for group address";
                            }
                            leaf source-address {
                              type string;
                              description
                                "Source address to join";
                            }
                            leaf source-mask-address {
                              type string;
                              description
                                "Increment mask for source address";
                            }
                            leaf group-address-count {
                              type string;
                              // NCS drop mandatory statement
                              description
                                "No. of group addresses to join";
                            }
                            leaf source-address-count {
                              type string;
                              // NCS drop mandatory statement
                              description
                                "No. of source addresses to join";
                            }
                          }
                        }
                      }
                    }
                  }
                }
              }
              container ipv6 {
                description
                  "IPv6 Address Family";
                container rp-addresses {
                  description
                    "Configure Rendezvous Point";
                  list rp-address {
                    // NCS patched for predictable order
                    ordered-by user;
                    key "address";
                    description
                      "Configure Rendezvous Point";
                    leaf address {
                      type string;
                      description
                        "Configure Rendezvous Point";
                    }
                    leaf access-list {
                      type xr:ncs_template_Cisco-ios-xr-string;
                      description
                        "Access list of groups that should map to given RP";
                    }
                    container override {
                      presence "Indicates a override node is configured.";
                      description
                        "Static RP config overrides auto-rp and BSR";
                    }
                  }
                  container bidir {
                    description
                      "Specify keyword bidir to configure a bidir RP";
                    list rp-address {
                      // NCS patched for predictable order
                      ordered-by user;
                      key "address";
                      description
                        "Configure Rendezvous Point";
                      leaf address {
                        type string;
                        description
                          "Configure Rendezvous Point";
                      }
                      leaf access-list {
                        type xr:ncs_template_Cisco-ios-xr-string;
                        description
                          "Access list of groups that should map to given RP";
                      }
                      container override {
                        presence "Indicates a override node is configured.";
                        description
                          "Static RP config overrides auto-rp and BSR";
                      }
                    }
                  }
                }
                leaf rp-static-deny {
                  type xr:ncs_template_Cisco-ios-xr-string;
                  description
                    "Configure static RP deny range";
                }
                leaf accept-register {
                  type xr:ncs_template_Cisco-ios-xr-string;
                  description
                    "Registers accept filter";
                }
                container suppress-data-registers {
                  presence "Indicates a suppress-data-registers node is configured.";
                  description
                    "Suppress data registers after initial state setup";
                }
                leaf register-source {
                  type xr:ncs_template_Interface-name;
                  description
                    "Source address to use for register messages";
                }
                container suppress-rpf-change-prunes {
                  presence "Indicates a suppress-rpf-change-prunes node is configured.";
                  description
                    "Suppress prunes triggered as a result of RPF changes";
                }
                leaf neighbor-filter {
                  type xr:ncs_template_Cisco-ios-xr-string;
                  description
                    "Neighbor filter";
                }
                container convergence {
                  description
                    "Convergence related parameters";
                  leaf rpf-conflict-join-delay {
                    type string;
                    description
                      "Delay in sending first join if RPF points to any downstream neighbor";
                  }
                  leaf link-down-prune-delay {
                    type string;
                    description
                      "Delay prunes if route join state transitions to not-joined on link down";
                  }
                }
                container spt-threshold {
                  description
                    "Configure threshold for switching to SPT on last-hop";
                  container infinity {
                    presence "Indicates a infinity node is configured.";
                    description
                      "Always stay on shared-tree";
                    leaf group-list {
                      type xr:ncs_template_Cisco-ios-xr-string;
                      description
                        "Only stay on the shared-tree for specified groups";
                    }
                  }
                }
                container old-register-checksum {
                  presence "Indicates a old-register-checksum node is configured.";
                  description
                    "Generate registers compatible with older IOS versions";
                }
                container neighbor-check-on-send {
                  description
                    "Check for PIM neighbor before sending control messages";
                  container enable {
                    presence "Indicates a enable node is configured.";
                    description
                      "Enable this feature";
                  }
                }
                container neighbor-check-on-recv {
                  description
                    "Check for PIM neighbor before rcv'ing control messages";
                  container enable {
                    presence "Indicates a enable node is configured.";
                    description
                      "Enable this feature";
                  }
                }
                leaf hello-interval {
                  type string;
                  description
                    "Inherited by all interfaces : Hello interval in seconds";
                }
                leaf dr-priority {
                  type string;
                  description
                    "Inherited by all interfaces : PIM Hello DR priority";
                }
                leaf join-prune-interval {
                  type string;
                  description
                    "Inherited by all interfaces : Join-Prune interval";
                }
                leaf join-prune-mtu {
                  type string;
                  description
                    "Inherited by all interfaces : Join-Prune MTU";
                }
                leaf propagation-delay {
                  type string;
                  description
                    "Inherited by all interfaces : PIM Hello Propagation delay";
                }
                leaf override-interval {
                  type string;
                  description
                    "Inherited by all interfaces : PIM Hello override interval";
                }
                container maximum {
                  description
                    "Maximum state limits";
                  container routes {
                    presence "Indicates a routes node is configured.";
                    description
                      "PIM routes";
                    leaf maximum-routes {
                      type string;
                      // NCS drop mandatory statement
                      description
                        "PIM routes";
                    }
                    leaf threshold {
                      type string;
                      // NCS drop must statement
                      description
                        "Set threshold to print warning";
                    }
                  }
                  container route-interfaces {
                    presence "Indicates a route-interfaces node is configured.";
                    description
                      "PIM total number of interfaces on all routes";
                    leaf maximum-route-interfaces {
                      type string;
                      // NCS drop mandatory statement
                      description
                        "PIM total number of interfaces on all routes";
                    }
                    leaf threshold {
                      type string;
                      // NCS drop must statement
                      description
                        "Set threshold to print warning";
                    }
                  }
                  container register-states {
                    presence "Indicates a register-states node is configured.";
                    description
                      "PIM source register states";
                    leaf maximum-register-states {
                      type string;
                      // NCS drop mandatory statement
                      description
                        "PIM source register states";
                    }
                    leaf threshold {
                      type string;
                      // NCS drop must statement
                      description
                        "Set threshold to print warning";
                    }
                  }
                  container group-mappings {
                    description
                      "PIM group-to-RP mapping ranges";
                    container bsr {
                      presence "Indicates a group-mappings node is configured.";
                      description
                        "Learned through the BSR distribution mechanism";
                      leaf maximum-bsr {
                        type string;
                        // NCS drop mandatory statement
                        description
                          "Learned through the BSR distribution mechanism";
                      }
                      leaf threshold {
                        type string;
                        // NCS drop must statement
                        description
                          "Set threshold to print warning";
                      }
                    }
                  }
                  container bsr {
                    description
                      "BSR maximum C-RP cache setting";
                    container crp-cache {
                      presence "Indicates a crp-cache node is configured.";
                      description
                        "Set maximum number of C-RP cache in BSR";
                      leaf maximum-crp-cache {
                        type string;
                        // NCS drop mandatory statement
                        description
                          "Set maximum number of C-RP cache in BSR";
                      }
                      leaf threshold {
                        type string;
                        // NCS drop must statement
                        description
                          "Set threshold to print warning";
                      }
                    }
                  }
                }
                leaf convergence-timeout {
                  type string;
                  description
                    "Timeout value for the RIB convergence notification";
                }
                container log {
                  description
                    "Enable PIM logging";
                  container neighbor {
                    description
                      "Enable PIM neighbor logging";
                    container changes {
                      presence "Indicates a changes node is configured.";
                      description
                        "Enable PIM neighbor state logging";
                    }
                  }
                }
                container rpf-vector {
                  presence "Indicates a rpf-vector node is configured.";
                  description
                    "Enable PIM RPF Vector";
                  container allow-ebgp {
                    presence "Indicates a allow-ebgp node is configured.";
                    description
                      "Allow origination of RPF vector over an eBGP session";
                  }
                  container disable-ibgp {
                    presence "Indicates a disable-ibgp node is configured.";
                    description
                      "Disable origination of RPF vector over an iBGP session";
                  }
                  container use-standard-encoding {
                    presence "Indicates a use-standard-encoding node is configured.";
                    description
                      "Use RFC standard encode type";
                  }
                }
                container rpf {
                  description
                    "RPF commands";
                  container topology {
                    description
                      "Select RPF topology";
                    leaf route-policy {
                      type xr:ncs_template_Route-policy-name;
                      description
                        "Route policy to select RPF topology";
                    }
                  }
                }
                container mdt {
                  description
                    "Multicast Distribution Tree commands";
                  leaf neighbor-filter {
                    type xr:ncs_template_Cisco-ios-xr-string;
                    description
                      "Neighbor filter";
                  }
                  container data {
                    description
                      "Data MDT Options";
                    leaf switchover-interval {
                      type string;
                      description
                        "Data MDT switchover interval";
                    }
                    leaf announce-interval {
                      type string;
                      description
                        "Periodic Data MDT Join TLV interval";
                    }
                    leaf max-aggregation {
                      type string;
                      description
                        "Data MDT max-aggregation";
                    }
                  }
                  container c-multicast-routing {
                    presence "Indicates a c-multicast-routing node is configured.";
                    description
                      "MVPN customer routing commands";
                    leaf type {
                      type string;
                      // NCS drop mandatory statement
                      description
                        "MVPN customer routing commands";
                    }
                    container announce-pim-join-tlv {
                      presence "Indicates a announce-pim-join-tlv node is configured.";
                      description
                        "Announce PIM MDT Join TLVs";
                    }
                    container suppress-shared-tree-join {
                      presence "Indicates a suppress-shared-tree-join node is configured.";
                      description
                        "Suppress shared tree joins";
                    }
                    container suppress-pim-data-signaling {
                      presence "Indicates a suppress-pim-data-signaling node is configured.";
                      description
                        "Suppress PIM data signaling";
                    }
                    container mdt-hello {
                      // NCS drop when statement
                      description
                        "PIM Hellos over MDT";
                      container enable {
                        presence "Indicates a enable node is configured.";
                        description
                          "Enable PIM Hellos over MDT";
                      }
                    }
                    leaf shared-tree-prune-delay {
                      type string;
                      description
                        "Delay before pruning I-S PMSI from S,G when SA received";
                    }
                    leaf source-tree-prune-delay {
                      type string;
                      description
                        "Delay before removing PMSI from olist after BGP withdrawal";
                    }
                    container migration {
                      presence "Indicates a migration node is configured.";
                      description
                        "customer routing migration";
                      leaf route-policy {
                        type xr:ncs_template_Route-policy-name;
                        description
                          "Route policy to select customer routing";
                      }
                    }
                    container unicast-reachability {
                      description
                        "Control addition of Extended Communities to Unicast VPN-IP routes";
                      container connector {
                        description
                          "Enable/Disable Connector";
                        container disable {
                          // NCS drop must statement
                          presence "Indicates a disable node is configured.";
                          description
                            "Disable Connector Attribute";
                        }
                        container enable {
                          // NCS drop must statement
                          presence "Indicates a enable node is configured.";
                          description
                            "Enable Connector Attribute";
                        }
                      }
                      container source-as {
                        description
                          "Enable/Disable Source AS";
                        container disable {
                          // NCS drop must statement
                          presence "Indicates a disable node is configured.";
                          description
                            "Disable Source-AS Attribute";
                        }
                        container enable {
                          // NCS drop must statement
                          presence "Indicates a enable node is configured.";
                          description
                            "Enable Source-AS Attribute";
                        }
                      }
                      container vrf-route-import {
                        description
                          "Enable/Disable VRF Route Import";
                        container disable {
                          // NCS drop must statement
                          presence "Indicates a disable node is configured.";
                          description
                            "Disable VRF Route Import Attribute";
                        }
                        container enable {
                          // NCS drop must statement
                          presence "Indicates a enable node is configured.";
                          description
                            "Enable VRF Route Import Attribute";
                        }
                      }
                    }
                  }
                }
                container allow-rp {
                  presence "Indicates a allow-rp node is configured.";
                  description
                    "Sparse-Mode RP addresses to be allowed";
                  leaf rp-list {
                    type xr:ncs_template_Cisco-ios-xr-string;
                    description
                      "Access-list for allowed RP addresses";
                  }
                  leaf group-list {
                    type xr:ncs_template_Cisco-ios-xr-string;
                    description
                      "Access-list for allowed group ranges";
                  }
                }
                container sg-expiry-timer {
                  presence "Indicates a sg-expiry-timer node is configured.";
                  description
                    "Configure SG expiry timer";
                  leaf sg-expiry-timer-value {
                    type string;
                    // NCS drop mandatory statement
                    description
                      "Configure SG expiry timer";
                  }
                  leaf sg-list {
                    type xr:ncs_template_Cisco-ios-xr-string;
                    description
                      "Access-list of (S,G) routes for which expiry timer is applicable";
                  }
                }
                container ssm {
                  description
                    "Configure a group range for Source-Specific use";
                  leaf range {
                    type xr:ncs_template_Cisco-ios-xr-string;
                    // NCS drop must statement
                    description
                      "Provide ACL that specifies non-standard SSM range";
                  }
                  container disable {
                    // NCS drop must statement
                    presence "Indicates a disable node is configured.";
                    description
                      "Disable use of all SSM group ranges";
                  }
                  container allow-override {
                    presence "Indicates a allow-override node is configured.";
                    description
                      "Allow SSM ranges to be overridden by more specific ranges";
                  }
                }
                container multipath {
                  presence "Indicates a multipath node is configured.";
                  description
                    "Enable equal-cost multipath routing";
                  container hash {
                    // NCS drop must statement
                    presence "Indicates a hash node is configured.";
                    description
                      "Enter a hashing algorithm";
                    container interface-extended {
                      // NCS drop must statement
                      presence "Indicates a interface-extended node is configured.";
                      description
                        "Enable interface extensions for non-unique next-hop addrs";
                    }
                    container source-nexthop {
                      // NCS drop must statement
                      presence "Indicates a source-nexthop node is configured.";
                      description
                        "Enable source with next-hop multipath hashing (better distribution)";
                    }
                    container source-group {
                      // NCS drop must statement
                      presence "Indicates a source-group node is configured.";
                      description
                        "Enable source, group based multipath hashing (Compatible with IOS versions)";
                    }
                  }
                }
                container interfaces {
                  description
                    "PIM interface configuration subcommands";
                  list interface {
                    // NCS patched for predictable order
                    ordered-by user;
                    key "interface-name";
                    description
                      "Select an interface to configure";
                    leaf interface-name {
                      type xr:ncs_template_Interface-name;
                      description
                        "Select an interface to configure";
                    }
                    leaf dr-priority {
                      type string;
                      description
                        "PIM Hello DR priority";
                    }
                    leaf hello-interval {
                      type string;
                      description
                        "PIM neighbor Hello announcement interval";
                    }
                    leaf join-prune-interval {
                      type string;
                      description
                        "PIM periodic Join-Prune announcement interval";
                    }
                    leaf join-prune-mtu {
                      type string;
                      description
                        "MTU to use when sending PIM J/P packets";
                    }
                    leaf propagation-delay {
                      type string;
                      description
                        "PIM Hello propagation delay";
                    }
                    leaf override-interval {
                      type string;
                      description
                        "PIM Hello override interval";
                    }
                    container bsr-border {
                      presence "Indicates a bsr-border node is configured.";
                      description
                        "Do not fwd BSR messages on this interface";
                    }
                    container enable {
                      // NCS drop must statement
                      presence "Indicates a enable node is configured.";
                      description
                        "Enable PIM processing on this interface";
                    }
                    container disable {
                      // NCS drop must statement
                      presence "Indicates a disable node is configured.";
                      description
                        "Disable PIM processing on this interface";
                    }
                    leaf neighbor-filter {
                      type xr:ncs_template_Cisco-ios-xr-string;
                      description
                        "PIM Neighbor filter on this interface";
                    }
                    container maximum {
                      description
                        "Per interface maximum state limits";
                      container route-interfaces {
                        presence "Indicates a route-interfaces node is configured.";
                        description
                          "PIM downstream joined interfaces";
                        leaf maximum-route-interfaces {
                          type string;
                          // NCS drop mandatory statement
                          description
                            "PIM downstream joined interfaces";
                        }
                        leaf threshold {
                          type string;
                          // NCS drop must statement
                          description
                            "Threshold warning";
                        }
                        leaf access-list {
                          type xr:ncs_template_Cisco-ios-xr-string;
                          description
                            "Name of ACL that specifies to which routes to apply the maximum limit";
                        }
                      }
                    }
                    container bfd {
                      description
                        "Configure BFD parameters";
                      container fast-detect {
                        presence "Indicates a fast-detect node is configured.";
                        description
                          "Enable Fast detection";
                      }
                      leaf minimum-interval {
                        type string;
                        description
                          "Hello interval";
                      }
                      leaf multiplier {
                        type string;
                        description
                          "Detect multiplier";
                      }
                    }
                  }
                }
                container bsr {
                  description
                    "BSR Configurations";
                  container candidate-bsr {
                    presence "Indicates a candidate-bsr node is configured.";
                    description
                      "configure candidate BSR";
                    leaf address {
                      type string;
                      // NCS drop mandatory statement
                      description
                        "IP address of configured BSR";
                    }
                    leaf hash-mask-len {
                      type string;
                      // NCS drop mandatory statement
                      description
                        "BSR Hash Mask Length";
                    }
                    leaf priority {
                      type string;
                      // NCS drop mandatory statement
                      description
                        "BSR Priority";
                    }
                  }
                  container candidate-rps {
                    description
                      "BSR Candidate RP Configurations";
                    list candidate-rp {
                      // NCS patched for predictable order
                      ordered-by user;
                      // NCS drop must statement
                      key "address";
                      description
                        "BSR Candidate RP Configurations";
                      leaf address {
                        type string;
                        description
                          "BSR Candidate RP Configurations";
                      }
                      leaf group-list {
                        type xr:ncs_template_Cisco-ios-xr-string;
                        description
                          "Group List access-list";
                      }
                      leaf priority {
                        type string;
                        description
                          "C-RP Priority";
                      }
                      leaf interval {
                        type string;
                        description
                          "C-RP Advertisement interval";
                      }
                      container bidir {
                        description
                          "To specify group ranges as Bidir";
                        leaf group-list {
                          type xr:ncs_template_Cisco-ios-xr-string;
                          description
                            "Group List access-list";
                        }
                        leaf priority {
                          type string;
                          description
                            "C-RP Priority";
                        }
                        leaf interval {
                          type string;
                          description
                            "C-RP Advertisement interval";
                        }
                      }
                    }
                  }
                  container relay {
                    description
                      "BSR RP relay config";
                    container vrfs {
                      description
                        "vrf";
                      list vrf {
                        // NCS patched for predictable order
                        ordered-by user;
                        key "vrf-name";
                        description
                          "vrf";
                        leaf vrf-name {
                          type xr:ncs_template_Cisco-ios-xr-string;
                          description
                            "vrf";
                        }
                        container listen {
                          presence "Indicates a listen node is configured.";
                          description
                            "Enable RP relay in listen mode";
                        }
                      }
                    }
                  }
                }
                container sr-p2mp-policies {
                  description
                    "Segment-routing P2MP policy";
                  list sr-p2mp-policy {
                    // NCS patched for predictable order
                    ordered-by user;
                    key "policy-name";
                    description
                      "Segment-routing P2MP policy";
                    leaf policy-name {
                      type xr:ncs_template_Cisco-ios-xr-string;
                      description
                        "Segment-routing P2MP policy";
                    }
                    container static-group {
                      description
                        "ipv6 static multicast group";
                      list group-address {
                        // NCS patched for predictable order
                        ordered-by user;
                        key "group-address";
                        description
                          "ipv6 static multicast group";
                        leaf group-address {
                          type string;
                          description
                            "ipv6 static multicast group";
                        }
                        container group-address-only {
                          presence "Indicates a group-address-only node is configured.";
                          description
                            "Group-address without increment mask/source-address";
                        }
                        container group-address-inc-masks {
                          description
                            "Group-address with increment mask for group address";
                          list inc-mask {
                            // NCS patched for predictable order
                            ordered-by user;
                            key "group-mask-address";
                            description
                              "Increment mask for group address";
                            leaf group-mask-address {
                              type string;
                              description
                                "Increment mask for group address";
                            }
                            leaf group-address-count {
                              type string;
                              // NCS drop mandatory statement
                              description
                                "No. of group addresses to join";
                            }
                          }
                        }
                        container group-address-source-address {
                          description
                            "Group-address with source-address";
                          list source-address {
                            // NCS patched for predictable order
                            ordered-by user;
                            key "source-address";
                            description
                              "Source address to join";
                            leaf source-address {
                              type string;
                              description
                                "Source address to join";
                            }
                          }
                        }
                        container group-address-inc-mask-source-address {
                          description
                            "Group-address with increment-mask and source-address";
                          list inc-mask {
                            // NCS patched for predictable order
                            ordered-by user;
                            key "group-mask-address source-address";
                            description
                              "Increment mask for group address";
                            leaf group-mask-address {
                              type string;
                              description
                                "Increment mask for group address";
                            }
                            leaf source-address {
                              type string;
                              description
                                "Source address to join";
                            }
                            leaf group-address-count {
                              type string;
                              // NCS drop mandatory statement
                              description
                                "No. of group addresses to join";
                            }
                          }
                        }
                        container group-address-source-address-inc-mask {
                          description
                            "Group-address and source-address with increment-mask";
                          list inc-mask {
                            // NCS patched for predictable order
                            ordered-by user;
                            key "source-address source-mask-address";
                            description
                              "Increment mask for group address";
                            leaf source-address {
                              type string;
                              description
                                "Source address to join";
                            }
                            leaf source-mask-address {
                              type string;
                              description
                                "Increment mask for source address";
                            }
                            leaf source-address-count {
                              type string;
                              // NCS drop mandatory statement
                              description
                                "No. of source addresses to join";
                            }
                          }
                        }
                        container group-inc-mask-source-inc-mask {
                          description
                            "Group-address with increment-mask and source-address with increment-mask";
                          list inc-mask {
                            // NCS patched for predictable order
                            ordered-by user;
                            key "group-mask-address source-address source-mask-address";
                            leaf group-mask-address {
                              type string;
                              description
                                "Increment mask for group address";
                            }
                            leaf source-address {
                              type string;
                              description
                                "Source address to join";
                            }
                            leaf source-mask-address {
                              type string;
                              description
                                "Increment mask for source address";
                            }
                            leaf group-address-count {
                              type string;
                              // NCS drop mandatory statement
                              description
                                "No. of group addresses to join";
                            }
                            leaf source-address-count {
                              type string;
                              // NCS drop mandatory statement
                              description
                                "No. of source addresses to join";
                            }
                          }
                        }
                      }
                    }
                  }
                }
                container embedded-rp {
                  description
                    "Set Embedded RP processing support";
                  list ip-addresses {
                    // NCS patched for predictable order
                    ordered-by user;
                    key "ip-address";
                    description
                      "IP name or address of Rendezvous Point";
                    leaf ip-address {
                      type string;
                      description
                        "IP name or address of Rendezvous Point";
                    }
                    leaf access-list-name {
                      type xr:ncs_template_Cisco-ios-xr-string;
                      // NCS drop mandatory statement
                      description
                        "Access list of groups that should map to given RP";
                    }
                  }
                  container disable {
                    presence "Indicates a disable node is configured.";
                    description
                      "Disable Embedded RP processing";
                  }
                }
              }
            }
          }
        }
        container address-family {
          description
            "Enter Address Family command mode";
          container ipv4 {
            description
              "IPv4 Address Family";
            container rp-addresses {
              description
                "Configure Rendezvous Point";
              list rp-address {
                // NCS patched for predictable order
                ordered-by user;
                key "address";
                description
                  "Configure Rendezvous Point";
                leaf address {
                  type string;
                  description
                    "Configure Rendezvous Point";
                }
                leaf access-list {
                  type xr:ncs_template_Cisco-ios-xr-string;
                  description
                    "Access list of groups that should map to given RP";
                }
                container override {
                  presence "Indicates a override node is configured.";
                  description
                    "Static RP config overrides auto-rp and BSR";
                }
              }
              container bidir {
                description
                  "Specify keyword bidir to configure a bidir RP";
                list rp-address {
                  // NCS patched for predictable order
                  ordered-by user;
                  key "address";
                  description
                    "Configure Rendezvous Point";
                  leaf address {
                    type string;
                    description
                      "Configure Rendezvous Point";
                  }
                  leaf access-list {
                    type xr:ncs_template_Cisco-ios-xr-string;
                    description
                      "Access list of groups that should map to given RP";
                  }
                  container override {
                    presence "Indicates a override node is configured.";
                    description
                      "Static RP config overrides auto-rp and BSR";
                  }
                }
              }
            }
            leaf rp-static-deny {
              type xr:ncs_template_Cisco-ios-xr-string;
              description
                "Configure static RP deny range";
            }
            leaf accept-register {
              type xr:ncs_template_Cisco-ios-xr-string;
              description
                "Registers accept filter";
            }
            container suppress-data-registers {
              presence "Indicates a suppress-data-registers node is configured.";
              description
                "Suppress data registers after initial state setup";
            }
            leaf register-source {
              type xr:ncs_template_Interface-name;
              description
                "Source address to use for register messages";
            }
            container suppress-rpf-change-prunes {
              presence "Indicates a suppress-rpf-change-prunes node is configured.";
              description
                "Suppress prunes triggered as a result of RPF changes";
            }
            leaf neighbor-filter {
              type xr:ncs_template_Cisco-ios-xr-string;
              description
                "Neighbor filter";
            }
            container convergence {
              description
                "Convergence related parameters";
              leaf rpf-conflict-join-delay {
                type string;
                description
                  "Delay in sending first join if RPF points to any downstream neighbor";
              }
              leaf link-down-prune-delay {
                type string;
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:ncs_template_Cisco-ios-xr-string;
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type string;
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type string;
              description
                "Inherited by all interfaces : Hello interval in seconds";
            }
            leaf mdt-hello-interval {
              type string;
              description
                "Hello interval for all MDT interfaces (seconds)";
            }
            leaf dr-priority {
              type string;
              description
                "Inherited by all interfaces : PIM Hello DR priority";
            }
            leaf join-prune-interval {
              type string;
              description
                "Inherited by all interfaces : Join-Prune interval";
            }
            leaf join-prune-mtu {
              type string;
              description
                "Inherited by all interfaces : Join-Prune MTU";
            }
            leaf propagation-delay {
              type string;
              description
                "Inherited by all interfaces : PIM Hello Propagation delay";
            }
            leaf override-interval {
              type string;
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type string;
                    // NCS drop mandatory statement
                    description
                      "PIM routes for all VRFs";
                  }
                  leaf threshold {
                    type string;
                    // NCS drop must statement
                    description
                      "Set threshold to print warning";
                  }
                }
                container route-interfaces {
                  presence "Indicates a route-interfaces node is configured.";
                  description
                    "PIM total interfaces on routes for all VRFs";
                  leaf maximum-route-interfaces {
                    type string;
                    // NCS drop mandatory statement
                    description
                      "PIM total interfaces on routes for all VRFs";
                  }
                  leaf threshold {
                    type string;
                    // NCS drop must statement
                    description
                      "Set threshold to print warning";
                  }
                }
                container register-states {
                  presence "Indicates a register-states node is configured.";
                  description
                    "PIM source register states for all VRFs";
                  leaf maximum-register-states {
                    type string;
                    // NCS drop mandatory statement
                    description
                      "PIM source register states for all VRFs";
                  }
                  leaf threshold {
                    type string;
                    // NCS drop must statement
                    description
                      "Set threshold to print warning";
                  }
                }
                container packet-queue {
                  description
                    "PIM Packet queue size in bytes";
                  leaf high-priority {
                    type string;
                    description
                      "PIM high priority packet queue size in bytes";
                  }
                  leaf low-priority {
                    type string;
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type string;
                      // NCS drop mandatory statement
                    }
                    leaf threshold {
                      type string;
                      // NCS drop must statement
                      description
                        "Set threshold to print warning";
                    }
                  }
                  container autorp {
                    presence "Indicates a autorp node is configured.";
                    description
                      "Learned through the Auto-RP distribution mechanism";
                    leaf maximum-autorp {
                      type string;
                      // NCS drop mandatory statement
                      description
                        "Learned through the Auto-RP distribution mechanism";
                    }
                    leaf threshold {
                      type string;
                      // NCS drop must statement
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type string;
                      // NCS drop mandatory statement
                      description
                        "Set maximum number of C-RP cache in BSR";
                    }
                    leaf threshold {
                      type string;
                      // NCS drop must statement
                      description
                        "Set threshold to print warning";
                    }
                  }
                }
              }
            }
            container maximum {
              description
                "Maximum state limits";
              container routes {
                presence "Indicates a routes node is configured.";
                description
                  "PIM routes";
                leaf maximum-routes {
                  type string;
                  // NCS drop mandatory statement
                  description
                    "PIM routes";
                }
                leaf threshold {
                  type string;
                  // NCS drop must statement
                  description
                    "Set threshold to print warning";
                }
              }
              container route-interfaces {
                presence "Indicates a route-interfaces node is configured.";
                description
                  "PIM total number of interfaces on all routes";
                leaf maximum-route-interfaces {
                  type string;
                  // NCS drop mandatory statement
                  description
                    "PIM total number of interfaces on all routes";
                }
                leaf threshold {
                  type string;
                  // NCS drop must statement
                  description
                    "Set threshold to print warning";
                }
              }
              container register-states {
                presence "Indicates a register-states node is configured.";
                description
                  "PIM source register states";
                leaf maximum-register-states {
                  type string;
                  // NCS drop mandatory statement
                  description
                    "PIM source register states";
                }
                leaf threshold {
                  type string;
                  // NCS drop must statement
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type string;
                    // NCS drop mandatory statement
                    description
                      "Learned through the BSR distribution mechanism";
                  }
                  leaf threshold {
                    type string;
                    // NCS drop must statement
                    description
                      "Set threshold to print warning";
                  }
                }
                container autorp {
                  presence "Indicates a autorp node is configured.";
                  description
                    "Learned through the Auto-RP distribution mechanism";
                  leaf maximum-autorp {
                    type string;
                    // NCS drop mandatory statement
                    description
                      "Learned through the Auto-RP distribution mechanism";
                  }
                  leaf threshold {
                    type string;
                    // NCS drop must statement
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type string;
                    // NCS drop mandatory statement
                    description
                      "Set maximum number of C-RP cache in BSR";
                  }
                  leaf threshold {
                    type string;
                    // NCS drop must statement
                    description
                      "Set threshold to print warning";
                  }
                }
              }
            }
            leaf convergence-timeout {
              type string;
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf-vector-injects {
              description
                "inject RPF vector";
              list inject {
                // NCS patched for predictable order
                ordered-by user;
                // NCS drop must statement
                key "source-address masklen";
                description
                  "inject RPF vector";
                leaf source-address {
                  type string;
                  description
                    "inject RPF vector";
                }
                leaf masklen {
                  type string;
                  description
                    "masklen";
                }
                leaf-list rpf-vector {
                  // NCS patched for predictable order
                  ordered-by user;
                  type string;
                  // NCS drop max-elements statement
                  description
                    "configure this node";
                }
              }
            }
            container explicit-rpf-vector {
              description
                "Enable Explicit PIM RPF Vector";
              container injects {
                description
                  "inject Explicit RPF vector";
                list inject {
                  // NCS patched for predictable order
                  ordered-by user;
                  // NCS drop must statement
                  key "source-address masklen";
                  description
                    "inject Explicit RPF vector";
                  leaf source-address {
                    type string;
                    description
                      "inject Explicit RPF vector";
                  }
                  leaf masklen {
                    type string;
                    description
                      "masklen";
                  }
                  leaf-list rpf-vector {
                    // NCS patched for predictable order
                    ordered-by user;
                    type string;
                    // NCS drop max-elements statement
                    description
                      "configure this node";
                  }
                }
              }
            }
            container rpf {
              description
                "RPF commands";
              container topology {
                description
                  "Select RPF topology";
                leaf route-policy {
                  type xr:ncs_template_Route-policy-name;
                  description
                    "Route policy to select RPF topology";
                }
              }
            }
            container mdt {
              description
                "Multicast Distribution Tree commands";
              leaf neighbor-filter {
                type xr:ncs_template_Cisco-ios-xr-string;
                description
                  "Neighbor filter";
              }
              container data {
                description
                  "Data MDT Options";
                leaf switchover-interval {
                  type string;
                  description
                    "Data MDT switchover interval";
                }
                leaf announce-interval {
                  type string;
                  description
                    "Periodic Data MDT Join TLV interval";
                }
                leaf max-aggregation {
                  type string;
                  description
                    "Data MDT max-aggregation";
                }
              }
              container c-multicast-routing {
                presence "Indicates a c-multicast-routing node is configured.";
                description
                  "MVPN customer routing commands";
                leaf type {
                  type string;
                  // NCS drop mandatory statement
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  // NCS drop when statement
                  description
                    "PIM Hellos over MDT";
                  container enable {
                    presence "Indicates a enable node is configured.";
                    description
                      "Enable PIM Hellos over MDT";
                  }
                }
                leaf shared-tree-prune-delay {
                  type string;
                  description
                    "Delay before pruning I-S PMSI from S,G when SA received";
                }
                leaf source-tree-prune-delay {
                  type string;
                  description
                    "Delay before removing PMSI from olist after BGP withdrawal";
                }
                container migration {
                  presence "Indicates a migration node is configured.";
                  description
                    "customer routing migration";
                  leaf route-policy {
                    type xr:ncs_template_Route-policy-name;
                    description
                      "Route policy to select customer routing";
                  }
                }
                container unicast-reachability {
                  description
                    "Control addition of Extended Communities to Unicast VPN-IP routes";
                  container connector {
                    description
                      "Enable/Disable Connector";
                    container disable {
                      // NCS drop must statement
                      presence "Indicates a disable node is configured.";
                      description
                        "Disable Connector Attribute";
                    }
                    container enable {
                      // NCS drop must statement
                      presence "Indicates a enable node is configured.";
                      description
                        "Enable Connector Attribute";
                    }
                  }
                  container source-as {
                    description
                      "Enable/Disable Source AS";
                    container disable {
                      // NCS drop must statement
                      presence "Indicates a disable node is configured.";
                      description
                        "Disable Source-AS Attribute";
                    }
                    container enable {
                      // NCS drop must statement
                      presence "Indicates a enable node is configured.";
                      description
                        "Enable Source-AS Attribute";
                    }
                  }
                  container vrf-route-import {
                    description
                      "Enable/Disable VRF Route Import";
                    container disable {
                      // NCS drop must statement
                      presence "Indicates a disable node is configured.";
                      description
                        "Disable VRF Route Import Attribute";
                    }
                    container enable {
                      // NCS drop must statement
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:ncs_template_Cisco-ios-xr-string;
                description
                  "Access-list for allowed RP addresses";
              }
              leaf group-list {
                type xr:ncs_template_Cisco-ios-xr-string;
                description
                  "Access-list for allowed group ranges";
              }
            }
            container sg-expiry-timer {
              presence "Indicates a sg-expiry-timer node is configured.";
              description
                "Configure SG expiry timer";
              leaf sg-expiry-timer-value {
                type string;
                // NCS drop mandatory statement
                description
                  "Configure SG expiry timer";
              }
              leaf sg-list {
                type xr:ncs_template_Cisco-ios-xr-string;
                description
                  "Access-list of (S,G) routes for which expiry timer is applicable";
              }
            }
            container ssm {
              description
                "Configure a group range for Source-Specific use";
              leaf range {
                type xr:ncs_template_Cisco-ios-xr-string;
                // NCS drop must statement
                description
                  "Provide ACL that specifies non-standard SSM range";
              }
              container disable {
                // NCS drop must statement
                presence "Indicates a disable node is configured.";
                description
                  "Disable use of all SSM group ranges";
              }
              container allow-override {
                presence "Indicates a allow-override node is configured.";
                description
                  "Allow SSM ranges to be overridden by more specific ranges";
              }
            }
            container rpf-redirect {
              description
                "Route policy for rpf-redirect bundles";
              leaf route-policy {
                type xr:ncs_template_Route-policy-name;
                description
                  "Bandwidth assigment (kbps) for SG routes";
              }
            }
            container multipath {
              presence "Indicates a multipath node is configured.";
              description
                "Enable equal-cost multipath routing";
              container hash {
                // NCS drop must statement
                presence "Indicates a hash node is configured.";
                description
                  "Enter a hashing algorithm";
                container source {
                  // NCS drop must statement
                  presence "Indicates a source node is configured.";
                  description
                    "Enable source based multipath hashing (Compatible with IOS versions)";
                }
                container source-nexthop {
                  // NCS drop must statement
                  presence "Indicates a source-nexthop node is configured.";
                  description
                    "Enable source with next-hop multipath hashing (better distribution)";
                }
                container source-group {
                  // NCS drop must statement
                  presence "Indicates a source-group node is configured.";
                  description
                    "Enable source, group based multipath hashing (Compatible with IOS versions)";
                }
              }
            }
            container auto-rp {
              description
                "Auto-RP Commands";
              container candidate-rps {
                description
                  "Configure as a Candidate RP";
                list candidate-rp {
                  // NCS patched for predictable order
                  ordered-by user;
                  // NCS drop must statement
                  key "interface-name";
                  description
                    "Candidate RP Configurations";
                  leaf interface-name {
                    type xr:ncs_template_Interface-name;
                    description
                      "Candidate RP Configurations";
                  }
                  leaf scope {
                    type string;
                    // NCS drop must statement
                    description
                      "TTL for the announcement";
                  }
                  leaf group-list {
                    type xr:ncs_template_Cisco-ios-xr-string;
                    description
                      "Be a candidate RP for groups specified by the acl";
                  }
                  leaf interval {
                    type string;
                    description
                      "time between announcements <in seconds>";
                  }
                  container bidir {
                    description
                      "to specify group ranges as bidir, default is pim-sm";
                    leaf scope {
                      type string;
                      // NCS drop must statement
                      description
                        "TTL for the announcement";
                    }
                    leaf group-list {
                      type xr:ncs_template_Cisco-ios-xr-string;
                      description
                        "Be a candidate RP for groups specified by the acl";
                    }
                    leaf interval {
                      type string;
                      description
                        "time between announcements <in seconds>";
                    }
                  }
                }
              }
              container mapping-agent {
                presence "Indicates a mapping-agent node is configured.";
                description
                  "Configure as a Mapping Agent";
                leaf interface-name {
                  type xr:ncs_template_Interface-name;
                  // NCS drop mandatory statement
                  description
                    "Candidate RP Configurations";
                }
                leaf scope {
                  type string;
                  // NCS drop mandatory statement
                  description
                    "TTL for the announcement";
                }
                leaf interval {
                  type string;
                  // NCS drop mandatory statement
                  description
                    "number of seconds between discovery messages";
                }
              }
              container listen {
                description
                  "RP discovery through AUTORP protocol";
                container disable {
                  presence "Indicates a disable node is configured.";
                  description
                    "Disable RP discovery through the AUTORP protocol";
                }
              }
              container relay {
                description
                  "relay";
                container vrfs {
                  description
                    "vrf";
                  list vrf {
                    // NCS patched for predictable order
                    ordered-by user;
                    key "vrf-name";
                    description
                      "vrf";
                    leaf vrf-name {
                      type xr:ncs_template_Cisco-ios-xr-string;
                      description
                        "vrf";
                    }
                    container listen {
                      presence "Indicates a listen node is configured.";
                      description
                        "Enable RP relay in listen mode";
                    }
                  }
                }
              }
            }
            container interface {
              description
                "PIM interface configuration subcommands";
              container interfaces {
                description
                  "Select an interface to configure";
                list interface {
                  // NCS patched for predictable order
                  ordered-by user;
                  key "interface-name";
                  description
                    "Select an interface to configure";
                  leaf interface-name {
                    type xr:ncs_template_Interface-name;
                    description
                      "Select an interface to configure";
                  }
                  leaf dr-priority {
                    type string;
                    description
                      "PIM Hello DR priority";
                  }
                  leaf hello-interval {
                    type string;
                    description
                      "PIM neighbor Hello announcement interval";
                  }
                  leaf join-prune-interval {
                    type string;
                    description
                      "PIM periodic Join-Prune announcement interval";
                  }
                  leaf join-prune-mtu {
                    type string;
                    description
                      "MTU to use when sending PIM J/P packets";
                  }
                  leaf propagation-delay {
                    type string;
                    description
                      "PIM Hello propagation delay";
                  }
                  leaf override-interval {
                    type string;
                    description
                      "PIM Hello override interval";
                  }
                  container bsr-border {
                    presence "Indicates a bsr-border node is configured.";
                    description
                      "Do not fwd BSR messages on this interface";
                  }
                  container enable {
                    // NCS drop must statement
                    presence "Indicates a enable node is configured.";
                    description
                      "Enable PIM processing on this interface";
                  }
                  container disable {
                    // NCS drop must statement
                    presence "Indicates a disable node is configured.";
                    description
                      "Disable PIM processing on this interface";
                  }
                  leaf neighbor-filter {
                    type xr:ncs_template_Cisco-ios-xr-string;
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type string;
                        // NCS drop mandatory statement
                        description
                          "PIM downstream joined interfaces";
                      }
                      leaf threshold {
                        type string;
                        // NCS drop must statement
                        description
                          "Threshold warning";
                      }
                      leaf access-list {
                        type xr:ncs_template_Cisco-ios-xr-string;
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type string;
                      description
                        "Hello interval";
                    }
                    leaf multiplier {
                      type string;
                      description
                        "Detect multiplier";
                    }
                  }
                  container rpf-redirect {
                    presence "Indicates a rpf-redirect node is configured.";
                    description
                      "RPF redirect bundle configuration";
                    leaf bundle {
                      type xr:ncs_template_Cisco-ios-xr-string;
                      // NCS drop mandatory statement
                      description
                        "Bundle name";
                    }
                    leaf bandwidth {
                      type string;
                      description
                        "Interface bandwidth in Kbps";
                    }
                    leaf threshold {
                      type string;
                      // NCS drop must statement
                      description
                        "Bandwidth threshold in Kbps";
                    }
                  }
                }
              }
            }
            container bsr {
              description
                "BSR Configurations";
              container candidate-bsr {
                presence "Indicates a candidate-bsr node is configured.";
                description
                  "configure candidate BSR";
                leaf address {
                  type string;
                  // NCS drop mandatory statement
                  description
                    "IP address of configured BSR";
                }
                leaf hash-mask-len {
                  type string;
                  // NCS drop mandatory statement
                  description
                    "BSR Hash Mask Length";
                }
                leaf priority {
                  type string;
                  // NCS drop mandatory statement
                  description
                    "BSR Priority";
                }
              }
              container candidate-rps {
                description
                  "BSR Candidate RP Configurations";
                list candidate-rp {
                  // NCS patched for predictable order
                  ordered-by user;
                  // NCS drop must statement
                  key "address";
                  description
                    "BSR Candidate RP Configurations";
                  leaf address {
                    type string;
                    description
                      "BSR Candidate RP Configurations";
                  }
                  leaf group-list {
                    type xr:ncs_template_Cisco-ios-xr-string;
                    description
                      "Group List access-list";
                  }
                  leaf priority {
                    type string;
                    description
                      "C-RP Priority";
                  }
                  leaf interval {
                    type string;
                    description
                      "C-RP Advertisement interval";
                  }
                  container bidir {
                    description
                      "To specify group ranges as Bidir";
                    leaf group-list {
                      type xr:ncs_template_Cisco-ios-xr-string;
                      description
                        "Group List access-list";
                    }
                    leaf priority {
                      type string;
                      description
                        "C-RP Priority";
                    }
                    leaf interval {
                      type string;
                      description
                        "C-RP Advertisement interval";
                    }
                  }
                }
              }
              container relay {
                description
                  "BSR RP relay config";
                container vrfs {
                  description
                    "vrf";
                  list vrf {
                    // NCS patched for predictable order
                    ordered-by user;
                    key "vrf-name";
                    description
                      "vrf";
                    leaf vrf-name {
                      type xr:ncs_template_Cisco-ios-xr-string;
                      description
                        "vrf";
                    }
                    container listen {
                      presence "Indicates a listen node is configured.";
                      description
                        "Enable RP relay in listen mode";
                    }
                  }
                }
              }
            }
            container mofrr {
              presence "Indicates a mofrr node is configured.";
              description
                "PIM Mofrr";
              leaf flow {
                type string;
                description
                  "Multicast Only FRR";
              }
              leaf rib {
                type string;
                description
                  "Use the rib keyword to restrict switchover triggers to RIB events";
              }
              container non-revertive {
                presence "Indicates a non-revertive node is configured.";
                description
                  "Non-revertive MoFRR";
              }
              container clone {
                description
                  "Use the clone keyword to clone";
                container joins {
                  description
                    "Use the join keyword to clone S,G as S1,G joins and S2,G joins";
                  list join {
                    // NCS patched for predictable order
                    ordered-by user;
                    // NCS drop must statement
                    key "address";
                    description
                      "Use the join keyword to clone S,G as S1,G joins as S2,G joins";
                    leaf address {
                      type string;
                      description
                        "Source S";
                    }
                    list to {
                      // NCS patched for predictable order
                      ordered-by user;
                      // NCS drop must statement
                      key "address";
                      description
                        "to";
                      leaf address {
                        type string;
                        description
                          "Source S1";
                      }
                      list and {
                        // NCS patched for predictable order
                        ordered-by user;
                        // NCS drop must statement
                        key "address";
                        description
                          "and";
                        leaf address {
                          type string;
                          description
                            "Source S2";
                        }
                        list masklen {
                          // NCS patched for predictable order
                          ordered-by user;
                          key "mask-length";
                          description
                            "masklen";
                          leaf mask-length {
                            type string;
                            description
                              "masklen";
                          }
                        }
                      }
                    }
                  }
                }
                container sources {
                  description
                    "Use the source keyword to clone S,G as S1,G traffic and S2,G traffic";
                  list source {
                    // NCS patched for predictable order
                    ordered-by user;
                    // NCS drop must statement
                    key "address";
                    description
                      "Use the source keyword to clone S,G as S1,G traffic and S2,G traffic";
                    leaf address {
                      type string;
                      description
                        "Source S";
                    }
                    list to {
                      // NCS patched for predictable order
                      ordered-by user;
                      // NCS drop must statement
                      key "address";
                      description
                        "to";
                      leaf address {
                        type string;
                        description
                          "Source S1";
                      }
                      list and {
                        // NCS patched for predictable order
                        ordered-by user;
                        // NCS drop must statement
                        key "address";
                        description
                          "and";
                        leaf address {
                          type string;
                          description
                            "Source S2";
                        }
                        list masklen {
                          // NCS patched for predictable order
                          ordered-by user;
                          key "mask-length";
                          description
                            "masklen";
                          leaf mask-length {
                            type string;
                            description
                              "masklen";
                          }
                        }
                      }
                    }
                  }
                }
              }
            }
            container sr-p2mp-policies {
              description
                "Segment-routing P2MP policy";
              list sr-p2mp-policy {
                // NCS patched for predictable order
                ordered-by user;
                key "sr-p2mp-policy-id";
                description
                  "Segment-routing P2MP policy";
                leaf sr-p2mp-policy-id {
                  type xr:ncs_template_Cisco-ios-xr-string;
                  description
                    "Segment-routing P2MP policy";
                }
                container static-group {
                  description
                    "ipv4 static multicast group";
                  list group-address {
                    // NCS patched for predictable order
                    ordered-by user;
                    key "group-address";
                    description
                      "ipv4 static multicast group";
                    leaf group-address {
                      type string;
                      description
                        "ipv4 static multicast group";
                    }
                    container group-address-only {
                      presence "Indicates a group-address-only node is configured.";
                      description
                        "Group-address without increment mask/source-address";
                    }
                    container group-address-inc-masks {
                      description
                        "Group-address with increment mask for group address";
                      list inc-mask {
                        // NCS patched for predictable order
                        ordered-by user;
                        key "group-mask-address";
                        description
                          "Increment mask for group address";
                        leaf group-mask-address {
                          type string;
                          description
                            "Increment mask for group address";
                        }
                        leaf group-address-count {
                          type string;
                          // NCS drop mandatory statement
                          description
                            "No. of group addresses to join";
                        }
                      }
                    }
                    container group-address-source-address {
                      description
                        "Group-address with source-address";
                      list source-address {
                        // NCS patched for predictable order
                        ordered-by user;
                        key "source-address";
                        description
                          "Source address to join";
                        leaf source-address {
                          type string;
                          description
                            "Source address to join";
                        }
                      }
                    }
                    container group-address-inc-mask-source-address {
                      description
                        "Group-address with increment-mask and source-address";
                      list inc-mask {
                        // NCS patched for predictable order
                        ordered-by user;
                        key "group-mask-address source-address";
                        description
                          "Increment mask for group address";
                        leaf group-mask-address {
                          type string;
                          description
                            "Increment mask for group address";
                        }
                        leaf source-address {
                          type string;
                          description
                            "Source address to join";
                        }
                        leaf group-address-count {
                          type string;
                          // NCS drop mandatory statement
                          description
                            "No. of group addresses to join";
                        }
                      }
                    }
                    container group-address-source-address-inc-mask {
                      description
                        "Group-address and source-address with increment-mask";
                      list inc-mask {
                        // NCS patched for predictable order
                        ordered-by user;
                        key "source-address source-mask-address";
                        description
                          "Increment mask for group address";
                        leaf source-address {
                          type string;
                          description
                            "Source address to join";
                        }
                        leaf source-mask-address {
                          type string;
                          description
                            "Increment mask for source address";
                        }
                        leaf source-address-count {
                          type string;
                          // NCS drop mandatory statement
                          description
                            "No. of source addresses to join";
                        }
                      }
                    }
                    container group-inc-mask-source-inc-mask {
                      description
                        "Group-address with increment-mask and source-address with increment-mask";
                      list inc-mask {
                        // NCS patched for predictable order
                        ordered-by user;
                        key "group-mask-address source-address source-mask-address";
                        leaf group-mask-address {
                          type string;
                          description
                            "Increment mask for group address";
                        }
                        leaf source-address {
                          type string;
                          description
                            "Source address to join";
                        }
                        leaf source-mask-address {
                          type string;
                          description
                            "Increment mask for source address";
                        }
                        leaf group-address-count {
                          type string;
                          // NCS drop mandatory statement
                          description
                            "No. of group addresses to join";
                        }
                        leaf source-address-count {
                          type string;
                          // NCS drop mandatory statement
                          description
                            "No. of source addresses to join";
                        }
                      }
                    }
                  }
                }
              }
            }
          }
          container ipv6 {
            description
              "IPv6 Address Family";
            container rp-addresses {
              description
                "Configure Rendezvous Point";
              list rp-address {
                // NCS patched for predictable order
                ordered-by user;
                key "address";
                description
                  "Configure Rendezvous Point";
                leaf address {
                  type string;
                  description
                    "Configure Rendezvous Point";
                }
                leaf access-list {
                  type xr:ncs_template_Cisco-ios-xr-string;
                  description
                    "Access list of groups that should map to given RP";
                }
                container override {
                  presence "Indicates a override node is configured.";
                  description
                    "Static RP config overrides auto-rp and BSR";
                }
              }
              container bidir {
                description
                  "Specify keyword bidir to configure a bidir RP";
                list rp-address {
                  // NCS patched for predictable order
                  ordered-by user;
                  key "address";
                  description
                    "Configure Rendezvous Point";
                  leaf address {
                    type string;
                    description
                      "Configure Rendezvous Point";
                  }
                  leaf access-list {
                    type xr:ncs_template_Cisco-ios-xr-string;
                    description
                      "Access list of groups that should map to given RP";
                  }
                  container override {
                    presence "Indicates a override node is configured.";
                    description
                      "Static RP config overrides auto-rp and BSR";
                  }
                }
              }
            }
            leaf rp-static-deny {
              type xr:ncs_template_Cisco-ios-xr-string;
              description
                "Configure static RP deny range";
            }
            leaf accept-register {
              type xr:ncs_template_Cisco-ios-xr-string;
              description
                "Registers accept filter";
            }
            container suppress-data-registers {
              presence "Indicates a suppress-data-registers node is configured.";
              description
                "Suppress data registers after initial state setup";
            }
            leaf register-source {
              type xr:ncs_template_Interface-name;
              description
                "Source address to use for register messages";
            }
            container suppress-rpf-change-prunes {
              presence "Indicates a suppress-rpf-change-prunes node is configured.";
              description
                "Suppress prunes triggered as a result of RPF changes";
            }
            leaf neighbor-filter {
              type xr:ncs_template_Cisco-ios-xr-string;
              description
                "Neighbor filter";
            }
            container convergence {
              description
                "Convergence related parameters";
              leaf rpf-conflict-join-delay {
                type string;
                description
                  "Delay in sending first join if RPF points to any downstream neighbor";
              }
              leaf link-down-prune-delay {
                type string;
                description
                  "Delay prunes if route join state transitions to not-joined on link down";
              }
            }
            container spt-threshold {
              description
                "Configure threshold for switching to SPT on last-hop";
              container infinity {
                presence "Indicates a infinity node is configured.";
                description
                  "Always stay on shared-tree";
                leaf group-list {
                  type xr:ncs_template_Cisco-ios-xr-string;
                  description
                    "Only stay on the shared-tree for specified groups";
                }
              }
            }
            container old-register-checksum {
              presence "Indicates a old-register-checksum node is configured.";
              description
                "Generate registers compatible with older IOS versions";
            }
            container nsf {
              description
                "Configure Non-stop forwarding (NSF) options";
              leaf lifetime {
                type string;
                description
                  "Override default maximum lifetime for PIM NSF mode";
              }
            }
            container neighbor-check-on-send {
              description
                "Check for PIM neighbor before sending control messages";
              container enable {
                presence "Indicates a enable node is configured.";
                description
                  "Enable this feature";
              }
            }
            container neighbor-check-on-recv {
              description
                "Check for PIM neighbor before rcv'ing control messages";
              container enable {
                presence "Indicates a enable node is configured.";
                description
                  "Enable this feature";
              }
            }
            leaf hello-interval {
              type string;
              description
                "Inherited by all interfaces : Hello interval in seconds";
            }
            leaf mdt-hello-interval {
              type string;
              description
                "Hello interval for all MDT interfaces (seconds)";
            }
            leaf dr-priority {
              type string;
              description
                "Inherited by all interfaces : PIM Hello DR priority";
            }
            leaf join-prune-interval {
              type string;
              description
                "Inherited by all interfaces : Join-Prune interval";
            }
            leaf join-prune-mtu {
              type string;
              description
                "Inherited by all interfaces : Join-Prune MTU";
            }
            leaf propagation-delay {
              type string;
              description
                "Inherited by all interfaces : PIM Hello Propagation delay";
            }
            leaf override-interval {
              type string;
              description
                "Inherited by all interfaces : PIM Hello override interval";
            }
            container global {
              description
                "Global maximum limits";
              container maximum {
                description
                  "Maximum state limits";
                container routes {
                  presence "Indicates a routes node is configured.";
                  description
                    "PIM routes for all VRFs";
                  leaf maximum-routes {
                    type string;
                    // NCS drop mandatory statement
                    description
                      "PIM routes for all VRFs";
                  }
                  leaf threshold {
                    type string;
                    // NCS drop must statement
                    description
                      "Set threshold to print warning";
                  }
                }
                container route-interfaces {
                  presence "Indicates a route-interfaces node is configured.";
                  description
                    "PIM total interfaces on routes for all VRFs";
                  leaf maximum-route-interfaces {
                    type string;
                    // NCS drop mandatory statement
                    description
                      "PIM total interfaces on routes for all VRFs";
                  }
                  leaf threshold {
                    type string;
                    // NCS drop must statement
                    description
                      "Set threshold to print warning";
                  }
                }
                container register-states {
                  presence "Indicates a register-states node is configured.";
                  description
                    "PIM source register states for all VRFs";
                  leaf maximum-register-states {
                    type string;
                    // NCS drop mandatory statement
                    description
                      "PIM source register states for all VRFs";
                  }
                  leaf threshold {
                    type string;
                    // NCS drop must statement
                    description
                      "Set threshold to print warning";
                  }
                }
                container packet-queue {
                  description
                    "PIM Packet queue size in bytes";
                  leaf high-priority {
                    type string;
                    description
                      "PIM high priority packet queue size in bytes";
                  }
                  leaf low-priority {
                    type string;
                    description
                      "PIM low priority packet queue size in bytes";
                  }
                }
                container group-mappings {
                  description
                    "PIM group-to-RP mapping ranges";
                  container bsr {
                    presence "Indicates a bsr node is configured.";
                    description
                      "Learned through the BSR distribution mechanism";
                    leaf maximum-bsr {
                      type string;
                      // NCS drop mandatory statement
                    }
                    leaf threshold {
                      type string;
                      // NCS drop must statement
                      description
                        "Set threshold to print warning";
                    }
                  }
                }
                container bsr {
                  description
                    "BSR maximum C-RP cache setting";
                  container crp-cache {
                    presence "Indicates a crp-cache node is configured.";
                    description
                      "Set maximum number of C-RP cache in BSR";
                    leaf maximum-crp-cache {
                      type string;
                      // NCS drop mandatory statement
                      description
                        "Set maximum number of C-RP cache in BSR";
                    }
                    leaf threshold {
                      type string;
                      // NCS drop must statement
                      description
                        "Set threshold to print warning";
                    }
                  }
                }
              }
            }
            container maximum {
              description
                "Maximum state limits";
              container routes {
                presence "Indicates a routes node is configured.";
                description
                  "PIM routes";
                leaf maximum-routes {
                  type string;
                  // NCS drop mandatory statement
                  description
                    "PIM routes";
                }
                leaf threshold {
                  type string;
                  // NCS drop must statement
                  description
                    "Set threshold to print warning";
                }
              }
              container route-interfaces {
                presence "Indicates a route-interfaces node is configured.";
                description
                  "PIM total number of interfaces on all routes";
                leaf maximum-route-interfaces {
                  type string;
                  // NCS drop mandatory statement
                  description
                    "PIM total number of interfaces on all routes";
                }
                leaf threshold {
                  type string;
                  // NCS drop must statement
                  description
                    "Set threshold to print warning";
                }
              }
              container register-states {
                presence "Indicates a register-states node is configured.";
                description
                  "PIM source register states";
                leaf maximum-register-states {
                  type string;
                  // NCS drop mandatory statement
                  description
                    "PIM source register states";
                }
                leaf threshold {
                  type string;
                  // NCS drop must statement
                  description
                    "Set threshold to print warning";
                }
              }
              container group-mappings {
                description
                  "PIM group-to-RP mapping ranges";
                container bsr {
                  presence "Indicates a group-mappings node is configured.";
                  description
                    "Learned through the BSR distribution mechanism";
                  leaf maximum-bsr {
                    type string;
                    // NCS drop mandatory statement
                    description
                      "Learned through the BSR distribution mechanism";
                  }
                  leaf threshold {
                    type string;
                    // NCS drop must statement
                    description
                      "Set threshold to print warning";
                  }
                }
              }
              container bsr {
                description
                  "BSR maximum C-RP cache setting";
                container crp-cache {
                  presence "Indicates a crp-cache node is configured.";
                  description
                    "Set maximum number of C-RP cache in BSR";
                  leaf maximum-crp-cache {
                    type string;
                    // NCS drop mandatory statement
                    description
                      "Set maximum number of C-RP cache in BSR";
                  }
                  leaf threshold {
                    type string;
                    // NCS drop must statement
                    description
                      "Set threshold to print warning";
                  }
                }
              }
            }
            leaf convergence-timeout {
              type string;
              description
                "Timeout value for the RIB convergence notification";
            }
            container log {
              description
                "Enable PIM logging";
              container neighbor {
                description
                  "Enable PIM neighbor logging";
                container changes {
                  presence "Indicates a changes node is configured.";
                  description
                    "Enable PIM neighbor state logging";
                }
              }
            }
            container rpf-vector {
              presence "Indicates a rpf-vector node is configured.";
              description
                "Enable PIM RPF Vector";
              container allow-ebgp {
                presence "Indicates a allow-ebgp node is configured.";
                description
                  "Allow origination of RPF vector over an eBGP session";
              }
              container disable-ibgp {
                presence "Indicates a disable-ibgp node is configured.";
                description
                  "Disable origination of RPF vector over an iBGP session";
              }
              container use-standard-encoding {
                presence "Indicates a use-standard-encoding node is configured.";
                description
                  "Use RFC standard encode type";
              }
            }
            container rpf {
              description
                "RPF commands";
              container topology {
                description
                  "Select RPF topology";
                leaf route-policy {
                  type xr:ncs_template_Route-policy-name;
                  description
                    "Route policy to select RPF topology";
                }
              }
            }
            container mdt {
              description
                "Multicast Distribution Tree commands";
              leaf neighbor-filter {
                type xr:ncs_template_Cisco-ios-xr-string;
                description
                  "Neighbor filter";
              }
              container data {
                description
                  "Data MDT Options";
                leaf switchover-interval {
                  type string;
                  description
                    "Data MDT switchover interval";
                }
                leaf announce-interval {
                  type string;
                  description
                    "Periodic Data MDT Join TLV interval";
                }
                leaf max-aggregation {
                  type string;
                  description
                    "Data MDT max-aggregation";
                }
              }
              container c-multicast-routing {
                presence "Indicates a c-multicast-routing node is configured.";
                description
                  "MVPN customer routing commands";
                leaf type {
                  type string;
                  // NCS drop mandatory statement
                  description
                    "MVPN customer routing commands";
                }
                container announce-pim-join-tlv {
                  presence "Indicates a announce-pim-join-tlv node is configured.";
                  description
                    "Announce PIM MDT Join TLVs";
                }
                container suppress-shared-tree-join {
                  presence "Indicates a suppress-shared-tree-join node is configured.";
                  description
                    "Suppress shared tree joins";
                }
                container suppress-pim-data-signaling {
                  presence "Indicates a suppress-pim-data-signaling node is configured.";
                  description
                    "Suppress PIM data signaling";
                }
                container mdt-hello {
                  // NCS drop when statement
                  description
                    "PIM Hellos over MDT";
                  container enable {
                    presence "Indicates a enable node is configured.";
                    description
                      "Enable PIM Hellos over MDT";
                  }
                }
                leaf shared-tree-prune-delay {
                  type string;
                  description
                    "Delay before pruning I-S PMSI from S,G when SA received";
                }
                leaf source-tree-prune-delay {
                  type string;
                  description
                    "Delay before removing PMSI from olist after BGP withdrawal";
                }
                container migration {
                  presence "Indicates a migration node is configured.";
                  description
                    "customer routing migration";
                  leaf route-policy {
                    type xr:ncs_template_Route-policy-name;
                    description
                      "Route policy to select customer routing";
                  }
                }
                container unicast-reachability {
                  description
                    "Control addition of Extended Communities to Unicast VPN-IP routes";
                  container connector {
                    description
                      "Enable/Disable Connector";
                    container disable {
                      // NCS drop must statement
                      presence "Indicates a disable node is configured.";
                      description
                        "Disable Connector Attribute";
                    }
                    container enable {
                      // NCS drop must statement
                      presence "Indicates a enable node is configured.";
                      description
                        "Enable Connector Attribute";
                    }
                  }
                  container source-as {
                    description
                      "Enable/Disable Source AS";
                    container disable {
                      // NCS drop must statement
                      presence "Indicates a disable node is configured.";
                      description
                        "Disable Source-AS Attribute";
                    }
                    container enable {
                      // NCS drop must statement
                      presence "Indicates a enable node is configured.";
                      description
                        "Enable Source-AS Attribute";
                    }
                  }
                  container vrf-route-import {
                    description
                      "Enable/Disable VRF Route Import";
                    container disable {
                      // NCS drop must statement
                      presence "Indicates a disable node is configured.";
                      description
                        "Disable VRF Route Import Attribute";
                    }
                    container enable {
                      // NCS drop must statement
                      presence "Indicates a enable node is configured.";
                      description
                        "Enable VRF Route Import Attribute";
                    }
                  }
                }
              }
            }
            container allow-rp {
              presence "Indicates a allow-rp node is configured.";
              description
                "Sparse-Mode RP addresses to be allowed";
              leaf rp-list {
                type xr:ncs_template_Cisco-ios-xr-string;
                description
                  "Access-list for allowed RP addresses";
              }
              leaf group-list {
                type xr:ncs_template_Cisco-ios-xr-string;
                description
                  "Access-list for allowed group ranges";
              }
            }
            container sg-expiry-timer {
              presence "Indicates a sg-expiry-timer node is configured.";
              description
                "Configure SG expiry timer";
              leaf sg-expiry-timer-value {
                type string;
                // NCS drop mandatory statement
                description
                  "Configure SG expiry timer";
              }
              leaf sg-list {
                type xr:ncs_template_Cisco-ios-xr-string;
                description
                  "Access-list of (S,G) routes for which expiry timer is applicable";
              }
            }
            container ssm {
              description
                "Configure a group range for Source-Specific use";
              leaf range {
                type xr:ncs_template_Cisco-ios-xr-string;
                // NCS drop must statement
                description
                  "Provide ACL that specifies non-standard SSM range";
              }
              container disable {
                // NCS drop must statement
                presence "Indicates a disable node is configured.";
                description
                  "Disable use of all SSM group ranges";
              }
              container allow-override {
                presence "Indicates a allow-override node is configured.";
                description
                  "Allow SSM ranges to be overridden by more specific ranges";
              }
            }
            container multipath {
              presence "Indicates a multipath node is configured.";
              description
                "Enable equal-cost multipath routing";
              container hash {
                // NCS drop must statement
                presence "Indicates a hash node is configured.";
                description
                  "Enter a hashing algorithm";
                container interface-extended {
                  // NCS drop must statement
                  presence "Indicates a interface-extended node is configured.";
                  description
                    "Enable interface extensions for non-unique next-hop addrs";
                }
                container source-nexthop {
                  // NCS drop must statement
                  presence "Indicates a source-nexthop node is configured.";
                  description
                    "Enable source with next-hop multipath hashing (better distribution)";
                }
                container source-group {
                  // NCS drop must statement
                  presence "Indicates a source-group node is configured.";
                  description
                    "Enable source, group based multipath hashing (Compatible with IOS versions)";
                }
              }
            }
            container interface {
              description
                "PIM interface configuration subcommands";
              container interfaces {
                description
                  "Select an interface to configure";
                list interface {
                  // NCS patched for predictable order
                  ordered-by user;
                  key "interface-name";
                  description
                    "Select an interface to configure";
                  leaf interface-name {
                    type xr:ncs_template_Interface-name;
                    description
                      "Select an interface to configure";
                  }
                  leaf dr-priority {
                    type string;
                    description
                      "PIM Hello DR priority";
                  }
                  leaf hello-interval {
                    type string;
                    description
                      "PIM neighbor Hello announcement interval";
                  }
                  leaf join-prune-interval {
                    type string;
                    description
                      "PIM periodic Join-Prune announcement interval";
                  }
                  leaf join-prune-mtu {
                    type string;
                    description
                      "MTU to use when sending PIM J/P packets";
                  }
                  leaf propagation-delay {
                    type string;
                    description
                      "PIM Hello propagation delay";
                  }
                  leaf override-interval {
                    type string;
                    description
                      "PIM Hello override interval";
                  }
                  container bsr-border {
                    presence "Indicates a bsr-border node is configured.";
                    description
                      "Do not fwd BSR messages on this interface";
                  }
                  container enable {
                    // NCS drop must statement
                    presence "Indicates a enable node is configured.";
                    description
                      "Enable PIM processing on this interface";
                  }
                  container disable {
                    // NCS drop must statement
                    presence "Indicates a disable node is configured.";
                    description
                      "Disable PIM processing on this interface";
                  }
                  leaf neighbor-filter {
                    type xr:ncs_template_Cisco-ios-xr-string;
                    description
                      "PIM Neighbor filter on this interface";
                  }
                  container maximum {
                    description
                      "Per interface maximum state limits";
                    container route-interfaces {
                      presence "Indicates a route-interfaces node is configured.";
                      description
                        "PIM downstream joined interfaces";
                      leaf maximum-route-interfaces {
                        type string;
                        // NCS drop mandatory statement
                        description
                          "PIM downstream joined interfaces";
                      }
                      leaf threshold {
                        type string;
                        // NCS drop must statement
                        description
                          "Threshold warning";
                      }
                      leaf access-list {
                        type xr:ncs_template_Cisco-ios-xr-string;
                        description
                          "Name of ACL that specifies to which routes to apply the maximum limit";
                      }
                    }
                  }
                  container bfd {
                    description
                      "Configure BFD parameters";
                    container fast-detect {
                      presence "Indicates a fast-detect node is configured.";
                      description
                        "Enable Fast detection";
                    }
                    leaf minimum-interval {
                      type string;
                      description
                        "Hello interval";
                    }
                    leaf multiplier {
                      type string;
                      description
                        "Detect multiplier";
                    }
                  }
                }
              }
            }
            container bsr {
              description
                "BSR Configurations";
              container candidate-bsr {
                presence "Indicates a candidate-bsr node is configured.";
                description
                  "configure candidate BSR";
                leaf address {
                  type string;
                  // NCS drop mandatory statement
                  description
                    "IP address of configured BSR";
                }
                leaf hash-mask-len {
                  type string;
                  // NCS drop mandatory statement
                  description
                    "BSR Hash Mask Length";
                }
                leaf priority {
                  type string;
                  // NCS drop mandatory statement
                  description
                    "BSR Priority";
                }
              }
              container candidate-rps {
                description
                  "BSR Candidate RP Configurations";
                list candidate-rp {
                  // NCS patched for predictable order
                  ordered-by user;
                  // NCS drop must statement
                  key "address";
                  description
                    "BSR Candidate RP Configurations";
                  leaf address {
                    type string;
                    description
                      "BSR Candidate RP Configurations";
                  }
                  leaf group-list {
                    type xr:ncs_template_Cisco-ios-xr-string;
                    description
                      "Group List access-list";
                  }
                  leaf priority {
                    type string;
                    description
                      "C-RP Priority";
                  }
                  leaf interval {
                    type string;
                    description
                      "C-RP Advertisement interval";
                  }
                  container bidir {
                    description
                      "To specify group ranges as Bidir";
                    leaf group-list {
                      type xr:ncs_template_Cisco-ios-xr-string;
                      description
                        "Group List access-list";
                    }
                    leaf priority {
                      type string;
                      description
                        "C-RP Priority";
                    }
                    leaf interval {
                      type string;
                      description
                        "C-RP Advertisement interval";
                    }
                  }
                }
              }
              container relay {
                description
                  "BSR RP relay config";
                container vrfs {
                  description
                    "vrf";
                  list vrf {
                    // NCS patched for predictable order
                    ordered-by user;
                    key "vrf-name";
                    description
                      "vrf";
                    leaf vrf-name {
                      type xr:ncs_template_Cisco-ios-xr-string;
                      description
                        "vrf";
                    }
                    container listen {
                      presence "Indicates a listen node is configured.";
                      description
                        "Enable RP relay in listen mode";
                    }
                  }
                }
              }
            }
            container sr-p2mp-policies {
              description
                "Segment-routing P2MP policy";
              list sr-p2mp-policy {
                // NCS patched for predictable order
                ordered-by user;
                key "sr-p2mp-policy-id";
                description
                  "Segment-routing P2MP policy";
                leaf sr-p2mp-policy-id {
                  type xr:ncs_template_Cisco-ios-xr-string;
                  description
                    "Segment-routing P2MP policy";
                }
                container static-group {
                  description
                    "ipv6 static multicast group";
                  list group-address {
                    // NCS patched for predictable order
                    ordered-by user;
                    key "group-address";
                    description
                      "ipv6 static multicast group";
                    leaf group-address {
                      type string;
                      description
                        "ipv6 static multicast group";
                    }
                    container group-address-only {
                      presence "Indicates a group-address-only node is configured.";
                      description
                        "Group-address without increment mask/source-address";
                    }
                    container group-address-inc-masks {
                      description
                        "Group-address with increment mask for group address";
                      list inc-mask {
                        // NCS patched for predictable order
                        ordered-by user;
                        key "group-mask-address";
                        description
                          "Increment mask for group address";
                        leaf group-mask-address {
                          type string;
                          description
                            "Increment mask for group address";
                        }
                        leaf group-address-count {
                          type string;
                          // NCS drop mandatory statement
                          description
                            "No. of group addresses to join";
                        }
                      }
                    }
                    container group-address-source-address {
                      description
                        "Group-address with source-address";
                      list source-address {
                        // NCS patched for predictable order
                        ordered-by user;
                        key "source-address";
                        description
                          "Source address to join";
                        leaf source-address {
                          type string;
                          description
                            "Source address to join";
                        }
                      }
                    }
                    container group-address-inc-mask-source-address {
                      description
                        "Group-address with increment-mask and source-address";
                      list inc-mask {
                        // NCS patched for predictable order
                        ordered-by user;
                        key "group-mask-address source-address";
                        description
                          "Increment mask for group address";
                        leaf group-mask-address {
                          type string;
                          description
                            "Increment mask for group address";
                        }
                        leaf source-address {
                          type string;
                          description
                            "Source address to join";
                        }
                        leaf group-address-count {
                          type string;
                          // NCS drop mandatory statement
                          description
                            "No. of group addresses to join";
                        }
                      }
                    }
                    container group-address-source-address-inc-mask {
                      description
                        "Group-address and source-address with increment-mask";
                      list inc-mask {
                        // NCS patched for predictable order
                        ordered-by user;
                        key "source-address source-mask-address";
                        description
                          "Increment mask for group address";
                        leaf source-address {
                          type string;
                          description
                            "Source address to join";
                        }
                        leaf source-mask-address {
                          type string;
                          description
                            "Increment mask for source address";
                        }
                        leaf source-address-count {
                          type string;
                          // NCS drop mandatory statement
                          description
                            "No. of source addresses to join";
                        }
                      }
                    }
                    container group-inc-mask-source-inc-mask {
                      description
                        "Group-address with increment-mask and source-address with increment-mask";
                      list inc-mask {
                        // NCS patched for predictable order
                        ordered-by user;
                        key "group-mask-address source-address source-mask-address";
                        leaf group-mask-address {
                          type string;
                          description
                            "Increment mask for group address";
                        }
                        leaf source-address {
                          type string;
                          description
                            "Source address to join";
                        }
                        leaf source-mask-address {
                          type string;
                          description
                            "Increment mask for source address";
                        }
                        leaf group-address-count {
                          type string;
                          // NCS drop mandatory statement
                          description
                            "No. of group addresses to join";
                        }
                        leaf source-address-count {
                          type string;
                          // NCS drop mandatory statement
                          description
                            "No. of source addresses to join";
                        }
                      }
                    }
                  }
                }
              }
            }
            container embedded-rp {
              description
                "Set Embedded RP processing support";
              list ip-addresses {
                // NCS patched for predictable order
                ordered-by user;
                key "ip-address";
                description
                  "IP name or address of Rendezvous Point";
                leaf ip-address {
                  type string;
                  description
                    "IP name or address of Rendezvous Point";
                }
                leaf access-list-name {
                  type xr:ncs_template_Cisco-ios-xr-string;
                  // NCS drop mandatory statement
                  description
                    "Access list of groups that should map to given RP";
                }
              }
              container disable {
                presence "Indicates a disable node is configured.";
                description
                  "Disable Embedded RP processing";
              }
            }
          }
        }
      }
    }
  }
}

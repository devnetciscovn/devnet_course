module Cisco-IOS-XR-cfgmgr-rollback-act {
  // Generated by yanger -t ncs
  tailf:mount-id "cisco-iosxr-nc-7.3:cisco-iosxr-nc-7.3";
  tailf:ncs-device-type "netconf";

  namespace "http://cisco.com/ns/yang/Cisco-IOS-XR-cfgmgr-rollback-act";
  prefix rollback-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2016-04-17 {
    description
      "IOS XR 6.1.1 revision.";
  }

  grouping ncs_template_ROLLBACK-ATTRIBUTES {
    description
      "Rollback Attributes";
    leaf force {
      // NCS drop when statement
      type string;
      // NCS drop default statement
      description
        "Override commit blocks";
    }
    leaf best-effort {
      // NCS drop when statement
      type string;
      // NCS drop default statement
      description
        "Rollback via best-effort operation";
    }
    leaf label {
      type string;
      description
        "Assign a label to this rollback";
    }
    leaf comment {
      type string;
      description
        "Assign a comment to this rollback";
    }
  }

  grouping ncs_rpc_notif_ROLLBACK-ATTRIBUTES {
    description
      "Rollback Attributes";
    leaf force {
      when "../best-effort = 'false'" {
        tailf:xpath-root 3;
        description
          "Only when best-effort is false.";
      }
      type boolean;
      default "false";
      description
        "Override commit blocks";
    }
    leaf best-effort {
      when "../force = 'false'" {
        tailf:xpath-root 3;
        description
          "Only when force is false.";
      }
      type boolean;
      default "false";
      description
        "Rollback via best-effort operation";
    }
    leaf label {
      type string;
      description
        "Assign a label to this rollback";
    }
    leaf comment {
      type string;
      description
        "Assign a comment to this rollback";
    }
  }

  grouping live_ncs_ROLLBACK-ATTRIBUTES {
    description
      "Rollback Attributes";
    leaf force {
      // NCS drop when statement
      type boolean;
      // NCS drop default statement
      description
        "Override commit blocks";
    }
    leaf best-effort {
      // NCS drop when statement
      type boolean;
      // NCS drop default statement
      description
        "Rollback via best-effort operation";
    }
    leaf label {
      type string;
      description
        "Assign a label to this rollback";
    }
    leaf comment {
      type string;
      description
        "Assign a comment to this rollback";
    }
  }

  grouping ROLLBACK-ATTRIBUTES {
    description
      "Rollback Attributes";
    leaf force {
      when "../best-effort = 'false'" {
        tailf:xpath-root 3;
        description
          "Only when best-effort is false.";
      }
      type boolean;
      default "false";
      description
        "Override commit blocks";
    }
    leaf best-effort {
      when "../force = 'false'" {
        tailf:xpath-root 3;
        description
          "Only when force is false.";
      }
      type boolean;
      default "false";
      description
        "Rollback via best-effort operation";
    }
    leaf label {
      type string;
      description
        "Assign a label to this rollback";
    }
    leaf comment {
      type string;
      description
        "Assign a comment to this rollback";
    }
  }

  augment "/ncs:devices/ncs:device/ncs:rpc" {
    container rpc-roll-back-configuration {
      tailf:ncs-device-type "netconf";
      tailf:display-when "not(../../ncs:module) or ../../ncs:module[ncs:name='Cisco-IOS-XR-cfgmgr-rollback-act']";
      tailf:action roll-back-configuration {
        tailf:actionpoint ncsproxy {
          tailf:internal;
        }
        description
          "Rollback a specific commit";
        input {
          leaf commit-id {
            type string;
            mandatory true;
            description
              "Commit ID";
          }
          uses ncs_rpc_notif_ROLLBACK-ATTRIBUTES;
        }
      }
    }
  }
  augment "/ncs:devices/ncs:device-group/ncs:ned-id/ncs:rpc" {
    container rpc-roll-back-configuration {
      tailf:ncs-device-type "netconf";
      tailf:display-when "/ncs:devices/ncs:device[ncs:name=current()/../../../ncs:member]/ncs:module[ncs:name='Cisco-IOS-XR-cfgmgr-rollback-act']";
      tailf:action roll-back-configuration {
        tailf:actionpoint ncsproxy {
          tailf:internal;
        }
        description
          "Rollback a specific commit";
        input {
          leaf commit-id {
            type string;
            mandatory true;
            description
              "Commit ID";
          }
          uses ncs_rpc_notif_ROLLBACK-ATTRIBUTES;
        }
      }
    }
  }
  augment "/ncs:devices/ncs:device/ncs:rpc" {
    container rpc-roll-back-configuration-to-exclude {
      tailf:ncs-device-type "netconf";
      tailf:display-when "not(../../ncs:module) or ../../ncs:module[ncs:name='Cisco-IOS-XR-cfgmgr-rollback-act']";
      tailf:action roll-back-configuration-to-exclude {
        tailf:actionpoint ncsproxy {
          tailf:internal;
        }
        description
          "Rollback up to (and excluding) a specific commit";
        input {
          leaf commit-id {
            type string;
            mandatory true;
            description
              "Commit ID";
          }
          uses ncs_rpc_notif_ROLLBACK-ATTRIBUTES;
        }
      }
    }
  }
  augment "/ncs:devices/ncs:device-group/ncs:ned-id/ncs:rpc" {
    container rpc-roll-back-configuration-to-exclude {
      tailf:ncs-device-type "netconf";
      tailf:display-when "/ncs:devices/ncs:device[ncs:name=current()/../../../ncs:member]/ncs:module[ncs:name='Cisco-IOS-XR-cfgmgr-rollback-act']";
      tailf:action roll-back-configuration-to-exclude {
        tailf:actionpoint ncsproxy {
          tailf:internal;
        }
        description
          "Rollback up to (and excluding) a specific commit";
        input {
          leaf commit-id {
            type string;
            mandatory true;
            description
              "Commit ID";
          }
          uses ncs_rpc_notif_ROLLBACK-ATTRIBUTES;
        }
      }
    }
  }
  augment "/ncs:devices/ncs:device/ncs:rpc" {
    container rpc-roll-back-configuration-to {
      tailf:ncs-device-type "netconf";
      tailf:display-when "not(../../ncs:module) or ../../ncs:module[ncs:name='Cisco-IOS-XR-cfgmgr-rollback-act']";
      tailf:action roll-back-configuration-to {
        tailf:actionpoint ncsproxy {
          tailf:internal;
        }
        description
          "Rollback up to (and including) a specific commit";
        input {
          leaf commit-id {
            type string;
            mandatory true;
            description
              "Commit ID";
          }
          uses ncs_rpc_notif_ROLLBACK-ATTRIBUTES;
        }
      }
    }
  }
  augment "/ncs:devices/ncs:device-group/ncs:ned-id/ncs:rpc" {
    container rpc-roll-back-configuration-to {
      tailf:ncs-device-type "netconf";
      tailf:display-when "/ncs:devices/ncs:device[ncs:name=current()/../../../ncs:member]/ncs:module[ncs:name='Cisco-IOS-XR-cfgmgr-rollback-act']";
      tailf:action roll-back-configuration-to {
        tailf:actionpoint ncsproxy {
          tailf:internal;
        }
        description
          "Rollback up to (and including) a specific commit";
        input {
          leaf commit-id {
            type string;
            mandatory true;
            description
              "Commit ID";
          }
          uses ncs_rpc_notif_ROLLBACK-ATTRIBUTES;
        }
      }
    }
  }
  augment "/ncs:devices/ncs:device/ncs:rpc" {
    container rpc-roll-back-configuration-last {
      tailf:ncs-device-type "netconf";
      tailf:display-when "not(../../ncs:module) or ../../ncs:module[ncs:name='Cisco-IOS-XR-cfgmgr-rollback-act']";
      tailf:action roll-back-configuration-last {
        tailf:actionpoint ncsproxy {
          tailf:internal;
        }
        description
          "Rollback last <n> commits made";
        input {
          leaf count {
            type int32 {
              range "1..100";
            }
            mandatory true;
            description
              "Number of commits to rollback";
          }
          uses ncs_rpc_notif_ROLLBACK-ATTRIBUTES;
        }
      }
    }
  }
  augment "/ncs:devices/ncs:device-group/ncs:ned-id/ncs:rpc" {
    container rpc-roll-back-configuration-last {
      tailf:ncs-device-type "netconf";
      tailf:display-when "/ncs:devices/ncs:device[ncs:name=current()/../../../ncs:member]/ncs:module[ncs:name='Cisco-IOS-XR-cfgmgr-rollback-act']";
      tailf:action roll-back-configuration-last {
        tailf:actionpoint ncsproxy {
          tailf:internal;
        }
        description
          "Rollback last <n> commits made";
        input {
          leaf count {
            type int32 {
              range "1..100";
            }
            mandatory true;
            description
              "Number of commits to rollback";
          }
          uses ncs_rpc_notif_ROLLBACK-ATTRIBUTES;
        }
      }
    }
  }
}

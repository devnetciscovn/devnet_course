submodule Cisco-IOS-XR-skywarp-netflow-oper-sub2 {
  // Generated by yanger -t ncs
  tailf:mount-id "cisco-iosxr-nc-7.3:cisco-iosxr-nc-7.3";

  belongs-to Cisco-IOS-XR-skywarp-netflow-oper {
    prefix Cisco-IOS-XR-skywarp-netflow-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR skywarp-netflow package operational data.

     Copyright (c) 2013-2020 by Cisco Systems, Inc.
     All rights reserved.";

  revision 2020-02-19 {
    description
      "sFlow Development for spitfire";
    semver:module-version "1.1.0";
  }
  revision 2019-04-05 {
    description
      "Establish semantic version baseline.";
    semver:module-version "1.0.0";
  }
  revision 2015-11-09 {
    description
      "IOS XR 6.0 revision.";
  }

  grouping ncs_template_NF-PRODUCER-STATS {
    description
      "Netflow Platform Producer Process statistics";
    leaf ethernet-pkts {
      type string;
      description
        "Ethernet Packets";
    }
    leaf drops-no-space {
      type string;
      description
        "Drops (no space)";
    }
    leaf drops-others {
      type string;
      description
        "Drops (others)";
    }
    leaf unknown-ingress-flows {
      type string;
      description
        "Unknown ingress flows";
    }
    leaf waiting-servers {
      type string;
      description
        "Number of waiting servers";
    }
    leaf spp-rx-counts {
      type string;
      description
        "Number of Rxed SPP Packets";
    }
    leaf flow-packet-counts {
      type string;
      description
        "Number of Rxed Flow Packets";
    }
    leaf last-cleared {
      type string;
      description
        "Last time Statistics cleared in 'Mon Jan 1 12:00
         :00 2xxx' format";
    }
  }

  grouping ncs_rpc_notif_NF-PRODUCER-STATS {
    description
      "Netflow Platform Producer Process statistics";
    leaf ethernet-pkts {
      type uint64;
      description
        "Ethernet Packets";
    }
    leaf drops-no-space {
      type uint64;
      description
        "Drops (no space)";
    }
    leaf drops-others {
      type uint64;
      description
        "Drops (others)";
    }
    leaf unknown-ingress-flows {
      type uint64;
      description
        "Unknown ingress flows";
    }
    leaf waiting-servers {
      type uint64;
      description
        "Number of waiting servers";
    }
    leaf spp-rx-counts {
      type uint64;
      description
        "Number of Rxed SPP Packets";
    }
    leaf flow-packet-counts {
      type uint64;
      description
        "Number of Rxed Flow Packets";
    }
    leaf last-cleared {
      type string;
      description
        "Last time Statistics cleared in 'Mon Jan 1 12:00
         :00 2xxx' format";
    }
  }

  grouping live_ncs_NF-PRODUCER-STATS {
    description
      "Netflow Platform Producer Process statistics";
    leaf ethernet-pkts {
      type uint64;
      description
        "Ethernet Packets";
    }
    leaf drops-no-space {
      type uint64;
      description
        "Drops (no space)";
    }
    leaf drops-others {
      type uint64;
      description
        "Drops (others)";
    }
    leaf unknown-ingress-flows {
      type uint64;
      description
        "Unknown ingress flows";
    }
    leaf waiting-servers {
      type uint64;
      description
        "Number of waiting servers";
    }
    leaf spp-rx-counts {
      type uint64;
      description
        "Number of Rxed SPP Packets";
    }
    leaf flow-packet-counts {
      type uint64;
      description
        "Number of Rxed Flow Packets";
    }
    leaf last-cleared {
      type string;
      description
        "Last time Statistics cleared in 'Mon Jan 1 12:00
         :00 2xxx' format";
    }
  }

  grouping NF-PRODUCER-STATS {
    description
      "Netflow Platform Producer Process statistics";
    leaf ethernet-pkts {
      type uint64;
      description
        "Ethernet Packets";
    }
    leaf drops-no-space {
      type uint64;
      description
        "Drops (no space)";
    }
    leaf drops-others {
      type uint64;
      description
        "Drops (others)";
    }
    leaf unknown-ingress-flows {
      type uint64;
      description
        "Unknown ingress flows";
    }
    leaf waiting-servers {
      type uint64;
      description
        "Number of waiting servers";
    }
    leaf spp-rx-counts {
      type uint64;
      description
        "Number of Rxed SPP Packets";
    }
    leaf flow-packet-counts {
      type uint64;
      description
        "Number of Rxed Flow Packets";
    }
    leaf last-cleared {
      type string;
      description
        "Last time Statistics cleared in 'Mon Jan 1 12:00
         :00 2xxx' format";
    }
  }
}

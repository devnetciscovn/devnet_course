module Cisco-IOS-XR-Ethernet-SPAN-oper {
  // Generated by yanger -t ncs
  tailf:mount-id "cisco-iosxr-nc-7.3:cisco-iosxr-nc-7.3";
  tailf:ncs-device-type "netconf";

  namespace "http://cisco.com/ns/yang/Cisco-IOS-XR-Ethernet-SPAN-oper";
  prefix ethernet-span-oper;

  import Cisco-IOS-XR-types {
    prefix xr;
  }
  import cisco-semver {
    prefix semver;
  }
  import Cisco-IOS-XR-Ethernet-SPAN-datatypes {
    prefix dt1;
  }
  include Cisco-IOS-XR-Ethernet-SPAN-oper-sub3 {
    revision-date 2020-09-14;
  }
  include Cisco-IOS-XR-Ethernet-SPAN-oper-sub2 {
    revision-date 2020-09-14;
  }
  include Cisco-IOS-XR-Ethernet-SPAN-oper-sub1 {
    revision-date 2020-09-14;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN package operational data.

     This module contains definitions
     for the following management objects:
       span-monitor-session: Monitor Session operational data

     Copyright (c) 2013-2020 by Cisco Systems, Inc.
     All rights reserved.";

  revision 2020-09-14 {
    description
      "Added support for mirror rx and tx traffic to separate destinations";
    semver:module-version "4.0.0";
  }
  revision 2020-01-30 {
    description
      "Added support for L3 IPv4 and IPv6 ACLs on a L2 ethernet SPAN session
       2019-12-12
       Added support for file format and PCAP filter expressions under file
       2019-10-02
       Added support for UDP destinations and CloudSPAN.";
    semver:module-version "3.0.0";
  }
  revision 2019-05-12 {
    description
      "Added support for file destinations.";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    // NCS drop config false container 'span-monitor-session'
  }
  augment "/ncs:devices/ncs:device/ncs:live-status" {
    container span-monitor-session {
      tailf:ncs-device-type "netconf";
      tailf:display-when "not(../../ncs:module) or ../../ncs:module[ncs:name='Cisco-IOS-XR-Ethernet-SPAN-oper'] or (../../ncs:live-status-protocol[not(ncs:capability)]) or (../../ncs:live-status-protocol/ncs:capability/ncs:module[.='Cisco-IOS-XR-Ethernet-SPAN-oper'])";
      description
        "Monitor Session operational data";
      container global {
        description
          "Global operational data";
        container statistics {
          description
            "Table of statistics for source interfaces";
          list statistic {
            key "session interface";
            description
              "Statistics for a particular source interface";
            leaf session {
              type dt1:live_ncs_Span-session-name;
              description
                "Session Name";
            }
            leaf interface {
              type xr:live_ncs_Interface-name;
              description
                "Interface";
            }
            uses live_ncs_SPAN-MA-STATISTICS-BAG;
          }
        }
        container global-sessions {
          description
            "Global Monitor Sessions table";
          list global-session {
            key "session";
            description
              "Information about a globally-configured
               monitor session";
            leaf session {
              type dt1:live_ncs_Span-session-name;
              description
                "Session Name";
            }
            uses live_ncs_SPAN-MGR-SESSION-BAG;
          }
        }
      }
      container nodes {
        description
          "Node table for node-specific operational data";
        list node {
          key "node";
          description
            "Node-specific data for a particular node";
          container attachments {
            description
              "Table of source interfaces configured as
               attached to a session";
            list attachment {
              key "session interface";
              description
                "Information about a particular source
                 interface configured as attached to monitor
                 session";
              leaf session {
                type dt1:live_ncs_Span-session-name;
                description
                  "Session Name";
              }
              leaf interface {
                type xr:live_ncs_Interface-name;
                description
                  "Interface";
              }
              uses live_ncs_SPAN-MA-ATTACHMENT-BAG;
            }
          }
          container hardware-sessions {
            description
              "Table of sessions set up in the hardware.
               When all sessions are operating correctly the
               entries in this table should match those
               entries in GlobalSessionTable that have a
               destination configured";
            list hardware-session {
              description
                "Information about a particular session that
                 is set up in the hardware";
              leaf session-class {
                type dt1:live_ncs_Span-session-class;
                description
                  "Sesssion class";
              }
              leaf session-id {
                type dt1:live_ncs_Span-session-id;
                description
                  "Session ID";
              }
              uses live_ncs_SPAN-EA-SESS-BAG;
            }
          }
          container interfaces {
            description
              "Table of source interfaces set up in the
               hardware.  The entries in this table should
               match the entries in AttachmentTable when all
               sessions are operating correctly";
            list interface {
              key "interface";
              description
                "Information about a particular interface that
                 is set up in the hardware";
              leaf interface {
                type xr:live_ncs_Interface-name;
                description
                  "Interface";
              }
              uses live_ncs_SPAN-EA-INTF-BAG;
            }
          }
          leaf node {
            type xr:live_ncs_Node-id;
            description
              "Node";
          }
        }
      }
    }
  }
  augment "/ncs:devices/ncs:template/ncs:ned-id/ncs:config" {
    // NCS drop config false container 'span-monitor-session'
  }
}

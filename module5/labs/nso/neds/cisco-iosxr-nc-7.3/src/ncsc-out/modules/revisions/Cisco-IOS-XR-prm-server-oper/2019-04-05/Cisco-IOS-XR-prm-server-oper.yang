module Cisco-IOS-XR-prm-server-oper {
  // Generated by yanger -t ncs
  tailf:mount-id "cisco-iosxr-nc-7.3:cisco-iosxr-nc-7.3";
  tailf:ncs-device-type "netconf";

  namespace "http://cisco.com/ns/yang/Cisco-IOS-XR-prm-server-oper";
  prefix prm-server-oper;

  import Cisco-IOS-XR-types {
    prefix xr;
  }
  import cisco-semver {
    prefix semver;
  }
  include Cisco-IOS-XR-prm-server-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR prm-server package operational data.

     This module contains definitions
     for the following management objects:
       hardware-module: PRM data
       prm: PRM data

     Copyright (c) 2013-2019 by Cisco Systems, Inc.
     All rights reserved.";

  revision 2019-04-05 {
    description
      "Establish semantic version baseline.";
    semver:module-version "1.0.0";
  }
  revision 2016-02-22 {
    description
      "Initial revision.";
  }
  revision 2015-11-09 {
    description
      "IOS XR 6.0 revision.";
  }

  augment "/ncs:devices/ncs:device/ncs:config" {
    // NCS drop config false container 'hardware-module'
    // NCS drop config false container prm
  }
  augment "/ncs:devices/ncs:device/ncs:live-status" {
    container hardware-module {
      tailf:ncs-device-type "netconf";
      tailf:display-when "not(../../ncs:module) or ../../ncs:module[ncs:name='Cisco-IOS-XR-prm-server-oper'] or (../../ncs:live-status-protocol[not(ncs:capability)]) or (../../ncs:live-status-protocol/ncs:capability/ncs:module[.='Cisco-IOS-XR-prm-server-oper'])";
      description
        "PRM data";
      container nodes {
        description
          "List of PRM Nodes";
        list node {
          key "node-name";
          description
            "Node Information";
          container np {
            description
              "Server specific";
            container cpu {
              description
                "Resource specific";
              container indexes {
                description
                  "Data for software resource";
                list index {
                  key "index";
                  description
                    "Queue Stats";
                  leaf index {
                    type uint32;
                    description
                      "Index value";
                  }
                  uses live_ncs_BCM-EDM-COSQ-INFO;
                }
              }
            }
            container platform-drop {
              description
                "Platform drops";
              container indxes {
                description
                  "Captured Packets";
                list indx {
                  key "index";
                  description
                    "Captured packets";
                  leaf index {
                    type uint32;
                    description
                      "Index value";
                  }
                  uses live_ncs_PLAT-DROP-CAPTURED-PAK;
                }
              }
              container idxes {
                description
                  "Stats for Drop packets";
                list idx {
                  key "index";
                  description
                    "Drop Stats";
                  leaf index {
                    type uint32;
                    description
                      "Index value";
                  }
                  uses live_ncs_PLAT-DROP-STATS-INFO;
                }
              }
            }
          }
          leaf node-name {
            type xr:live_ncs_Node-id;
            description
              "The node name";
          }
        }
      }
    }
    container prm {
      tailf:ncs-device-type "netconf";
      tailf:display-when "not(../../ncs:module) or ../../ncs:module[ncs:name='Cisco-IOS-XR-prm-server-oper'] or (../../ncs:live-status-protocol[not(ncs:capability)]) or (../../ncs:live-status-protocol/ncs:capability/ncs:module[.='Cisco-IOS-XR-prm-server-oper'])";
      description
        "PRM data";
      container nodes {
        description
          "List of PRM Nodes";
        list node {
          key "node-name";
          description
            "Node Information";
          container server {
            description
              "Server specific";
            container resource {
              description
                "Resource specific";
              container indexes {
                description
                  "Data for software resource";
                list index {
                  key "index";
                  description
                    "Data for software resource";
                  leaf index {
                    type uint32;
                    description
                      "Index value";
                  }
                  uses live_ncs_RESOURCE-EDM-DATA;
                }
              }
            }
          }
          leaf node-name {
            type xr:live_ncs_Node-id;
            description
              "The node name";
          }
        }
      }
    }
  }
  augment "/ncs:devices/ncs:template/ncs:ned-id/ncs:config" {
    // NCS drop config false container 'hardware-module'
    // NCS drop config false container prm
  }
}

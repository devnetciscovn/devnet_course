module Cisco-IOS-XR-segment-routing-ms-oper {
  // Generated by yanger -t ncs
  tailf:mount-id "cisco-iosxr-nc-7.3:cisco-iosxr-nc-7.3";
  tailf:ncs-device-type "netconf";

  namespace "http://cisco.com/ns/yang/Cisco-IOS-XR-segment-routing-ms-oper";
  prefix segment-routing-ms-oper;

  import Cisco-IOS-XR-types {
    prefix xr;
  }
  import cisco-semver {
    prefix semver;
  }
  include Cisco-IOS-XR-segment-routing-ms-oper-sub3 {
    revision-date 2019-07-19;
  }
  include Cisco-IOS-XR-segment-routing-ms-oper-sub2 {
    revision-date 2019-07-19;
  }
  include Cisco-IOS-XR-segment-routing-ms-oper-sub1 {
    revision-date 2019-07-19;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR segment-routing-ms package operational data.

     This module contains definitions
     for the following management objects:
       standby-srms: Standby Segment Routing Mapping Server
         operational data
       srms: Active Segment Routing Mapping Server operational data
       srlb: Segment Routing Local Block operational data

     Copyright (c) 2013-2019 by Cisco Systems, Inc.
     All rights reserved.";

  revision 2019-07-19 {
    description
      "Additional items added to operational model.";
    semver:module-version "2.0.0";
  }
  revision 2019-04-05 {
    description
      "Establish semantic version baseline.";
    semver:module-version "1.0.0";
  }
  revision 2017-09-07 {
    description
      "Fixed type translation error.";
  }
  revision 2015-11-09 {
    description
      "IOS XR 6.0 revision.";
  }

  typedef ncs_template_Sid-type-enum {
    type string;
    description
      "Sid type enum";
  }

  typedef ncs_rpc_notif_Sid-type-enum {
    type enumeration {
      enum "absolute" {
        value 1;
        description
          "Absolute SID";
      }
      enum "index" {
        value 2;
        description
          "Index SID";
      }
    }
    description
      "Sid type enum";
  }

  typedef live_ncs_Sid-type-enum {
    type enumeration {
      enum "absolute" {
        value 1;
        description
          "Absolute SID";
      }
      enum "index" {
        value 2;
        description
          "Index SID";
      }
    }
    description
      "Sid type enum";
  }

  typedef Sid-type-enum {
    type enumeration {
      enum "absolute" {
        value 1;
        description
          "Absolute SID";
      }
      enum "index" {
        value 2;
        description
          "Index SID";
      }
    }
    description
      "Sid type enum";
  }

  grouping ncs_template_MAPPING-MI {
    description
      "Common node of mapping-ipv4, mapping-ipv6";
    list mapping-mi {
      // NCS patched for predictable order
      ordered-by user;
      description
        "IP prefix to SID mapping item. It's not possible
         to list all of the IP prefix to SID mappings, as
         the set of valid prefixes could be very large.
         Instead, SID map information must be retrieved
         individually for each prefix of interest.";
      leaf ip {
        type xr:ncs_template_Cisco-ios-xr-string;
        description
          "IP";
      }
      leaf prefixlen {
        type string;
        description
          "Prefixlen";
      }
      uses ncs_template_SRMS-MI-T-B;
    }
  }

  grouping ncs_template_SID-RECORD-TABLE {
    description
      "Common node of l2-adjacency, ipv4, ipv6, all-afi";
    container sid-records {
      description
        "SID directory";
      list sid-record {
        // NCS patched for predictable order
        ordered-by user;
        description
          "SID record";
        leaf sid-type {
          type ncs_template_Sid-type-enum;
          description
            "SID type";
        }
        leaf sid-value {
          type string;
          description
            "SID value";
        }
        uses ncs_template_SRMS-L2-ADJ-T-B;
      }
    }
  }

  grouping ncs_template_POLICY-MI {
    description
      "Common node of policy-ipv4-active,
       policy-ipv4-backup, policy-ipv6-active,
       policy-ipv6-backup";
    list policy-mi {
      // NCS patched for predictable order
      ordered-by user;
      key "mi-id";
      description
        "Mapping Item";
      leaf mi-id {
        type xr:ncs_template_Cisco-ios-xr-string;
        description
          "Mapping Item ID (0, 1, 2, ...)";
      }
      uses ncs_template_SRMS-MI-T-B;
    }
  }

  grouping ncs_template_POLICY {
    description
      "Common node of srms, standby-srms";
    container policy {
      description
        "Policy operational data";
      container policy-ipv4 {
        description
          "IPv4 policy operational data";
        container policy-ipv4-backup {
          description
            "IPv4 backup policy operational data";
          uses ncs_template_POLICY-MI;
        }
        container policy-ipv4-active {
          description
            "IPv4 active policy operational data";
          uses ncs_template_POLICY-MI;
        }
      }
      container policy-ipv6 {
        description
          "IPv6 policy operational data";
        container policy-ipv6-backup {
          description
            "IPv6 backup policy operational data";
          uses ncs_template_POLICY-MI;
        }
        container policy-ipv6-active {
          description
            "IPv6 active policy operational data";
          uses ncs_template_POLICY-MI;
        }
      }
    }
  }

  grouping ncs_template_MAPPING {
    description
      "Common node of srms, standby-srms";
    container mapping {
      description
        "IP prefix to SID mappings";
      container mapping-ipv4 {
        description
          "IPv4 prefix to SID mappings";
        uses ncs_template_MAPPING-MI;
      }
      container mapping-ipv6 {
        description
          "IPv6 prefix to SID mappings";
        uses ncs_template_MAPPING-MI;
      }
    }
  }

  grouping ncs_rpc_notif_MAPPING-MI {
    description
      "Common node of mapping-ipv4, mapping-ipv6";
    list mapping-mi {
      description
        "IP prefix to SID mapping item. It's not possible
         to list all of the IP prefix to SID mappings, as
         the set of valid prefixes could be very large.
         Instead, SID map information must be retrieved
         individually for each prefix of interest.";
      leaf ip {
        type xr:ncs_rpc_notif_Cisco-ios-xr-string;
        description
          "IP";
      }
      leaf prefixlen {
        type uint32 {
          range "1..128";
        }
        description
          "Prefixlen";
      }
      uses ncs_rpc_notif_SRMS-MI-T-B;
    }
  }

  grouping ncs_rpc_notif_SID-RECORD-TABLE {
    description
      "Common node of l2-adjacency, ipv4, ipv6, all-afi";
    container sid-records {
      description
        "SID directory";
      list sid-record {
        description
          "SID record";
        leaf sid-type {
          type ncs_rpc_notif_Sid-type-enum;
          description
            "SID type";
        }
        leaf sid-value {
          type uint32 {
            range "0..1048575";
          }
          description
            "SID value";
        }
        uses ncs_rpc_notif_SRMS-L2-ADJ-T-B;
      }
    }
  }

  grouping ncs_rpc_notif_POLICY-MI {
    description
      "Common node of policy-ipv4-active,
       policy-ipv4-backup, policy-ipv6-active,
       policy-ipv6-backup";
    list policy-mi {
      key "mi-id";
      description
        "Mapping Item";
      leaf mi-id {
        type xr:ncs_rpc_notif_Cisco-ios-xr-string;
        description
          "Mapping Item ID (0, 1, 2, ...)";
      }
      uses ncs_rpc_notif_SRMS-MI-T-B;
    }
  }

  grouping ncs_rpc_notif_POLICY {
    description
      "Common node of srms, standby-srms";
    container policy {
      description
        "Policy operational data";
      container policy-ipv4 {
        description
          "IPv4 policy operational data";
        container policy-ipv4-backup {
          description
            "IPv4 backup policy operational data";
          uses ncs_rpc_notif_POLICY-MI;
        }
        container policy-ipv4-active {
          description
            "IPv4 active policy operational data";
          uses ncs_rpc_notif_POLICY-MI;
        }
      }
      container policy-ipv6 {
        description
          "IPv6 policy operational data";
        container policy-ipv6-backup {
          description
            "IPv6 backup policy operational data";
          uses ncs_rpc_notif_POLICY-MI;
        }
        container policy-ipv6-active {
          description
            "IPv6 active policy operational data";
          uses ncs_rpc_notif_POLICY-MI;
        }
      }
    }
  }

  grouping ncs_rpc_notif_MAPPING {
    description
      "Common node of srms, standby-srms";
    container mapping {
      description
        "IP prefix to SID mappings";
      container mapping-ipv4 {
        description
          "IPv4 prefix to SID mappings";
        uses ncs_rpc_notif_MAPPING-MI;
      }
      container mapping-ipv6 {
        description
          "IPv6 prefix to SID mappings";
        uses ncs_rpc_notif_MAPPING-MI;
      }
    }
  }

  grouping live_ncs_MAPPING-MI {
    description
      "Common node of mapping-ipv4, mapping-ipv6";
    list mapping-mi {
      description
        "IP prefix to SID mapping item. It's not possible
         to list all of the IP prefix to SID mappings, as
         the set of valid prefixes could be very large.
         Instead, SID map information must be retrieved
         individually for each prefix of interest.";
      leaf ip {
        type xr:live_ncs_Cisco-ios-xr-string;
        description
          "IP";
      }
      leaf prefixlen {
        type uint32 {
          range "1..128";
        }
        description
          "Prefixlen";
      }
      uses live_ncs_SRMS-MI-T-B;
    }
  }

  grouping live_ncs_SID-RECORD-TABLE {
    description
      "Common node of l2-adjacency, ipv4, ipv6, all-afi";
    container sid-records {
      description
        "SID directory";
      list sid-record {
        description
          "SID record";
        leaf sid-type {
          type live_ncs_Sid-type-enum;
          description
            "SID type";
        }
        leaf sid-value {
          type uint32 {
            range "0..1048575";
          }
          description
            "SID value";
        }
        uses live_ncs_SRMS-L2-ADJ-T-B;
      }
    }
  }

  grouping live_ncs_POLICY-MI {
    description
      "Common node of policy-ipv4-active,
       policy-ipv4-backup, policy-ipv6-active,
       policy-ipv6-backup";
    list policy-mi {
      key "mi-id";
      description
        "Mapping Item";
      leaf mi-id {
        type xr:live_ncs_Cisco-ios-xr-string;
        description
          "Mapping Item ID (0, 1, 2, ...)";
      }
      uses live_ncs_SRMS-MI-T-B;
    }
  }

  grouping live_ncs_POLICY {
    description
      "Common node of srms, standby-srms";
    container policy {
      description
        "Policy operational data";
      container policy-ipv4 {
        description
          "IPv4 policy operational data";
        container policy-ipv4-backup {
          description
            "IPv4 backup policy operational data";
          uses live_ncs_POLICY-MI;
        }
        container policy-ipv4-active {
          description
            "IPv4 active policy operational data";
          uses live_ncs_POLICY-MI;
        }
      }
      container policy-ipv6 {
        description
          "IPv6 policy operational data";
        container policy-ipv6-backup {
          description
            "IPv6 backup policy operational data";
          uses live_ncs_POLICY-MI;
        }
        container policy-ipv6-active {
          description
            "IPv6 active policy operational data";
          uses live_ncs_POLICY-MI;
        }
      }
    }
  }

  grouping live_ncs_MAPPING {
    description
      "Common node of srms, standby-srms";
    container mapping {
      description
        "IP prefix to SID mappings";
      container mapping-ipv4 {
        description
          "IPv4 prefix to SID mappings";
        uses live_ncs_MAPPING-MI;
      }
      container mapping-ipv6 {
        description
          "IPv6 prefix to SID mappings";
        uses live_ncs_MAPPING-MI;
      }
    }
  }

  grouping MAPPING-MI {
    description
      "Common node of mapping-ipv4, mapping-ipv6";
    list mapping-mi {
      description
        "IP prefix to SID mapping item. It's not possible
         to list all of the IP prefix to SID mappings, as
         the set of valid prefixes could be very large.
         Instead, SID map information must be retrieved
         individually for each prefix of interest.";
      leaf ip {
        type xr:Cisco-ios-xr-string;
        description
          "IP";
      }
      leaf prefixlen {
        type uint32 {
          range "1..128";
        }
        description
          "Prefixlen";
      }
      uses SRMS-MI-T-B;
    }
  }

  grouping SID-RECORD-TABLE {
    description
      "Common node of l2-adjacency, ipv4, ipv6, all-afi";
    container sid-records {
      description
        "SID directory";
      list sid-record {
        description
          "SID record";
        leaf sid-type {
          type Sid-type-enum;
          description
            "SID type";
        }
        leaf sid-value {
          type uint32 {
            range "0..1048575";
          }
          description
            "SID value";
        }
        uses SRMS-L2-ADJ-T-B;
      }
    }
  }

  grouping POLICY-MI {
    description
      "Common node of policy-ipv4-active,
       policy-ipv4-backup, policy-ipv6-active,
       policy-ipv6-backup";
    list policy-mi {
      key "mi-id";
      description
        "Mapping Item";
      leaf mi-id {
        type xr:Cisco-ios-xr-string;
        description
          "Mapping Item ID (0, 1, 2, ...)";
      }
      uses SRMS-MI-T-B;
    }
  }

  grouping POLICY {
    description
      "Common node of srms, standby-srms";
    container policy {
      description
        "Policy operational data";
      container policy-ipv4 {
        description
          "IPv4 policy operational data";
        container policy-ipv4-backup {
          description
            "IPv4 backup policy operational data";
          uses POLICY-MI;
        }
        container policy-ipv4-active {
          description
            "IPv4 active policy operational data";
          uses POLICY-MI;
        }
      }
      container policy-ipv6 {
        description
          "IPv6 policy operational data";
        container policy-ipv6-backup {
          description
            "IPv6 backup policy operational data";
          uses POLICY-MI;
        }
        container policy-ipv6-active {
          description
            "IPv6 active policy operational data";
          uses POLICY-MI;
        }
      }
    }
  }

  grouping MAPPING {
    description
      "Common node of srms, standby-srms";
    container mapping {
      description
        "IP prefix to SID mappings";
      container mapping-ipv4 {
        description
          "IPv4 prefix to SID mappings";
        uses MAPPING-MI;
      }
      container mapping-ipv6 {
        description
          "IPv6 prefix to SID mappings";
        uses MAPPING-MI;
      }
    }
  }

  augment "/ncs:devices/ncs:device/ncs:config" {
    // NCS drop config false container 'standby-srms'
    // NCS drop config false container srms
    // NCS drop config false container srlb
  }
  augment "/ncs:devices/ncs:device/ncs:live-status" {
    container standby-srms {
      tailf:ncs-device-type "netconf";
      tailf:display-when "not(../../ncs:module) or ../../ncs:module[ncs:name='Cisco-IOS-XR-segment-routing-ms-oper'] or (../../ncs:live-status-protocol[not(ncs:capability)]) or (../../ncs:live-status-protocol/ncs:capability/ncs:module[.='Cisco-IOS-XR-segment-routing-ms-oper'])";
      description
        "Standby Segment Routing Mapping Server
         operational data";
      uses live_ncs_MAPPING;
      uses live_ncs_POLICY;
    }
    container srms {
      tailf:ncs-device-type "netconf";
      tailf:display-when "not(../../ncs:module) or ../../ncs:module[ncs:name='Cisco-IOS-XR-segment-routing-ms-oper'] or (../../ncs:live-status-protocol[not(ncs:capability)]) or (../../ncs:live-status-protocol/ncs:capability/ncs:module[.='Cisco-IOS-XR-segment-routing-ms-oper'])";
      description
        "Active Segment Routing Mapping Server operational
         data";
      container adjacency-sid {
        description
          "Adjacency SID";
        container l2-adjacency {
          description
            "L2 Adjacency Option";
          container interfaces {
            description
              "Interface directory";
            list interface {
              key "interface-name";
              description
                "Segment Routing Adjacency SID Interface";
              container address-family {
                description
                  "address family container";
                container all-afi {
                  description
                    "both IPv4 and IPv6";
                  uses live_ncs_SID-RECORD-TABLE;
                }
                container ipv4 {
                  description
                    "IP version 4";
                  uses live_ncs_SID-RECORD-TABLE;
                }
                container ipv6 {
                  description
                    "IP version 6";
                  uses live_ncs_SID-RECORD-TABLE;
                }
              }
              leaf interface-name {
                type xr:live_ncs_Interface-name;
                description
                  "Interface name";
              }
            }
          }
          uses live_ncs_SID-RECORD-TABLE;
        }
      }
      uses live_ncs_MAPPING;
      uses live_ncs_POLICY;
    }
    container srlb {
      tailf:ncs-device-type "netconf";
      tailf:display-when "not(../../ncs:module) or ../../ncs:module[ncs:name='Cisco-IOS-XR-segment-routing-ms-oper'] or (../../ncs:live-status-protocol[not(ncs:capability)]) or (../../ncs:live-status-protocol/ncs:capability/ncs:module[.='Cisco-IOS-XR-segment-routing-ms-oper'])";
      description
        "Segment Routing Local Block operational data";
      container srlb-inconsistency {
        description
          "SRLB Inconsistencies";
        uses live_ncs_MPLS-LSD-SRLB-INCONSISTENCY;
      }
    }
  }
  augment "/ncs:devices/ncs:template/ncs:ned-id/ncs:config" {
    // NCS drop config false container 'standby-srms'
    // NCS drop config false container srms
    // NCS drop config false container srlb
  }
}

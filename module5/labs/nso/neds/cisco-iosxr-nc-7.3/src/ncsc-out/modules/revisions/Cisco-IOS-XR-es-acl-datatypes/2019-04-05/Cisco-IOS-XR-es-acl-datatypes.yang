module Cisco-IOS-XR-es-acl-datatypes {
  // Generated by yanger -t ncs
  tailf:mount-id "cisco-iosxr-nc-7.3:cisco-iosxr-nc-7.3";
  tailf:ncs-device-type "netconf";

  namespace "http://cisco.com/ns/yang/Cisco-IOS-XR-es-acl-datatypes";
  prefix es-acl-datatypes;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2019 by Cisco Systems, Inc.
     All rights reserved.";

  revision 2019-04-05 {
    description
      "Establish semantic version baseline.";
    semver:module-version "1.0.0";
  }
  revision 2017-05-01 {
    description
      "Fixing backward compatibility error in module.";
  }
  revision 2015-11-09 {
    description
      "IOS XR 6.0 revision.";
  }

  typedef ncs_template_Es-acl-dei-range {
    type string;
    description
      "Es acl dei range";
  }

  typedef ncs_template_Es-acl-name {
    type xr:ncs_template_Cisco-ios-xr-string;
    description
      "Es acl name";
  }

  typedef ncs_template_Es-acl-vlan-range {
    type string;
    description
      "Es acl vlan range";
  }

  typedef ncs_template_Acl-usage-app-id-enum {
    type string;
    description
      "Acl usage app id enum";
  }

  typedef ncs_template_Es-acl-cos-range {
    type string;
    description
      "Es acl cos range";
  }

  typedef ncs_template_Acl-sequence-number-range {
    type string;
    description
      "Acl sequence number range";
  }

  typedef ncs_template_Es-acl-log-range {
    type string;
    description
      "Es acl log range";
  }

  typedef ncs_rpc_notif_Es-acl-dei-range {
    type uint32 {
      range "0..1";
    }
    description
      "Es acl dei range";
  }

  typedef ncs_rpc_notif_Es-acl-name {
    type xr:ncs_rpc_notif_Cisco-ios-xr-string;
    description
      "Es acl name";
  }

  typedef ncs_rpc_notif_Es-acl-vlan-range {
    type uint32 {
      range "0..4095";
    }
    description
      "Es acl vlan range";
  }

  typedef ncs_rpc_notif_Acl-usage-app-id-enum {
    type enumeration {
      enum "pfilter" {
        value 1;
        description
          "General Usage Statistics";
      }
      enum "bgp" {
        value 2;
        description
          "Usage staistics related to BGP Traffic";
      }
      enum "ospf" {
        value 3;
        description
          "Usage staistics related to OSPF Traffic";
      }
    }
    description
      "Acl usage app id enum";
  }

  typedef ncs_rpc_notif_Es-acl-cos-range {
    type uint32 {
      range "0..7";
    }
    description
      "Es acl cos range";
  }

  typedef ncs_rpc_notif_Acl-sequence-number-range {
    type uint32 {
      range "1..2147483646";
    }
    description
      "Acl sequence number range";
  }

  typedef ncs_rpc_notif_Es-acl-log-range {
    type uint32 {
      range "0..1";
    }
    description
      "Es acl log range";
  }

  typedef live_ncs_Es-acl-dei-range {
    type uint32 {
      range "0..1";
    }
    description
      "Es acl dei range";
  }

  typedef live_ncs_Es-acl-name {
    type xr:live_ncs_Cisco-ios-xr-string;
    description
      "Es acl name";
  }

  typedef live_ncs_Es-acl-vlan-range {
    type uint32 {
      range "0..4095";
    }
    description
      "Es acl vlan range";
  }

  typedef live_ncs_Acl-usage-app-id-enum {
    type enumeration {
      enum "pfilter" {
        value 1;
        description
          "General Usage Statistics";
      }
      enum "bgp" {
        value 2;
        description
          "Usage staistics related to BGP Traffic";
      }
      enum "ospf" {
        value 3;
        description
          "Usage staistics related to OSPF Traffic";
      }
    }
    description
      "Acl usage app id enum";
  }

  typedef live_ncs_Es-acl-cos-range {
    type uint32 {
      range "0..7";
    }
    description
      "Es acl cos range";
  }

  typedef live_ncs_Acl-sequence-number-range {
    type uint32 {
      range "1..2147483646";
    }
    description
      "Acl sequence number range";
  }

  typedef live_ncs_Es-acl-log-range {
    type uint32 {
      range "0..1";
    }
    description
      "Es acl log range";
  }

  typedef Es-acl-dei-range {
    type uint32 {
      range "0..1";
    }
    description
      "Es acl dei range";
  }

  typedef Es-acl-name {
    type xr:Cisco-ios-xr-string {
      length "1..64";
    }
    description
      "Es acl name";
  }

  typedef Es-acl-vlan-range {
    type uint32 {
      range "0..4095";
    }
    description
      "Es acl vlan range";
  }

  typedef Acl-usage-app-id-enum {
    type enumeration {
      enum "pfilter" {
        value 1;
        description
          "General Usage Statistics";
      }
      enum "bgp" {
        value 2;
        description
          "Usage staistics related to BGP Traffic";
      }
      enum "ospf" {
        value 3;
        description
          "Usage staistics related to OSPF Traffic";
      }
    }
    description
      "Acl usage app id enum";
  }

  typedef Es-acl-cos-range {
    type uint32 {
      range "0..7";
    }
    description
      "Es acl cos range";
  }

  typedef Acl-sequence-number-range {
    type uint32 {
      range "1..2147483646";
    }
    description
      "Acl sequence number range";
  }

  typedef Es-acl-log-range {
    type uint32 {
      range "0..1";
    }
    description
      "Es acl log range";
  }
}

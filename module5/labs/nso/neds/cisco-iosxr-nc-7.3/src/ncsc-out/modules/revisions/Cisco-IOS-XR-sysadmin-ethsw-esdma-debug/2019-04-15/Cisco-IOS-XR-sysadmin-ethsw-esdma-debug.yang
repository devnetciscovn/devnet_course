module Cisco-IOS-XR-sysadmin-ethsw-esdma-debug {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-debug";
  prefix esdma_debug;

  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the hidden Cisco IOS-XR SysAdmin
     'show controller switch debug counters' command.

     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping ncs_template_switch-debug-data {
    container debug {
      container counters {
        list location {
          // NCS patched for predictable order
          ordered-by user;
          key "rack card switch-id";
          leaf rack {
            type esdma_types:ncs_template_esdma-rack-num-enum;
          }
          leaf card {
            type esdma_types:ncs_template_esdma-cpu;
          }
          leaf switch-id {
            type esdma_types:ncs_template_esdma-switch-type-enum;
          }
          container counters {
            leaf phy-polling-enabled {
              type string;
            }
            leaf tx-thread-wdog-cnt {
              type string;
            }
            leaf rx-thread-wdog-cnt {
              type string;
            }
            leaf task-lock-longest-wait-time {
              type string;
            }
            leaf task-lock-longest-wait-event {
              type string;
            }
            leaf task-lock-longest-held-time {
              type string;
            }
            leaf task-lock-longest-held-event {
              type string;
            }
            leaf task-unlock-longest-wait-time {
              type string;
            }
            leaf task-unlock-longest-wait-event {
              type string;
            }
            leaf dma-max-rx-dequeued-per-int {
              type string;
            }
            leaf dma-rx-packets-dequeued {
              type string;
            }
            leaf dma-rx-packet-dequeue-errors {
              type string;
            }
            leaf dma-tx-packets-queued {
              type string;
            }
            leaf dma-tx-packets-completed {
              type string;
            }
            leaf dma-tx-packet-no-msg-errors {
              type string;
            }
            leaf dma-tx-packet-msg-too-big-errors {
              type string;
            }
            leaf dma-tx-packet-no-buffer-errors {
              type string;
            }
            leaf dma-tx-packet-queue-errors {
              type string;
            }
            leaf dma-tx-packet-completion-errors {
              type string;
            }
            leaf dma-max-tx-freed-per-int {
              type string;
            }
            leaf dma-tx-buf-alloc-count {
              type string;
            }
            leaf dma-tx-buf-free-count {
              type string;
            }
            list switch-core {
              // NCS patched for predictable order
              ordered-by user;
              key "core";
              leaf core {
                type string;
              }
              leaf msi-count {
                type string;
              }
              leaf aer-count {
                type string;
              }
              leaf hp-count {
                type string;
              }
              leaf wdog-count {
                type string;
              }
              leaf core-task-lock-longest-wait-time {
                type string;
              }
              leaf core-task-lock-longest-held-time {
                type string;
              }
              leaf core-task-unlock-longest-wait-time {
                type string;
              }
            }
          }
        }
      }
    }
  }

  grouping ncs_template_switch-debug-group {
    container switch-debug-cont {
      uses ncs_template_switch-debug-data;
    }
  }

  grouping ncs_rpc_notif_switch-debug-data {
    container debug {
      container counters {
        list location {
          key "rack card switch-id";
          leaf rack {
            type esdma_types:ncs_rpc_notif_esdma-rack-num-enum;
          }
          leaf card {
            type esdma_types:ncs_rpc_notif_esdma-cpu;
          }
          leaf switch-id {
            type esdma_types:ncs_rpc_notif_esdma-switch-type-enum;
          }
          container counters {
            leaf phy-polling-enabled {
              type boolean;
            }
            leaf tx-thread-wdog-cnt {
              type uint64;
            }
            leaf rx-thread-wdog-cnt {
              type uint64;
            }
            leaf task-lock-longest-wait-time {
              type uint64;
            }
            leaf task-lock-longest-wait-event {
              type uint32;
            }
            leaf task-lock-longest-held-time {
              type uint64;
            }
            leaf task-lock-longest-held-event {
              type uint32;
            }
            leaf task-unlock-longest-wait-time {
              type uint64;
            }
            leaf task-unlock-longest-wait-event {
              type uint32;
            }
            leaf dma-max-rx-dequeued-per-int {
              type uint64;
            }
            leaf dma-rx-packets-dequeued {
              type uint64;
            }
            leaf dma-rx-packet-dequeue-errors {
              type uint64;
            }
            leaf dma-tx-packets-queued {
              type uint64;
            }
            leaf dma-tx-packets-completed {
              type uint64;
            }
            leaf dma-tx-packet-no-msg-errors {
              type uint64;
            }
            leaf dma-tx-packet-msg-too-big-errors {
              type uint64;
            }
            leaf dma-tx-packet-no-buffer-errors {
              type uint64;
            }
            leaf dma-tx-packet-queue-errors {
              type uint64;
            }
            leaf dma-tx-packet-completion-errors {
              type uint64;
            }
            leaf dma-max-tx-freed-per-int {
              type uint64;
            }
            leaf dma-tx-buf-alloc-count {
              type uint64;
            }
            leaf dma-tx-buf-free-count {
              type uint64;
            }
            list switch-core {
              key "core";
              leaf core {
                type uint8;
              }
              leaf msi-count {
                type uint64;
              }
              leaf aer-count {
                type uint64;
              }
              leaf hp-count {
                type uint64;
              }
              leaf wdog-count {
                type uint64;
              }
              leaf core-task-lock-longest-wait-time {
                type uint64;
              }
              leaf core-task-lock-longest-held-time {
                type uint64;
              }
              leaf core-task-unlock-longest-wait-time {
                type uint64;
              }
            }
          }
        }
      }
    }
  }

  grouping ncs_rpc_notif_switch-debug-group {
    container switch-debug-cont {
      uses ncs_rpc_notif_switch-debug-data;
    }
  }

  grouping live_ncs_switch-debug-data {
    container debug {
      container counters {
        list location {
          key "rack card switch-id";
          leaf rack {
            type esdma_types:live_ncs_esdma-rack-num-enum;
          }
          leaf card {
            type esdma_types:live_ncs_esdma-cpu;
          }
          leaf switch-id {
            type esdma_types:live_ncs_esdma-switch-type-enum;
          }
          container counters {
            leaf phy-polling-enabled {
              type boolean;
            }
            leaf tx-thread-wdog-cnt {
              type uint64;
            }
            leaf rx-thread-wdog-cnt {
              type uint64;
            }
            leaf task-lock-longest-wait-time {
              type uint64;
            }
            leaf task-lock-longest-wait-event {
              type uint32;
            }
            leaf task-lock-longest-held-time {
              type uint64;
            }
            leaf task-lock-longest-held-event {
              type uint32;
            }
            leaf task-unlock-longest-wait-time {
              type uint64;
            }
            leaf task-unlock-longest-wait-event {
              type uint32;
            }
            leaf dma-max-rx-dequeued-per-int {
              type uint64;
            }
            leaf dma-rx-packets-dequeued {
              type uint64;
            }
            leaf dma-rx-packet-dequeue-errors {
              type uint64;
            }
            leaf dma-tx-packets-queued {
              type uint64;
            }
            leaf dma-tx-packets-completed {
              type uint64;
            }
            leaf dma-tx-packet-no-msg-errors {
              type uint64;
            }
            leaf dma-tx-packet-msg-too-big-errors {
              type uint64;
            }
            leaf dma-tx-packet-no-buffer-errors {
              type uint64;
            }
            leaf dma-tx-packet-queue-errors {
              type uint64;
            }
            leaf dma-tx-packet-completion-errors {
              type uint64;
            }
            leaf dma-max-tx-freed-per-int {
              type uint64;
            }
            leaf dma-tx-buf-alloc-count {
              type uint64;
            }
            leaf dma-tx-buf-free-count {
              type uint64;
            }
            list switch-core {
              key "core";
              leaf core {
                type uint8;
              }
              leaf msi-count {
                type uint64;
              }
              leaf aer-count {
                type uint64;
              }
              leaf hp-count {
                type uint64;
              }
              leaf wdog-count {
                type uint64;
              }
              leaf core-task-lock-longest-wait-time {
                type uint64;
              }
              leaf core-task-lock-longest-held-time {
                type uint64;
              }
              leaf core-task-unlock-longest-wait-time {
                type uint64;
              }
            }
          }
        }
      }
    }
  }

  grouping live_ncs_switch-debug-group {
    container switch-debug-cont {
      uses live_ncs_switch-debug-data;
    }
  }

  grouping switch-debug-data {
    container debug {
      container counters {
        list location {
          key "rack card switch-id";
          leaf rack {
            type esdma_types:esdma-rack-num-enum;
          }
          leaf card {
            type esdma_types:esdma-cpu;
          }
          leaf switch-id {
            type esdma_types:esdma-switch-type-enum;
          }
          container counters {
            leaf phy-polling-enabled {
              type boolean;
            }
            leaf tx-thread-wdog-cnt {
              type uint64;
            }
            leaf rx-thread-wdog-cnt {
              type uint64;
            }
            leaf task-lock-longest-wait-time {
              type uint64;
            }
            leaf task-lock-longest-wait-event {
              type uint32;
            }
            leaf task-lock-longest-held-time {
              type uint64;
            }
            leaf task-lock-longest-held-event {
              type uint32;
            }
            leaf task-unlock-longest-wait-time {
              type uint64;
            }
            leaf task-unlock-longest-wait-event {
              type uint32;
            }
            leaf dma-max-rx-dequeued-per-int {
              type uint64;
            }
            leaf dma-rx-packets-dequeued {
              type uint64;
            }
            leaf dma-rx-packet-dequeue-errors {
              type uint64;
            }
            leaf dma-tx-packets-queued {
              type uint64;
            }
            leaf dma-tx-packets-completed {
              type uint64;
            }
            leaf dma-tx-packet-no-msg-errors {
              type uint64;
            }
            leaf dma-tx-packet-msg-too-big-errors {
              type uint64;
            }
            leaf dma-tx-packet-no-buffer-errors {
              type uint64;
            }
            leaf dma-tx-packet-queue-errors {
              type uint64;
            }
            leaf dma-tx-packet-completion-errors {
              type uint64;
            }
            leaf dma-max-tx-freed-per-int {
              type uint64;
            }
            leaf dma-tx-buf-alloc-count {
              type uint64;
            }
            leaf dma-tx-buf-free-count {
              type uint64;
            }
            list switch-core {
              key "core";
              leaf core {
                type uint8;
              }
              leaf msi-count {
                type uint64;
              }
              leaf aer-count {
                type uint64;
              }
              leaf hp-count {
                type uint64;
              }
              leaf wdog-count {
                type uint64;
              }
              leaf core-task-lock-longest-wait-time {
                type uint64;
              }
              leaf core-task-lock-longest-held-time {
                type uint64;
              }
              leaf core-task-unlock-longest-wait-time {
                type uint64;
              }
            }
          }
        }
      }
    }
  }

  grouping switch-debug-group {
    container switch-debug-cont {
      uses switch-debug-data;
    }
  }
}

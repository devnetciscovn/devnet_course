module Cisco-IOS-XR-fsdbagg-cfg {
  // Generated by yanger -t ncs
  tailf:mount-id "cisco-iosxr-nc-7.3:cisco-iosxr-nc-7.3";
  tailf:ncs-device-type "netconf";

  namespace "http://cisco.com/ns/yang/Cisco-IOS-XR-fsdbagg-cfg";
  prefix fsdbagg-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fsdbagg package configuration.

     This module contains definitions
     for the following management objects:
       fsdb-agg-config: none

     Copyright (c) 2013-2021 by Cisco Systems, Inc.
     All rights reserved.";

  revision 2021-03-22 {
    description
      "Yang Schema update to support new oversubscribedFC mode.";
    semver:module-version "1.0.0";
  }
  revision 2020-10-27 {
    description
      "Yang Schema update to support new 5fc config.";
    semver:module-version "1.0.0";
  }
  revision 2020-06-26 {
    description
      "Yang Schema added with 5fc config support and task-name.";
  }
  revision 2019-04-05 {
    description
      "Establish semantic version baseline.";
  }
  revision 2015-11-09 {
    description
      "IOS XR 6.0 revision.";
  }

  augment "/ncs:devices/ncs:device/ncs:config" {
    container fsdb-agg-config {
      tailf:ncs-device-type "netconf";
      tailf:display-when "not(../../ncs:module) or ../../ncs:module[ncs:name='Cisco-IOS-XR-fsdbagg-cfg']";
      description
        "none";
      container fabric-mode {
        description
          "Configure Fabric Mode as either 8FC or 5FC";
        leaf five-fc {
          type uint32;
          description
            "enable 5FC(slot:1-2-3-4-5)=1; enable 5FC(slot
             :0-2-4-5-6)=2";
        }
      }
      container planes {
        description
          "Configure fabric.";
        list plane {
          key "plane";
          description
            "Configure fabric planes";
          leaf plane-shutdown {
            type uint32;
            description
              "Shutdown fabric planes";
          }
          leaf plane {
            type uint32;
            description
              "Plane";
          }
        }
      }
    }
  }
  augment "/ncs:devices/ncs:device/ncs:live-status" {
    container fsdb-agg-config {
      tailf:ncs-device-type "netconf";
      tailf:display-when "not(../../ncs:module) or ../../ncs:module[ncs:name='Cisco-IOS-XR-fsdbagg-cfg'] or (../../ncs:live-status-protocol[not(ncs:capability)]) or (../../ncs:live-status-protocol/ncs:capability/ncs:module[.='Cisco-IOS-XR-fsdbagg-cfg'])";
      description
        "none";
      container fabric-mode {
        description
          "Configure Fabric Mode as either 8FC or 5FC";
        leaf five-fc {
          type uint32;
          description
            "enable 5FC(slot:1-2-3-4-5)=1; enable 5FC(slot
             :0-2-4-5-6)=2";
        }
      }
      container planes {
        description
          "Configure fabric.";
        list plane {
          key "plane";
          description
            "Configure fabric planes";
          leaf plane-shutdown {
            type uint32;
            description
              "Shutdown fabric planes";
          }
          leaf plane {
            type uint32;
            description
              "Plane";
          }
        }
      }
    }
  }
  augment "/ncs:devices/ncs:template/ncs:ned-id/ncs:config" {
    container fsdb-agg-config {
      description
        "none";
      container fabric-mode {
        description
          "Configure Fabric Mode as either 8FC or 5FC";
        leaf five-fc {
          type string;
          description
            "enable 5FC(slot:1-2-3-4-5)=1; enable 5FC(slot
             :0-2-4-5-6)=2";
        }
      }
      container planes {
        description
          "Configure fabric.";
        list plane {
          // NCS patched for predictable order
          ordered-by user;
          key "plane";
          description
            "Configure fabric planes";
          leaf plane-shutdown {
            type string;
            description
              "Shutdown fabric planes";
          }
          leaf plane {
            type string;
            description
              "Plane";
          }
        }
      }
    }
  }
}

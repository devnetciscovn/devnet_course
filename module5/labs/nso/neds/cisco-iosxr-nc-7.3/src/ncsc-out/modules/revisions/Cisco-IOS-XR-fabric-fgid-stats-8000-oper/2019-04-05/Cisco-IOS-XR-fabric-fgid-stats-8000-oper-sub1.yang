submodule Cisco-IOS-XR-fabric-fgid-stats-8000-oper-sub1 {
  // Generated by yanger -t ncs
  tailf:mount-id "cisco-iosxr-nc-7.3:cisco-iosxr-nc-7.3";

  belongs-to Cisco-IOS-XR-fabric-fgid-stats-8000-oper {
    prefix Cisco-IOS-XR-fabric-fgid-stats-8000-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR fabric-fgid-stats-8000 package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_FE-HW-FGID-BITMAP {
    description
      "Fgid bitmap on FE Asic HW";
    leaf asic-name {
      type string;
      description
        "FE Asic";
    }
    leaf asic-type {
      type string;
      description
        "FE Asic type";
    }
    leaf status {
      type string;
      description
        "SW/HW fgid bitmap match";
    }
    list bitmap {
      // NCS patched for predictable order
      ordered-by user;
      // NCS drop max-elements statement
      description
        "FGID Bitmap";
      leaf entry {
        type string;
        description
          "FGID Bitmap";
      }
    }
  }

  grouping ncs_template_FGID-DIAG-INFO {
    description
      "Fgid bitmap on rack FE asics";
    leaf rack-num {
      type string;
      description
        "Rack num";
    }
    list fe-asic {
      // NCS patched for predictable order
      ordered-by user;
      description
        "FGID bitmaps info on FE HW";
      uses ncs_template_FE-HW-FGID-BITMAP;
    }
  }

  grouping ncs_template_RACK-FGID-BITMAP {
    description
      "Rack Fgid Bitmaps";
    leaf rack {
      type string;
      description
        "Rack";
    }
    list bitmap {
      // NCS patched for predictable order
      ordered-by user;
      // NCS drop max-elements statement
      description
        "Fgid bitmap";
      leaf entry {
        type string;
        description
          "Fgid bitmap";
      }
    }
  }

  grouping ncs_template_FAPID-INFO {
    description
      "Fabid information";
    leaf fapid {
      type string;
      description
        "Fapid";
    }
    leaf rack {
      type string;
      description
        "Rack";
    }
    leaf slot {
      type string;
      description
        "Slot";
    }
    leaf asic {
      type string;
      description
        "Asic";
    }
  }

  grouping ncs_template_FGID-INFO {
    description
      "Per FGID ID information";
    leaf fgid-id-xr {
      type string;
      description
        "FGID ID";
    }
    leaf num-fapids {
      type string;
      description
        "Number of assoicated fapids";
    }
    leaf client-id {
      type string;
      description
        "Client ID";
    }
    leaf client-name {
      type string;
      description
        "Client name";
    }
    leaf sdr-name {
      type string;
      description
        "SDR Name";
    }
    leaf num-up-racks {
      type string;
      description
        "Number of UP Racks";
    }
    leaf max-lcc-racks {
      type string;
      description
        "Maximum LCC Racks";
    }
    list fapid {
      // NCS patched for predictable order
      ordered-by user;
      description
        "Associated fapids";
      uses ncs_template_FAPID-INFO;
    }
    list fgid-bitmap {
      // NCS patched for predictable order
      ordered-by user;
      description
        "Racks FGID Bitmaps";
      uses ncs_template_RACK-FGID-BITMAP;
    }
    list rack-fgid-diag-info {
      // NCS patched for predictable order
      ordered-by user;
      description
        "FGID Diag per rack";
      uses ncs_template_FGID-DIAG-INFO;
    }
  }

  grouping ncs_template_FGID-APPL-STATS-INFO {
    description
      "Per application basis fabric multicast resource
       statistics information - no LR info";
    leaf appl-name {
      type string;
      description
        "multicast resource application name";
    }
    leaf inuse-fgids {
      type string;
      description
        "the number of inuse FGIDs by the appl";
    }
    leaf hwm-inuse-fgids {
      type string;
      description
        "the high water mark of inused FGIDs";
    }
    leaf inuse-fgids-act {
      type string;
      description
        "inuse FGIDs by the appl at appl registration
         time";
    }
    leaf alloc-fgids-act {
      type string;
      description
        "number allocated FGIDs by the appl after appl
         registration";
    }
    leaf free-fgids-act {
      type string;
      description
        "number free FGIDs by the appl after appl
         registration";
    }
  }

  grouping ncs_template_FGID-SYS-STATS-INFO {
    description
      "Per HFR basis fabric multicast resource
       statistics information";
    leaf total-fgids {
      type string;
      description
        "the total number of FGIDs";
    }
    leaf inuse-fgids {
      type string;
      description
        "the number of inuse FGIDs";
    }
    leaf hwm-inuse-fgids {
      type string;
      description
        "the high water mark of inuse FGIDs";
    }
  }

  grouping ncs_template_FGID-ALL-STATS-INFO {
    description
      "Fgid statistics information";
    container sys-stats {
      description
        "FGID system statistics";
      uses ncs_template_FGID-SYS-STATS-INFO;
    }
    list appl-stat {
      // NCS patched for predictable order
      ordered-by user;
      description
        "Application statistics";
      uses ncs_template_FGID-APPL-STATS-INFO;
    }
  }

  grouping ncs_rpc_notif_FE-HW-FGID-BITMAP {
    description
      "Fgid bitmap on FE Asic HW";
    leaf asic-name {
      type string {
        length "0..16";
      }
      description
        "FE Asic";
    }
    leaf asic-type {
      type string {
        length "0..8";
      }
      description
        "FE Asic type";
    }
    leaf status {
      type string {
        length "0..4";
      }
      description
        "SW/HW fgid bitmap match";
    }
    list bitmap {
      max-elements 2;
      description
        "FGID Bitmap";
      leaf entry {
        type uint64;
        description
          "FGID Bitmap";
      }
    }
  }

  grouping ncs_rpc_notif_FGID-DIAG-INFO {
    description
      "Fgid bitmap on rack FE asics";
    leaf rack-num {
      type uint32;
      description
        "Rack num";
    }
    list fe-asic {
      description
        "FGID bitmaps info on FE HW";
      uses ncs_rpc_notif_FE-HW-FGID-BITMAP;
    }
  }

  grouping ncs_rpc_notif_RACK-FGID-BITMAP {
    description
      "Rack Fgid Bitmaps";
    leaf rack {
      type uint32;
      description
        "Rack";
    }
    list bitmap {
      max-elements 2;
      description
        "Fgid bitmap";
      leaf entry {
        type uint64;
        description
          "Fgid bitmap";
      }
    }
  }

  grouping ncs_rpc_notif_FAPID-INFO {
    description
      "Fabid information";
    leaf fapid {
      type uint32;
      description
        "Fapid";
    }
    leaf rack {
      type uint32;
      description
        "Rack";
    }
    leaf slot {
      type uint32;
      description
        "Slot";
    }
    leaf asic {
      type uint32;
      description
        "Asic";
    }
  }

  grouping ncs_rpc_notif_FGID-INFO {
    description
      "Per FGID ID information";
    leaf fgid-id-xr {
      type uint32;
      description
        "FGID ID";
    }
    leaf num-fapids {
      type uint32;
      description
        "Number of assoicated fapids";
    }
    leaf client-id {
      type uint32;
      description
        "Client ID";
    }
    leaf client-name {
      type string;
      description
        "Client name";
    }
    leaf sdr-name {
      type string;
      description
        "SDR Name";
    }
    leaf num-up-racks {
      type uint32;
      description
        "Number of UP Racks";
    }
    leaf max-lcc-racks {
      type uint32;
      description
        "Maximum LCC Racks";
    }
    list fapid {
      description
        "Associated fapids";
      uses ncs_rpc_notif_FAPID-INFO;
    }
    list fgid-bitmap {
      description
        "Racks FGID Bitmaps";
      uses ncs_rpc_notif_RACK-FGID-BITMAP;
    }
    list rack-fgid-diag-info {
      description
        "FGID Diag per rack";
      uses ncs_rpc_notif_FGID-DIAG-INFO;
    }
  }

  grouping ncs_rpc_notif_FGID-APPL-STATS-INFO {
    description
      "Per application basis fabric multicast resource
       statistics information - no LR info";
    leaf appl-name {
      type string;
      description
        "multicast resource application name";
    }
    leaf inuse-fgids {
      type uint32;
      description
        "the number of inuse FGIDs by the appl";
    }
    leaf hwm-inuse-fgids {
      type uint32;
      description
        "the high water mark of inused FGIDs";
    }
    leaf inuse-fgids-act {
      type uint32;
      description
        "inuse FGIDs by the appl at appl registration
         time";
    }
    leaf alloc-fgids-act {
      type uint32;
      description
        "number allocated FGIDs by the appl after appl
         registration";
    }
    leaf free-fgids-act {
      type uint32;
      description
        "number free FGIDs by the appl after appl
         registration";
    }
  }

  grouping ncs_rpc_notif_FGID-SYS-STATS-INFO {
    description
      "Per HFR basis fabric multicast resource
       statistics information";
    leaf total-fgids {
      type uint32;
      description
        "the total number of FGIDs";
    }
    leaf inuse-fgids {
      type uint32;
      description
        "the number of inuse FGIDs";
    }
    leaf hwm-inuse-fgids {
      type uint32;
      description
        "the high water mark of inuse FGIDs";
    }
  }

  grouping ncs_rpc_notif_FGID-ALL-STATS-INFO {
    description
      "Fgid statistics information";
    container sys-stats {
      description
        "FGID system statistics";
      uses ncs_rpc_notif_FGID-SYS-STATS-INFO;
    }
    list appl-stat {
      description
        "Application statistics";
      uses ncs_rpc_notif_FGID-APPL-STATS-INFO;
    }
  }

  grouping live_ncs_FE-HW-FGID-BITMAP {
    description
      "Fgid bitmap on FE Asic HW";
    leaf asic-name {
      type string {
        length "0..16";
      }
      description
        "FE Asic";
    }
    leaf asic-type {
      type string {
        length "0..8";
      }
      description
        "FE Asic type";
    }
    leaf status {
      type string {
        length "0..4";
      }
      description
        "SW/HW fgid bitmap match";
    }
    list bitmap {
      // NCS drop max-elements statement
      description
        "FGID Bitmap";
      leaf entry {
        type uint64;
        description
          "FGID Bitmap";
      }
    }
  }

  grouping live_ncs_FGID-DIAG-INFO {
    description
      "Fgid bitmap on rack FE asics";
    leaf rack-num {
      type uint32;
      description
        "Rack num";
    }
    list fe-asic {
      description
        "FGID bitmaps info on FE HW";
      uses live_ncs_FE-HW-FGID-BITMAP;
    }
  }

  grouping live_ncs_RACK-FGID-BITMAP {
    description
      "Rack Fgid Bitmaps";
    leaf rack {
      type uint32;
      description
        "Rack";
    }
    list bitmap {
      // NCS drop max-elements statement
      description
        "Fgid bitmap";
      leaf entry {
        type uint64;
        description
          "Fgid bitmap";
      }
    }
  }

  grouping live_ncs_FAPID-INFO {
    description
      "Fabid information";
    leaf fapid {
      type uint32;
      description
        "Fapid";
    }
    leaf rack {
      type uint32;
      description
        "Rack";
    }
    leaf slot {
      type uint32;
      description
        "Slot";
    }
    leaf asic {
      type uint32;
      description
        "Asic";
    }
  }

  grouping live_ncs_FGID-INFO {
    description
      "Per FGID ID information";
    leaf fgid-id-xr {
      type uint32;
      description
        "FGID ID";
    }
    leaf num-fapids {
      type uint32;
      description
        "Number of assoicated fapids";
    }
    leaf client-id {
      type uint32;
      description
        "Client ID";
    }
    leaf client-name {
      type string;
      description
        "Client name";
    }
    leaf sdr-name {
      type string;
      description
        "SDR Name";
    }
    leaf num-up-racks {
      type uint32;
      description
        "Number of UP Racks";
    }
    leaf max-lcc-racks {
      type uint32;
      description
        "Maximum LCC Racks";
    }
    list fapid {
      description
        "Associated fapids";
      uses live_ncs_FAPID-INFO;
    }
    list fgid-bitmap {
      description
        "Racks FGID Bitmaps";
      uses live_ncs_RACK-FGID-BITMAP;
    }
    list rack-fgid-diag-info {
      description
        "FGID Diag per rack";
      uses live_ncs_FGID-DIAG-INFO;
    }
  }

  grouping live_ncs_FGID-APPL-STATS-INFO {
    description
      "Per application basis fabric multicast resource
       statistics information - no LR info";
    leaf appl-name {
      type string;
      description
        "multicast resource application name";
    }
    leaf inuse-fgids {
      type uint32;
      description
        "the number of inuse FGIDs by the appl";
    }
    leaf hwm-inuse-fgids {
      type uint32;
      description
        "the high water mark of inused FGIDs";
    }
    leaf inuse-fgids-act {
      type uint32;
      description
        "inuse FGIDs by the appl at appl registration
         time";
    }
    leaf alloc-fgids-act {
      type uint32;
      description
        "number allocated FGIDs by the appl after appl
         registration";
    }
    leaf free-fgids-act {
      type uint32;
      description
        "number free FGIDs by the appl after appl
         registration";
    }
  }

  grouping live_ncs_FGID-SYS-STATS-INFO {
    description
      "Per HFR basis fabric multicast resource
       statistics information";
    leaf total-fgids {
      type uint32;
      description
        "the total number of FGIDs";
    }
    leaf inuse-fgids {
      type uint32;
      description
        "the number of inuse FGIDs";
    }
    leaf hwm-inuse-fgids {
      type uint32;
      description
        "the high water mark of inuse FGIDs";
    }
  }

  grouping live_ncs_FGID-ALL-STATS-INFO {
    description
      "Fgid statistics information";
    container sys-stats {
      description
        "FGID system statistics";
      uses live_ncs_FGID-SYS-STATS-INFO;
    }
    list appl-stat {
      description
        "Application statistics";
      uses live_ncs_FGID-APPL-STATS-INFO;
    }
  }

  grouping FE-HW-FGID-BITMAP {
    description
      "Fgid bitmap on FE Asic HW";
    leaf asic-name {
      type string {
        length "0..16";
      }
      description
        "FE Asic";
    }
    leaf asic-type {
      type string {
        length "0..8";
      }
      description
        "FE Asic type";
    }
    leaf status {
      type string {
        length "0..4";
      }
      description
        "SW/HW fgid bitmap match";
    }
    list bitmap {
      max-elements 2;
      description
        "FGID Bitmap";
      leaf entry {
        type uint64;
        description
          "FGID Bitmap";
      }
    }
  }

  grouping FGID-DIAG-INFO {
    description
      "Fgid bitmap on rack FE asics";
    leaf rack-num {
      type uint32;
      description
        "Rack num";
    }
    list fe-asic {
      description
        "FGID bitmaps info on FE HW";
      uses FE-HW-FGID-BITMAP;
    }
  }

  grouping RACK-FGID-BITMAP {
    description
      "Rack Fgid Bitmaps";
    leaf rack {
      type uint32;
      description
        "Rack";
    }
    list bitmap {
      max-elements 2;
      description
        "Fgid bitmap";
      leaf entry {
        type uint64;
        description
          "Fgid bitmap";
      }
    }
  }

  grouping FAPID-INFO {
    description
      "Fabid information";
    leaf fapid {
      type uint32;
      description
        "Fapid";
    }
    leaf rack {
      type uint32;
      description
        "Rack";
    }
    leaf slot {
      type uint32;
      description
        "Slot";
    }
    leaf asic {
      type uint32;
      description
        "Asic";
    }
  }

  grouping FGID-INFO {
    description
      "Per FGID ID information";
    leaf fgid-id-xr {
      type uint32;
      description
        "FGID ID";
    }
    leaf num-fapids {
      type uint32;
      description
        "Number of assoicated fapids";
    }
    leaf client-id {
      type uint32;
      description
        "Client ID";
    }
    leaf client-name {
      type string;
      description
        "Client name";
    }
    leaf sdr-name {
      type string;
      description
        "SDR Name";
    }
    leaf num-up-racks {
      type uint32;
      description
        "Number of UP Racks";
    }
    leaf max-lcc-racks {
      type uint32;
      description
        "Maximum LCC Racks";
    }
    list fapid {
      description
        "Associated fapids";
      uses FAPID-INFO;
    }
    list fgid-bitmap {
      description
        "Racks FGID Bitmaps";
      uses RACK-FGID-BITMAP;
    }
    list rack-fgid-diag-info {
      description
        "FGID Diag per rack";
      uses FGID-DIAG-INFO;
    }
  }

  grouping FGID-APPL-STATS-INFO {
    description
      "Per application basis fabric multicast resource
       statistics information - no LR info";
    leaf appl-name {
      type string;
      description
        "multicast resource application name";
    }
    leaf inuse-fgids {
      type uint32;
      description
        "the number of inuse FGIDs by the appl";
    }
    leaf hwm-inuse-fgids {
      type uint32;
      description
        "the high water mark of inused FGIDs";
    }
    leaf inuse-fgids-act {
      type uint32;
      description
        "inuse FGIDs by the appl at appl registration
         time";
    }
    leaf alloc-fgids-act {
      type uint32;
      description
        "number allocated FGIDs by the appl after appl
         registration";
    }
    leaf free-fgids-act {
      type uint32;
      description
        "number free FGIDs by the appl after appl
         registration";
    }
  }

  grouping FGID-SYS-STATS-INFO {
    description
      "Per HFR basis fabric multicast resource
       statistics information";
    leaf total-fgids {
      type uint32;
      description
        "the total number of FGIDs";
    }
    leaf inuse-fgids {
      type uint32;
      description
        "the number of inuse FGIDs";
    }
    leaf hwm-inuse-fgids {
      type uint32;
      description
        "the high water mark of inuse FGIDs";
    }
  }

  grouping FGID-ALL-STATS-INFO {
    description
      "Fgid statistics information";
    container sys-stats {
      description
        "FGID system statistics";
      uses FGID-SYS-STATS-INFO;
    }
    list appl-stat {
      description
        "Application statistics";
      uses FGID-APPL-STATS-INFO;
    }
  }
}

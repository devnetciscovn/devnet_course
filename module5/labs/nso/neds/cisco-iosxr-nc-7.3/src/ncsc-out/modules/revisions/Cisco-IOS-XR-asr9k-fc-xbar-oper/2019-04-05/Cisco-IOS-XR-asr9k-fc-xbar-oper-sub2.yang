submodule Cisco-IOS-XR-asr9k-fc-xbar-oper-sub2 {
  // Generated by yanger -t ncs
  tailf:mount-id "cisco-iosxr-nc-7.3:cisco-iosxr-nc-7.3";

  belongs-to Cisco-IOS-XR-asr9k-fc-xbar-oper {
    prefix Cisco-IOS-XR-asr9k-fc-xbar-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-fc-xbar package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_XBAR-EDM-SKB-XPS-STATS {
    description
      "XBAR EDM SKB XPS STATS";
    leaf uc-timer-drop {
      type string;
      description
        "UC TIMERDROP";
    }
    leaf uc-timer-truncate {
      type string;
      description
        "UC TIMERTRUNCATE";
    }
    leaf mc-timer-drop {
      type string;
      description
        "MC TIMERDROP";
    }
    leaf mc-timer-truncate {
      type string;
      description
        "MC TIMERTRUNCATE";
    }
  }

  grouping ncs_template_XBAR-EDM-SKB-CFL-EG-MISC-STATS {
    description
      "XBAR EDM SKB CFL EG MISC STATS";
    leaf ecc-corr-err {
      type string;
      description
        "ECC CORR ERR";
    }
    leaf ecc-uncorr-err {
      type string;
      description
        "ECC UNCORR ERR";
    }
    leaf ecc-raw-corr-err {
      type string;
      description
        "ECC RAW CORR ERR";
    }
    leaf ecc-raw-uncorr-err {
      type string;
      description
        "ECC RAW UNCORR ERR";
    }
    leaf eg-total-rate {
      type string;
      description
        "Egress CFL Total Rate";
    }
  }

  grouping ncs_template_XBAR-EDM-SKB-CFL-EG-MC-STATS {
    description
      "XBAR EDM SKB CFL EG MC STATS";
    leaf pkts-truncated {
      type string;
      description
        "PKTS TRUNCATED";
    }
    leaf pkts-from-ob-to-port {
      type string;
      description
        "PKTS FROM OB TO PORT";
    }
    leaf eg-mc-rate {
      type string;
      description
        "Egress CFL Multicast Rate";
    }
  }

  grouping ncs_template_XBAR-EDM-SKB-CFL-EG-UC-STATS {
    description
      "XBAR EDM SKB CFL EG UC STATS";
    leaf pkts-truncated {
      type string;
      description
        "PKTS TRUNCATED";
    }
    leaf pkts-from-ob-to-port {
      type string;
      description
        "PKTS FROM OB TO PORT";
    }
    leaf eg-uc-rate {
      type string;
      description
        "Egress CFL Unicast Rate";
    }
  }

  grouping ncs_template_XBAR-EDM-SKB-CFL-EG-STATS {
    description
      "XBAR EDM SKB CFL EG STATS";
    container cfl-uc-stats {
      description
        "Egress CFL Unicast Stats";
      uses ncs_template_XBAR-EDM-SKB-CFL-EG-UC-STATS;
    }
    container cfl-mc-stats {
      description
        "Egress CFL Multicast Stats";
      uses ncs_template_XBAR-EDM-SKB-CFL-EG-MC-STATS;
    }
    container cfl-misc-stats {
      description
        "Egress CFL Miscellaneous Stats";
      uses ncs_template_XBAR-EDM-SKB-CFL-EG-MISC-STATS;
    }
  }

  grouping ncs_template_XBAR-EDM-SKB-OBU-MC-STATS {
    description
      "XBAR EDM SKB OBU MC STATS";
    leaf pktin {
      type string;
      description
        "PKTIN";
    }
    leaf pktout {
      type string;
      description
        "PKTOUT";
    }
    leaf bytein {
      type string;
      description
        "BYTEIN";
    }
    leaf byteout {
      type string;
      description
        "BYTEOUT";
    }
    leaf pkttrunc {
      type string;
      description
        "PKTTRUNC";
    }
  }

  grouping ncs_template_XBAR-EDM-SKB-OBU-UC-STATS {
    description
      "XBAR EDM SKB OBU UC STATS";
    leaf pktin {
      type string;
      description
        "PKTIN";
    }
    leaf pktout {
      type string;
      description
        "PKTOUT";
    }
    leaf bytein {
      type string;
      description
        "BYTEIN";
    }
    leaf byteout {
      type string;
      description
        "BYTEOUT";
    }
    leaf pkttrunc {
      type string;
      description
        "PKTTRUNC";
    }
  }

  grouping ncs_template_XBAR-EDM-SKB-OBU-STATS {
    description
      "XBAR EDM SKB OBU STATS";
    list data-queque {
      // NCS patched for predictable order
      ordered-by user;
      // NCS drop max-elements statement
      description
        "Output Buffer Data Queue Queue Count";
      leaf entry {
        type string;
        description
          "Output Buffer Data Queue Queue Count";
      }
    }
  }

  grouping ncs_template_XBAR-EDM-SKB-EG-STATS {
    description
      "XBAR EDM SKB EG STATS";
    container obu-stats {
      description
        "Output Buffer Stats";
      uses ncs_template_XBAR-EDM-SKB-OBU-STATS;
    }
    container obu-uc-stats {
      description
        "Output Buffer UC Stats";
      uses ncs_template_XBAR-EDM-SKB-OBU-UC-STATS;
    }
    container obu-mc-stats {
      description
        "Output Buffer MC Stats";
      uses ncs_template_XBAR-EDM-SKB-OBU-MC-STATS;
    }
    container cfl-stats {
      description
        "Egress Common Fabric Link Stats";
      uses ncs_template_XBAR-EDM-SKB-CFL-EG-STATS;
    }
  }

  grouping ncs_template_XBAR-EDM-SKB-CFL-IN-MISC-STATS {
    description
      "XBAR EDM SKB CFL IN MISC STATS";
    leaf crc-stomp {
      type string;
      description
        "CRC STOMP";
    }
    leaf crc-new-err {
      type string;
      description
        "CRC NEW ERR";
    }
    leaf in-total-rate {
      type string;
      description
        "Ingress CFL Total Rate";
    }
  }

  grouping ncs_template_XBAR-EDM-SKB-CFL-IN-MC-STATS {
    description
      "XBAR EDM SKB CFL IN MC STATS";
    leaf crc-match-pattern {
      type string;
      description
        "CRC MATCH PATTERN";
    }
    leaf pkts-rcvd {
      type string;
      description
        "PKTS RCVD";
    }
    leaf packed-pkts-rcvd {
      type string;
      description
        "PACKED PKTS RCVD";
    }
    leaf pkts-flushed {
      type string;
      description
        "PKTS FLUSHED";
    }
    leaf runt-pkts-drop-ped {
      type string;
      description
        "RUNT PKTS DROPPED";
    }
    leaf small-pkts-drop-ped {
      type string;
      description
        "SMALL PKTS DROPPED";
    }
    leaf pkts-to-ib-from-port {
      type string;
      description
        "PKTS TO IB FROM PORT";
    }
    leaf in-mc-rate {
      type string;
      description
        "Ingress CFL Multicast Rate";
    }
  }

  grouping ncs_template_XBAR-EDM-SKB-CFL-IN-UC-STATS {
    description
      "XBAR EDM SKB CFL IN UC STATS";
    leaf crc-match-pattern {
      type string;
      description
        "CRC MATCH PATTERN";
    }
    leaf pkts-rcvd {
      type string;
      description
        "PKTS RCVD";
    }
    leaf packed-pkts-rcvd {
      type string;
      description
        "PACKED PKTS RCVD";
    }
    leaf pkts-flushed {
      type string;
      description
        "PKTS FLUSHED";
    }
    leaf runt-pkts-drop-ped {
      type string;
      description
        "RUNT PKTS DROPPED";
    }
    leaf small-pkts-drop-ped {
      type string;
      description
        "SMALL PKTS DROPPED";
    }
    leaf pkts-to-ib-from-port {
      type string;
      description
        "PKTS TO IB FROM PORT";
    }
    leaf in-uc-rate {
      type string;
      description
        "Ingress CFL Unicast Rate";
    }
  }

  grouping ncs_template_XBAR-EDM-SKB-CFL-IN-STATS {
    description
      "XBAR EDM SKB CFL IN STATS";
    container cfl-uc-stats {
      description
        "Ingress CFL Unicast Stats";
      uses ncs_template_XBAR-EDM-SKB-CFL-IN-UC-STATS;
    }
    container cfl-mc-stats {
      description
        "Ingress CFL Multicast Stats";
      uses ncs_template_XBAR-EDM-SKB-CFL-IN-MC-STATS;
    }
    container cfl-misc-stats {
      description
        "Ingress CFL Miscellaneous Stats";
      uses ncs_template_XBAR-EDM-SKB-CFL-IN-MISC-STATS;
    }
  }

  grouping ncs_template_XBAR-EDM-SKB-IBF-MC-STATS {
    description
      "XBAR EDM SKB IBF MC STATS";
    leaf pktcnt {
      type string;
      description
        "PKTCNT";
    }
    leaf pktoutcnt {
      type string;
      description
        "PKTOUTCNT";
    }
    leaf pkthi-copy-sup-event {
      type string;
      description
        "PKTHICOPYSUPEVENT";
    }
    leaf pktlo-copy-sup-event {
      type string;
      description
        "PKTLOCOPYSUPEVENT";
    }
    leaf pkt-input-err-drop {
      type string;
      description
        "PKTINPUTERRDROP";
    }
    leaf pktfgid-addr-err-drop {
      type string;
      description
        "PKTFGIDADDRERRDROP";
    }
    leaf pktfgidlkuperr-drop {
      type string;
      description
        "PKTFGIDLKUPERRDROP";
    }
    leaf pkt-null-poe-drop {
      type string;
      description
        "PKTNULLPOEDROP";
    }
    leaf pkt-copy-sup-drop {
      type string;
      description
        "PKTCOPYSUPDROP";
    }
    leaf pkt-disp-oe-drop {
      type string;
      description
        "PKTDISPOEDROP";
    }
    leaf pktto-drop-cnt {
      type string;
      description
        "PKTTODROPCNT";
    }
  }

  grouping ncs_template_XBAR-EDM-SKB-IBB-MC-STATS {
    description
      "XBAR EDM SKB IBB MC STATS";
    leaf ipc-data-tot {
      type string;
      description
        "IPCDATATOT";
    }
    leaf ipc-data-totsz {
      type string;
      description
        "IPCDATATOTSZ";
    }
    leaf ipcrunt {
      type string;
      description
        "IPCRUNT";
    }
    leaf ipcgiant {
      type string;
      description
        "IPCGIANT";
    }
    leaf ipc-data-err {
      type string;
      description
        "IPCDATAERR";
    }
    leaf ipclinkerr {
      type string;
      description
        "IPCLINKERR";
    }
    leaf ipcptcerr {
      type string;
      description
        "IPCPTCERR";
    }
    leaf ipcpkt-drop {
      type string;
      description
        "IPCPKTDROP";
    }
    leaf ipcdes-drop {
      type string;
      description
        "IPCDESDROP";
    }
    leaf dhehitail-drop {
      type string;
      description
        "DHEHITAILDROP";
    }
    leaf dhelotail-drop {
      type string;
      description
        "DHELOTAILDROP";
    }
    leaf ibmoutsop {
      type string;
      description
        "IBMOUTSOP";
    }
    leaf ibmouteop {
      type string;
      description
        "IBMOUTEOP";
    }
    leaf ibmoutbyte {
      type string;
      description
        "IBMOUTBYTE";
    }
    leaf icmenq {
      type string;
      description
        "ICMENQ";
    }
    leaf icmdeq {
      type string;
      description
        "ICMDEQ";
    }
    leaf icmfcxoff {
      type string;
      description
        "ICMFCXOFF";
    }
    leaf icmfcxon {
      type string;
      description
        "ICMFCXON";
    }
  }

  grouping ncs_template_XBAR-EDM-SKB-IBF-UC-STATS {
    description
      "XBAR EDM SKB IBF UC STATS";
    leaf pktcnt {
      type string;
      description
        "PKTCNT";
    }
    leaf pktoutp0cnt {
      type string;
      description
        "PKTOUTP0CNT";
    }
    leaf pktoutp1cnt {
      type string;
      description
        "PKTOUTP1CNT";
    }
    leaf pkt-input-err-drop {
      type string;
      description
        "PKTINPUTERRDROP";
    }
    leaf pkthwerr-drop {
      type string;
      description
        "PKTHWERRDROP";
    }
    leaf pkt-null-poe-drop {
      type string;
      description
        "PKTNULLPOEDROP";
    }
    leaf pkt-disp-oe-drop {
      type string;
      description
        "PKTDISPOEDROP";
    }
  }

  grouping ncs_template_XBAR-EDM-SKB-IBB-UC-STATS {
    description
      "XBAR EDM SKB IBB UC STATS";
    leaf ipc-data-tot {
      type string;
      description
        "IPCDATATOT";
    }
    leaf ipc-data-totsz {
      type string;
      description
        "IPCDATATOTSZ";
    }
    leaf ipcrunt {
      type string;
      description
        "IPCRUNT";
    }
    leaf ipcgiant {
      type string;
      description
        "IPCGIANT";
    }
    leaf ipc-data-err {
      type string;
      description
        "IPCDATAERR";
    }
    leaf ipclinkerr {
      type string;
      description
        "IPCLINKERR";
    }
    leaf ipcptcerr {
      type string;
      description
        "IPCPTCERR";
    }
    leaf ipcpkt-drop {
      type string;
      description
        "IPCPKTDROP";
    }
    leaf ipcdes-drop {
      type string;
      description
        "IPCDESDROP";
    }
    leaf dhetail-drop {
      type string;
      description
        "DHETAILDROP";
    }
    leaf ibmoutsop {
      type string;
      description
        "IBMOUTSOP";
    }
    leaf ibmouteop {
      type string;
      description
        "IBMOUTEOP";
    }
    leaf ibmoutbyte {
      type string;
      description
        "IBMOUTBYTE";
    }
    leaf icmenq {
      type string;
      description
        "ICMENQ";
    }
    leaf icmdeq {
      type string;
      description
        "ICMDEQ";
    }
    leaf icmfcxoff {
      type string;
      description
        "ICMFCXOFF";
    }
    leaf icmfcxon {
      type string;
      description
        "ICMFCXON";
    }
  }

  grouping ncs_template_XBAR-EDM-SKB-IBF-STATS {
    description
      "XBAR EDM SKB IBF STATS";
    leaf unused {
      type string;
      description
        "Ingress Unused Counter";
    }
  }

  grouping ncs_template_XBAR-EDM-SKB-IBB-STATS {
    description
      "XBAR EDM SKB IBB STATS";
    leaf ipcicmtail-drop {
      type string;
      description
        "IPCICMTAILDROP";
    }
    leaf dhe-diag-pkt {
      type string;
      description
        "DHEDIAGPKT";
    }
    leaf ibmdnouttot {
      type string;
      description
        "IBMDNOUTTOT";
    }
    leaf icmdnenq {
      type string;
      description
        "ICMDNENQ";
    }
    leaf icmdndeq {
      type string;
      description
        "ICMDNDEQ";
    }
    leaf ibmcsrccouttot {
      type string;
      description
        "IBMCSRCCOUTTOT";
    }
  }

  grouping ncs_template_XBAR-EDM-SKB-IN-STATS {
    description
      "XBAR EDM SKB IN STATS";
    container ibb-stats {
      description
        "Input Buffer Block Stats";
      uses ncs_template_XBAR-EDM-SKB-IBB-STATS;
    }
    container ibf-stats {
      description
        "Input Forwarding Block Stats";
      uses ncs_template_XBAR-EDM-SKB-IBF-STATS;
    }
    container ibb-uc-stats {
      description
        "Input Buffer Block UC Stats";
      uses ncs_template_XBAR-EDM-SKB-IBB-UC-STATS;
    }
    container ibf-uc-stats {
      description
        "Input Forwarding Block UC Stats";
      uses ncs_template_XBAR-EDM-SKB-IBF-UC-STATS;
    }
    container ibb-mc-stats {
      description
        "Input Buffer Block MC Stats";
      uses ncs_template_XBAR-EDM-SKB-IBB-MC-STATS;
    }
    container ibf-mc-stats {
      description
        "Input Forwarding Block MC Stats";
      uses ncs_template_XBAR-EDM-SKB-IBF-MC-STATS;
    }
    container cfl-stats {
      description
        "Ingress Common Fabric Link Stats";
      uses ncs_template_XBAR-EDM-SKB-CFL-IN-STATS;
    }
  }

  grouping ncs_template_XBAR-EDM-SKB-PORT-STATS {
    description
      "XBAR EDM SKB PORT STATS";
    container in-stats {
      description
        "Ingress Stats";
      uses ncs_template_XBAR-EDM-SKB-IN-STATS;
    }
    container eg-stats {
      description
        "Egress Stats";
      uses ncs_template_XBAR-EDM-SKB-EG-STATS;
    }
    container xps-stats {
      description
        "Crosspoint Scheduler Stats";
      uses ncs_template_XBAR-EDM-SKB-XPS-STATS;
    }
    leaf internal-err-cnt {
      type string;
      description
        "Internal Error Count";
    }
  }

  grouping ncs_rpc_notif_XBAR-EDM-SKB-XPS-STATS {
    description
      "XBAR EDM SKB XPS STATS";
    leaf uc-timer-drop {
      type uint64;
      description
        "UC TIMERDROP";
    }
    leaf uc-timer-truncate {
      type uint64;
      description
        "UC TIMERTRUNCATE";
    }
    leaf mc-timer-drop {
      type uint64;
      description
        "MC TIMERDROP";
    }
    leaf mc-timer-truncate {
      type uint64;
      description
        "MC TIMERTRUNCATE";
    }
  }

  grouping ncs_rpc_notif_XBAR-EDM-SKB-CFL-EG-MISC-STATS {
    description
      "XBAR EDM SKB CFL EG MISC STATS";
    leaf ecc-corr-err {
      type uint64;
      description
        "ECC CORR ERR";
    }
    leaf ecc-uncorr-err {
      type uint64;
      description
        "ECC UNCORR ERR";
    }
    leaf ecc-raw-corr-err {
      type uint64;
      description
        "ECC RAW CORR ERR";
    }
    leaf ecc-raw-uncorr-err {
      type uint64;
      description
        "ECC RAW UNCORR ERR";
    }
    leaf eg-total-rate {
      type uint64;
      description
        "Egress CFL Total Rate";
    }
  }

  grouping ncs_rpc_notif_XBAR-EDM-SKB-CFL-EG-MC-STATS {
    description
      "XBAR EDM SKB CFL EG MC STATS";
    leaf pkts-truncated {
      type uint64;
      description
        "PKTS TRUNCATED";
    }
    leaf pkts-from-ob-to-port {
      type uint64;
      description
        "PKTS FROM OB TO PORT";
    }
    leaf eg-mc-rate {
      type uint64;
      description
        "Egress CFL Multicast Rate";
    }
  }

  grouping ncs_rpc_notif_XBAR-EDM-SKB-CFL-EG-UC-STATS {
    description
      "XBAR EDM SKB CFL EG UC STATS";
    leaf pkts-truncated {
      type uint64;
      description
        "PKTS TRUNCATED";
    }
    leaf pkts-from-ob-to-port {
      type uint64;
      description
        "PKTS FROM OB TO PORT";
    }
    leaf eg-uc-rate {
      type uint64;
      description
        "Egress CFL Unicast Rate";
    }
  }

  grouping ncs_rpc_notif_XBAR-EDM-SKB-CFL-EG-STATS {
    description
      "XBAR EDM SKB CFL EG STATS";
    container cfl-uc-stats {
      description
        "Egress CFL Unicast Stats";
      uses ncs_rpc_notif_XBAR-EDM-SKB-CFL-EG-UC-STATS;
    }
    container cfl-mc-stats {
      description
        "Egress CFL Multicast Stats";
      uses ncs_rpc_notif_XBAR-EDM-SKB-CFL-EG-MC-STATS;
    }
    container cfl-misc-stats {
      description
        "Egress CFL Miscellaneous Stats";
      uses ncs_rpc_notif_XBAR-EDM-SKB-CFL-EG-MISC-STATS;
    }
  }

  grouping ncs_rpc_notif_XBAR-EDM-SKB-OBU-MC-STATS {
    description
      "XBAR EDM SKB OBU MC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping ncs_rpc_notif_XBAR-EDM-SKB-OBU-UC-STATS {
    description
      "XBAR EDM SKB OBU UC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping ncs_rpc_notif_XBAR-EDM-SKB-OBU-STATS {
    description
      "XBAR EDM SKB OBU STATS";
    list data-queque {
      max-elements 24;
      description
        "Output Buffer Data Queue Queue Count";
      leaf entry {
        type uint32;
        description
          "Output Buffer Data Queue Queue Count";
      }
    }
  }

  grouping ncs_rpc_notif_XBAR-EDM-SKB-EG-STATS {
    description
      "XBAR EDM SKB EG STATS";
    container obu-stats {
      description
        "Output Buffer Stats";
      uses ncs_rpc_notif_XBAR-EDM-SKB-OBU-STATS;
    }
    container obu-uc-stats {
      description
        "Output Buffer UC Stats";
      uses ncs_rpc_notif_XBAR-EDM-SKB-OBU-UC-STATS;
    }
    container obu-mc-stats {
      description
        "Output Buffer MC Stats";
      uses ncs_rpc_notif_XBAR-EDM-SKB-OBU-MC-STATS;
    }
    container cfl-stats {
      description
        "Egress Common Fabric Link Stats";
      uses ncs_rpc_notif_XBAR-EDM-SKB-CFL-EG-STATS;
    }
  }

  grouping ncs_rpc_notif_XBAR-EDM-SKB-CFL-IN-MISC-STATS {
    description
      "XBAR EDM SKB CFL IN MISC STATS";
    leaf crc-stomp {
      type uint64;
      description
        "CRC STOMP";
    }
    leaf crc-new-err {
      type uint64;
      description
        "CRC NEW ERR";
    }
    leaf in-total-rate {
      type uint64;
      description
        "Ingress CFL Total Rate";
    }
  }

  grouping ncs_rpc_notif_XBAR-EDM-SKB-CFL-IN-MC-STATS {
    description
      "XBAR EDM SKB CFL IN MC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-mc-rate {
      type uint64;
      description
        "Ingress CFL Multicast Rate";
    }
  }

  grouping ncs_rpc_notif_XBAR-EDM-SKB-CFL-IN-UC-STATS {
    description
      "XBAR EDM SKB CFL IN UC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-uc-rate {
      type uint64;
      description
        "Ingress CFL Unicast Rate";
    }
  }

  grouping ncs_rpc_notif_XBAR-EDM-SKB-CFL-IN-STATS {
    description
      "XBAR EDM SKB CFL IN STATS";
    container cfl-uc-stats {
      description
        "Ingress CFL Unicast Stats";
      uses ncs_rpc_notif_XBAR-EDM-SKB-CFL-IN-UC-STATS;
    }
    container cfl-mc-stats {
      description
        "Ingress CFL Multicast Stats";
      uses ncs_rpc_notif_XBAR-EDM-SKB-CFL-IN-MC-STATS;
    }
    container cfl-misc-stats {
      description
        "Ingress CFL Miscellaneous Stats";
      uses ncs_rpc_notif_XBAR-EDM-SKB-CFL-IN-MISC-STATS;
    }
  }

  grouping ncs_rpc_notif_XBAR-EDM-SKB-IBF-MC-STATS {
    description
      "XBAR EDM SKB IBF MC STATS";
    leaf pktcnt {
      type uint64;
      description
        "PKTCNT";
    }
    leaf pktoutcnt {
      type uint64;
      description
        "PKTOUTCNT";
    }
    leaf pkthi-copy-sup-event {
      type uint64;
      description
        "PKTHICOPYSUPEVENT";
    }
    leaf pktlo-copy-sup-event {
      type uint64;
      description
        "PKTLOCOPYSUPEVENT";
    }
    leaf pkt-input-err-drop {
      type uint64;
      description
        "PKTINPUTERRDROP";
    }
    leaf pktfgid-addr-err-drop {
      type uint64;
      description
        "PKTFGIDADDRERRDROP";
    }
    leaf pktfgidlkuperr-drop {
      type uint64;
      description
        "PKTFGIDLKUPERRDROP";
    }
    leaf pkt-null-poe-drop {
      type uint64;
      description
        "PKTNULLPOEDROP";
    }
    leaf pkt-copy-sup-drop {
      type uint64;
      description
        "PKTCOPYSUPDROP";
    }
    leaf pkt-disp-oe-drop {
      type uint64;
      description
        "PKTDISPOEDROP";
    }
    leaf pktto-drop-cnt {
      type uint64;
      description
        "PKTTODROPCNT";
    }
  }

  grouping ncs_rpc_notif_XBAR-EDM-SKB-IBB-MC-STATS {
    description
      "XBAR EDM SKB IBB MC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhehitail-drop {
      type uint64;
      description
        "DHEHITAILDROP";
    }
    leaf dhelotail-drop {
      type uint64;
      description
        "DHELOTAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping ncs_rpc_notif_XBAR-EDM-SKB-IBF-UC-STATS {
    description
      "XBAR EDM SKB IBF UC STATS";
    leaf pktcnt {
      type uint64;
      description
        "PKTCNT";
    }
    leaf pktoutp0cnt {
      type uint64;
      description
        "PKTOUTP0CNT";
    }
    leaf pktoutp1cnt {
      type uint64;
      description
        "PKTOUTP1CNT";
    }
    leaf pkt-input-err-drop {
      type uint64;
      description
        "PKTINPUTERRDROP";
    }
    leaf pkthwerr-drop {
      type uint64;
      description
        "PKTHWERRDROP";
    }
    leaf pkt-null-poe-drop {
      type uint64;
      description
        "PKTNULLPOEDROP";
    }
    leaf pkt-disp-oe-drop {
      type uint64;
      description
        "PKTDISPOEDROP";
    }
  }

  grouping ncs_rpc_notif_XBAR-EDM-SKB-IBB-UC-STATS {
    description
      "XBAR EDM SKB IBB UC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhetail-drop {
      type uint64;
      description
        "DHETAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping ncs_rpc_notif_XBAR-EDM-SKB-IBF-STATS {
    description
      "XBAR EDM SKB IBF STATS";
    leaf unused {
      type uint64;
      description
        "Ingress Unused Counter";
    }
  }

  grouping ncs_rpc_notif_XBAR-EDM-SKB-IBB-STATS {
    description
      "XBAR EDM SKB IBB STATS";
    leaf ipcicmtail-drop {
      type uint64;
      description
        "IPCICMTAILDROP";
    }
    leaf dhe-diag-pkt {
      type uint64;
      description
        "DHEDIAGPKT";
    }
    leaf ibmdnouttot {
      type uint64;
      description
        "IBMDNOUTTOT";
    }
    leaf icmdnenq {
      type uint64;
      description
        "ICMDNENQ";
    }
    leaf icmdndeq {
      type uint64;
      description
        "ICMDNDEQ";
    }
    leaf ibmcsrccouttot {
      type uint64;
      description
        "IBMCSRCCOUTTOT";
    }
  }

  grouping ncs_rpc_notif_XBAR-EDM-SKB-IN-STATS {
    description
      "XBAR EDM SKB IN STATS";
    container ibb-stats {
      description
        "Input Buffer Block Stats";
      uses ncs_rpc_notif_XBAR-EDM-SKB-IBB-STATS;
    }
    container ibf-stats {
      description
        "Input Forwarding Block Stats";
      uses ncs_rpc_notif_XBAR-EDM-SKB-IBF-STATS;
    }
    container ibb-uc-stats {
      description
        "Input Buffer Block UC Stats";
      uses ncs_rpc_notif_XBAR-EDM-SKB-IBB-UC-STATS;
    }
    container ibf-uc-stats {
      description
        "Input Forwarding Block UC Stats";
      uses ncs_rpc_notif_XBAR-EDM-SKB-IBF-UC-STATS;
    }
    container ibb-mc-stats {
      description
        "Input Buffer Block MC Stats";
      uses ncs_rpc_notif_XBAR-EDM-SKB-IBB-MC-STATS;
    }
    container ibf-mc-stats {
      description
        "Input Forwarding Block MC Stats";
      uses ncs_rpc_notif_XBAR-EDM-SKB-IBF-MC-STATS;
    }
    container cfl-stats {
      description
        "Ingress Common Fabric Link Stats";
      uses ncs_rpc_notif_XBAR-EDM-SKB-CFL-IN-STATS;
    }
  }

  grouping ncs_rpc_notif_XBAR-EDM-SKB-PORT-STATS {
    description
      "XBAR EDM SKB PORT STATS";
    container in-stats {
      description
        "Ingress Stats";
      uses ncs_rpc_notif_XBAR-EDM-SKB-IN-STATS;
    }
    container eg-stats {
      description
        "Egress Stats";
      uses ncs_rpc_notif_XBAR-EDM-SKB-EG-STATS;
    }
    container xps-stats {
      description
        "Crosspoint Scheduler Stats";
      uses ncs_rpc_notif_XBAR-EDM-SKB-XPS-STATS;
    }
    leaf internal-err-cnt {
      type uint64;
      description
        "Internal Error Count";
    }
  }

  grouping live_ncs_XBAR-EDM-SKB-XPS-STATS {
    description
      "XBAR EDM SKB XPS STATS";
    leaf uc-timer-drop {
      type uint64;
      description
        "UC TIMERDROP";
    }
    leaf uc-timer-truncate {
      type uint64;
      description
        "UC TIMERTRUNCATE";
    }
    leaf mc-timer-drop {
      type uint64;
      description
        "MC TIMERDROP";
    }
    leaf mc-timer-truncate {
      type uint64;
      description
        "MC TIMERTRUNCATE";
    }
  }

  grouping live_ncs_XBAR-EDM-SKB-CFL-EG-MISC-STATS {
    description
      "XBAR EDM SKB CFL EG MISC STATS";
    leaf ecc-corr-err {
      type uint64;
      description
        "ECC CORR ERR";
    }
    leaf ecc-uncorr-err {
      type uint64;
      description
        "ECC UNCORR ERR";
    }
    leaf ecc-raw-corr-err {
      type uint64;
      description
        "ECC RAW CORR ERR";
    }
    leaf ecc-raw-uncorr-err {
      type uint64;
      description
        "ECC RAW UNCORR ERR";
    }
    leaf eg-total-rate {
      type uint64;
      description
        "Egress CFL Total Rate";
    }
  }

  grouping live_ncs_XBAR-EDM-SKB-CFL-EG-MC-STATS {
    description
      "XBAR EDM SKB CFL EG MC STATS";
    leaf pkts-truncated {
      type uint64;
      description
        "PKTS TRUNCATED";
    }
    leaf pkts-from-ob-to-port {
      type uint64;
      description
        "PKTS FROM OB TO PORT";
    }
    leaf eg-mc-rate {
      type uint64;
      description
        "Egress CFL Multicast Rate";
    }
  }

  grouping live_ncs_XBAR-EDM-SKB-CFL-EG-UC-STATS {
    description
      "XBAR EDM SKB CFL EG UC STATS";
    leaf pkts-truncated {
      type uint64;
      description
        "PKTS TRUNCATED";
    }
    leaf pkts-from-ob-to-port {
      type uint64;
      description
        "PKTS FROM OB TO PORT";
    }
    leaf eg-uc-rate {
      type uint64;
      description
        "Egress CFL Unicast Rate";
    }
  }

  grouping live_ncs_XBAR-EDM-SKB-CFL-EG-STATS {
    description
      "XBAR EDM SKB CFL EG STATS";
    container cfl-uc-stats {
      description
        "Egress CFL Unicast Stats";
      uses live_ncs_XBAR-EDM-SKB-CFL-EG-UC-STATS;
    }
    container cfl-mc-stats {
      description
        "Egress CFL Multicast Stats";
      uses live_ncs_XBAR-EDM-SKB-CFL-EG-MC-STATS;
    }
    container cfl-misc-stats {
      description
        "Egress CFL Miscellaneous Stats";
      uses live_ncs_XBAR-EDM-SKB-CFL-EG-MISC-STATS;
    }
  }

  grouping live_ncs_XBAR-EDM-SKB-OBU-MC-STATS {
    description
      "XBAR EDM SKB OBU MC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping live_ncs_XBAR-EDM-SKB-OBU-UC-STATS {
    description
      "XBAR EDM SKB OBU UC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping live_ncs_XBAR-EDM-SKB-OBU-STATS {
    description
      "XBAR EDM SKB OBU STATS";
    list data-queque {
      // NCS drop max-elements statement
      description
        "Output Buffer Data Queue Queue Count";
      leaf entry {
        type uint32;
        description
          "Output Buffer Data Queue Queue Count";
      }
    }
  }

  grouping live_ncs_XBAR-EDM-SKB-EG-STATS {
    description
      "XBAR EDM SKB EG STATS";
    container obu-stats {
      description
        "Output Buffer Stats";
      uses live_ncs_XBAR-EDM-SKB-OBU-STATS;
    }
    container obu-uc-stats {
      description
        "Output Buffer UC Stats";
      uses live_ncs_XBAR-EDM-SKB-OBU-UC-STATS;
    }
    container obu-mc-stats {
      description
        "Output Buffer MC Stats";
      uses live_ncs_XBAR-EDM-SKB-OBU-MC-STATS;
    }
    container cfl-stats {
      description
        "Egress Common Fabric Link Stats";
      uses live_ncs_XBAR-EDM-SKB-CFL-EG-STATS;
    }
  }

  grouping live_ncs_XBAR-EDM-SKB-CFL-IN-MISC-STATS {
    description
      "XBAR EDM SKB CFL IN MISC STATS";
    leaf crc-stomp {
      type uint64;
      description
        "CRC STOMP";
    }
    leaf crc-new-err {
      type uint64;
      description
        "CRC NEW ERR";
    }
    leaf in-total-rate {
      type uint64;
      description
        "Ingress CFL Total Rate";
    }
  }

  grouping live_ncs_XBAR-EDM-SKB-CFL-IN-MC-STATS {
    description
      "XBAR EDM SKB CFL IN MC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-mc-rate {
      type uint64;
      description
        "Ingress CFL Multicast Rate";
    }
  }

  grouping live_ncs_XBAR-EDM-SKB-CFL-IN-UC-STATS {
    description
      "XBAR EDM SKB CFL IN UC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-uc-rate {
      type uint64;
      description
        "Ingress CFL Unicast Rate";
    }
  }

  grouping live_ncs_XBAR-EDM-SKB-CFL-IN-STATS {
    description
      "XBAR EDM SKB CFL IN STATS";
    container cfl-uc-stats {
      description
        "Ingress CFL Unicast Stats";
      uses live_ncs_XBAR-EDM-SKB-CFL-IN-UC-STATS;
    }
    container cfl-mc-stats {
      description
        "Ingress CFL Multicast Stats";
      uses live_ncs_XBAR-EDM-SKB-CFL-IN-MC-STATS;
    }
    container cfl-misc-stats {
      description
        "Ingress CFL Miscellaneous Stats";
      uses live_ncs_XBAR-EDM-SKB-CFL-IN-MISC-STATS;
    }
  }

  grouping live_ncs_XBAR-EDM-SKB-IBF-MC-STATS {
    description
      "XBAR EDM SKB IBF MC STATS";
    leaf pktcnt {
      type uint64;
      description
        "PKTCNT";
    }
    leaf pktoutcnt {
      type uint64;
      description
        "PKTOUTCNT";
    }
    leaf pkthi-copy-sup-event {
      type uint64;
      description
        "PKTHICOPYSUPEVENT";
    }
    leaf pktlo-copy-sup-event {
      type uint64;
      description
        "PKTLOCOPYSUPEVENT";
    }
    leaf pkt-input-err-drop {
      type uint64;
      description
        "PKTINPUTERRDROP";
    }
    leaf pktfgid-addr-err-drop {
      type uint64;
      description
        "PKTFGIDADDRERRDROP";
    }
    leaf pktfgidlkuperr-drop {
      type uint64;
      description
        "PKTFGIDLKUPERRDROP";
    }
    leaf pkt-null-poe-drop {
      type uint64;
      description
        "PKTNULLPOEDROP";
    }
    leaf pkt-copy-sup-drop {
      type uint64;
      description
        "PKTCOPYSUPDROP";
    }
    leaf pkt-disp-oe-drop {
      type uint64;
      description
        "PKTDISPOEDROP";
    }
    leaf pktto-drop-cnt {
      type uint64;
      description
        "PKTTODROPCNT";
    }
  }

  grouping live_ncs_XBAR-EDM-SKB-IBB-MC-STATS {
    description
      "XBAR EDM SKB IBB MC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhehitail-drop {
      type uint64;
      description
        "DHEHITAILDROP";
    }
    leaf dhelotail-drop {
      type uint64;
      description
        "DHELOTAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping live_ncs_XBAR-EDM-SKB-IBF-UC-STATS {
    description
      "XBAR EDM SKB IBF UC STATS";
    leaf pktcnt {
      type uint64;
      description
        "PKTCNT";
    }
    leaf pktoutp0cnt {
      type uint64;
      description
        "PKTOUTP0CNT";
    }
    leaf pktoutp1cnt {
      type uint64;
      description
        "PKTOUTP1CNT";
    }
    leaf pkt-input-err-drop {
      type uint64;
      description
        "PKTINPUTERRDROP";
    }
    leaf pkthwerr-drop {
      type uint64;
      description
        "PKTHWERRDROP";
    }
    leaf pkt-null-poe-drop {
      type uint64;
      description
        "PKTNULLPOEDROP";
    }
    leaf pkt-disp-oe-drop {
      type uint64;
      description
        "PKTDISPOEDROP";
    }
  }

  grouping live_ncs_XBAR-EDM-SKB-IBB-UC-STATS {
    description
      "XBAR EDM SKB IBB UC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhetail-drop {
      type uint64;
      description
        "DHETAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping live_ncs_XBAR-EDM-SKB-IBF-STATS {
    description
      "XBAR EDM SKB IBF STATS";
    leaf unused {
      type uint64;
      description
        "Ingress Unused Counter";
    }
  }

  grouping live_ncs_XBAR-EDM-SKB-IBB-STATS {
    description
      "XBAR EDM SKB IBB STATS";
    leaf ipcicmtail-drop {
      type uint64;
      description
        "IPCICMTAILDROP";
    }
    leaf dhe-diag-pkt {
      type uint64;
      description
        "DHEDIAGPKT";
    }
    leaf ibmdnouttot {
      type uint64;
      description
        "IBMDNOUTTOT";
    }
    leaf icmdnenq {
      type uint64;
      description
        "ICMDNENQ";
    }
    leaf icmdndeq {
      type uint64;
      description
        "ICMDNDEQ";
    }
    leaf ibmcsrccouttot {
      type uint64;
      description
        "IBMCSRCCOUTTOT";
    }
  }

  grouping live_ncs_XBAR-EDM-SKB-IN-STATS {
    description
      "XBAR EDM SKB IN STATS";
    container ibb-stats {
      description
        "Input Buffer Block Stats";
      uses live_ncs_XBAR-EDM-SKB-IBB-STATS;
    }
    container ibf-stats {
      description
        "Input Forwarding Block Stats";
      uses live_ncs_XBAR-EDM-SKB-IBF-STATS;
    }
    container ibb-uc-stats {
      description
        "Input Buffer Block UC Stats";
      uses live_ncs_XBAR-EDM-SKB-IBB-UC-STATS;
    }
    container ibf-uc-stats {
      description
        "Input Forwarding Block UC Stats";
      uses live_ncs_XBAR-EDM-SKB-IBF-UC-STATS;
    }
    container ibb-mc-stats {
      description
        "Input Buffer Block MC Stats";
      uses live_ncs_XBAR-EDM-SKB-IBB-MC-STATS;
    }
    container ibf-mc-stats {
      description
        "Input Forwarding Block MC Stats";
      uses live_ncs_XBAR-EDM-SKB-IBF-MC-STATS;
    }
    container cfl-stats {
      description
        "Ingress Common Fabric Link Stats";
      uses live_ncs_XBAR-EDM-SKB-CFL-IN-STATS;
    }
  }

  grouping live_ncs_XBAR-EDM-SKB-PORT-STATS {
    description
      "XBAR EDM SKB PORT STATS";
    container in-stats {
      description
        "Ingress Stats";
      uses live_ncs_XBAR-EDM-SKB-IN-STATS;
    }
    container eg-stats {
      description
        "Egress Stats";
      uses live_ncs_XBAR-EDM-SKB-EG-STATS;
    }
    container xps-stats {
      description
        "Crosspoint Scheduler Stats";
      uses live_ncs_XBAR-EDM-SKB-XPS-STATS;
    }
    leaf internal-err-cnt {
      type uint64;
      description
        "Internal Error Count";
    }
  }

  grouping XBAR-EDM-SKB-XPS-STATS {
    description
      "XBAR EDM SKB XPS STATS";
    leaf uc-timer-drop {
      type uint64;
      description
        "UC TIMERDROP";
    }
    leaf uc-timer-truncate {
      type uint64;
      description
        "UC TIMERTRUNCATE";
    }
    leaf mc-timer-drop {
      type uint64;
      description
        "MC TIMERDROP";
    }
    leaf mc-timer-truncate {
      type uint64;
      description
        "MC TIMERTRUNCATE";
    }
  }

  grouping XBAR-EDM-SKB-CFL-EG-MISC-STATS {
    description
      "XBAR EDM SKB CFL EG MISC STATS";
    leaf ecc-corr-err {
      type uint64;
      description
        "ECC CORR ERR";
    }
    leaf ecc-uncorr-err {
      type uint64;
      description
        "ECC UNCORR ERR";
    }
    leaf ecc-raw-corr-err {
      type uint64;
      description
        "ECC RAW CORR ERR";
    }
    leaf ecc-raw-uncorr-err {
      type uint64;
      description
        "ECC RAW UNCORR ERR";
    }
    leaf eg-total-rate {
      type uint64;
      description
        "Egress CFL Total Rate";
    }
  }

  grouping XBAR-EDM-SKB-CFL-EG-MC-STATS {
    description
      "XBAR EDM SKB CFL EG MC STATS";
    leaf pkts-truncated {
      type uint64;
      description
        "PKTS TRUNCATED";
    }
    leaf pkts-from-ob-to-port {
      type uint64;
      description
        "PKTS FROM OB TO PORT";
    }
    leaf eg-mc-rate {
      type uint64;
      description
        "Egress CFL Multicast Rate";
    }
  }

  grouping XBAR-EDM-SKB-CFL-EG-UC-STATS {
    description
      "XBAR EDM SKB CFL EG UC STATS";
    leaf pkts-truncated {
      type uint64;
      description
        "PKTS TRUNCATED";
    }
    leaf pkts-from-ob-to-port {
      type uint64;
      description
        "PKTS FROM OB TO PORT";
    }
    leaf eg-uc-rate {
      type uint64;
      description
        "Egress CFL Unicast Rate";
    }
  }

  grouping XBAR-EDM-SKB-CFL-EG-STATS {
    description
      "XBAR EDM SKB CFL EG STATS";
    container cfl-uc-stats {
      description
        "Egress CFL Unicast Stats";
      uses XBAR-EDM-SKB-CFL-EG-UC-STATS;
    }
    container cfl-mc-stats {
      description
        "Egress CFL Multicast Stats";
      uses XBAR-EDM-SKB-CFL-EG-MC-STATS;
    }
    container cfl-misc-stats {
      description
        "Egress CFL Miscellaneous Stats";
      uses XBAR-EDM-SKB-CFL-EG-MISC-STATS;
    }
  }

  grouping XBAR-EDM-SKB-OBU-MC-STATS {
    description
      "XBAR EDM SKB OBU MC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping XBAR-EDM-SKB-OBU-UC-STATS {
    description
      "XBAR EDM SKB OBU UC STATS";
    leaf pktin {
      type uint64;
      description
        "PKTIN";
    }
    leaf pktout {
      type uint64;
      description
        "PKTOUT";
    }
    leaf bytein {
      type uint64;
      description
        "BYTEIN";
    }
    leaf byteout {
      type uint64;
      description
        "BYTEOUT";
    }
    leaf pkttrunc {
      type uint64;
      description
        "PKTTRUNC";
    }
  }

  grouping XBAR-EDM-SKB-OBU-STATS {
    description
      "XBAR EDM SKB OBU STATS";
    list data-queque {
      max-elements 24;
      description
        "Output Buffer Data Queue Queue Count";
      leaf entry {
        type uint32;
        description
          "Output Buffer Data Queue Queue Count";
      }
    }
  }

  grouping XBAR-EDM-SKB-EG-STATS {
    description
      "XBAR EDM SKB EG STATS";
    container obu-stats {
      description
        "Output Buffer Stats";
      uses XBAR-EDM-SKB-OBU-STATS;
    }
    container obu-uc-stats {
      description
        "Output Buffer UC Stats";
      uses XBAR-EDM-SKB-OBU-UC-STATS;
    }
    container obu-mc-stats {
      description
        "Output Buffer MC Stats";
      uses XBAR-EDM-SKB-OBU-MC-STATS;
    }
    container cfl-stats {
      description
        "Egress Common Fabric Link Stats";
      uses XBAR-EDM-SKB-CFL-EG-STATS;
    }
  }

  grouping XBAR-EDM-SKB-CFL-IN-MISC-STATS {
    description
      "XBAR EDM SKB CFL IN MISC STATS";
    leaf crc-stomp {
      type uint64;
      description
        "CRC STOMP";
    }
    leaf crc-new-err {
      type uint64;
      description
        "CRC NEW ERR";
    }
    leaf in-total-rate {
      type uint64;
      description
        "Ingress CFL Total Rate";
    }
  }

  grouping XBAR-EDM-SKB-CFL-IN-MC-STATS {
    description
      "XBAR EDM SKB CFL IN MC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-mc-rate {
      type uint64;
      description
        "Ingress CFL Multicast Rate";
    }
  }

  grouping XBAR-EDM-SKB-CFL-IN-UC-STATS {
    description
      "XBAR EDM SKB CFL IN UC STATS";
    leaf crc-match-pattern {
      type uint64;
      description
        "CRC MATCH PATTERN";
    }
    leaf pkts-rcvd {
      type uint64;
      description
        "PKTS RCVD";
    }
    leaf packed-pkts-rcvd {
      type uint64;
      description
        "PACKED PKTS RCVD";
    }
    leaf pkts-flushed {
      type uint64;
      description
        "PKTS FLUSHED";
    }
    leaf runt-pkts-drop-ped {
      type uint64;
      description
        "RUNT PKTS DROPPED";
    }
    leaf small-pkts-drop-ped {
      type uint64;
      description
        "SMALL PKTS DROPPED";
    }
    leaf pkts-to-ib-from-port {
      type uint64;
      description
        "PKTS TO IB FROM PORT";
    }
    leaf in-uc-rate {
      type uint64;
      description
        "Ingress CFL Unicast Rate";
    }
  }

  grouping XBAR-EDM-SKB-CFL-IN-STATS {
    description
      "XBAR EDM SKB CFL IN STATS";
    container cfl-uc-stats {
      description
        "Ingress CFL Unicast Stats";
      uses XBAR-EDM-SKB-CFL-IN-UC-STATS;
    }
    container cfl-mc-stats {
      description
        "Ingress CFL Multicast Stats";
      uses XBAR-EDM-SKB-CFL-IN-MC-STATS;
    }
    container cfl-misc-stats {
      description
        "Ingress CFL Miscellaneous Stats";
      uses XBAR-EDM-SKB-CFL-IN-MISC-STATS;
    }
  }

  grouping XBAR-EDM-SKB-IBF-MC-STATS {
    description
      "XBAR EDM SKB IBF MC STATS";
    leaf pktcnt {
      type uint64;
      description
        "PKTCNT";
    }
    leaf pktoutcnt {
      type uint64;
      description
        "PKTOUTCNT";
    }
    leaf pkthi-copy-sup-event {
      type uint64;
      description
        "PKTHICOPYSUPEVENT";
    }
    leaf pktlo-copy-sup-event {
      type uint64;
      description
        "PKTLOCOPYSUPEVENT";
    }
    leaf pkt-input-err-drop {
      type uint64;
      description
        "PKTINPUTERRDROP";
    }
    leaf pktfgid-addr-err-drop {
      type uint64;
      description
        "PKTFGIDADDRERRDROP";
    }
    leaf pktfgidlkuperr-drop {
      type uint64;
      description
        "PKTFGIDLKUPERRDROP";
    }
    leaf pkt-null-poe-drop {
      type uint64;
      description
        "PKTNULLPOEDROP";
    }
    leaf pkt-copy-sup-drop {
      type uint64;
      description
        "PKTCOPYSUPDROP";
    }
    leaf pkt-disp-oe-drop {
      type uint64;
      description
        "PKTDISPOEDROP";
    }
    leaf pktto-drop-cnt {
      type uint64;
      description
        "PKTTODROPCNT";
    }
  }

  grouping XBAR-EDM-SKB-IBB-MC-STATS {
    description
      "XBAR EDM SKB IBB MC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhehitail-drop {
      type uint64;
      description
        "DHEHITAILDROP";
    }
    leaf dhelotail-drop {
      type uint64;
      description
        "DHELOTAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping XBAR-EDM-SKB-IBF-UC-STATS {
    description
      "XBAR EDM SKB IBF UC STATS";
    leaf pktcnt {
      type uint64;
      description
        "PKTCNT";
    }
    leaf pktoutp0cnt {
      type uint64;
      description
        "PKTOUTP0CNT";
    }
    leaf pktoutp1cnt {
      type uint64;
      description
        "PKTOUTP1CNT";
    }
    leaf pkt-input-err-drop {
      type uint64;
      description
        "PKTINPUTERRDROP";
    }
    leaf pkthwerr-drop {
      type uint64;
      description
        "PKTHWERRDROP";
    }
    leaf pkt-null-poe-drop {
      type uint64;
      description
        "PKTNULLPOEDROP";
    }
    leaf pkt-disp-oe-drop {
      type uint64;
      description
        "PKTDISPOEDROP";
    }
  }

  grouping XBAR-EDM-SKB-IBB-UC-STATS {
    description
      "XBAR EDM SKB IBB UC STATS";
    leaf ipc-data-tot {
      type uint64;
      description
        "IPCDATATOT";
    }
    leaf ipc-data-totsz {
      type uint64;
      description
        "IPCDATATOTSZ";
    }
    leaf ipcrunt {
      type uint64;
      description
        "IPCRUNT";
    }
    leaf ipcgiant {
      type uint64;
      description
        "IPCGIANT";
    }
    leaf ipc-data-err {
      type uint64;
      description
        "IPCDATAERR";
    }
    leaf ipclinkerr {
      type uint64;
      description
        "IPCLINKERR";
    }
    leaf ipcptcerr {
      type uint64;
      description
        "IPCPTCERR";
    }
    leaf ipcpkt-drop {
      type uint64;
      description
        "IPCPKTDROP";
    }
    leaf ipcdes-drop {
      type uint64;
      description
        "IPCDESDROP";
    }
    leaf dhetail-drop {
      type uint64;
      description
        "DHETAILDROP";
    }
    leaf ibmoutsop {
      type uint64;
      description
        "IBMOUTSOP";
    }
    leaf ibmouteop {
      type uint64;
      description
        "IBMOUTEOP";
    }
    leaf ibmoutbyte {
      type uint64;
      description
        "IBMOUTBYTE";
    }
    leaf icmenq {
      type uint64;
      description
        "ICMENQ";
    }
    leaf icmdeq {
      type uint64;
      description
        "ICMDEQ";
    }
    leaf icmfcxoff {
      type uint64;
      description
        "ICMFCXOFF";
    }
    leaf icmfcxon {
      type uint64;
      description
        "ICMFCXON";
    }
  }

  grouping XBAR-EDM-SKB-IBF-STATS {
    description
      "XBAR EDM SKB IBF STATS";
    leaf unused {
      type uint64;
      description
        "Ingress Unused Counter";
    }
  }

  grouping XBAR-EDM-SKB-IBB-STATS {
    description
      "XBAR EDM SKB IBB STATS";
    leaf ipcicmtail-drop {
      type uint64;
      description
        "IPCICMTAILDROP";
    }
    leaf dhe-diag-pkt {
      type uint64;
      description
        "DHEDIAGPKT";
    }
    leaf ibmdnouttot {
      type uint64;
      description
        "IBMDNOUTTOT";
    }
    leaf icmdnenq {
      type uint64;
      description
        "ICMDNENQ";
    }
    leaf icmdndeq {
      type uint64;
      description
        "ICMDNDEQ";
    }
    leaf ibmcsrccouttot {
      type uint64;
      description
        "IBMCSRCCOUTTOT";
    }
  }

  grouping XBAR-EDM-SKB-IN-STATS {
    description
      "XBAR EDM SKB IN STATS";
    container ibb-stats {
      description
        "Input Buffer Block Stats";
      uses XBAR-EDM-SKB-IBB-STATS;
    }
    container ibf-stats {
      description
        "Input Forwarding Block Stats";
      uses XBAR-EDM-SKB-IBF-STATS;
    }
    container ibb-uc-stats {
      description
        "Input Buffer Block UC Stats";
      uses XBAR-EDM-SKB-IBB-UC-STATS;
    }
    container ibf-uc-stats {
      description
        "Input Forwarding Block UC Stats";
      uses XBAR-EDM-SKB-IBF-UC-STATS;
    }
    container ibb-mc-stats {
      description
        "Input Buffer Block MC Stats";
      uses XBAR-EDM-SKB-IBB-MC-STATS;
    }
    container ibf-mc-stats {
      description
        "Input Forwarding Block MC Stats";
      uses XBAR-EDM-SKB-IBF-MC-STATS;
    }
    container cfl-stats {
      description
        "Ingress Common Fabric Link Stats";
      uses XBAR-EDM-SKB-CFL-IN-STATS;
    }
  }

  grouping XBAR-EDM-SKB-PORT-STATS {
    description
      "XBAR EDM SKB PORT STATS";
    container in-stats {
      description
        "Ingress Stats";
      uses XBAR-EDM-SKB-IN-STATS;
    }
    container eg-stats {
      description
        "Egress Stats";
      uses XBAR-EDM-SKB-EG-STATS;
    }
    container xps-stats {
      description
        "Crosspoint Scheduler Stats";
      uses XBAR-EDM-SKB-XPS-STATS;
    }
    leaf internal-err-cnt {
      type uint64;
      description
        "Internal Error Count";
    }
  }
}

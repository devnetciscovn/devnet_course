module Cisco-IOS-XR-sysadmin-sdr-mgr {
  // Generated by yanger -t ncs
  tailf:mount-id "cisco-iosxr-nc-7.3:cisco-iosxr-nc-7.3";
  tailf:ncs-device-type "netconf";

  namespace "http://www.cisco.com/ns/yang/Cisco-IOS-XR-sysadmin-sdr-mgr";
  prefix calvados_sdr;

  import tailf-common {
    prefix tailf;
  }
  import ietf-inet-types {
    prefix inet;
  }
  import Cisco-IOS-XR-sysadmin-show-trace {
    prefix show_trace;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the SDR-SM support config for SDR

     Copyright (c) 2011-2020 by Cisco Systems, Inc.
     All rights reserved.";

  revision 2020-08-20 {
    description
      "Supporting 48 LCs or DCP";
    semver:module-version "2.0.0";
  }
  revision 2019-06-12 {
    description
      "Fixed canonical order error for keywords key/type/mandantory";
    semver:module-version "1.0.0";
  }
  revision 2019-04-15 {
    description
      "Establish semantic version baseline.";
  }
  revision 2019-04-12 {
    description
      "Added tailf:cli-full-command for issu and pairing-mode config";
  }
  revision 2018-10-22 {
    description
      "Removed choice for action re_pair";
  }
  revision 2018-10-15 {
    description
      "Removed confirm txt for reload/shut/start actions";
  }
  revision 2018-05-15 {
    description
      "Added node-type leaf in sdr-operation container";
  }
  revision 2018-04-09 {
    description
      "Required changes for ConfD 6.4.5";
  }
  revision 2018-03-05 {
    description
      "Added slice option in sdr-config";
  }
  revision 2018-02-20 {
    description
      "Added sdr-operation container to display SDR operation progress";
  }
  revision 2018-02-02 {
    description
      "Added cli-suppress-table for container detail and corrected alignment for container reboot-hist";
  }
  revision 2017-07-22 {
    description
      "Updated location pattern to include Compute Cards";
  }
  revision 2017-06-20 {
    description
      "Changed the type of rp leaves in container pairing2 to string";
  }
  revision 2017-06-16 {
    description
      "Added leaf issu to provide an option to disable SDR ISSU";
  }
  revision 2017-06-09 {
    description
      "SDR config will now take a list of initial images";
  }
  revision 2017-04-12 {
    description
      "Changed the namespace and module name";
  }
  revision 2016-10-12 {
    description
      "Unhide commands and configs. Moved to advanced-grp";
  }
  revision 2016-05-12 {
    description
      "Initial Version";
  }

  typedef ncs_template_Location {
    type string;
    description
      "A system location in Rack/Slot/Instance";
  }

  typedef ncs_template_RPLocation {
    type string;
    description
      "A system location in Rack/Slot/Instance";
  }

  typedef ncs_template_VMLocation {
    type string;
    description
      "A system location in Rack/Slot/Instance";
  }

  typedef ncs_template_VMLocationall {
    type string;
    description
      "A system location in Rack/Slot/Instance";
  }

  typedef ncs_template_CardType {
    type string;
    description
      "The List of supported Card Types";
  }

  typedef ncs_template_vm_reload_reason {
    type string;
    description
      "The List of vm reload reasons";
  }

  typedef ncs_rpc_notif_Location {
    type string {
      pattern '((0?[0-9]|[1-3][0-9]|4[0-7]|([bB]|[dD])\d)/(([rR][pP]|[lL][cC]|[cC][bB])?\d{1,2}))(/[cC][pP][uU]0)?|all';
    }
    description
      "A system location in Rack/Slot/Instance";
  }

  typedef ncs_rpc_notif_RPLocation {
    type string {
      pattern '((0?[0-9]|1[1-5]|([bB]|[dD])\d)/(([rR][pP]|[cC][bB])\d{1,2}))(/[cC][pP][uU]0)?';
    }
    description
      "A system location in Rack/Slot/Instance";
  }

  typedef ncs_rpc_notif_VMLocation {
    type string {
      pattern '((0?[0-9]|[1-3][0-9]|4[0-7]|([bB]|[dD])\d)/((([rR]([sS]){0,1}[pP])|[cC][bB])?\d{1,2})/[V][M](0?[0-9]|1[1-5]))?';
    }
    description
      "A system location in Rack/Slot/Instance";
  }

  typedef ncs_rpc_notif_VMLocationall {
    type string {
      pattern '((0?[0-9]|[1-3][0-9]|4[0-7]|([bB]|[dD])\d)/((([rR]([sS]){0,1}[pP])|[cC][bB])?\d{1,2})/[V][M](0?[0-9]|1[1-5]))?|all';
    }
    description
      "A system location in Rack/Slot/Instance";
  }

  typedef ncs_rpc_notif_CardType {
    type enumeration {
      enum "RP";
      enum "LC";
      enum "CC";
    }
    description
      "The List of supported Card Types";
  }

  typedef ncs_rpc_notif_vm_reload_reason {
    type enumeration {
      enum "CARD_OFFLINE";
      enum "CARD_SHUTDOWN";
      enum "ALL_VM_RELOAD";
      enum "VM_REQUESTED_GRACEFUL_RELOAD";
      enum "VM_REQUESTED_UNGRACEFUL_RELOAD";
      enum "SDR_CLI_REQUESTED";
      enum "SDR_VCPU_VMEM_CHANGED";
      enum "SDR_HEARTBEAT_FAILURE";
      enum "FIRST_BOOT";
      enum "SMU";
      enum "REASON_UNKNOWN";
    }
    description
      "The List of vm reload reasons";
  }

  typedef live_ncs_Location {
    type string {
      pattern '((0?[0-9]|[1-3][0-9]|4[0-7]|([bB]|[dD])\d)/(([rR][pP]|[lL][cC]|[cC][bB])?\d{1,2}))(/[cC][pP][uU]0)?|all';
    }
    description
      "A system location in Rack/Slot/Instance";
  }

  typedef live_ncs_RPLocation {
    type string {
      pattern '((0?[0-9]|1[1-5]|([bB]|[dD])\d)/(([rR][pP]|[cC][bB])\d{1,2}))(/[cC][pP][uU]0)?';
    }
    description
      "A system location in Rack/Slot/Instance";
  }

  typedef live_ncs_VMLocation {
    type string {
      pattern '((0?[0-9]|[1-3][0-9]|4[0-7]|([bB]|[dD])\d)/((([rR]([sS]){0,1}[pP])|[cC][bB])?\d{1,2})/[V][M](0?[0-9]|1[1-5]))?';
    }
    description
      "A system location in Rack/Slot/Instance";
  }

  typedef live_ncs_VMLocationall {
    type string {
      pattern '((0?[0-9]|[1-3][0-9]|4[0-7]|([bB]|[dD])\d)/((([rR]([sS]){0,1}[pP])|[cC][bB])?\d{1,2})/[V][M](0?[0-9]|1[1-5]))?|all';
    }
    description
      "A system location in Rack/Slot/Instance";
  }

  typedef live_ncs_CardType {
    type enumeration {
      enum "RP";
      enum "LC";
      enum "CC";
    }
    description
      "The List of supported Card Types";
  }

  typedef live_ncs_vm_reload_reason {
    type enumeration {
      enum "CARD_OFFLINE";
      enum "CARD_SHUTDOWN";
      enum "ALL_VM_RELOAD";
      enum "VM_REQUESTED_GRACEFUL_RELOAD";
      enum "VM_REQUESTED_UNGRACEFUL_RELOAD";
      enum "SDR_CLI_REQUESTED";
      enum "SDR_VCPU_VMEM_CHANGED";
      enum "SDR_HEARTBEAT_FAILURE";
      enum "FIRST_BOOT";
      enum "SMU";
      enum "REASON_UNKNOWN";
    }
    description
      "The List of vm reload reasons";
  }

  typedef Location {
    type string {
      pattern '((0?[0-9]|[1-3][0-9]|4[0-7]|([bB]|[dD])\d)/(([rR][pP]|[lL][cC]|[cC][bB])?\d{1,2}))(/[cC][pP][uU]0)?|all';
    }
    description
      "A system location in Rack/Slot/Instance";
  }

  typedef RPLocation {
    type string {
      pattern '((0?[0-9]|1[1-5]|([bB]|[dD])\d)/(([rR][pP]|[cC][bB])\d{1,2}))(/[cC][pP][uU]0)?';
    }
    description
      "A system location in Rack/Slot/Instance";
  }

  typedef VMLocation {
    type string {
      pattern '((0?[0-9]|[1-3][0-9]|4[0-7]|([bB]|[dD])\d)/((([rR]([sS]){0,1}[pP])|[cC][bB])?\d{1,2})/[V][M](0?[0-9]|1[1-5]))?';
    }
    description
      "A system location in Rack/Slot/Instance";
  }

  typedef VMLocationall {
    type string {
      pattern '((0?[0-9]|[1-3][0-9]|4[0-7]|([bB]|[dD])\d)/((([rR]([sS]){0,1}[pP])|[cC][bB])?\d{1,2})/[V][M](0?[0-9]|1[1-5]))?|all';
    }
    description
      "A system location in Rack/Slot/Instance";
  }

  typedef CardType {
    type enumeration {
      enum "RP";
      enum "LC";
      enum "CC";
    }
    description
      "The List of supported Card Types";
  }

  typedef vm_reload_reason {
    type enumeration {
      enum "CARD_OFFLINE";
      enum "CARD_SHUTDOWN";
      enum "ALL_VM_RELOAD";
      enum "VM_REQUESTED_GRACEFUL_RELOAD";
      enum "VM_REQUESTED_UNGRACEFUL_RELOAD";
      enum "SDR_CLI_REQUESTED";
      enum "SDR_VCPU_VMEM_CHANGED";
      enum "SDR_HEARTBEAT_FAILURE";
      enum "FIRST_BOOT";
      enum "SMU";
      enum "REASON_UNKNOWN";
    }
    description
      "The List of vm reload reasons";
  }

  augment "/ncs:devices/ncs:device/ncs:config" {
    container sdr-config {
      tailf:ncs-device-type "netconf";
      tailf:display-when "not(../../ncs:module) or ../../ncs:module[ncs:name='Cisco-IOS-XR-sysadmin-sdr-mgr']";
      list sdr {
        key "name";
        description
          "Add/Edit a Secure Domain Router by name";
        leaf name {
          type string {
            pattern '[a-zA-Z0-9_-]{1,30}';
          }
          description
            "Name of the Secure Domain Router , 30 max characters";
        }
        leaf initial-image {
          type string;
          description
            "List of the initial image and packages for the Secure Domain Router.";
        }
        leaf lead_down_delta {
          type uint32;
          description
            "Amount of time between lead down to declare SDR down";
        }
        leaf pairing-mode {
          type enumeration {
            enum "intra-rack";
            enum "inter-rack";
          }
          description
            "Setting for pairing mode";
        }
        leaf issu {
          type enumeration {
            enum "disable";
          }
          description
            "ISSU flag. Once disabled, ISSU won't be performed for this SDR.";
        }
        container resources {
          description
            "Edit resources for a Secure Domain Router";
          leaf fgid {
            type uint32 {
              range "25000..524288";
            }
            description
              "Fgids for a Secure Domain Router";
          }
          leaf mgmt_ext_vlan {
            type uint32 {
              range "2..4094";
            }
            description
              "Management External VLAN for Secure Domain Router";
          }
          list card-type {
            key "type";
            leaf type {
              type CardType;
              description
                "Card Type";
            }
            leaf vm-memory {
              type uint32 {
                range "1..128";
              }
              description
                "VM Memory Size in units of [GB]";
            }
            leaf vm-cpu {
              type uint32 {
                range "1..128";
              }
              description
                "VM Number of CPUs";
            }
          }
        }
        list location {
          key "node-location";
          min-elements 1;
          max-elements 64;
          description
            "Enter list of nodes' location to add to this LR";
          leaf node-location {
            type Location;
            description
              "Enter location or all";
          }
          leaf-list slice {
            type uint8 {
              range "0 .. 4";
            }
            max-elements 4;
            description
              "Enter list of slices to add to this SDR";
          }
        }
        // NCS drop config false container 'Action'
        // NCS drop config false container detail
        // NCS drop config false container 'reboot-history'
        // NCS drop config false container nodes
        // NCS drop config false container pairing2
        list pairing {
          key "name";
          description
            "Add/Edit a RP Pairing by name";
          leaf name {
            type string {
              pattern '[a-zA-Z0-9_-]{1,64}';
            }
          }
          leaf rp1 {
            type RPLocation;
            mandatory true;
            description
              "Enter RP Node location";
          }
          leaf rp2 {
            type RPLocation;
            mandatory true;
            description
              "Enter RP Node location";
          }
        }
      }
    }
    // NCS drop config false container 'sdr-manager'
    // NCS drop config false container 'sdr-operation'
    container private-sdr {
      tailf:ncs-device-type "netconf";
      tailf:display-when "not(../../ncs:module) or ../../ncs:module[ncs:name='Cisco-IOS-XR-sysadmin-sdr-mgr']";
      list sdr-name {
        key "name";
        min-elements 0;
        max-elements 64;
        leaf name {
          type string;
        }
        leaf id {
          type uint32;
        }
        leaf lead_rack0 {
          type uint32;
        }
        leaf lead_rack1 {
          type uint32;
        }
        list pairing {
          key "num";
          min-elements 0;
          max-elements 64;
          leaf num {
            type uint32;
          }
          leaf second_exist {
            type boolean;
          }
          leaf rp1_rack {
            type uint32;
          }
          leaf rp1_slot {
            type uint32;
          }
          leaf rp2_rack {
            type uint32;
          }
          leaf rp2_slot {
            type uint32;
          }
        }
      }
    }
  }
  augment "/ncs:devices/ncs:device/ncs:live-status" {
    container sdr-config {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr {
        key "name";
        description
          "Add/Edit a Secure Domain Router by name";
        leaf name {
          type string {
            pattern '[a-zA-Z0-9_-]{1,30}';
          }
          description
            "Name of the Secure Domain Router , 30 max characters";
        }
        leaf initial-image {
          type string;
          description
            "List of the initial image and packages for the Secure Domain Router.";
        }
        leaf lead_down_delta {
          type uint32;
          description
            "Amount of time between lead down to declare SDR down";
        }
        leaf pairing-mode {
          type enumeration {
            enum "intra-rack";
            enum "inter-rack";
          }
          description
            "Setting for pairing mode";
        }
        leaf issu {
          type enumeration {
            enum "disable";
          }
          description
            "ISSU flag. Once disabled, ISSU won't be performed for this SDR.";
        }
        container resources {
          description
            "Edit resources for a Secure Domain Router";
          leaf fgid {
            type uint32 {
              range "25000..524288";
            }
            description
              "Fgids for a Secure Domain Router";
          }
          leaf mgmt_ext_vlan {
            type uint32 {
              range "2..4094";
            }
            description
              "Management External VLAN for Secure Domain Router";
          }
          list card-type {
            key "type";
            leaf type {
              type live_ncs_CardType;
              description
                "Card Type";
            }
            leaf vm-memory {
              type uint32 {
                range "1..128";
              }
              description
                "VM Memory Size in units of [GB]";
            }
            leaf vm-cpu {
              type uint32 {
                range "1..128";
              }
              description
                "VM Number of CPUs";
            }
          }
        }
        list location {
          key "node-location";
          // NCS drop min-elements statement
          // NCS drop max-elements statement
          description
            "Enter list of nodes' location to add to this LR";
          leaf node-location {
            type live_ncs_Location;
            description
              "Enter location or all";
          }
          leaf-list slice {
            type uint8 {
              range "0 .. 4";
            }
            // NCS drop max-elements statement
            description
              "Enter list of slices to add to this SDR";
          }
        }
        container Action {
          list location {
            key "node-location";
            // NCS drop min-elements statement
            // NCS drop max-elements statement
            leaf node-location {
              type live_ncs_VMLocationall;
              description
                "Enter location or all";
            }
          }
        }
        container detail {
          list location {
            key "node-location";
            // NCS drop min-elements statement
            // NCS drop max-elements statement
            leaf node-location {
              type live_ncs_VMLocation;
            }
            leaf sdr-id {
              type uint32;
            }
            leaf ip-addr {
              type inet:ip-address;
              description
                "IP address of VM";
            }
            leaf mac-address {
              type string;
              description
                "MAC address of VM";
            }
            leaf boot_part {
              type string;
            }
            leaf data_part {
              type string;
            }
            leaf big_disk {
              type string;
            }
            leaf vm_id {
              type uint32;
            }
            leaf vmcpu {
              type uint32;
            }
            leaf vmmemory {
              type uint32;
            }
            leaf card-type {
              type string;
            }
            leaf card_serial {
              type string;
            }
            leaf rack-type {
              type string;
            }
            leaf-list slice {
              type union {
                type uint8;
                type string;
              }
              description
                "Slice numbers if configured";
            }
            leaf chassis_serial {
              type string;
            }
            leaf hw_version {
              type string;
            }
            leaf mgmt_ext_vlan {
              type string;
            }
            leaf state {
              type string;
              description
                "State of VM";
            }
            leaf start-time {
              type string;
            }
            leaf reboot_count {
              type uint32;
              description
                "Number of times rebooted since first boot";
            }
            leaf rh_count {
              type uint32;
              description
                "Number of times rebooted since lasr card reload";
            }
            list reboot_hist1 {
              key "count";
              leaf count {
                type uint32;
              }
              leaf Time {
                type string;
              }
              leaf Reason {
                type string;
                description
                  "Reason for reload";
              }
            }
          }
        }
        container reboot-history {

          grouping rebhist {
            list location {
              key "node-location";
              // NCS drop min-elements statement
              // NCS drop max-elements statement
              leaf node-location {
                type live_ncs_VMLocation;
              }
              leaf reboot_count {
                type uint32;
                description
                  "Number of times rebooted since first boot";
              }
              leaf rh_count {
                type uint32;
                description
                  "Number of times rebooted since last card reload";
              }
              list reboot_hist2 {
                key "count";
                leaf count {
                  type uint32;
                }
                leaf Time {
                  type string;
                }
                leaf Reason {
                  type string;
                  description
                    "Reason for reload";
                }
              }
            }
          }
          container reverse {
            uses rebhist;
          }
          container default-disp {
            uses rebhist;
          }
        }
        container nodes {
          list location {
            key "node-location";
            // NCS drop min-elements statement
            // NCS drop max-elements statement
            leaf node-location {
              type live_ncs_VMLocation;
            }
            leaf sdr-id {
              type uint32;
            }
            leaf ip-addr {
              type inet:ip-address;
              description
                "IP address of VM";
            }
            leaf mac-address {
              type string;
              description
                "MAC address of VM";
            }
            leaf state {
              type string;
              description
                "State of VM";
            }
            leaf start-time {
              type string;
            }
            leaf reload_reason {
              type string;
              description
                "Reason for last reload";
            }
            leaf reboot_count {
              type uint32;
              description
                "Number of times rebooted since first boot";
            }
            leaf rh_count {
              type uint32;
              description
                "Number of times rebooted since first boot";
            }
          }
        }
        container pairing2 {
          leaf pairing-mode {
            type string;
            description
              "Mode of Pairing";
          }
          container sdrlead {
            leaf rp1 {
              type string;
            }
            leaf rp2 {
              type string;
            }
          }
          list pairing {
            key "name";
            // NCS drop min-elements statement
            // NCS drop max-elements statement
            leaf name {
              type string;
            }
            leaf rp1 {
              type string;
            }
            leaf rp2 {
              type string;
            }
          }
        }
        list pairing {
          key "name";
          description
            "Add/Edit a RP Pairing by name";
          leaf name {
            type string {
              pattern '[a-zA-Z0-9_-]{1,64}';
            }
          }
          leaf rp1 {
            type live_ncs_RPLocation;
            // NCS drop mandatory statement
            description
              "Enter RP Node location";
          }
          leaf rp2 {
            type live_ncs_RPLocation;
            // NCS drop mandatory statement
            description
              "Enter RP Node location";
          }
        }
      }
    }
    container sdr-manager {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      container sdr_mgr {
        uses show_trace:live_ncs_traceable;
      }
    }
    container sdr-operation {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr {
        key "name";
        description
          "SDR";
        leaf name {
          type string {
            pattern '[a-zA-Z0-9_-]{1,30}';
          }
          description
            "Name of the Secure Domain Router, 30 max characters";
        }
        container nodes {
          list location {
            key "node-location node-type";
            // NCS drop min-elements statement
            // NCS drop max-elements statement
            leaf node-location {
              type string;
            }
            leaf node-type {
              type uint32;
            }
            leaf progress {
              type string;
              description
                "Progress of Operation";
            }
            leaf state {
              type string;
              description
                "State of Operation";
            }
          }
        }
      }
    }
    container private-sdr {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr-name {
        key "name";
        // NCS drop min-elements statement
        // NCS drop max-elements statement
        leaf name {
          type string;
        }
        leaf id {
          type uint32;
        }
        leaf lead_rack0 {
          type uint32;
        }
        leaf lead_rack1 {
          type uint32;
        }
        list pairing {
          key "num";
          // NCS drop min-elements statement
          // NCS drop max-elements statement
          leaf num {
            type uint32;
          }
          leaf second_exist {
            type boolean;
          }
          leaf rp1_rack {
            type uint32;
          }
          leaf rp1_slot {
            type uint32;
          }
          leaf rp2_rack {
            type uint32;
          }
          leaf rp2_slot {
            type uint32;
          }
        }
      }
    }
  }
  augment "/ncs:devices/ncs:template/ncs:ned-id/ncs:config" {
    container sdr-config {
      list sdr {
        // NCS patched for predictable order
        ordered-by user;
        key "name";
        description
          "Add/Edit a Secure Domain Router by name";
        leaf name {
          type string;
          description
            "Name of the Secure Domain Router , 30 max characters";
        }
        leaf initial-image {
          type string;
          description
            "List of the initial image and packages for the Secure Domain Router.";
        }
        leaf lead_down_delta {
          type string;
          description
            "Amount of time between lead down to declare SDR down";
        }
        leaf pairing-mode {
          type string;
          description
            "Setting for pairing mode";
        }
        leaf issu {
          type string;
          description
            "ISSU flag. Once disabled, ISSU won't be performed for this SDR.";
        }
        container resources {
          description
            "Edit resources for a Secure Domain Router";
          leaf fgid {
            type string;
            description
              "Fgids for a Secure Domain Router";
          }
          leaf mgmt_ext_vlan {
            type string;
            description
              "Management External VLAN for Secure Domain Router";
          }
          list card-type {
            // NCS patched for predictable order
            ordered-by user;
            key "type";
            leaf type {
              type ncs_template_CardType;
              description
                "Card Type";
            }
            leaf vm-memory {
              type string;
              description
                "VM Memory Size in units of [GB]";
            }
            leaf vm-cpu {
              type string;
              description
                "VM Number of CPUs";
            }
          }
        }
        list location {
          // NCS patched for predictable order
          ordered-by user;
          key "node-location";
          // NCS drop min-elements statement
          // NCS drop max-elements statement
          description
            "Enter list of nodes' location to add to this LR";
          leaf node-location {
            type ncs_template_Location;
            description
              "Enter location or all";
          }
          leaf-list slice {
            // NCS patched for predictable order
            ordered-by user;
            type string;
            // NCS drop max-elements statement
            description
              "Enter list of slices to add to this SDR";
          }
        }
        // NCS drop config false container 'Action'
        // NCS drop config false container detail
        // NCS drop config false container 'reboot-history'
        // NCS drop config false container nodes
        // NCS drop config false container pairing2
        list pairing {
          // NCS patched for predictable order
          ordered-by user;
          key "name";
          description
            "Add/Edit a RP Pairing by name";
          leaf name {
            type string;
          }
          leaf rp1 {
            type ncs_template_RPLocation;
            // NCS drop mandatory statement
            description
              "Enter RP Node location";
          }
          leaf rp2 {
            type ncs_template_RPLocation;
            // NCS drop mandatory statement
            description
              "Enter RP Node location";
          }
        }
      }
    }
    // NCS drop config false container 'sdr-manager'
    // NCS drop config false container 'sdr-operation'
    container private-sdr {
      list sdr-name {
        // NCS patched for predictable order
        ordered-by user;
        key "name";
        // NCS drop min-elements statement
        // NCS drop max-elements statement
        leaf name {
          type string;
        }
        leaf id {
          type string;
        }
        leaf lead_rack0 {
          type string;
        }
        leaf lead_rack1 {
          type string;
        }
        list pairing {
          // NCS patched for predictable order
          ordered-by user;
          key "num";
          // NCS drop min-elements statement
          // NCS drop max-elements statement
          leaf num {
            type string;
          }
          leaf second_exist {
            type string;
          }
          leaf rp1_rack {
            type string;
          }
          leaf rp1_slot {
            type string;
          }
          leaf rp2_rack {
            type string;
          }
          leaf rp2_slot {
            type string;
          }
        }
      }
    }
  }
}

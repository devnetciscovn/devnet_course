module Cisco-IOS-XR-ipv4-pim-oper {
  // Generated by yanger -t ncs
  tailf:mount-id "cisco-iosxr-nc-7.3:cisco-iosxr-nc-7.3";
  tailf:ncs-device-type "netconf";

  namespace "http://cisco.com/ns/yang/Cisco-IOS-XR-ipv4-pim-oper";
  prefix ipv4-pim-oper;

  import ietf-inet-types {
    prefix inet;
  }
  import Cisco-IOS-XR-types {
    prefix xr;
  }
  import cisco-semver {
    prefix semver;
  }
  include Cisco-IOS-XR-ipv4-pim-oper-sub2 {
    revision-date 2020-10-11;
  }
  include Cisco-IOS-XR-ipv4-pim-oper-sub1 {
    revision-date 2020-10-11;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-pim package operational data.

     This model is deprecated and is replaced by
     Cisco-IOS-XR-pim-oper.yang which will provide the
     compatible functionalities.

     This module contains definitions
     for the following management objects:
       pim-ma: PIM MA operational data
       pim: PIM operational data
       ipv6-pim: IPv6 PIM operational data
       pim6-ma: PIM6 MA operational data

     Copyright (c) 2013-2020 by Cisco Systems, Inc.
     All rights reserved.";

  revision 2020-10-11 {
    description
      "Changes to IOS-XR PIM oper";
    semver:module-version "2.1.0";
  }
  revision 2019-10-31 {
    description
      "Changes to IOS-XR PIM oper
       2019-08-27
       Providing pim information";
    semver:module-version "2.0.0";
  }
  revision 2019-04-05 {
    description
      "Establish semantic version baseline.";
    semver:module-version "1.0.0";
  }
  revision 2017-09-07 {
    description
      "Fixed type translation error.";
  }
  revision 2017-06-26 {
    description
      "Change identifiers to be more readable.";
  }
  revision 2017-05-27 {
    description
      "Removed deprecated leaves under traffic-counters. Added missing leaves under context. Removed checkpoint-statistics container because the corresponding CLI command requires cisco-support permissions.";
  }
  revision 2015-11-09 {
    description
      "IOS XR 6.0 revision.";
  }

  typedef ncs_template_Pim-topology-interface-flag {
    type string;
    description
      "Pim topology interface flag";
  }

  typedef ncs_template_Pim-safi {
    type string;
    description
      "Pim safi";
  }

  typedef ncs_template_Pim-client {
    type string;
    description
      "Pim client";
  }

  typedef ncs_template_Pim-topology-entry-flag {
    type string;
    description
      "Pim topology entry flag";
  }

  typedef ncs_template_Pim-protocol {
    type string;
    description
      "Pim protocol";
  }

  typedef ncs_rpc_notif_Pim-topology-interface-flag {
    type enumeration {
      enum "lh" {
        value 0;
        description
          "LH";
      }
      enum "ld" {
        value 1;
        description
          "LD";
      }
      enum "li" {
        value 2;
        description
          "LI";
      }
      enum "ii" {
        value 3;
        description
          "II";
      }
      enum "id" {
        value 4;
        description
          "ID";
      }
      enum "as" {
        value 5;
        description
          "AS";
      }
      enum "ab" {
        value 6;
        description
          "AB";
      }
      enum "ex" {
        value 7;
        description
          "EX";
      }
    }
    description
      "Pim topology interface flag";
  }

  typedef ncs_rpc_notif_Pim-safi {
    type enumeration {
      enum "unicast" {
        value 1;
        description
          "SAFI unicast";
      }
      enum "multicast" {
        value 2;
        description
          "SAFI Multicast";
      }
      enum "all" {
        value 3;
        description
          "SAFI all";
      }
      enum "default" {
        value 4;
        description
          "SAFI default";
      }
    }
    description
      "Pim safi";
  }

  typedef ncs_rpc_notif_Pim-client {
    type enumeration {
      enum "none" {
        value 0;
        description
          "No Client";
      }
      enum "configured-embedded-rp" {
        value 1;
        description
          "Embedded RP from configuration";
      }
      enum "embedded" {
        value 2;
        description
          "Embedded RP learnt from the Group addr";
      }
      enum "permanent" {
        value 3;
        description
          "Permanent";
      }
      enum "auto-rp" {
        value 4;
        description
          "AutoRP";
      }
      enum "bsr" {
        value 5;
        description
          "BSR";
      }
      enum "configured" {
        value 6;
        description
          "Configured";
      }
      enum "static" {
        value 7;
        description
          "Static";
      }
    }
    description
      "Pim client";
  }

  typedef ncs_rpc_notif_Pim-topology-entry-flag {
    type enumeration {
      enum "kat" {
        value 0;
        description
          "KAT";
      }
      enum "aa" {
        value 1;
        description
          "AA";
      }
      enum "pa" {
        value 2;
        description
          "PA";
      }
      enum "ra" {
        value 3;
        description
          "RA";
      }
      enum "ia" {
        value 4;
        description
          "IA";
      }
      enum "rr" {
        value 5;
        description
          "RR";
      }
      enum "lh" {
        value 6;
        description
          "LH";
      }
      enum "dss" {
        value 7;
        description
          "DSS";
      }
      enum "dcc" {
        value 8;
        description
          "DCC";
      }
      enum "sr" {
        value 9;
        description
          "SR";
      }
      enum "e" {
        value 10;
        description
          "E";
      }
      enum "ex" {
        value 11;
        description
          "EX";
      }
      enum "ma" {
        value 12;
        description
          "MA";
      }
      enum "mt" {
        value 13;
        description
          "MT";
      }
      enum "mfa" {
        value 14;
        description
          "MFA";
      }
      enum "mfp" {
        value 15;
        description
          "MFP";
      }
      enum "mfb" {
        value 16;
        description
          "MFB";
      }
    }
    description
      "Pim topology entry flag";
  }

  typedef ncs_rpc_notif_Pim-protocol {
    type enumeration {
      enum "non-routable" {
        value 0;
        description
          "Non Routable";
      }
      enum "sparse-mode" {
        value 1;
        description
          "Sparse Mode";
      }
      enum "dense-mode" {
        value 2;
        description
          "Dense Mode";
      }
      enum "bidir" {
        value 3;
        description
          "Bidirectional Mode";
      }
      enum "ssm" {
        value 4;
        description
          "Source Specific Multicast Mode";
      }
      enum "maximum" {
        value 5;
        description
          "Maximum";
      }
      enum "any" {
        value 6;
        description
          "Any";
      }
    }
    description
      "Pim protocol";
  }

  typedef live_ncs_Pim-topology-interface-flag {
    type enumeration {
      enum "lh" {
        value 0;
        description
          "LH";
      }
      enum "ld" {
        value 1;
        description
          "LD";
      }
      enum "li" {
        value 2;
        description
          "LI";
      }
      enum "ii" {
        value 3;
        description
          "II";
      }
      enum "id" {
        value 4;
        description
          "ID";
      }
      enum "as" {
        value 5;
        description
          "AS";
      }
      enum "ab" {
        value 6;
        description
          "AB";
      }
      enum "ex" {
        value 7;
        description
          "EX";
      }
    }
    description
      "Pim topology interface flag";
  }

  typedef live_ncs_Pim-safi {
    type enumeration {
      enum "unicast" {
        value 1;
        description
          "SAFI unicast";
      }
      enum "multicast" {
        value 2;
        description
          "SAFI Multicast";
      }
      enum "all" {
        value 3;
        description
          "SAFI all";
      }
      enum "default" {
        value 4;
        description
          "SAFI default";
      }
    }
    description
      "Pim safi";
  }

  typedef live_ncs_Pim-client {
    type enumeration {
      enum "none" {
        value 0;
        description
          "No Client";
      }
      enum "configured-embedded-rp" {
        value 1;
        description
          "Embedded RP from configuration";
      }
      enum "embedded" {
        value 2;
        description
          "Embedded RP learnt from the Group addr";
      }
      enum "permanent" {
        value 3;
        description
          "Permanent";
      }
      enum "auto-rp" {
        value 4;
        description
          "AutoRP";
      }
      enum "bsr" {
        value 5;
        description
          "BSR";
      }
      enum "configured" {
        value 6;
        description
          "Configured";
      }
      enum "static" {
        value 7;
        description
          "Static";
      }
    }
    description
      "Pim client";
  }

  typedef live_ncs_Pim-topology-entry-flag {
    type enumeration {
      enum "kat" {
        value 0;
        description
          "KAT";
      }
      enum "aa" {
        value 1;
        description
          "AA";
      }
      enum "pa" {
        value 2;
        description
          "PA";
      }
      enum "ra" {
        value 3;
        description
          "RA";
      }
      enum "ia" {
        value 4;
        description
          "IA";
      }
      enum "rr" {
        value 5;
        description
          "RR";
      }
      enum "lh" {
        value 6;
        description
          "LH";
      }
      enum "dss" {
        value 7;
        description
          "DSS";
      }
      enum "dcc" {
        value 8;
        description
          "DCC";
      }
      enum "sr" {
        value 9;
        description
          "SR";
      }
      enum "e" {
        value 10;
        description
          "E";
      }
      enum "ex" {
        value 11;
        description
          "EX";
      }
      enum "ma" {
        value 12;
        description
          "MA";
      }
      enum "mt" {
        value 13;
        description
          "MT";
      }
      enum "mfa" {
        value 14;
        description
          "MFA";
      }
      enum "mfp" {
        value 15;
        description
          "MFP";
      }
      enum "mfb" {
        value 16;
        description
          "MFB";
      }
    }
    description
      "Pim topology entry flag";
  }

  typedef live_ncs_Pim-protocol {
    type enumeration {
      enum "non-routable" {
        value 0;
        description
          "Non Routable";
      }
      enum "sparse-mode" {
        value 1;
        description
          "Sparse Mode";
      }
      enum "dense-mode" {
        value 2;
        description
          "Dense Mode";
      }
      enum "bidir" {
        value 3;
        description
          "Bidirectional Mode";
      }
      enum "ssm" {
        value 4;
        description
          "Source Specific Multicast Mode";
      }
      enum "maximum" {
        value 5;
        description
          "Maximum";
      }
      enum "any" {
        value 6;
        description
          "Any";
      }
    }
    description
      "Pim protocol";
  }

  typedef Pim-topology-interface-flag {
    type enumeration {
      enum "lh" {
        value 0;
        description
          "LH";
      }
      enum "ld" {
        value 1;
        description
          "LD";
      }
      enum "li" {
        value 2;
        description
          "LI";
      }
      enum "ii" {
        value 3;
        description
          "II";
      }
      enum "id" {
        value 4;
        description
          "ID";
      }
      enum "as" {
        value 5;
        description
          "AS";
      }
      enum "ab" {
        value 6;
        description
          "AB";
      }
      enum "ex" {
        value 7;
        description
          "EX";
      }
    }
    description
      "Pim topology interface flag";
  }

  typedef Pim-safi {
    type enumeration {
      enum "unicast" {
        value 1;
        description
          "SAFI unicast";
      }
      enum "multicast" {
        value 2;
        description
          "SAFI Multicast";
      }
      enum "all" {
        value 3;
        description
          "SAFI all";
      }
      enum "default" {
        value 4;
        description
          "SAFI default";
      }
    }
    description
      "Pim safi";
  }

  typedef Pim-client {
    type enumeration {
      enum "none" {
        value 0;
        description
          "No Client";
      }
      enum "configured-embedded-rp" {
        value 1;
        description
          "Embedded RP from configuration";
      }
      enum "embedded" {
        value 2;
        description
          "Embedded RP learnt from the Group addr";
      }
      enum "permanent" {
        value 3;
        description
          "Permanent";
      }
      enum "auto-rp" {
        value 4;
        description
          "AutoRP";
      }
      enum "bsr" {
        value 5;
        description
          "BSR";
      }
      enum "configured" {
        value 6;
        description
          "Configured";
      }
      enum "static" {
        value 7;
        description
          "Static";
      }
    }
    description
      "Pim client";
  }

  typedef Pim-topology-entry-flag {
    type enumeration {
      enum "kat" {
        value 0;
        description
          "KAT";
      }
      enum "aa" {
        value 1;
        description
          "AA";
      }
      enum "pa" {
        value 2;
        description
          "PA";
      }
      enum "ra" {
        value 3;
        description
          "RA";
      }
      enum "ia" {
        value 4;
        description
          "IA";
      }
      enum "rr" {
        value 5;
        description
          "RR";
      }
      enum "lh" {
        value 6;
        description
          "LH";
      }
      enum "dss" {
        value 7;
        description
          "DSS";
      }
      enum "dcc" {
        value 8;
        description
          "DCC";
      }
      enum "sr" {
        value 9;
        description
          "SR";
      }
      enum "e" {
        value 10;
        description
          "E";
      }
      enum "ex" {
        value 11;
        description
          "EX";
      }
      enum "ma" {
        value 12;
        description
          "MA";
      }
      enum "mt" {
        value 13;
        description
          "MT";
      }
      enum "mfa" {
        value 14;
        description
          "MFA";
      }
      enum "mfp" {
        value 15;
        description
          "MFP";
      }
      enum "mfb" {
        value 16;
        description
          "MFB";
      }
    }
    description
      "Pim topology entry flag";
  }

  typedef Pim-protocol {
    type enumeration {
      enum "non-routable" {
        value 0;
        description
          "Non Routable";
      }
      enum "sparse-mode" {
        value 1;
        description
          "Sparse Mode";
      }
      enum "dense-mode" {
        value 2;
        description
          "Dense Mode";
      }
      enum "bidir" {
        value 3;
        description
          "Bidirectional Mode";
      }
      enum "ssm" {
        value 4;
        description
          "Source Specific Multicast Mode";
      }
      enum "maximum" {
        value 5;
        description
          "Maximum";
      }
      enum "any" {
        value 6;
        description
          "Any";
      }
    }
    description
      "Pim protocol";
  }

  grouping ncs_template_ROUTE-POLICY {
    description
      "Common node of vrf, default-context";
    container route-policy {
      description
        "PIM route policy";
      container route-policy-statistics {
        description
          "PIM route policy statistics";
        uses ncs_template_PIM-RPF-POLICY-STATS-BAG;
      }
    }
  }

  grouping ncs_template_GROUP-MAP-SOURCE-TABLE {
    description
      "Common node of vrf, default-context";
    container group-map-sources {
      description
        "PIM group-mapping with source information";
      list group-map-source {
        // NCS patched for predictable order
        ordered-by user;
        key "prefix prefix-length client protocol rp-address priority";
        description
          "PIM Group Mapping Entry with source information";
        leaf prefix {
          type string;
          description
            "Prefix";
        }
        leaf prefix-length {
          type string;
          description
            "Prefix length";
        }
        leaf client {
          type ncs_template_Pim-client;
          description
            "Client";
        }
        leaf protocol {
          type ncs_template_Pim-protocol;
          description
            "Protocol";
        }
        leaf rp-address {
          type string;
          description
            "RP address";
        }
        leaf priority {
          type string;
          description
            "RP Priority";
        }
        uses ncs_template_PIM-GRP-MAP-INFOSRC-BAG;
      }
    }
  }

  grouping ncs_template_BIDIR-DF-STATE-TABLE {
    description
      "Common node of vrf, default-context";
    container bidir-df-states {
      description
        "Bidirectional PIM DF election state table";
      list bidir-df-state {
        // NCS patched for predictable order
        ordered-by user;
        key "rp-address interface-name";
        description
          "Bidirectional PIM DF Election Table Entry";
        leaf rp-address {
          type string;
          description
            "RP address";
        }
        leaf interface-name {
          type xr:ncs_template_Interface-name;
          description
            "Interface name";
        }
        uses ncs_template_PIM-BIDIR-DF-STATE-BAG;
      }
    }
  }

  grouping ncs_template_MIB-DATABASE-TABLE {
    description
      "Common node of vrf, default-context";
    container mib-databases {
      description
        "PIM group database for mroute mibs table";
      list mib-database {
        // NCS patched for predictable order
        ordered-by user;
        key "source-address group-address source-netmask";
        description
          "PIM multicast static route information";
        leaf source-address {
          type string;
          description
            "Multicast static route source address";
        }
        leaf group-address {
          type string;
          description
            "Multicast satic route group address";
        }
        leaf source-netmask {
          type string;
          description
            "Source mask";
        }
        uses ncs_template_PIM-MROUTE-BAG;
      }
    }
  }

  grouping ncs_template_TOPOLOGY-ENTRY-FLAG-ROUTE-COUNT-TABLE {
    description
      "Common node of vrf, default-context";
    container topology-entry-flag-route-counts {
      description
        "Route count for topology with entry flag set";
      list topology-entry-flag-route-count {
        // NCS patched for predictable order
        ordered-by user;
        key "entry-flag";
        description
          "Route count for topology with entry flag set";
        leaf entry-flag {
          type ncs_template_Pim-topology-entry-flag;
          description
            "entry flag";
        }
        uses ncs_template_PIM-TT-SUMM-BAG;
      }
    }
  }

  grouping ncs_template_BIDIR-DF-WINNER-TABLE {
    description
      "Common node of vrf, default-context";
    container bidir-df-winners {
      description
        "Bidirectional PIM DF election winner table";
      list bidir-df-winner {
        // NCS patched for predictable order
        ordered-by user;
        key "rp-address interface-name";
        description
          "Bidirectional PIM DF election table entry";
        leaf rp-address {
          type string;
          description
            "RP address";
        }
        leaf interface-name {
          type xr:ncs_template_Interface-name;
          description
            "Interface name";
        }
        uses ncs_template_PIM-BIDIR-DF-BAG;
      }
    }
  }

  grouping ncs_template_TABLE-CONTEXT-TABLE {
    description
      "Common node of vrf, default-context";
    container table-contexts {
      description
        "PIM table context list";
      list table-context {
        // NCS patched for predictable order
        ordered-by user;
        key "saf-name topology-name";
        description
          "PIM table context information";
        leaf saf-name {
          type ncs_template_Pim-safi;
          description
            "SAF name";
        }
        leaf topology-name {
          type xr:ncs_template_Cisco-ios-xr-string;
          description
            "Topology name";
        }
        uses ncs_template_PIM-TABLE-CTX-BAG;
      }
    }
  }

  grouping ncs_template_VRF-TABLE {
    description
      "Common node of active, standby";
    container vrfs {
      description
        "VRF Table";
      list vrf {
        // NCS patched for predictable order
        ordered-by user;
        key "vrf-name";
        description
          "VRF name";
        leaf vrf-name {
          type xr:ncs_template_Cisco-ios-xr-string;
          description
            "VRF name ";
        }
        uses ncs_template_IFRS-INTERFACE-TABLE;
        uses ncs_template_INTERFACE-STATISTICS-TABLE;
        uses ncs_template_TOPOLOGY-ROUTE-COUNT;
        uses ncs_template_JP-STATISTICS-TABLE;
        uses ncs_template_MIB-DATABASE-TABLE;
        uses ncs_template_IFRS-SUMMARY;
        uses ncs_template_RANGE-LIST-TABLE;
        uses ncs_template_BSR;
        uses ncs_template_ROUTE-POLICY;
        uses ncs_template_RPF-SUMMARY;
        uses ncs_template_IPV4-PIM-COMMON-OPER-INTERFACE-TABLE;
        uses ncs_template_NET-IO-TUNNEL-TABLE;
        uses ncs_template_BIDIR-DF-STATE-TABLE;
        uses ncs_template_TOPOLOGY-TABLE;
        uses ncs_template_TOPOLOGY-INTERFACE-FLAG-ROUTE-COUNT-TABLE;
        uses ncs_template_GROUP-MAP-SOURCE-TABLE;
        uses ncs_template_TRAFFIC-COUNTERS;
        uses ncs_template_GROUP-MAP-RPF-TABLE;
        uses ncs_template_SUMMARY;
        uses ncs_template_GRE;
        uses ncs_template_BIDIR-DF-WINNER-TABLE;
        uses ncs_template_TABLE-CONTEXT-TABLE;
        uses ncs_template_NEIGHBOR-SUMMARY-TABLE;
        uses ncs_template_CONTEXT;
        uses ncs_template_TOPOLOGY-ENTRY-FLAG-ROUTE-COUNT-TABLE;
        uses ncs_template_RPF-REDIRECT;
        uses ncs_template_TUNNEL-TABLE;
        uses ncs_template_MULTICAST-STATIC-ROUTE-TABLE;
        uses ncs_template_NEIGHBOR-TABLE;
      }
    }
  }

  grouping ncs_template_BSR {
    description
      "Common node of vrf, default-context";
    container bsr {
      description
        "PIM BSR information";
      container rp-caches {
        description
          "PIM BSR RP cache table";
        list rp-cache {
          // NCS patched for predictable order
          ordered-by user;
          key "group-prefix prefix-length";
          description
            "PIM BSR RP cache";
          leaf group-prefix {
            type string;
            description
              "Group prefix";
          }
          leaf prefix-length {
            type string;
            description
              "Prefix Length";
          }
          uses ncs_template_PIM-BSR-RP-CACHE-BAG;
        }
      }
      container candidate-rps {
        description
          "PIM candidate-RP";
        list candidate-rp {
          // NCS patched for predictable order
          ordered-by user;
          key "rp-address";
          description
            "PIM BSR candidate RP information";
          leaf rp-address {
            type string;
            description
              "Candidate-RP address";
          }
          uses ncs_template_PIM-BSR-CANDIDATE-RP-BAG;
        }
      }
      container bsr-elections {
        description
          "PIM BSR election state";
        list bsr-election {
          // NCS patched for predictable order
          ordered-by user;
          key "pim-scope";
          description
            "PIM BSR information";
          leaf pim-scope {
            type string;
            description
              "BSR information";
          }
          uses ncs_template_PIM-BSR-ELECTION-BAG;
        }
      }
    }
  }

  grouping ncs_template_NET-IO-TUNNEL-TABLE {
    description
      "Common node of vrf, default-context";
    container net-io-tunnels {
      description
        "Tunnel information that NETIO has ";
      list net-io-tunnel {
        // NCS patched for predictable order
        ordered-by user;
        key "tunnel-name";
        description
          "PIM netio tunnel information";
        leaf tunnel-name {
          type xr:ncs_template_Cisco-ios-xr-string;
          description
            "Tunnel name";
        }
        uses ncs_template_PIM-TUNNEL-INFO-BAG;
      }
    }
  }

  grouping ncs_template_RPF-SUMMARY {
    description
      "Common node of vrf, default-context";
    container rpf-summary {
      description
        "PIM RPF registration summary";
      uses ncs_template_PIM-RPF-SUMMARY-BAG;
    }
  }

  grouping ncs_template_IFRS-INTERFACE-TABLE {
    description
      "Common node of vrf, default-context";
    container ifrs-interfaces {
      description
        "PIM interfaces in forward reference store table";
      list ifrs-interface {
        // NCS patched for predictable order
        ordered-by user;
        key "interface-name";
        description
          "PIM IFRS interface information";
        leaf interface-name {
          type xr:ncs_template_Interface-name;
          description
            "Interface name";
        }
        uses ncs_template_PIM-IDB-BAG;
      }
    }
  }

  grouping ncs_template_PROCESS {
    description
      "Common node of active, standby";
    container process {
      description
        "Process";
      container nsr {
        description
          "NSR Information";
        uses ncs_template_PIM-NSR-BAG;
      }
      container summary {
        description
          "PIM Global Summary";
        uses ncs_template_PIM-SUMMARY-BAG;
      }
      container nsf {
        description
          "PIM NSF information";
        uses ncs_template_PIM-NSF-BAG;
      }
      container issu {
        description
          "ISSU Information";
        uses ncs_template_PIM-ISSU-BAG;
      }
    }
  }

  grouping ncs_template_JP-STATISTICS-TABLE {
    description
      "Common node of vrf, default-context";
    container jp-statistics {
      description
        "PIM join prune statistics table";
      list jp-statistic {
        // NCS patched for predictable order
        ordered-by user;
        key "interface-name";
        description
          "PIM Join Prune Statistics";
        leaf interface-name {
          type xr:ncs_template_Interface-name;
          description
            "Interface name";
        }
        uses ncs_template_PIM-JPSTATS-BAG;
      }
    }
  }

  grouping ncs_template_TOPOLOGY-TABLE {
    description
      "Common node of vrf, default-context";
    container topologies {
      description
        "PIM topology table";
      list topology {
        // NCS patched for predictable order
        ordered-by user;
        key "source-address group-address rpt";
        description
          "PIM topology information";
        leaf source-address {
          type string;
          description
            "Source address";
        }
        leaf group-address {
          type string;
          description
            "Group address";
        }
        leaf rpt {
          type string;
          description
            "RPT bit";
        }
        uses ncs_template_PIM-TT-ROUTE-BAG;
      }
    }
  }

  grouping ncs_template_NEIGHBOR-SUMMARY-TABLE {
    description
      "Common node of vrf, default-context";
    container neighbor-summaries {
      description
        "PIM neighbor summary table";
      list neighbor-summary {
        // NCS patched for predictable order
        ordered-by user;
        key "interface-name";
        description
          "PIM neighbor summary information";
        leaf interface-name {
          type xr:ncs_template_Interface-name;
          description
            "Interface name";
        }
        uses ncs_template_PIM-NBR-SUMM-BAG;
      }
    }
  }

  grouping ncs_template_TRAFFIC-COUNTERS {
    description
      "Common node of vrf, default-context";
    container traffic-counters {
      description
        "PIM message traffic counters";
      uses ncs_template_PIM-TRAFFIC-BAG;
    }
  }

  grouping ncs_template_TOPOLOGY-ROUTE-COUNT {
    description
      "Common node of vrf, default-context";
    container topology-route-count {
      description
        "Topology route count information from PIM
         topology table";
      uses ncs_template_PIM-TT-SUMM-BAG;
    }
  }

  grouping ncs_template_TUNNEL-TABLE {
    description
      "Common node of vrf, default-context";
    container tunnels {
      description
        "Tunnels information that PIM has";
      list tunnel {
        // NCS patched for predictable order
        ordered-by user;
        key "tunnel-name";
        description
          "PIM tunnel information";
        leaf tunnel-name {
          type xr:ncs_template_Cisco-ios-xr-string;
          description
            "Tunnel name";
        }
        uses ncs_template_PIM-TUNNEL-INFO-BAG;
      }
    }
  }

  grouping ncs_template_PIM-MA-COMMON-OPER-PIM-MA-SUMMARY-MP {
    description
      "Common node of active, standby";
    container pim-ma-summary {
      description
        "PIM MA summary";
      uses ncs_template_PIM-MA-SUMMARY;
    }
  }

  grouping ncs_template_ACTIVE {
    description
      "Common node of pim-ma, pim6-ma";
    container active {
      description
        "Active Process";
      uses ncs_template_INTERFACE-TABLE;
      uses ncs_template_PIM-MA-COMMON-OPER-PIM-MA-SUMMARY-MP;
    }
  }

  grouping ncs_template_IPV4-PIM-ROLE-LVL-OPER-ACTIVE {
    description
      "Common node of pim-ma, pim6-maCommon node of pim,
       ipv6-pim";
    container active {
      description
        "Active Process";
      uses ncs_template_DEFAULT-CONTEXT;
      uses ncs_template_PROCESS;
      uses ncs_template_VRF-TABLE;
    }
  }

  grouping ncs_template_GROUP-MAP-RPF-TABLE {
    description
      "Common node of vrf, default-context";
    container group-map-rpfs {
      description
        "PIM group mapping information";
      list group-map-rpf {
        // NCS patched for predictable order
        ordered-by user;
        key "prefix prefix-length client protocol rp-address rp-priority";
        description
          "PIM group mapping entry";
        leaf prefix {
          type string;
          description
            "Prefix";
        }
        leaf prefix-length {
          type string;
          description
            "Prefix length";
        }
        leaf client {
          type ncs_template_Pim-client;
          description
            "Client";
        }
        leaf protocol {
          type ncs_template_Pim-protocol;
          description
            "Protocol";
        }
        leaf rp-address {
          type string;
          description
            "RP address";
        }
        leaf rp-priority {
          type string;
          description
            "RP priority";
        }
        uses ncs_template_PIM-GRP-MAP-INFORPF-BAG;
      }
    }
  }

  grouping ncs_template_RPF-REDIRECT {
    description
      "Common node of vrf, default-context";
    container rpf-redirect {
      description
        "PIM ECMP RPF-redirect bundle";
      container redirect-route-databases {
        description
          "PIM ECMP RPF-redirect route database";
        list redirect-route-database {
          // NCS patched for predictable order
          ordered-by user;
          key "source-address group-address";
          description
            "PIM ECMP RPF-redirect route information";
          leaf source-address {
            type string;
            description
              "Source address";
          }
          leaf group-address {
            type string;
            description
              "Group address";
          }
          uses ncs_template_PIM-RPF-RDRCT-ROUTE-BAG;
        }
      }
      container bundle-interfaces {
        description
          "PIM ECMP RPF-redirect bundle information";
        list bundle-interface {
          // NCS patched for predictable order
          ordered-by user;
          key "bundle-name interface-name";
          description
            "PIM ECMP RPF-redirect bundle interface
             information";
          leaf bundle-name {
            type xr:ncs_template_Cisco-ios-xr-string;
            description
              "Bundle name";
          }
          leaf interface-name {
            type xr:ncs_template_Interface-name;
            description
              "Bundle interface name";
          }
          uses ncs_template_PIM-RPF-RDRCT-BNDL-BAG;
        }
      }
    }
  }

  grouping ncs_template_CONTEXT {
    description
      "Common node of vrf, default-context";
    container context {
      description
        "PIM context information";
      uses ncs_template_PIM-CONTEXT-BAG;
    }
  }

  grouping ncs_template_INTERFACE-TABLE {
    description
      "Common node of active, standby";
    container interface-table {
      description
        "Interface Table";
      container interface-by-handles {
        description
          "Table of PIM MA interfaces indexed by handle";
        list interface-by-handle {
          // NCS patched for predictable order
          ordered-by user;
          key "interface-handle";
          description
            "PIM MA interface referenced by handle";
          leaf interface-handle {
            type string;
            description
              "Interface handle";
          }
          uses ncs_template_PIM-MA-IDB;
        }
      }
      container interface-by-names {
        description
          "Table of PIM MA interfaces indexed by name";
        list interface-by-name {
          // NCS patched for predictable order
          ordered-by user;
          key "interface-name";
          description
            "PIM MA interface referenced by name";
          leaf interface-name {
            type xr:ncs_template_Interface-name;
            description
              "Interface name";
          }
          uses ncs_template_PIM-MA-IDB;
        }
      }
    }
  }

  grouping ncs_template_IPV4-PIM-COMMON-OPER-INTERFACE-TABLE {
    description
      "Common node of active, standbyCommon node of vrf,
       default-context";
    container interfaces {
      description
        "PIM interfaces";
      list interface {
        // NCS patched for predictable order
        ordered-by user;
        key "interface-name";
        description
          "PIM interface name";
        leaf interface-name {
          type xr:ncs_template_Interface-name;
          description
            "Interface name";
        }
        uses ncs_template_PIM-IDB-BAG;
      }
    }
  }

  grouping ncs_template_SUMMARY {
    description
      "Common node of vrf, default-context";
    container summary {
      description
        "PIM summary";
      uses ncs_template_PIM-SUMMARY-BAG;
    }
  }

  grouping ncs_template_TOPOLOGY-INTERFACE-FLAG-ROUTE-COUNT-TABLE {
    description
      "Common node of vrf, default-context";
    container topology-interface-flag-route-counts {
      description
        "Route count for topology with interface flag set";
      list topology-interface-flag-route-count {
        // NCS patched for predictable order
        ordered-by user;
        key "interface-flag";
        description
          "Route count for topology with interface flag
           set";
        leaf interface-flag {
          type ncs_template_Pim-topology-interface-flag;
          description
            "Interface flag";
        }
        uses ncs_template_PIM-TT-SUMM-BAG;
      }
    }
  }

  grouping ncs_template_INTERFACE-STATISTICS-TABLE {
    description
      "Common node of vrf, default-context";
    container interface-statistics {
      description
        "PIM interface statistics";
      list interface-statistic {
        // NCS patched for predictable order
        ordered-by user;
        key "interface-name";
        description
          "PIM interface statistics";
        leaf interface-name {
          type xr:ncs_template_Interface-name;
          description
            "Interface name";
        }
        uses ncs_template_PIM-IFSTATS-BAG;
      }
    }
  }

  grouping ncs_template_GRE {
    description
      "Common node of vrf, default-context";
    container gre {
      description
        "GRE information";
      container gre-next-hops {
        description
          "GRE destination neighbor table";
        list gre-next-hop {
          // NCS patched for predictable order
          ordered-by user;
          key "destination-address";
          description
            "PIM GRE address next-hop information";
          leaf destination-address {
            type string;
            description
              "GRE destination address";
          }
          uses ncs_template_PIM-GRE-INFO-BAG;
        }
      }
    }
  }

  grouping ncs_template_IFRS-SUMMARY {
    description
      "Common node of vrf, default-context";
    container ifrs-summary {
      description
        "PIM interfaces in forward reference store
         summary";
      uses ncs_template_PIM-IDB-SUMM-BAG;
    }
  }

  grouping ncs_template_DEFAULT-CONTEXT {
    description
      "Common node of active, standby";
    container default-context {
      description
        "Default Context";
      container global-interfaces {
        description
          "PIM global interface table";
        list global-interface {
          // NCS patched for predictable order
          ordered-by user;
          key "interface-name";
          description
            "PIM interface name";
          leaf interface-name {
            type xr:ncs_template_Interface-name;
            description
              "Interface name";
          }
          uses ncs_template_PIM-IDB-BAG;
        }
      }
      uses ncs_template_IFRS-INTERFACE-TABLE;
      uses ncs_template_INTERFACE-STATISTICS-TABLE;
      uses ncs_template_TOPOLOGY-ROUTE-COUNT;
      uses ncs_template_JP-STATISTICS-TABLE;
      uses ncs_template_MIB-DATABASE-TABLE;
      uses ncs_template_IFRS-SUMMARY;
      uses ncs_template_RANGE-LIST-TABLE;
      uses ncs_template_BSR;
      uses ncs_template_ROUTE-POLICY;
      uses ncs_template_RPF-SUMMARY;
      uses ncs_template_IPV4-PIM-COMMON-OPER-INTERFACE-TABLE;
      uses ncs_template_NET-IO-TUNNEL-TABLE;
      uses ncs_template_BIDIR-DF-STATE-TABLE;
      uses ncs_template_TOPOLOGY-TABLE;
      uses ncs_template_TOPOLOGY-INTERFACE-FLAG-ROUTE-COUNT-TABLE;
      uses ncs_template_GROUP-MAP-SOURCE-TABLE;
      uses ncs_template_TRAFFIC-COUNTERS;
      uses ncs_template_GROUP-MAP-RPF-TABLE;
      uses ncs_template_SUMMARY;
      uses ncs_template_GRE;
      uses ncs_template_BIDIR-DF-WINNER-TABLE;
      uses ncs_template_TABLE-CONTEXT-TABLE;
      uses ncs_template_NEIGHBOR-SUMMARY-TABLE;
      uses ncs_template_CONTEXT;
      uses ncs_template_TOPOLOGY-ENTRY-FLAG-ROUTE-COUNT-TABLE;
      uses ncs_template_RPF-REDIRECT;
      uses ncs_template_TUNNEL-TABLE;
      uses ncs_template_MULTICAST-STATIC-ROUTE-TABLE;
      uses ncs_template_NEIGHBOR-TABLE;
    }
  }

  grouping ncs_template_NEIGHBOR-TABLE {
    description
      "Common node of vrf, default-context";
    container neighbors {
      description
        "PIM neighbor table";
      list neighbor {
        // NCS patched for predictable order
        ordered-by user;
        key "interface-name neighbor-address";
        description
          "PIM neighbor information";
        leaf interface-name {
          type xr:ncs_template_Interface-name;
          description
            "Interface name";
        }
        leaf neighbor-address {
          type string;
          description
            "Neighbor address";
        }
        uses ncs_template_PIM-NBR-BAG;
      }
    }
  }

  grouping ncs_template_MULTICAST-STATIC-ROUTE-TABLE {
    description
      "Common node of vrf, default-context";
    container multicast-static-routes {
      description
        "PIM multicast static route table";
      list multicast-static-route {
        // NCS patched for predictable order
        ordered-by user;
        key "address prefix-length";
        description
          "PIM multicast static route information";
        leaf address {
          type string;
          description
            "Network address";
        }
        leaf prefix-length {
          type string;
          description
            "Prefix length";
        }
        uses ncs_template_PIM-MSTATIC-BAG;
      }
    }
  }

  grouping ncs_template_RANGE-LIST-TABLE {
    description
      "Common node of vrf, default-context";
    container ranges {
      description
        "PIM range list information";
      list range {
        // NCS patched for predictable order
        ordered-by user;
        key "rp-address client";
        description
          "PIM range list information";
        leaf rp-address {
          type string;
          description
            "RP address";
        }
        leaf client {
          type ncs_template_Pim-client;
          description
            "Client";
        }
        uses ncs_template_PIM-RL-BAG;
      }
    }
  }

  grouping ncs_template_STANDBY {
    description
      "Common node of pim-ma, pim6-ma";
    container standby {
      description
        "Standby Process";
      uses ncs_template_INTERFACE-TABLE;
      uses ncs_template_PIM-MA-COMMON-OPER-PIM-MA-SUMMARY-MP;
    }
  }

  grouping ncs_template_IPV4-PIM-ROLE-LVL-OPER-STANDBY {
    description
      "Common node of pim-ma, pim6-maCommon node of pim,
       ipv6-pim";
    container standby {
      description
        "Standby Process";
      uses ncs_template_DEFAULT-CONTEXT;
      uses ncs_template_PROCESS;
      uses ncs_template_VRF-TABLE;
    }
  }

  grouping ncs_rpc_notif_ROUTE-POLICY {
    description
      "Common node of vrf, default-context";
    container route-policy {
      description
        "PIM route policy";
      container route-policy-statistics {
        description
          "PIM route policy statistics";
        uses ncs_rpc_notif_PIM-RPF-POLICY-STATS-BAG;
      }
    }
  }

  grouping ncs_rpc_notif_GROUP-MAP-SOURCE-TABLE {
    description
      "Common node of vrf, default-context";
    container group-map-sources {
      description
        "PIM group-mapping with source information";
      list group-map-source {
        key "prefix prefix-length client protocol rp-address priority";
        description
          "PIM Group Mapping Entry with source information";
        leaf prefix {
          type inet:ip-address-no-zone;
          description
            "Prefix";
        }
        leaf prefix-length {
          type uint32;
          description
            "Prefix length";
        }
        leaf client {
          type ncs_rpc_notif_Pim-client;
          description
            "Client";
        }
        leaf protocol {
          type ncs_rpc_notif_Pim-protocol;
          description
            "Protocol";
        }
        leaf rp-address {
          type inet:ip-address-no-zone;
          description
            "RP address";
        }
        leaf priority {
          type uint32;
          description
            "RP Priority";
        }
        uses ncs_rpc_notif_PIM-GRP-MAP-INFOSRC-BAG;
      }
    }
  }

  grouping ncs_rpc_notif_BIDIR-DF-STATE-TABLE {
    description
      "Common node of vrf, default-context";
    container bidir-df-states {
      description
        "Bidirectional PIM DF election state table";
      list bidir-df-state {
        key "rp-address interface-name";
        description
          "Bidirectional PIM DF Election Table Entry";
        leaf rp-address {
          type inet:ip-address-no-zone;
          description
            "RP address";
        }
        leaf interface-name {
          type xr:ncs_rpc_notif_Interface-name;
          description
            "Interface name";
        }
        uses ncs_rpc_notif_PIM-BIDIR-DF-STATE-BAG;
      }
    }
  }

  grouping ncs_rpc_notif_MIB-DATABASE-TABLE {
    description
      "Common node of vrf, default-context";
    container mib-databases {
      description
        "PIM group database for mroute mibs table";
      list mib-database {
        key "source-address group-address source-netmask";
        description
          "PIM multicast static route information";
        leaf source-address {
          type inet:ip-address-no-zone;
          description
            "Multicast static route source address";
        }
        leaf group-address {
          type inet:ip-address-no-zone;
          description
            "Multicast satic route group address";
        }
        leaf source-netmask {
          type uint32;
          description
            "Source mask";
        }
        uses ncs_rpc_notif_PIM-MROUTE-BAG;
      }
    }
  }

  grouping ncs_rpc_notif_TOPOLOGY-ENTRY-FLAG-ROUTE-COUNT-TABLE {
    description
      "Common node of vrf, default-context";
    container topology-entry-flag-route-counts {
      description
        "Route count for topology with entry flag set";
      list topology-entry-flag-route-count {
        key "entry-flag";
        description
          "Route count for topology with entry flag set";
        leaf entry-flag {
          type ncs_rpc_notif_Pim-topology-entry-flag;
          description
            "entry flag";
        }
        uses ncs_rpc_notif_PIM-TT-SUMM-BAG;
      }
    }
  }

  grouping ncs_rpc_notif_BIDIR-DF-WINNER-TABLE {
    description
      "Common node of vrf, default-context";
    container bidir-df-winners {
      description
        "Bidirectional PIM DF election winner table";
      list bidir-df-winner {
        key "rp-address interface-name";
        description
          "Bidirectional PIM DF election table entry";
        leaf rp-address {
          type inet:ip-address-no-zone;
          description
            "RP address";
        }
        leaf interface-name {
          type xr:ncs_rpc_notif_Interface-name;
          description
            "Interface name";
        }
        uses ncs_rpc_notif_PIM-BIDIR-DF-BAG;
      }
    }
  }

  grouping ncs_rpc_notif_TABLE-CONTEXT-TABLE {
    description
      "Common node of vrf, default-context";
    container table-contexts {
      description
        "PIM table context list";
      list table-context {
        key "saf-name topology-name";
        description
          "PIM table context information";
        leaf saf-name {
          type ncs_rpc_notif_Pim-safi;
          description
            "SAF name";
        }
        leaf topology-name {
          type xr:ncs_rpc_notif_Cisco-ios-xr-string;
          description
            "Topology name";
        }
        uses ncs_rpc_notif_PIM-TABLE-CTX-BAG;
      }
    }
  }

  grouping ncs_rpc_notif_VRF-TABLE {
    description
      "Common node of active, standby";
    container vrfs {
      description
        "VRF Table";
      list vrf {
        key "vrf-name";
        description
          "VRF name";
        leaf vrf-name {
          type xr:ncs_rpc_notif_Cisco-ios-xr-string;
          description
            "VRF name ";
        }
        uses ncs_rpc_notif_IFRS-INTERFACE-TABLE;
        uses ncs_rpc_notif_INTERFACE-STATISTICS-TABLE;
        uses ncs_rpc_notif_TOPOLOGY-ROUTE-COUNT;
        uses ncs_rpc_notif_JP-STATISTICS-TABLE;
        uses ncs_rpc_notif_MIB-DATABASE-TABLE;
        uses ncs_rpc_notif_IFRS-SUMMARY;
        uses ncs_rpc_notif_RANGE-LIST-TABLE;
        uses ncs_rpc_notif_BSR;
        uses ncs_rpc_notif_ROUTE-POLICY;
        uses ncs_rpc_notif_RPF-SUMMARY;
        uses ncs_rpc_notif_IPV4-PIM-COMMON-OPER-INTERFACE-TABLE;
        uses ncs_rpc_notif_NET-IO-TUNNEL-TABLE;
        uses ncs_rpc_notif_BIDIR-DF-STATE-TABLE;
        uses ncs_rpc_notif_TOPOLOGY-TABLE;
        uses ncs_rpc_notif_TOPOLOGY-INTERFACE-FLAG-ROUTE-COUNT-TABLE;
        uses ncs_rpc_notif_GROUP-MAP-SOURCE-TABLE;
        uses ncs_rpc_notif_TRAFFIC-COUNTERS;
        uses ncs_rpc_notif_GROUP-MAP-RPF-TABLE;
        uses ncs_rpc_notif_SUMMARY;
        uses ncs_rpc_notif_GRE;
        uses ncs_rpc_notif_BIDIR-DF-WINNER-TABLE;
        uses ncs_rpc_notif_TABLE-CONTEXT-TABLE;
        uses ncs_rpc_notif_NEIGHBOR-SUMMARY-TABLE;
        uses ncs_rpc_notif_CONTEXT;
        uses ncs_rpc_notif_TOPOLOGY-ENTRY-FLAG-ROUTE-COUNT-TABLE;
        uses ncs_rpc_notif_RPF-REDIRECT;
        uses ncs_rpc_notif_TUNNEL-TABLE;
        uses ncs_rpc_notif_MULTICAST-STATIC-ROUTE-TABLE;
        uses ncs_rpc_notif_NEIGHBOR-TABLE;
      }
    }
  }

  grouping ncs_rpc_notif_BSR {
    description
      "Common node of vrf, default-context";
    container bsr {
      description
        "PIM BSR information";
      container rp-caches {
        description
          "PIM BSR RP cache table";
        list rp-cache {
          key "group-prefix prefix-length";
          description
            "PIM BSR RP cache";
          leaf group-prefix {
            type inet:ip-address-no-zone;
            description
              "Group prefix";
          }
          leaf prefix-length {
            type uint32;
            description
              "Prefix Length";
          }
          uses ncs_rpc_notif_PIM-BSR-RP-CACHE-BAG;
        }
      }
      container candidate-rps {
        description
          "PIM candidate-RP";
        list candidate-rp {
          key "rp-address";
          description
            "PIM BSR candidate RP information";
          leaf rp-address {
            type inet:ip-address-no-zone;
            description
              "Candidate-RP address";
          }
          uses ncs_rpc_notif_PIM-BSR-CANDIDATE-RP-BAG;
        }
      }
      container bsr-elections {
        description
          "PIM BSR election state";
        list bsr-election {
          key "pim-scope";
          description
            "PIM BSR information";
          leaf pim-scope {
            type uint32;
            description
              "BSR information";
          }
          uses ncs_rpc_notif_PIM-BSR-ELECTION-BAG;
        }
      }
    }
  }

  grouping ncs_rpc_notif_NET-IO-TUNNEL-TABLE {
    description
      "Common node of vrf, default-context";
    container net-io-tunnels {
      description
        "Tunnel information that NETIO has ";
      list net-io-tunnel {
        key "tunnel-name";
        description
          "PIM netio tunnel information";
        leaf tunnel-name {
          type xr:ncs_rpc_notif_Cisco-ios-xr-string;
          description
            "Tunnel name";
        }
        uses ncs_rpc_notif_PIM-TUNNEL-INFO-BAG;
      }
    }
  }

  grouping ncs_rpc_notif_RPF-SUMMARY {
    description
      "Common node of vrf, default-context";
    container rpf-summary {
      description
        "PIM RPF registration summary";
      uses ncs_rpc_notif_PIM-RPF-SUMMARY-BAG;
    }
  }

  grouping ncs_rpc_notif_IFRS-INTERFACE-TABLE {
    description
      "Common node of vrf, default-context";
    container ifrs-interfaces {
      description
        "PIM interfaces in forward reference store table";
      list ifrs-interface {
        key "interface-name";
        description
          "PIM IFRS interface information";
        leaf interface-name {
          type xr:ncs_rpc_notif_Interface-name;
          description
            "Interface name";
        }
        uses ncs_rpc_notif_PIM-IDB-BAG;
      }
    }
  }

  grouping ncs_rpc_notif_PROCESS {
    description
      "Common node of active, standby";
    container process {
      description
        "Process";
      container nsr {
        description
          "NSR Information";
        uses ncs_rpc_notif_PIM-NSR-BAG;
      }
      container summary {
        description
          "PIM Global Summary";
        uses ncs_rpc_notif_PIM-SUMMARY-BAG;
      }
      container nsf {
        description
          "PIM NSF information";
        uses ncs_rpc_notif_PIM-NSF-BAG;
      }
      container issu {
        description
          "ISSU Information";
        uses ncs_rpc_notif_PIM-ISSU-BAG;
      }
    }
  }

  grouping ncs_rpc_notif_JP-STATISTICS-TABLE {
    description
      "Common node of vrf, default-context";
    container jp-statistics {
      description
        "PIM join prune statistics table";
      list jp-statistic {
        key "interface-name";
        description
          "PIM Join Prune Statistics";
        leaf interface-name {
          type xr:ncs_rpc_notif_Interface-name;
          description
            "Interface name";
        }
        uses ncs_rpc_notif_PIM-JPSTATS-BAG;
      }
    }
  }

  grouping ncs_rpc_notif_TOPOLOGY-TABLE {
    description
      "Common node of vrf, default-context";
    container topologies {
      description
        "PIM topology table";
      list topology {
        key "source-address group-address rpt";
        description
          "PIM topology information";
        leaf source-address {
          type inet:ip-address-no-zone;
          description
            "Source address";
        }
        leaf group-address {
          type inet:ip-address-no-zone;
          description
            "Group address";
        }
        leaf rpt {
          type uint32;
          description
            "RPT bit";
        }
        uses ncs_rpc_notif_PIM-TT-ROUTE-BAG;
      }
    }
  }

  grouping ncs_rpc_notif_NEIGHBOR-SUMMARY-TABLE {
    description
      "Common node of vrf, default-context";
    container neighbor-summaries {
      description
        "PIM neighbor summary table";
      list neighbor-summary {
        key "interface-name";
        description
          "PIM neighbor summary information";
        leaf interface-name {
          type xr:ncs_rpc_notif_Interface-name;
          description
            "Interface name";
        }
        uses ncs_rpc_notif_PIM-NBR-SUMM-BAG;
      }
    }
  }

  grouping ncs_rpc_notif_TRAFFIC-COUNTERS {
    description
      "Common node of vrf, default-context";
    container traffic-counters {
      description
        "PIM message traffic counters";
      uses ncs_rpc_notif_PIM-TRAFFIC-BAG;
    }
  }

  grouping ncs_rpc_notif_TOPOLOGY-ROUTE-COUNT {
    description
      "Common node of vrf, default-context";
    container topology-route-count {
      description
        "Topology route count information from PIM
         topology table";
      uses ncs_rpc_notif_PIM-TT-SUMM-BAG;
    }
  }

  grouping ncs_rpc_notif_TUNNEL-TABLE {
    description
      "Common node of vrf, default-context";
    container tunnels {
      description
        "Tunnels information that PIM has";
      list tunnel {
        key "tunnel-name";
        description
          "PIM tunnel information";
        leaf tunnel-name {
          type xr:ncs_rpc_notif_Cisco-ios-xr-string;
          description
            "Tunnel name";
        }
        uses ncs_rpc_notif_PIM-TUNNEL-INFO-BAG;
      }
    }
  }

  grouping ncs_rpc_notif_PIM-MA-COMMON-OPER-PIM-MA-SUMMARY-MP {
    description
      "Common node of active, standby";
    container pim-ma-summary {
      description
        "PIM MA summary";
      uses ncs_rpc_notif_PIM-MA-SUMMARY;
    }
  }

  grouping ncs_rpc_notif_ACTIVE {
    description
      "Common node of pim-ma, pim6-ma";
    container active {
      description
        "Active Process";
      uses ncs_rpc_notif_INTERFACE-TABLE;
      uses ncs_rpc_notif_PIM-MA-COMMON-OPER-PIM-MA-SUMMARY-MP;
    }
  }

  grouping ncs_rpc_notif_IPV4-PIM-ROLE-LVL-OPER-ACTIVE {
    description
      "Common node of pim-ma, pim6-maCommon node of pim,
       ipv6-pim";
    container active {
      description
        "Active Process";
      uses ncs_rpc_notif_DEFAULT-CONTEXT;
      uses ncs_rpc_notif_PROCESS;
      uses ncs_rpc_notif_VRF-TABLE;
    }
  }

  grouping ncs_rpc_notif_GROUP-MAP-RPF-TABLE {
    description
      "Common node of vrf, default-context";
    container group-map-rpfs {
      description
        "PIM group mapping information";
      list group-map-rpf {
        key "prefix prefix-length client protocol rp-address rp-priority";
        description
          "PIM group mapping entry";
        leaf prefix {
          type inet:ip-address-no-zone;
          description
            "Prefix";
        }
        leaf prefix-length {
          type uint32;
          description
            "Prefix length";
        }
        leaf client {
          type ncs_rpc_notif_Pim-client;
          description
            "Client";
        }
        leaf protocol {
          type ncs_rpc_notif_Pim-protocol;
          description
            "Protocol";
        }
        leaf rp-address {
          type inet:ip-address-no-zone;
          description
            "RP address";
        }
        leaf rp-priority {
          type uint32;
          description
            "RP priority";
        }
        uses ncs_rpc_notif_PIM-GRP-MAP-INFORPF-BAG;
      }
    }
  }

  grouping ncs_rpc_notif_RPF-REDIRECT {
    description
      "Common node of vrf, default-context";
    container rpf-redirect {
      description
        "PIM ECMP RPF-redirect bundle";
      container redirect-route-databases {
        description
          "PIM ECMP RPF-redirect route database";
        list redirect-route-database {
          key "source-address group-address";
          description
            "PIM ECMP RPF-redirect route information";
          leaf source-address {
            type inet:ip-address-no-zone;
            description
              "Source address";
          }
          leaf group-address {
            type inet:ip-address-no-zone;
            description
              "Group address";
          }
          uses ncs_rpc_notif_PIM-RPF-RDRCT-ROUTE-BAG;
        }
      }
      container bundle-interfaces {
        description
          "PIM ECMP RPF-redirect bundle information";
        list bundle-interface {
          key "bundle-name interface-name";
          description
            "PIM ECMP RPF-redirect bundle interface
             information";
          leaf bundle-name {
            type xr:ncs_rpc_notif_Cisco-ios-xr-string;
            description
              "Bundle name";
          }
          leaf interface-name {
            type xr:ncs_rpc_notif_Interface-name;
            description
              "Bundle interface name";
          }
          uses ncs_rpc_notif_PIM-RPF-RDRCT-BNDL-BAG;
        }
      }
    }
  }

  grouping ncs_rpc_notif_CONTEXT {
    description
      "Common node of vrf, default-context";
    container context {
      description
        "PIM context information";
      uses ncs_rpc_notif_PIM-CONTEXT-BAG;
    }
  }

  grouping ncs_rpc_notif_INTERFACE-TABLE {
    description
      "Common node of active, standby";
    container interface-table {
      description
        "Interface Table";
      container interface-by-handles {
        description
          "Table of PIM MA interfaces indexed by handle";
        list interface-by-handle {
          key "interface-handle";
          description
            "PIM MA interface referenced by handle";
          leaf interface-handle {
            type uint32;
            description
              "Interface handle";
          }
          uses ncs_rpc_notif_PIM-MA-IDB;
        }
      }
      container interface-by-names {
        description
          "Table of PIM MA interfaces indexed by name";
        list interface-by-name {
          key "interface-name";
          description
            "PIM MA interface referenced by name";
          leaf interface-name {
            type xr:ncs_rpc_notif_Interface-name;
            description
              "Interface name";
          }
          uses ncs_rpc_notif_PIM-MA-IDB;
        }
      }
    }
  }

  grouping ncs_rpc_notif_IPV4-PIM-COMMON-OPER-INTERFACE-TABLE {
    description
      "Common node of active, standbyCommon node of vrf,
       default-context";
    container interfaces {
      description
        "PIM interfaces";
      list interface {
        key "interface-name";
        description
          "PIM interface name";
        leaf interface-name {
          type xr:ncs_rpc_notif_Interface-name;
          description
            "Interface name";
        }
        uses ncs_rpc_notif_PIM-IDB-BAG;
      }
    }
  }

  grouping ncs_rpc_notif_SUMMARY {
    description
      "Common node of vrf, default-context";
    container summary {
      description
        "PIM summary";
      uses ncs_rpc_notif_PIM-SUMMARY-BAG;
    }
  }

  grouping ncs_rpc_notif_TOPOLOGY-INTERFACE-FLAG-ROUTE-COUNT-TABLE {
    description
      "Common node of vrf, default-context";
    container topology-interface-flag-route-counts {
      description
        "Route count for topology with interface flag set";
      list topology-interface-flag-route-count {
        key "interface-flag";
        description
          "Route count for topology with interface flag
           set";
        leaf interface-flag {
          type ncs_rpc_notif_Pim-topology-interface-flag;
          description
            "Interface flag";
        }
        uses ncs_rpc_notif_PIM-TT-SUMM-BAG;
      }
    }
  }

  grouping ncs_rpc_notif_INTERFACE-STATISTICS-TABLE {
    description
      "Common node of vrf, default-context";
    container interface-statistics {
      description
        "PIM interface statistics";
      list interface-statistic {
        key "interface-name";
        description
          "PIM interface statistics";
        leaf interface-name {
          type xr:ncs_rpc_notif_Interface-name;
          description
            "Interface name";
        }
        uses ncs_rpc_notif_PIM-IFSTATS-BAG;
      }
    }
  }

  grouping ncs_rpc_notif_GRE {
    description
      "Common node of vrf, default-context";
    container gre {
      description
        "GRE information";
      container gre-next-hops {
        description
          "GRE destination neighbor table";
        list gre-next-hop {
          key "destination-address";
          description
            "PIM GRE address next-hop information";
          leaf destination-address {
            type inet:ip-address-no-zone;
            description
              "GRE destination address";
          }
          uses ncs_rpc_notif_PIM-GRE-INFO-BAG;
        }
      }
    }
  }

  grouping ncs_rpc_notif_IFRS-SUMMARY {
    description
      "Common node of vrf, default-context";
    container ifrs-summary {
      description
        "PIM interfaces in forward reference store
         summary";
      uses ncs_rpc_notif_PIM-IDB-SUMM-BAG;
    }
  }

  grouping ncs_rpc_notif_DEFAULT-CONTEXT {
    description
      "Common node of active, standby";
    container default-context {
      description
        "Default Context";
      container global-interfaces {
        description
          "PIM global interface table";
        list global-interface {
          key "interface-name";
          description
            "PIM interface name";
          leaf interface-name {
            type xr:ncs_rpc_notif_Interface-name;
            description
              "Interface name";
          }
          uses ncs_rpc_notif_PIM-IDB-BAG;
        }
      }
      uses ncs_rpc_notif_IFRS-INTERFACE-TABLE;
      uses ncs_rpc_notif_INTERFACE-STATISTICS-TABLE;
      uses ncs_rpc_notif_TOPOLOGY-ROUTE-COUNT;
      uses ncs_rpc_notif_JP-STATISTICS-TABLE;
      uses ncs_rpc_notif_MIB-DATABASE-TABLE;
      uses ncs_rpc_notif_IFRS-SUMMARY;
      uses ncs_rpc_notif_RANGE-LIST-TABLE;
      uses ncs_rpc_notif_BSR;
      uses ncs_rpc_notif_ROUTE-POLICY;
      uses ncs_rpc_notif_RPF-SUMMARY;
      uses ncs_rpc_notif_IPV4-PIM-COMMON-OPER-INTERFACE-TABLE;
      uses ncs_rpc_notif_NET-IO-TUNNEL-TABLE;
      uses ncs_rpc_notif_BIDIR-DF-STATE-TABLE;
      uses ncs_rpc_notif_TOPOLOGY-TABLE;
      uses ncs_rpc_notif_TOPOLOGY-INTERFACE-FLAG-ROUTE-COUNT-TABLE;
      uses ncs_rpc_notif_GROUP-MAP-SOURCE-TABLE;
      uses ncs_rpc_notif_TRAFFIC-COUNTERS;
      uses ncs_rpc_notif_GROUP-MAP-RPF-TABLE;
      uses ncs_rpc_notif_SUMMARY;
      uses ncs_rpc_notif_GRE;
      uses ncs_rpc_notif_BIDIR-DF-WINNER-TABLE;
      uses ncs_rpc_notif_TABLE-CONTEXT-TABLE;
      uses ncs_rpc_notif_NEIGHBOR-SUMMARY-TABLE;
      uses ncs_rpc_notif_CONTEXT;
      uses ncs_rpc_notif_TOPOLOGY-ENTRY-FLAG-ROUTE-COUNT-TABLE;
      uses ncs_rpc_notif_RPF-REDIRECT;
      uses ncs_rpc_notif_TUNNEL-TABLE;
      uses ncs_rpc_notif_MULTICAST-STATIC-ROUTE-TABLE;
      uses ncs_rpc_notif_NEIGHBOR-TABLE;
    }
  }

  grouping ncs_rpc_notif_NEIGHBOR-TABLE {
    description
      "Common node of vrf, default-context";
    container neighbors {
      description
        "PIM neighbor table";
      list neighbor {
        key "interface-name neighbor-address";
        description
          "PIM neighbor information";
        leaf interface-name {
          type xr:ncs_rpc_notif_Interface-name;
          description
            "Interface name";
        }
        leaf neighbor-address {
          type inet:ip-address-no-zone;
          description
            "Neighbor address";
        }
        uses ncs_rpc_notif_PIM-NBR-BAG;
      }
    }
  }

  grouping ncs_rpc_notif_MULTICAST-STATIC-ROUTE-TABLE {
    description
      "Common node of vrf, default-context";
    container multicast-static-routes {
      description
        "PIM multicast static route table";
      list multicast-static-route {
        key "address prefix-length";
        description
          "PIM multicast static route information";
        leaf address {
          type inet:ip-address-no-zone;
          description
            "Network address";
        }
        leaf prefix-length {
          type uint32;
          description
            "Prefix length";
        }
        uses ncs_rpc_notif_PIM-MSTATIC-BAG;
      }
    }
  }

  grouping ncs_rpc_notif_RANGE-LIST-TABLE {
    description
      "Common node of vrf, default-context";
    container ranges {
      description
        "PIM range list information";
      list range {
        key "rp-address client";
        description
          "PIM range list information";
        leaf rp-address {
          type inet:ip-address-no-zone;
          description
            "RP address";
        }
        leaf client {
          type ncs_rpc_notif_Pim-client;
          description
            "Client";
        }
        uses ncs_rpc_notif_PIM-RL-BAG;
      }
    }
  }

  grouping ncs_rpc_notif_STANDBY {
    description
      "Common node of pim-ma, pim6-ma";
    container standby {
      description
        "Standby Process";
      uses ncs_rpc_notif_INTERFACE-TABLE;
      uses ncs_rpc_notif_PIM-MA-COMMON-OPER-PIM-MA-SUMMARY-MP;
    }
  }

  grouping ncs_rpc_notif_IPV4-PIM-ROLE-LVL-OPER-STANDBY {
    description
      "Common node of pim-ma, pim6-maCommon node of pim,
       ipv6-pim";
    container standby {
      description
        "Standby Process";
      uses ncs_rpc_notif_DEFAULT-CONTEXT;
      uses ncs_rpc_notif_PROCESS;
      uses ncs_rpc_notif_VRF-TABLE;
    }
  }

  grouping live_ncs_ROUTE-POLICY {
    description
      "Common node of vrf, default-context";
    container route-policy {
      description
        "PIM route policy";
      container route-policy-statistics {
        description
          "PIM route policy statistics";
        uses live_ncs_PIM-RPF-POLICY-STATS-BAG;
      }
    }
  }

  grouping live_ncs_GROUP-MAP-SOURCE-TABLE {
    description
      "Common node of vrf, default-context";
    container group-map-sources {
      description
        "PIM group-mapping with source information";
      list group-map-source {
        key "prefix prefix-length client protocol rp-address priority";
        description
          "PIM Group Mapping Entry with source information";
        leaf prefix {
          type inet:ip-address-no-zone;
          description
            "Prefix";
        }
        leaf prefix-length {
          type uint32;
          description
            "Prefix length";
        }
        leaf client {
          type live_ncs_Pim-client;
          description
            "Client";
        }
        leaf protocol {
          type live_ncs_Pim-protocol;
          description
            "Protocol";
        }
        leaf rp-address {
          type inet:ip-address-no-zone;
          description
            "RP address";
        }
        leaf priority {
          type uint32;
          description
            "RP Priority";
        }
        uses live_ncs_PIM-GRP-MAP-INFOSRC-BAG;
      }
    }
  }

  grouping live_ncs_BIDIR-DF-STATE-TABLE {
    description
      "Common node of vrf, default-context";
    container bidir-df-states {
      description
        "Bidirectional PIM DF election state table";
      list bidir-df-state {
        key "rp-address interface-name";
        description
          "Bidirectional PIM DF Election Table Entry";
        leaf rp-address {
          type inet:ip-address-no-zone;
          description
            "RP address";
        }
        leaf interface-name {
          type xr:live_ncs_Interface-name;
          description
            "Interface name";
        }
        uses live_ncs_PIM-BIDIR-DF-STATE-BAG;
      }
    }
  }

  grouping live_ncs_MIB-DATABASE-TABLE {
    description
      "Common node of vrf, default-context";
    container mib-databases {
      description
        "PIM group database for mroute mibs table";
      list mib-database {
        key "source-address group-address source-netmask";
        description
          "PIM multicast static route information";
        leaf source-address {
          type inet:ip-address-no-zone;
          description
            "Multicast static route source address";
        }
        leaf group-address {
          type inet:ip-address-no-zone;
          description
            "Multicast satic route group address";
        }
        leaf source-netmask {
          type uint32;
          description
            "Source mask";
        }
        uses live_ncs_PIM-MROUTE-BAG;
      }
    }
  }

  grouping live_ncs_TOPOLOGY-ENTRY-FLAG-ROUTE-COUNT-TABLE {
    description
      "Common node of vrf, default-context";
    container topology-entry-flag-route-counts {
      description
        "Route count for topology with entry flag set";
      list topology-entry-flag-route-count {
        key "entry-flag";
        description
          "Route count for topology with entry flag set";
        leaf entry-flag {
          type live_ncs_Pim-topology-entry-flag;
          description
            "entry flag";
        }
        uses live_ncs_PIM-TT-SUMM-BAG;
      }
    }
  }

  grouping live_ncs_BIDIR-DF-WINNER-TABLE {
    description
      "Common node of vrf, default-context";
    container bidir-df-winners {
      description
        "Bidirectional PIM DF election winner table";
      list bidir-df-winner {
        key "rp-address interface-name";
        description
          "Bidirectional PIM DF election table entry";
        leaf rp-address {
          type inet:ip-address-no-zone;
          description
            "RP address";
        }
        leaf interface-name {
          type xr:live_ncs_Interface-name;
          description
            "Interface name";
        }
        uses live_ncs_PIM-BIDIR-DF-BAG;
      }
    }
  }

  grouping live_ncs_TABLE-CONTEXT-TABLE {
    description
      "Common node of vrf, default-context";
    container table-contexts {
      description
        "PIM table context list";
      list table-context {
        key "saf-name topology-name";
        description
          "PIM table context information";
        leaf saf-name {
          type live_ncs_Pim-safi;
          description
            "SAF name";
        }
        leaf topology-name {
          type xr:live_ncs_Cisco-ios-xr-string;
          description
            "Topology name";
        }
        uses live_ncs_PIM-TABLE-CTX-BAG;
      }
    }
  }

  grouping live_ncs_VRF-TABLE {
    description
      "Common node of active, standby";
    container vrfs {
      description
        "VRF Table";
      list vrf {
        key "vrf-name";
        description
          "VRF name";
        leaf vrf-name {
          type xr:live_ncs_Cisco-ios-xr-string;
          description
            "VRF name ";
        }
        uses live_ncs_IFRS-INTERFACE-TABLE;
        uses live_ncs_INTERFACE-STATISTICS-TABLE;
        uses live_ncs_TOPOLOGY-ROUTE-COUNT;
        uses live_ncs_JP-STATISTICS-TABLE;
        uses live_ncs_MIB-DATABASE-TABLE;
        uses live_ncs_IFRS-SUMMARY;
        uses live_ncs_RANGE-LIST-TABLE;
        uses live_ncs_BSR;
        uses live_ncs_ROUTE-POLICY;
        uses live_ncs_RPF-SUMMARY;
        uses live_ncs_IPV4-PIM-COMMON-OPER-INTERFACE-TABLE;
        uses live_ncs_NET-IO-TUNNEL-TABLE;
        uses live_ncs_BIDIR-DF-STATE-TABLE;
        uses live_ncs_TOPOLOGY-TABLE;
        uses live_ncs_TOPOLOGY-INTERFACE-FLAG-ROUTE-COUNT-TABLE;
        uses live_ncs_GROUP-MAP-SOURCE-TABLE;
        uses live_ncs_TRAFFIC-COUNTERS;
        uses live_ncs_GROUP-MAP-RPF-TABLE;
        uses live_ncs_SUMMARY;
        uses live_ncs_GRE;
        uses live_ncs_BIDIR-DF-WINNER-TABLE;
        uses live_ncs_TABLE-CONTEXT-TABLE;
        uses live_ncs_NEIGHBOR-SUMMARY-TABLE;
        uses live_ncs_CONTEXT;
        uses live_ncs_TOPOLOGY-ENTRY-FLAG-ROUTE-COUNT-TABLE;
        uses live_ncs_RPF-REDIRECT;
        uses live_ncs_TUNNEL-TABLE;
        uses live_ncs_MULTICAST-STATIC-ROUTE-TABLE;
        uses live_ncs_NEIGHBOR-TABLE;
      }
    }
  }

  grouping live_ncs_BSR {
    description
      "Common node of vrf, default-context";
    container bsr {
      description
        "PIM BSR information";
      container rp-caches {
        description
          "PIM BSR RP cache table";
        list rp-cache {
          key "group-prefix prefix-length";
          description
            "PIM BSR RP cache";
          leaf group-prefix {
            type inet:ip-address-no-zone;
            description
              "Group prefix";
          }
          leaf prefix-length {
            type uint32;
            description
              "Prefix Length";
          }
          uses live_ncs_PIM-BSR-RP-CACHE-BAG;
        }
      }
      container candidate-rps {
        description
          "PIM candidate-RP";
        list candidate-rp {
          key "rp-address";
          description
            "PIM BSR candidate RP information";
          leaf rp-address {
            type inet:ip-address-no-zone;
            description
              "Candidate-RP address";
          }
          uses live_ncs_PIM-BSR-CANDIDATE-RP-BAG;
        }
      }
      container bsr-elections {
        description
          "PIM BSR election state";
        list bsr-election {
          key "pim-scope";
          description
            "PIM BSR information";
          leaf pim-scope {
            type uint32;
            description
              "BSR information";
          }
          uses live_ncs_PIM-BSR-ELECTION-BAG;
        }
      }
    }
  }

  grouping live_ncs_NET-IO-TUNNEL-TABLE {
    description
      "Common node of vrf, default-context";
    container net-io-tunnels {
      description
        "Tunnel information that NETIO has ";
      list net-io-tunnel {
        key "tunnel-name";
        description
          "PIM netio tunnel information";
        leaf tunnel-name {
          type xr:live_ncs_Cisco-ios-xr-string;
          description
            "Tunnel name";
        }
        uses live_ncs_PIM-TUNNEL-INFO-BAG;
      }
    }
  }

  grouping live_ncs_RPF-SUMMARY {
    description
      "Common node of vrf, default-context";
    container rpf-summary {
      description
        "PIM RPF registration summary";
      uses live_ncs_PIM-RPF-SUMMARY-BAG;
    }
  }

  grouping live_ncs_IFRS-INTERFACE-TABLE {
    description
      "Common node of vrf, default-context";
    container ifrs-interfaces {
      description
        "PIM interfaces in forward reference store table";
      list ifrs-interface {
        key "interface-name";
        description
          "PIM IFRS interface information";
        leaf interface-name {
          type xr:live_ncs_Interface-name;
          description
            "Interface name";
        }
        uses live_ncs_PIM-IDB-BAG;
      }
    }
  }

  grouping live_ncs_PROCESS {
    description
      "Common node of active, standby";
    container process {
      description
        "Process";
      container nsr {
        description
          "NSR Information";
        uses live_ncs_PIM-NSR-BAG;
      }
      container summary {
        description
          "PIM Global Summary";
        uses live_ncs_PIM-SUMMARY-BAG;
      }
      container nsf {
        description
          "PIM NSF information";
        uses live_ncs_PIM-NSF-BAG;
      }
      container issu {
        description
          "ISSU Information";
        uses live_ncs_PIM-ISSU-BAG;
      }
    }
  }

  grouping live_ncs_JP-STATISTICS-TABLE {
    description
      "Common node of vrf, default-context";
    container jp-statistics {
      description
        "PIM join prune statistics table";
      list jp-statistic {
        key "interface-name";
        description
          "PIM Join Prune Statistics";
        leaf interface-name {
          type xr:live_ncs_Interface-name;
          description
            "Interface name";
        }
        uses live_ncs_PIM-JPSTATS-BAG;
      }
    }
  }

  grouping live_ncs_TOPOLOGY-TABLE {
    description
      "Common node of vrf, default-context";
    container topologies {
      description
        "PIM topology table";
      list topology {
        key "source-address group-address rpt";
        description
          "PIM topology information";
        leaf source-address {
          type inet:ip-address-no-zone;
          description
            "Source address";
        }
        leaf group-address {
          type inet:ip-address-no-zone;
          description
            "Group address";
        }
        leaf rpt {
          type uint32;
          description
            "RPT bit";
        }
        uses live_ncs_PIM-TT-ROUTE-BAG;
      }
    }
  }

  grouping live_ncs_NEIGHBOR-SUMMARY-TABLE {
    description
      "Common node of vrf, default-context";
    container neighbor-summaries {
      description
        "PIM neighbor summary table";
      list neighbor-summary {
        key "interface-name";
        description
          "PIM neighbor summary information";
        leaf interface-name {
          type xr:live_ncs_Interface-name;
          description
            "Interface name";
        }
        uses live_ncs_PIM-NBR-SUMM-BAG;
      }
    }
  }

  grouping live_ncs_TRAFFIC-COUNTERS {
    description
      "Common node of vrf, default-context";
    container traffic-counters {
      description
        "PIM message traffic counters";
      uses live_ncs_PIM-TRAFFIC-BAG;
    }
  }

  grouping live_ncs_TOPOLOGY-ROUTE-COUNT {
    description
      "Common node of vrf, default-context";
    container topology-route-count {
      description
        "Topology route count information from PIM
         topology table";
      uses live_ncs_PIM-TT-SUMM-BAG;
    }
  }

  grouping live_ncs_TUNNEL-TABLE {
    description
      "Common node of vrf, default-context";
    container tunnels {
      description
        "Tunnels information that PIM has";
      list tunnel {
        key "tunnel-name";
        description
          "PIM tunnel information";
        leaf tunnel-name {
          type xr:live_ncs_Cisco-ios-xr-string;
          description
            "Tunnel name";
        }
        uses live_ncs_PIM-TUNNEL-INFO-BAG;
      }
    }
  }

  grouping live_ncs_PIM-MA-COMMON-OPER-PIM-MA-SUMMARY-MP {
    description
      "Common node of active, standby";
    container pim-ma-summary {
      description
        "PIM MA summary";
      uses live_ncs_PIM-MA-SUMMARY;
    }
  }

  grouping live_ncs_ACTIVE {
    description
      "Common node of pim-ma, pim6-ma";
    container active {
      description
        "Active Process";
      uses live_ncs_INTERFACE-TABLE;
      uses live_ncs_PIM-MA-COMMON-OPER-PIM-MA-SUMMARY-MP;
    }
  }

  grouping live_ncs_IPV4-PIM-ROLE-LVL-OPER-ACTIVE {
    description
      "Common node of pim-ma, pim6-maCommon node of pim,
       ipv6-pim";
    container active {
      description
        "Active Process";
      uses live_ncs_DEFAULT-CONTEXT;
      uses live_ncs_PROCESS;
      uses live_ncs_VRF-TABLE;
    }
  }

  grouping live_ncs_GROUP-MAP-RPF-TABLE {
    description
      "Common node of vrf, default-context";
    container group-map-rpfs {
      description
        "PIM group mapping information";
      list group-map-rpf {
        key "prefix prefix-length client protocol rp-address rp-priority";
        description
          "PIM group mapping entry";
        leaf prefix {
          type inet:ip-address-no-zone;
          description
            "Prefix";
        }
        leaf prefix-length {
          type uint32;
          description
            "Prefix length";
        }
        leaf client {
          type live_ncs_Pim-client;
          description
            "Client";
        }
        leaf protocol {
          type live_ncs_Pim-protocol;
          description
            "Protocol";
        }
        leaf rp-address {
          type inet:ip-address-no-zone;
          description
            "RP address";
        }
        leaf rp-priority {
          type uint32;
          description
            "RP priority";
        }
        uses live_ncs_PIM-GRP-MAP-INFORPF-BAG;
      }
    }
  }

  grouping live_ncs_RPF-REDIRECT {
    description
      "Common node of vrf, default-context";
    container rpf-redirect {
      description
        "PIM ECMP RPF-redirect bundle";
      container redirect-route-databases {
        description
          "PIM ECMP RPF-redirect route database";
        list redirect-route-database {
          key "source-address group-address";
          description
            "PIM ECMP RPF-redirect route information";
          leaf source-address {
            type inet:ip-address-no-zone;
            description
              "Source address";
          }
          leaf group-address {
            type inet:ip-address-no-zone;
            description
              "Group address";
          }
          uses live_ncs_PIM-RPF-RDRCT-ROUTE-BAG;
        }
      }
      container bundle-interfaces {
        description
          "PIM ECMP RPF-redirect bundle information";
        list bundle-interface {
          key "bundle-name interface-name";
          description
            "PIM ECMP RPF-redirect bundle interface
             information";
          leaf bundle-name {
            type xr:live_ncs_Cisco-ios-xr-string;
            description
              "Bundle name";
          }
          leaf interface-name {
            type xr:live_ncs_Interface-name;
            description
              "Bundle interface name";
          }
          uses live_ncs_PIM-RPF-RDRCT-BNDL-BAG;
        }
      }
    }
  }

  grouping live_ncs_CONTEXT {
    description
      "Common node of vrf, default-context";
    container context {
      description
        "PIM context information";
      uses live_ncs_PIM-CONTEXT-BAG;
    }
  }

  grouping live_ncs_INTERFACE-TABLE {
    description
      "Common node of active, standby";
    container interface-table {
      description
        "Interface Table";
      container interface-by-handles {
        description
          "Table of PIM MA interfaces indexed by handle";
        list interface-by-handle {
          key "interface-handle";
          description
            "PIM MA interface referenced by handle";
          leaf interface-handle {
            type uint32;
            description
              "Interface handle";
          }
          uses live_ncs_PIM-MA-IDB;
        }
      }
      container interface-by-names {
        description
          "Table of PIM MA interfaces indexed by name";
        list interface-by-name {
          key "interface-name";
          description
            "PIM MA interface referenced by name";
          leaf interface-name {
            type xr:live_ncs_Interface-name;
            description
              "Interface name";
          }
          uses live_ncs_PIM-MA-IDB;
        }
      }
    }
  }

  grouping live_ncs_IPV4-PIM-COMMON-OPER-INTERFACE-TABLE {
    description
      "Common node of active, standbyCommon node of vrf,
       default-context";
    container interfaces {
      description
        "PIM interfaces";
      list interface {
        key "interface-name";
        description
          "PIM interface name";
        leaf interface-name {
          type xr:live_ncs_Interface-name;
          description
            "Interface name";
        }
        uses live_ncs_PIM-IDB-BAG;
      }
    }
  }

  grouping live_ncs_SUMMARY {
    description
      "Common node of vrf, default-context";
    container summary {
      description
        "PIM summary";
      uses live_ncs_PIM-SUMMARY-BAG;
    }
  }

  grouping live_ncs_TOPOLOGY-INTERFACE-FLAG-ROUTE-COUNT-TABLE {
    description
      "Common node of vrf, default-context";
    container topology-interface-flag-route-counts {
      description
        "Route count for topology with interface flag set";
      list topology-interface-flag-route-count {
        key "interface-flag";
        description
          "Route count for topology with interface flag
           set";
        leaf interface-flag {
          type live_ncs_Pim-topology-interface-flag;
          description
            "Interface flag";
        }
        uses live_ncs_PIM-TT-SUMM-BAG;
      }
    }
  }

  grouping live_ncs_INTERFACE-STATISTICS-TABLE {
    description
      "Common node of vrf, default-context";
    container interface-statistics {
      description
        "PIM interface statistics";
      list interface-statistic {
        key "interface-name";
        description
          "PIM interface statistics";
        leaf interface-name {
          type xr:live_ncs_Interface-name;
          description
            "Interface name";
        }
        uses live_ncs_PIM-IFSTATS-BAG;
      }
    }
  }

  grouping live_ncs_GRE {
    description
      "Common node of vrf, default-context";
    container gre {
      description
        "GRE information";
      container gre-next-hops {
        description
          "GRE destination neighbor table";
        list gre-next-hop {
          key "destination-address";
          description
            "PIM GRE address next-hop information";
          leaf destination-address {
            type inet:ip-address-no-zone;
            description
              "GRE destination address";
          }
          uses live_ncs_PIM-GRE-INFO-BAG;
        }
      }
    }
  }

  grouping live_ncs_IFRS-SUMMARY {
    description
      "Common node of vrf, default-context";
    container ifrs-summary {
      description
        "PIM interfaces in forward reference store
         summary";
      uses live_ncs_PIM-IDB-SUMM-BAG;
    }
  }

  grouping live_ncs_DEFAULT-CONTEXT {
    description
      "Common node of active, standby";
    container default-context {
      description
        "Default Context";
      container global-interfaces {
        description
          "PIM global interface table";
        list global-interface {
          key "interface-name";
          description
            "PIM interface name";
          leaf interface-name {
            type xr:live_ncs_Interface-name;
            description
              "Interface name";
          }
          uses live_ncs_PIM-IDB-BAG;
        }
      }
      uses live_ncs_IFRS-INTERFACE-TABLE;
      uses live_ncs_INTERFACE-STATISTICS-TABLE;
      uses live_ncs_TOPOLOGY-ROUTE-COUNT;
      uses live_ncs_JP-STATISTICS-TABLE;
      uses live_ncs_MIB-DATABASE-TABLE;
      uses live_ncs_IFRS-SUMMARY;
      uses live_ncs_RANGE-LIST-TABLE;
      uses live_ncs_BSR;
      uses live_ncs_ROUTE-POLICY;
      uses live_ncs_RPF-SUMMARY;
      uses live_ncs_IPV4-PIM-COMMON-OPER-INTERFACE-TABLE;
      uses live_ncs_NET-IO-TUNNEL-TABLE;
      uses live_ncs_BIDIR-DF-STATE-TABLE;
      uses live_ncs_TOPOLOGY-TABLE;
      uses live_ncs_TOPOLOGY-INTERFACE-FLAG-ROUTE-COUNT-TABLE;
      uses live_ncs_GROUP-MAP-SOURCE-TABLE;
      uses live_ncs_TRAFFIC-COUNTERS;
      uses live_ncs_GROUP-MAP-RPF-TABLE;
      uses live_ncs_SUMMARY;
      uses live_ncs_GRE;
      uses live_ncs_BIDIR-DF-WINNER-TABLE;
      uses live_ncs_TABLE-CONTEXT-TABLE;
      uses live_ncs_NEIGHBOR-SUMMARY-TABLE;
      uses live_ncs_CONTEXT;
      uses live_ncs_TOPOLOGY-ENTRY-FLAG-ROUTE-COUNT-TABLE;
      uses live_ncs_RPF-REDIRECT;
      uses live_ncs_TUNNEL-TABLE;
      uses live_ncs_MULTICAST-STATIC-ROUTE-TABLE;
      uses live_ncs_NEIGHBOR-TABLE;
    }
  }

  grouping live_ncs_NEIGHBOR-TABLE {
    description
      "Common node of vrf, default-context";
    container neighbors {
      description
        "PIM neighbor table";
      list neighbor {
        key "interface-name neighbor-address";
        description
          "PIM neighbor information";
        leaf interface-name {
          type xr:live_ncs_Interface-name;
          description
            "Interface name";
        }
        leaf neighbor-address {
          type inet:ip-address-no-zone;
          description
            "Neighbor address";
        }
        uses live_ncs_PIM-NBR-BAG;
      }
    }
  }

  grouping live_ncs_MULTICAST-STATIC-ROUTE-TABLE {
    description
      "Common node of vrf, default-context";
    container multicast-static-routes {
      description
        "PIM multicast static route table";
      list multicast-static-route {
        key "address prefix-length";
        description
          "PIM multicast static route information";
        leaf address {
          type inet:ip-address-no-zone;
          description
            "Network address";
        }
        leaf prefix-length {
          type uint32;
          description
            "Prefix length";
        }
        uses live_ncs_PIM-MSTATIC-BAG;
      }
    }
  }

  grouping live_ncs_RANGE-LIST-TABLE {
    description
      "Common node of vrf, default-context";
    container ranges {
      description
        "PIM range list information";
      list range {
        key "rp-address client";
        description
          "PIM range list information";
        leaf rp-address {
          type inet:ip-address-no-zone;
          description
            "RP address";
        }
        leaf client {
          type live_ncs_Pim-client;
          description
            "Client";
        }
        uses live_ncs_PIM-RL-BAG;
      }
    }
  }

  grouping live_ncs_STANDBY {
    description
      "Common node of pim-ma, pim6-ma";
    container standby {
      description
        "Standby Process";
      uses live_ncs_INTERFACE-TABLE;
      uses live_ncs_PIM-MA-COMMON-OPER-PIM-MA-SUMMARY-MP;
    }
  }

  grouping live_ncs_IPV4-PIM-ROLE-LVL-OPER-STANDBY {
    description
      "Common node of pim-ma, pim6-maCommon node of pim,
       ipv6-pim";
    container standby {
      description
        "Standby Process";
      uses live_ncs_DEFAULT-CONTEXT;
      uses live_ncs_PROCESS;
      uses live_ncs_VRF-TABLE;
    }
  }

  grouping ROUTE-POLICY {
    description
      "Common node of vrf, default-context";
    container route-policy {
      description
        "PIM route policy";
      container route-policy-statistics {
        description
          "PIM route policy statistics";
        uses PIM-RPF-POLICY-STATS-BAG;
      }
    }
  }

  grouping GROUP-MAP-SOURCE-TABLE {
    description
      "Common node of vrf, default-context";
    container group-map-sources {
      description
        "PIM group-mapping with source information";
      list group-map-source {
        key "prefix prefix-length client protocol rp-address priority";
        description
          "PIM Group Mapping Entry with source information";
        leaf prefix {
          type inet:ip-address-no-zone;
          description
            "Prefix";
        }
        leaf prefix-length {
          type uint32;
          description
            "Prefix length";
        }
        leaf client {
          type Pim-client;
          description
            "Client";
        }
        leaf protocol {
          type Pim-protocol;
          description
            "Protocol";
        }
        leaf rp-address {
          type inet:ip-address-no-zone;
          description
            "RP address";
        }
        leaf priority {
          type uint32;
          description
            "RP Priority";
        }
        uses PIM-GRP-MAP-INFOSRC-BAG;
      }
    }
  }

  grouping BIDIR-DF-STATE-TABLE {
    description
      "Common node of vrf, default-context";
    container bidir-df-states {
      description
        "Bidirectional PIM DF election state table";
      list bidir-df-state {
        key "rp-address interface-name";
        description
          "Bidirectional PIM DF Election Table Entry";
        leaf rp-address {
          type inet:ip-address-no-zone;
          description
            "RP address";
        }
        leaf interface-name {
          type xr:Interface-name;
          description
            "Interface name";
        }
        uses PIM-BIDIR-DF-STATE-BAG;
      }
    }
  }

  grouping MIB-DATABASE-TABLE {
    description
      "Common node of vrf, default-context";
    container mib-databases {
      description
        "PIM group database for mroute mibs table";
      list mib-database {
        key "source-address group-address source-netmask";
        description
          "PIM multicast static route information";
        leaf source-address {
          type inet:ip-address-no-zone;
          description
            "Multicast static route source address";
        }
        leaf group-address {
          type inet:ip-address-no-zone;
          description
            "Multicast satic route group address";
        }
        leaf source-netmask {
          type uint32;
          description
            "Source mask";
        }
        uses PIM-MROUTE-BAG;
      }
    }
  }

  grouping TOPOLOGY-ENTRY-FLAG-ROUTE-COUNT-TABLE {
    description
      "Common node of vrf, default-context";
    container topology-entry-flag-route-counts {
      description
        "Route count for topology with entry flag set";
      list topology-entry-flag-route-count {
        key "entry-flag";
        description
          "Route count for topology with entry flag set";
        leaf entry-flag {
          type Pim-topology-entry-flag;
          description
            "entry flag";
        }
        uses PIM-TT-SUMM-BAG;
      }
    }
  }

  grouping BIDIR-DF-WINNER-TABLE {
    description
      "Common node of vrf, default-context";
    container bidir-df-winners {
      description
        "Bidirectional PIM DF election winner table";
      list bidir-df-winner {
        key "rp-address interface-name";
        description
          "Bidirectional PIM DF election table entry";
        leaf rp-address {
          type inet:ip-address-no-zone;
          description
            "RP address";
        }
        leaf interface-name {
          type xr:Interface-name;
          description
            "Interface name";
        }
        uses PIM-BIDIR-DF-BAG;
      }
    }
  }

  grouping TABLE-CONTEXT-TABLE {
    description
      "Common node of vrf, default-context";
    container table-contexts {
      description
        "PIM table context list";
      list table-context {
        key "saf-name topology-name";
        description
          "PIM table context information";
        leaf saf-name {
          type Pim-safi;
          description
            "SAF name";
        }
        leaf topology-name {
          type xr:Cisco-ios-xr-string {
            length "1..32";
          }
          description
            "Topology name";
        }
        uses PIM-TABLE-CTX-BAG;
      }
    }
  }

  grouping VRF-TABLE {
    description
      "Common node of active, standby";
    container vrfs {
      description
        "VRF Table";
      list vrf {
        key "vrf-name";
        description
          "VRF name";
        leaf vrf-name {
          type xr:Cisco-ios-xr-string {
            length "1..32";
          }
          description
            "VRF name ";
        }
        uses IFRS-INTERFACE-TABLE;
        uses INTERFACE-STATISTICS-TABLE;
        uses TOPOLOGY-ROUTE-COUNT;
        uses JP-STATISTICS-TABLE;
        uses MIB-DATABASE-TABLE;
        uses IFRS-SUMMARY;
        uses RANGE-LIST-TABLE;
        uses BSR;
        uses ROUTE-POLICY;
        uses RPF-SUMMARY;
        uses IPV4-PIM-COMMON-OPER-INTERFACE-TABLE;
        uses NET-IO-TUNNEL-TABLE;
        uses BIDIR-DF-STATE-TABLE;
        uses TOPOLOGY-TABLE;
        uses TOPOLOGY-INTERFACE-FLAG-ROUTE-COUNT-TABLE;
        uses GROUP-MAP-SOURCE-TABLE;
        uses TRAFFIC-COUNTERS;
        uses GROUP-MAP-RPF-TABLE;
        uses SUMMARY;
        uses GRE;
        uses BIDIR-DF-WINNER-TABLE;
        uses TABLE-CONTEXT-TABLE;
        uses NEIGHBOR-SUMMARY-TABLE;
        uses CONTEXT;
        uses TOPOLOGY-ENTRY-FLAG-ROUTE-COUNT-TABLE;
        uses RPF-REDIRECT;
        uses TUNNEL-TABLE;
        uses MULTICAST-STATIC-ROUTE-TABLE;
        uses NEIGHBOR-TABLE;
      }
    }
  }

  grouping BSR {
    description
      "Common node of vrf, default-context";
    container bsr {
      description
        "PIM BSR information";
      container rp-caches {
        description
          "PIM BSR RP cache table";
        list rp-cache {
          key "group-prefix prefix-length";
          description
            "PIM BSR RP cache";
          leaf group-prefix {
            type inet:ip-address-no-zone;
            description
              "Group prefix";
          }
          leaf prefix-length {
            type uint32;
            description
              "Prefix Length";
          }
          uses PIM-BSR-RP-CACHE-BAG;
        }
      }
      container candidate-rps {
        description
          "PIM candidate-RP";
        list candidate-rp {
          key "rp-address";
          description
            "PIM BSR candidate RP information";
          leaf rp-address {
            type inet:ip-address-no-zone;
            description
              "Candidate-RP address";
          }
          uses PIM-BSR-CANDIDATE-RP-BAG;
        }
      }
      container bsr-elections {
        description
          "PIM BSR election state";
        list bsr-election {
          key "pim-scope";
          description
            "PIM BSR information";
          leaf pim-scope {
            type uint32;
            description
              "BSR information";
          }
          uses PIM-BSR-ELECTION-BAG;
        }
      }
    }
  }

  grouping NET-IO-TUNNEL-TABLE {
    description
      "Common node of vrf, default-context";
    container net-io-tunnels {
      description
        "Tunnel information that NETIO has ";
      list net-io-tunnel {
        key "tunnel-name";
        description
          "PIM netio tunnel information";
        leaf tunnel-name {
          type xr:Cisco-ios-xr-string {
            length "1..64";
          }
          description
            "Tunnel name";
        }
        uses PIM-TUNNEL-INFO-BAG;
      }
    }
  }

  grouping RPF-SUMMARY {
    description
      "Common node of vrf, default-context";
    container rpf-summary {
      description
        "PIM RPF registration summary";
      uses PIM-RPF-SUMMARY-BAG;
    }
  }

  grouping IFRS-INTERFACE-TABLE {
    description
      "Common node of vrf, default-context";
    container ifrs-interfaces {
      description
        "PIM interfaces in forward reference store table";
      list ifrs-interface {
        key "interface-name";
        description
          "PIM IFRS interface information";
        leaf interface-name {
          type xr:Interface-name;
          description
            "Interface name";
        }
        uses PIM-IDB-BAG;
      }
    }
  }

  grouping PROCESS {
    description
      "Common node of active, standby";
    container process {
      description
        "Process";
      container nsr {
        description
          "NSR Information";
        uses PIM-NSR-BAG;
      }
      container summary {
        description
          "PIM Global Summary";
        uses PIM-SUMMARY-BAG;
      }
      container nsf {
        description
          "PIM NSF information";
        uses PIM-NSF-BAG;
      }
      container issu {
        description
          "ISSU Information";
        uses PIM-ISSU-BAG;
      }
    }
  }

  grouping JP-STATISTICS-TABLE {
    description
      "Common node of vrf, default-context";
    container jp-statistics {
      description
        "PIM join prune statistics table";
      list jp-statistic {
        key "interface-name";
        description
          "PIM Join Prune Statistics";
        leaf interface-name {
          type xr:Interface-name;
          description
            "Interface name";
        }
        uses PIM-JPSTATS-BAG;
      }
    }
  }

  grouping TOPOLOGY-TABLE {
    description
      "Common node of vrf, default-context";
    container topologies {
      description
        "PIM topology table";
      list topology {
        key "source-address group-address rpt";
        description
          "PIM topology information";
        leaf source-address {
          type inet:ip-address-no-zone;
          description
            "Source address";
        }
        leaf group-address {
          type inet:ip-address-no-zone;
          description
            "Group address";
        }
        leaf rpt {
          type uint32;
          description
            "RPT bit";
        }
        uses PIM-TT-ROUTE-BAG;
      }
    }
  }

  grouping NEIGHBOR-SUMMARY-TABLE {
    description
      "Common node of vrf, default-context";
    container neighbor-summaries {
      description
        "PIM neighbor summary table";
      list neighbor-summary {
        key "interface-name";
        description
          "PIM neighbor summary information";
        leaf interface-name {
          type xr:Interface-name;
          description
            "Interface name";
        }
        uses PIM-NBR-SUMM-BAG;
      }
    }
  }

  grouping TRAFFIC-COUNTERS {
    description
      "Common node of vrf, default-context";
    container traffic-counters {
      description
        "PIM message traffic counters";
      uses PIM-TRAFFIC-BAG;
    }
  }

  grouping TOPOLOGY-ROUTE-COUNT {
    description
      "Common node of vrf, default-context";
    container topology-route-count {
      description
        "Topology route count information from PIM
         topology table";
      uses PIM-TT-SUMM-BAG;
    }
  }

  grouping TUNNEL-TABLE {
    description
      "Common node of vrf, default-context";
    container tunnels {
      description
        "Tunnels information that PIM has";
      list tunnel {
        key "tunnel-name";
        description
          "PIM tunnel information";
        leaf tunnel-name {
          type xr:Cisco-ios-xr-string {
            length "1..64";
          }
          description
            "Tunnel name";
        }
        uses PIM-TUNNEL-INFO-BAG;
      }
    }
  }

  grouping PIM-MA-COMMON-OPER-PIM-MA-SUMMARY-MP {
    description
      "Common node of active, standby";
    container pim-ma-summary {
      description
        "PIM MA summary";
      uses PIM-MA-SUMMARY;
    }
  }

  grouping ACTIVE {
    description
      "Common node of pim-ma, pim6-ma";
    container active {
      description
        "Active Process";
      uses INTERFACE-TABLE;
      uses PIM-MA-COMMON-OPER-PIM-MA-SUMMARY-MP;
    }
  }

  grouping IPV4-PIM-ROLE-LVL-OPER-ACTIVE {
    description
      "Common node of pim-ma, pim6-maCommon node of pim,
       ipv6-pim";
    container active {
      description
        "Active Process";
      uses DEFAULT-CONTEXT;
      uses PROCESS;
      uses VRF-TABLE;
    }
  }

  grouping GROUP-MAP-RPF-TABLE {
    description
      "Common node of vrf, default-context";
    container group-map-rpfs {
      description
        "PIM group mapping information";
      list group-map-rpf {
        key "prefix prefix-length client protocol rp-address rp-priority";
        description
          "PIM group mapping entry";
        leaf prefix {
          type inet:ip-address-no-zone;
          description
            "Prefix";
        }
        leaf prefix-length {
          type uint32;
          description
            "Prefix length";
        }
        leaf client {
          type Pim-client;
          description
            "Client";
        }
        leaf protocol {
          type Pim-protocol;
          description
            "Protocol";
        }
        leaf rp-address {
          type inet:ip-address-no-zone;
          description
            "RP address";
        }
        leaf rp-priority {
          type uint32;
          description
            "RP priority";
        }
        uses PIM-GRP-MAP-INFORPF-BAG;
      }
    }
  }

  grouping RPF-REDIRECT {
    description
      "Common node of vrf, default-context";
    container rpf-redirect {
      description
        "PIM ECMP RPF-redirect bundle";
      container redirect-route-databases {
        description
          "PIM ECMP RPF-redirect route database";
        list redirect-route-database {
          key "source-address group-address";
          description
            "PIM ECMP RPF-redirect route information";
          leaf source-address {
            type inet:ip-address-no-zone;
            description
              "Source address";
          }
          leaf group-address {
            type inet:ip-address-no-zone;
            description
              "Group address";
          }
          uses PIM-RPF-RDRCT-ROUTE-BAG;
        }
      }
      container bundle-interfaces {
        description
          "PIM ECMP RPF-redirect bundle information";
        list bundle-interface {
          key "bundle-name interface-name";
          description
            "PIM ECMP RPF-redirect bundle interface
             information";
          leaf bundle-name {
            type xr:Cisco-ios-xr-string {
              length "1..32";
            }
            description
              "Bundle name";
          }
          leaf interface-name {
            type xr:Interface-name;
            description
              "Bundle interface name";
          }
          uses PIM-RPF-RDRCT-BNDL-BAG;
        }
      }
    }
  }

  grouping CONTEXT {
    description
      "Common node of vrf, default-context";
    container context {
      description
        "PIM context information";
      uses PIM-CONTEXT-BAG;
    }
  }

  grouping INTERFACE-TABLE {
    description
      "Common node of active, standby";
    container interface-table {
      description
        "Interface Table";
      container interface-by-handles {
        description
          "Table of PIM MA interfaces indexed by handle";
        list interface-by-handle {
          key "interface-handle";
          description
            "PIM MA interface referenced by handle";
          leaf interface-handle {
            type uint32;
            description
              "Interface handle";
          }
          uses PIM-MA-IDB;
        }
      }
      container interface-by-names {
        description
          "Table of PIM MA interfaces indexed by name";
        list interface-by-name {
          key "interface-name";
          description
            "PIM MA interface referenced by name";
          leaf interface-name {
            type xr:Interface-name;
            description
              "Interface name";
          }
          uses PIM-MA-IDB;
        }
      }
    }
  }

  grouping IPV4-PIM-COMMON-OPER-INTERFACE-TABLE {
    description
      "Common node of active, standbyCommon node of vrf,
       default-context";
    container interfaces {
      description
        "PIM interfaces";
      list interface {
        key "interface-name";
        description
          "PIM interface name";
        leaf interface-name {
          type xr:Interface-name;
          description
            "Interface name";
        }
        uses PIM-IDB-BAG;
      }
    }
  }

  grouping SUMMARY {
    description
      "Common node of vrf, default-context";
    container summary {
      description
        "PIM summary";
      uses PIM-SUMMARY-BAG;
    }
  }

  grouping TOPOLOGY-INTERFACE-FLAG-ROUTE-COUNT-TABLE {
    description
      "Common node of vrf, default-context";
    container topology-interface-flag-route-counts {
      description
        "Route count for topology with interface flag set";
      list topology-interface-flag-route-count {
        key "interface-flag";
        description
          "Route count for topology with interface flag
           set";
        leaf interface-flag {
          type Pim-topology-interface-flag;
          description
            "Interface flag";
        }
        uses PIM-TT-SUMM-BAG;
      }
    }
  }

  grouping INTERFACE-STATISTICS-TABLE {
    description
      "Common node of vrf, default-context";
    container interface-statistics {
      description
        "PIM interface statistics";
      list interface-statistic {
        key "interface-name";
        description
          "PIM interface statistics";
        leaf interface-name {
          type xr:Interface-name;
          description
            "Interface name";
        }
        uses PIM-IFSTATS-BAG;
      }
    }
  }

  grouping GRE {
    description
      "Common node of vrf, default-context";
    container gre {
      description
        "GRE information";
      container gre-next-hops {
        description
          "GRE destination neighbor table";
        list gre-next-hop {
          key "destination-address";
          description
            "PIM GRE address next-hop information";
          leaf destination-address {
            type inet:ip-address-no-zone;
            description
              "GRE destination address";
          }
          uses PIM-GRE-INFO-BAG;
        }
      }
    }
  }

  grouping IFRS-SUMMARY {
    description
      "Common node of vrf, default-context";
    container ifrs-summary {
      description
        "PIM interfaces in forward reference store
         summary";
      uses PIM-IDB-SUMM-BAG;
    }
  }

  grouping DEFAULT-CONTEXT {
    description
      "Common node of active, standby";
    container default-context {
      description
        "Default Context";
      container global-interfaces {
        description
          "PIM global interface table";
        list global-interface {
          key "interface-name";
          description
            "PIM interface name";
          leaf interface-name {
            type xr:Interface-name;
            description
              "Interface name";
          }
          uses PIM-IDB-BAG;
        }
      }
      uses IFRS-INTERFACE-TABLE;
      uses INTERFACE-STATISTICS-TABLE;
      uses TOPOLOGY-ROUTE-COUNT;
      uses JP-STATISTICS-TABLE;
      uses MIB-DATABASE-TABLE;
      uses IFRS-SUMMARY;
      uses RANGE-LIST-TABLE;
      uses BSR;
      uses ROUTE-POLICY;
      uses RPF-SUMMARY;
      uses IPV4-PIM-COMMON-OPER-INTERFACE-TABLE;
      uses NET-IO-TUNNEL-TABLE;
      uses BIDIR-DF-STATE-TABLE;
      uses TOPOLOGY-TABLE;
      uses TOPOLOGY-INTERFACE-FLAG-ROUTE-COUNT-TABLE;
      uses GROUP-MAP-SOURCE-TABLE;
      uses TRAFFIC-COUNTERS;
      uses GROUP-MAP-RPF-TABLE;
      uses SUMMARY;
      uses GRE;
      uses BIDIR-DF-WINNER-TABLE;
      uses TABLE-CONTEXT-TABLE;
      uses NEIGHBOR-SUMMARY-TABLE;
      uses CONTEXT;
      uses TOPOLOGY-ENTRY-FLAG-ROUTE-COUNT-TABLE;
      uses RPF-REDIRECT;
      uses TUNNEL-TABLE;
      uses MULTICAST-STATIC-ROUTE-TABLE;
      uses NEIGHBOR-TABLE;
    }
  }

  grouping NEIGHBOR-TABLE {
    description
      "Common node of vrf, default-context";
    container neighbors {
      description
        "PIM neighbor table";
      list neighbor {
        key "interface-name neighbor-address";
        description
          "PIM neighbor information";
        leaf interface-name {
          type xr:Interface-name;
          description
            "Interface name";
        }
        leaf neighbor-address {
          type inet:ip-address-no-zone;
          description
            "Neighbor address";
        }
        uses PIM-NBR-BAG;
      }
    }
  }

  grouping MULTICAST-STATIC-ROUTE-TABLE {
    description
      "Common node of vrf, default-context";
    container multicast-static-routes {
      description
        "PIM multicast static route table";
      list multicast-static-route {
        key "address prefix-length";
        description
          "PIM multicast static route information";
        leaf address {
          type inet:ip-address-no-zone;
          description
            "Network address";
        }
        leaf prefix-length {
          type uint32;
          description
            "Prefix length";
        }
        uses PIM-MSTATIC-BAG;
      }
    }
  }

  grouping RANGE-LIST-TABLE {
    description
      "Common node of vrf, default-context";
    container ranges {
      description
        "PIM range list information";
      list range {
        key "rp-address client";
        description
          "PIM range list information";
        leaf rp-address {
          type inet:ip-address-no-zone;
          description
            "RP address";
        }
        leaf client {
          type Pim-client;
          description
            "Client";
        }
        uses PIM-RL-BAG;
      }
    }
  }

  grouping STANDBY {
    description
      "Common node of pim-ma, pim6-ma";
    container standby {
      description
        "Standby Process";
      uses INTERFACE-TABLE;
      uses PIM-MA-COMMON-OPER-PIM-MA-SUMMARY-MP;
    }
  }

  grouping IPV4-PIM-ROLE-LVL-OPER-STANDBY {
    description
      "Common node of pim-ma, pim6-maCommon node of pim,
       ipv6-pim";
    container standby {
      description
        "Standby Process";
      uses DEFAULT-CONTEXT;
      uses PROCESS;
      uses VRF-TABLE;
    }
  }

  augment "/ncs:devices/ncs:device/ncs:config" {
    // NCS drop config false container 'pim-ma'
    // NCS drop config false container pim
    // NCS drop config false container 'ipv6-pim'
    // NCS drop config false container 'pim6-ma'
  }
  augment "/ncs:devices/ncs:device/ncs:live-status" {
    container pim-ma {
      tailf:ncs-device-type "netconf";
      tailf:display-when "not(../../ncs:module) or ../../ncs:module[ncs:name='Cisco-IOS-XR-ipv4-pim-oper'] or (../../ncs:live-status-protocol[not(ncs:capability)]) or (../../ncs:live-status-protocol/ncs:capability/ncs:module[.='Cisco-IOS-XR-ipv4-pim-oper'])";
      status deprecated;
      description
        "This model is deprecated and is replaced by
         Cisco-IOS-XR-pim-oper.yang which will provide the
         compatible functionalities.  PIM MA operational
         data";
      uses live_ncs_ACTIVE;
      uses live_ncs_STANDBY;
    }
    container pim {
      tailf:ncs-device-type "netconf";
      tailf:display-when "not(../../ncs:module) or ../../ncs:module[ncs:name='Cisco-IOS-XR-ipv4-pim-oper'] or (../../ncs:live-status-protocol[not(ncs:capability)]) or (../../ncs:live-status-protocol/ncs:capability/ncs:module[.='Cisco-IOS-XR-ipv4-pim-oper'])";
      status deprecated;
      description
        "This model is deprecated and is replaced by
         Cisco-IOS-XR-pim-oper.yang which will provide the
         compatible functionalities.  PIM operational data";
      uses live_ncs_IPV4-PIM-ROLE-LVL-OPER-STANDBY;
      uses live_ncs_IPV4-PIM-ROLE-LVL-OPER-ACTIVE;
    }
    container ipv6-pim {
      tailf:ncs-device-type "netconf";
      tailf:display-when "not(../../ncs:module) or ../../ncs:module[ncs:name='Cisco-IOS-XR-ipv4-pim-oper'] or (../../ncs:live-status-protocol[not(ncs:capability)]) or (../../ncs:live-status-protocol/ncs:capability/ncs:module[.='Cisco-IOS-XR-ipv4-pim-oper'])";
      status deprecated;
      description
        "This model is deprecated and is replaced by
         Cisco-IOS-XR-pim-oper.yang which will provide the
         compatible functionalities.  IPv6 PIM operational
         data";
      uses live_ncs_IPV4-PIM-ROLE-LVL-OPER-STANDBY;
      uses live_ncs_IPV4-PIM-ROLE-LVL-OPER-ACTIVE;
    }
    container pim6-ma {
      tailf:ncs-device-type "netconf";
      tailf:display-when "not(../../ncs:module) or ../../ncs:module[ncs:name='Cisco-IOS-XR-ipv4-pim-oper'] or (../../ncs:live-status-protocol[not(ncs:capability)]) or (../../ncs:live-status-protocol/ncs:capability/ncs:module[.='Cisco-IOS-XR-ipv4-pim-oper'])";
      status deprecated;
      description
        "This model is deprecated and is replaced by
         Cisco-IOS-XR-pim-oper.yang which will provide the
         compatible functionalities.  PIM6 MA operational
         data";
      uses live_ncs_ACTIVE;
      uses live_ncs_STANDBY;
    }
  }
  augment "/ncs:devices/ncs:template/ncs:ned-id/ncs:config" {
    // NCS drop config false container 'pim-ma'
    // NCS drop config false container pim
    // NCS drop config false container 'ipv6-pim'
    // NCS drop config false container 'pim6-ma'
  }
}

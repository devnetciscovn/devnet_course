module ntp {
  // Generated by yanger -t ncs
  tailf:mount-id "cisco-iosxr-nc-7.3:cisco-iosxr-nc-7.3";
  tailf:ncs-device-type "netconf";

  namespace "http://cisco.com/calvados/ntp";
  prefix ntp;

  import tailf-common {
    prefix tailf;
  }
  import ietf-yang-types {
    prefix yang;
  }
  import Cisco-IOS-XR-sysadmin-show-trace {
    prefix show_trace;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR syadmin NTP configuration.

     This module contains definitions
     for the following management objects:
     NTP configuration data

     Copyright (c) 2013-2020 by Cisco Systems, Inc.
     All rights reserved.";

  revision 2016-07-04 {
    description
      "Remove refine stmt";
  }
  revision 2016-05-12 {
    description
      "Initial version";
  }

  grouping ncs_template_ntp_target {
    leaf name {
      type string;
    }
    leaf version {
      type string;
    }
    leaf key-id {
      type string;
    }
    leaf prefer {
      type empty;
    }
  }

  grouping ncs_rpc_notif_ntp_target {
    leaf name {
      type string;
    }
    leaf version {
      type int32 {
        range "1 .. 4";
      }
    }
    leaf key-id {
      type int32 {
        range "1 .. 65534";
      }
    }
    leaf prefer {
      type empty;
    }
  }

  grouping live_ncs_ntp_target {
    leaf name {
      type string;
    }
    leaf version {
      type int32 {
        range "1 .. 4";
      }
    }
    leaf key-id {
      type int32 {
        range "1 .. 65534";
      }
    }
    leaf prefer {
      type empty;
    }
  }

  grouping ntp_target {
    leaf name {
      type string;
    }
    leaf version {
      type int32 {
        range "1 .. 4";
      }
    }
    leaf key-id {
      type int32 {
        range "1 .. 65534";
      }
    }
    leaf prefer {
      type empty;
    }
  }

  augment "/ncs:devices/ncs:device/ncs:config" {
    container ntp {
      tailf:ncs-device-type "netconf";
      tailf:display-when "not(../../ncs:module) or ../../ncs:module[ncs:name='ntp']";
      list peer {
        key "name";
        uses ntp_target;
      }
      list server {
        key "name";
        uses ntp_target;
      }
      leaf-list trusted-key {
        type int32 {
          range "1 .. 65534";
        }
      }
      leaf authenticate {
        type empty;
      }
      list authentication-key {
        key "key-number";
        leaf key-number {
          type int32 {
            range "1 .. 65534";
          }
        }
        leaf md5-keyword {
          mandatory true;
          type enumeration {
            enum "md5";
          }
        }
        leaf encryption {
          mandatory false;
          type enumeration {
            enum "clear";
            enum "encrypted";
          }
        }
        leaf keyname {
          type string {
            length "min .. 32";
          }
          mandatory true;
        }
      }
      // NCS drop config false container trace
    }
    // NCS drop config false container 'clock-action'
  }
  augment "/ncs:devices/ncs:device/ncs:live-status" {
    container ntp {
      tailf:ncs-device-type "netconf";
      tailf:display-when "not(../../ncs:module) or ../../ncs:module[ncs:name='ntp'] or (../../ncs:live-status-protocol[not(ncs:capability)]) or (../../ncs:live-status-protocol/ncs:capability/ncs:module[.='ntp'])";
      list peer {
        key "name";
        uses live_ncs_ntp_target;
      }
      list server {
        key "name";
        uses live_ncs_ntp_target;
      }
      leaf-list trusted-key {
        type int32 {
          range "1 .. 65534";
        }
      }
      leaf authenticate {
        type empty;
      }
      list authentication-key {
        key "key-number";
        leaf key-number {
          type int32 {
            range "1 .. 65534";
          }
        }
        leaf md5-keyword {
          // NCS drop mandatory statement
          type enumeration {
            enum "md5";
          }
        }
        leaf encryption {
          // NCS drop mandatory statement
          type enumeration {
            enum "clear";
            enum "encrypted";
          }
        }
        leaf keyname {
          type string {
            length "min .. 32";
          }
          // NCS drop mandatory statement
        }
      }
      container trace {
        container ntp_helper {
          uses show_trace:live_ncs_traceable;
        }
      }
    }
    container clock-action {
      tailf:ncs-device-type "netconf";
      tailf:display-when "not(../../ncs:module) or ../../ncs:module[ncs:name='ntp'] or (../../ncs:live-status-protocol[not(ncs:capability)]) or (../../ncs:live-status-protocol/ncs:capability/ncs:module[.='ntp'])";
      container clock {
        container Action;
      }
    }
  }
  augment "/ncs:devices/ncs:template/ncs:ned-id/ncs:config" {
    container ntp {
      list peer {
        // NCS patched for predictable order
        ordered-by user;
        key "name";
        uses ncs_template_ntp_target;
      }
      list server {
        // NCS patched for predictable order
        ordered-by user;
        key "name";
        uses ncs_template_ntp_target;
      }
      leaf-list trusted-key {
        // NCS patched for predictable order
        ordered-by user;
        type string;
      }
      leaf authenticate {
        type empty;
      }
      list authentication-key {
        // NCS patched for predictable order
        ordered-by user;
        key "key-number";
        leaf key-number {
          type string;
        }
        leaf md5-keyword {
          // NCS drop mandatory statement
          type string;
        }
        leaf encryption {
          // NCS drop mandatory statement
          type string;
        }
        leaf keyname {
          type string;
          // NCS drop mandatory statement
        }
      }
      // NCS drop config false container trace
    }
    // NCS drop config false container 'clock-action'
  }
}

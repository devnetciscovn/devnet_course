module Cisco-IOS-XR-um-ipv6-prefix-list-cfg {
  // Generated by yanger -t ncs
  tailf:mount-id "cisco-iosxr-nc-7.3:cisco-iosxr-nc-7.3";
  tailf:ncs-device-type "netconf";

  namespace "http://cisco.com/ns/yang/Cisco-IOS-XR-um-ipv6-prefix-list-cfg";
  prefix um-ipv6-prefix-list-cfg;

  import cisco-semver {
    prefix semver;
  }
  import Cisco-IOS-XR-types {
    prefix xr;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv6-prefix-list package configuration.

     This YANG module augments the
     modules with configuration data.

     Copyright (c) 2019-2020 by Cisco Systems, Inc.
     All rights reserved.";

  revision 2020-12-03 {
    description
      "Limit Remark leaf length.";
    semver:module-version "1.0.0";
  }
  revision 2019-06-10 {
    description
      "Establish semantic version baseline.";
    semver:module-version "1.0.0";
  }
  revision 2019-04-02 {
    description
      "Initial version";
  }

  augment "/ncs:devices/ncs:device/ncs:config" {
    container ipv6 {
      tailf:ncs-device-type "netconf";
      tailf:display-when "not(../../ncs:module) or ../../ncs:module[ncs:name='Cisco-IOS-XR-um-ipv6-prefix-list-cfg']";
      description
        "IPv6 prefix list";
      container prefix-lists {
        description
          "Prefix list";
        list prefix-list {
          key "prefix-list-name";
          description
            "prefix list";
          leaf prefix-list-name {
            type xr:Cisco-ios-xr-string {
              length "1..32" {
                description
                  "Name of a prefix list - maximum 32 characters";
              }
            }
            description
              "Name of a prefix list - maximum 32 characters";
          }
          container sequences {
            description
              "Sequence number";
            list sequence {
              must '(remark and not(permission) and not(prefix) and not(mask) and not(zone) and not(match-prefix-length/ge or match-prefix-length/le or match-prefix-length/eq)) or (not(remark) and permission and prefix and mask)' {
                tailf:xpath-root 3;
              }
              key "sequence-number";
              description
                "Sequence number";
              leaf sequence-number {
                type uint32 {
                  range "1..2147483646" {
                    description
                      "Sequence number";
                  }
                }
                description
                  "Sequence number";
              }
              leaf remark {
                type string {
                  length "0..255" {
                    description
                      "Comments for the prefix list entry item";
                  }
                }
                description
                  "Comments for prefix list";
              }
              leaf permission {
                type enumeration {
                  enum "deny" {
                    value 0;
                    description
                      "Specify prefixes to reject";
                  }
                  enum "permit" {
                    value 1;
                    description
                      "Specify prefixes to permit";
                  }
                }
                description
                  "specify the type to be either deny (or) permit";
              }
              leaf prefix {
                type inet:ipv6-address-no-zone;
                description
                  "IPv6 address prefix";
              }
              leaf zone {
                type xr:Cisco-ios-xr-string {
                  length "1..32" {
                    description
                      "IPv6 zone if entered with IPv6 address";
                  }
                }
                description
                  "IPv6 zone if entered with IPv6 address";
              }
              leaf mask {
                type xr:Ipv6-prefix-length;
                description
                  "Mask length of IPv6 address";
              }
              container match-prefix-length {
                description
                  "Prefix length to be matched";
                leaf eq {
                  type uint32 {
                    range "0..128" {
                      description
                        "Prefix length";
                    }
                  }
                  must 'not(../ge or ../le)' {
                    tailf:xpath-root 3;
                  }
                  description
                    "Exact prefix length to be matched";
                }
                leaf ge {
                  type uint32 {
                    range "0..128" {
                      description
                        "Minimum prefix length";
                    }
                  }
                  must 'not(../eq)' {
                    tailf:xpath-root 3;
                  }
                  description
                    "Minimum prefix length to be matched";
                }
                leaf le {
                  type uint32 {
                    range "0..128" {
                      description
                        "Maximum prefix length";
                    }
                  }
                  must 'not(../eq)' {
                    tailf:xpath-root 3;
                  }
                  description
                    "Maximum prefix length to be matched";
                }
              }
            }
          }
        }
      }
    }
  }
  augment "/ncs:devices/ncs:device/ncs:live-status" {
    container ipv6 {
      tailf:ncs-device-type "netconf";
      tailf:display-when "not(../../ncs:module) or ../../ncs:module[ncs:name='Cisco-IOS-XR-um-ipv6-prefix-list-cfg'] or (../../ncs:live-status-protocol[not(ncs:capability)]) or (../../ncs:live-status-protocol/ncs:capability/ncs:module[.='Cisco-IOS-XR-um-ipv6-prefix-list-cfg'])";
      description
        "IPv6 prefix list";
      container prefix-lists {
        description
          "Prefix list";
        list prefix-list {
          key "prefix-list-name";
          description
            "prefix list";
          leaf prefix-list-name {
            type xr:live_ncs_Cisco-ios-xr-string;
            description
              "Name of a prefix list - maximum 32 characters";
          }
          container sequences {
            description
              "Sequence number";
            list sequence {
              // NCS drop must statement
              key "sequence-number";
              description
                "Sequence number";
              leaf sequence-number {
                type uint32 {
                  range "1..2147483646" {
                    description
                      "Sequence number";
                  }
                }
                description
                  "Sequence number";
              }
              leaf remark {
                type string {
                  length "0..255" {
                    description
                      "Comments for the prefix list entry item";
                  }
                }
                description
                  "Comments for prefix list";
              }
              leaf permission {
                type enumeration {
                  enum "deny" {
                    value 0;
                    description
                      "Specify prefixes to reject";
                  }
                  enum "permit" {
                    value 1;
                    description
                      "Specify prefixes to permit";
                  }
                }
                description
                  "specify the type to be either deny (or) permit";
              }
              leaf prefix {
                type inet:ipv6-address-no-zone;
                description
                  "IPv6 address prefix";
              }
              leaf zone {
                type xr:live_ncs_Cisco-ios-xr-string;
                description
                  "IPv6 zone if entered with IPv6 address";
              }
              leaf mask {
                type xr:live_ncs_Ipv6-prefix-length;
                description
                  "Mask length of IPv6 address";
              }
              container match-prefix-length {
                description
                  "Prefix length to be matched";
                leaf eq {
                  type uint32 {
                    range "0..128" {
                      description
                        "Prefix length";
                    }
                  }
                  // NCS drop must statement
                  description
                    "Exact prefix length to be matched";
                }
                leaf ge {
                  type uint32 {
                    range "0..128" {
                      description
                        "Minimum prefix length";
                    }
                  }
                  // NCS drop must statement
                  description
                    "Minimum prefix length to be matched";
                }
                leaf le {
                  type uint32 {
                    range "0..128" {
                      description
                        "Maximum prefix length";
                    }
                  }
                  // NCS drop must statement
                  description
                    "Maximum prefix length to be matched";
                }
              }
            }
          }
        }
      }
    }
  }
  augment "/ncs:devices/ncs:template/ncs:ned-id/ncs:config" {
    container ipv6 {
      description
        "IPv6 prefix list";
      container prefix-lists {
        description
          "Prefix list";
        list prefix-list {
          // NCS patched for predictable order
          ordered-by user;
          key "prefix-list-name";
          description
            "prefix list";
          leaf prefix-list-name {
            type xr:ncs_template_Cisco-ios-xr-string;
            description
              "Name of a prefix list - maximum 32 characters";
          }
          container sequences {
            description
              "Sequence number";
            list sequence {
              // NCS patched for predictable order
              ordered-by user;
              // NCS drop must statement
              key "sequence-number";
              description
                "Sequence number";
              leaf sequence-number {
                type string;
                description
                  "Sequence number";
              }
              leaf remark {
                type string;
                description
                  "Comments for prefix list";
              }
              leaf permission {
                type string;
                description
                  "specify the type to be either deny (or) permit";
              }
              leaf prefix {
                type string;
                description
                  "IPv6 address prefix";
              }
              leaf zone {
                type xr:ncs_template_Cisco-ios-xr-string;
                description
                  "IPv6 zone if entered with IPv6 address";
              }
              leaf mask {
                type xr:ncs_template_Ipv6-prefix-length;
                description
                  "Mask length of IPv6 address";
              }
              container match-prefix-length {
                description
                  "Prefix length to be matched";
                leaf eq {
                  type string;
                  // NCS drop must statement
                  description
                    "Exact prefix length to be matched";
                }
                leaf ge {
                  type string;
                  // NCS drop must statement
                  description
                    "Minimum prefix length to be matched";
                }
                leaf le {
                  type string;
                  // NCS drop must statement
                  description
                    "Maximum prefix length to be matched";
                }
              }
            }
          }
        }
      }
    }
  }
}

module Cisco-IOS-XR-sysadmin-ncs1004-envmon-types {
  // Generated by yanger -t ncs
  tailf:mount-id "cisco-iosxr-nc-7.3:cisco-iosxr-nc-7.3";
  tailf:ncs-device-type "netconf";

  namespace "http://www.cisco.com/ns/Cisco-IOS-XR-sysadmin-ncs1004-envmon-types";
  prefix envmon-types;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2019-04-15 {
    description
      "Establish semantic version baseline.";
    semver:module-version "1.0.0";
  }
  revision 2018-06-25 {
    description
      "Namespace change to comply with Cisco guidelines on namespace";
  }

  typedef ncs_template_num_pm {
    type string;
  }

  typedef ncs_rpc_notif_num_pm {
    type uint32 {
      range "0..12";
    }
  }

  typedef live_ncs_num_pm {
    type uint32 {
      range "0..12";
    }
  }

  typedef num_pm {
    type uint32 {
      range "0..12";
    }
  }

  grouping ncs_template_fan-speed-group {
    // NCS drop config false leaf 'raise-fan-speed'
  }

  grouping ncs_template_fan-ctrl-optics-group {
    // NCS drop config false leaf 'fan-ctrl-optics'
  }

  grouping ncs_template_vin-uv-shut-group {
    // NCS drop config false leaf 'graceful-shutdown'
  }

  grouping ncs_rpc_notif_fan-speed-group {
    leaf raise-fan-speed {
      type uint32 {
        range "0..100";
      }
      config false;
    }
  }

  grouping ncs_rpc_notif_fan-ctrl-optics-group {
    leaf fan-ctrl-optics {
      type uint32 {
        range "0..1";
      }
      config false;
    }
  }

  grouping ncs_rpc_notif_vin-uv-shut-group {
    leaf graceful-shutdown {
      type uint32 {
        range "0..1";
      }
      config false;
    }
  }

  grouping live_ncs_fan-speed-group {
    leaf raise-fan-speed {
      type uint32 {
        range "0..100";
      }
    }
  }

  grouping live_ncs_fan-ctrl-optics-group {
    leaf fan-ctrl-optics {
      type uint32 {
        range "0..1";
      }
    }
  }

  grouping live_ncs_vin-uv-shut-group {
    leaf graceful-shutdown {
      type uint32 {
        range "0..1";
      }
    }
  }

  grouping fan-speed-group {
    // NCS drop config false leaf 'raise-fan-speed'
  }

  grouping fan-ctrl-optics-group {
    // NCS drop config false leaf 'fan-ctrl-optics'
  }

  grouping vin-uv-shut-group {
    // NCS drop config false leaf 'graceful-shutdown'
  }
}

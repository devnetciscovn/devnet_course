module Cisco-IOS-XR-ncs5k-fea-pfilter-nonatomic-cfg {
  // Generated by yanger -t ncs
  tailf:mount-id "cisco-iosxr-nc-7.3:cisco-iosxr-nc-7.3";
  tailf:ncs-device-type "netconf";

  namespace "http://cisco.com/ns/yang/Cisco-IOS-XR-ncs5k-fea-pfilter-nonatomic-cfg";
  prefix ncs5k-fea-pfilter-nonatomic-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs5k-fea-pfilter-nonatomic package configuration.

     This module contains definitions
     for the following management objects:
       hardware: Hardware

     Copyright (c) 2013-2019 by Cisco Systems, Inc.
     All rights reserved.";

  revision 2019-04-05 {
    description
      "Establish semantic version baseline.";
    semver:module-version "1.0.0";
  }
  revision 2016-09-01 {
    description
      "Implementing Conf Yang Model for Non-Atomic ACL";
  }
  revision 2015-11-09 {
    description
      "IOS XR 6.0 revision.";
  }

  typedef ncs_template_Atomic-disable-dflt-actn {
    type string;
    description
      "Atomic disable dflt actn";
  }

  typedef ncs_rpc_notif_Atomic-disable-dflt-actn {
    type enumeration {
      enum "default-action-deny" {
        value 1;
        description
          "Drops traffic during modification";
      }
      enum "default-action-permit" {
        value 2;
        description
          "Forward traffic during modification";
      }
    }
    description
      "Atomic disable dflt actn";
  }

  typedef live_ncs_Atomic-disable-dflt-actn {
    type enumeration {
      enum "default-action-deny" {
        value 1;
        description
          "Drops traffic during modification";
      }
      enum "default-action-permit" {
        value 2;
        description
          "Forward traffic during modification";
      }
    }
    description
      "Atomic disable dflt actn";
  }

  typedef Atomic-disable-dflt-actn {
    type enumeration {
      enum "default-action-deny" {
        value 1;
        description
          "Drops traffic during modification";
      }
      enum "default-action-permit" {
        value 2;
        description
          "Forward traffic during modification";
      }
    }
    description
      "Atomic disable dflt actn";
  }

  augment "/ncs:devices/ncs:device/ncs:config" {
    container hardware {
      tailf:ncs-device-type "netconf";
      tailf:display-when "not(../../ncs:module) or ../../ncs:module[ncs:name='Cisco-IOS-XR-ncs5k-fea-pfilter-nonatomic-cfg']";
      description
        "Hardware";
      container access-list {
        description
          "Access-list option";
        leaf atomic-disable {
          type Atomic-disable-dflt-actn;
          description
            "Specify Option for Atomic disable";
        }
      }
    }
  }
  augment "/ncs:devices/ncs:device/ncs:live-status" {
    container hardware {
      tailf:ncs-device-type "netconf";
      tailf:display-when "not(../../ncs:module) or ../../ncs:module[ncs:name='Cisco-IOS-XR-ncs5k-fea-pfilter-nonatomic-cfg'] or (../../ncs:live-status-protocol[not(ncs:capability)]) or (../../ncs:live-status-protocol/ncs:capability/ncs:module[.='Cisco-IOS-XR-ncs5k-fea-pfilter-nonatomic-cfg'])";
      description
        "Hardware";
      container access-list {
        description
          "Access-list option";
        leaf atomic-disable {
          type live_ncs_Atomic-disable-dflt-actn;
          description
            "Specify Option for Atomic disable";
        }
      }
    }
  }
  augment "/ncs:devices/ncs:template/ncs:ned-id/ncs:config" {
    container hardware {
      description
        "Hardware";
      container access-list {
        description
          "Access-list option";
        leaf atomic-disable {
          type ncs_template_Atomic-disable-dflt-actn;
          description
            "Specify Option for Atomic disable";
        }
      }
    }
  }
}

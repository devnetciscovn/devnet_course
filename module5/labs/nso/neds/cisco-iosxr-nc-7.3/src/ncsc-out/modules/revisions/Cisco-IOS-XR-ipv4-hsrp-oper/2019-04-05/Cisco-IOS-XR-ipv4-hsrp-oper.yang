module Cisco-IOS-XR-ipv4-hsrp-oper {
  // Generated by yanger -t ncs
  tailf:mount-id "cisco-iosxr-nc-7.3:cisco-iosxr-nc-7.3";
  tailf:ncs-device-type "netconf";

  namespace "http://cisco.com/ns/yang/Cisco-IOS-XR-ipv4-hsrp-oper";
  prefix ipv4-hsrp-oper;

  import ietf-inet-types {
    prefix inet;
  }
  import Cisco-IOS-XR-types {
    prefix xr;
  }
  import cisco-semver {
    prefix semver;
  }
  include Cisco-IOS-XR-ipv4-hsrp-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-hsrp package operational data.

     This module contains definitions
     for the following management objects:
       hsrp: HSRP operational data

     Copyright (c) 2013-2019 by Cisco Systems, Inc.
     All rights reserved.";

  revision 2019-04-05 {
    description
      "Establish semantic version baseline.";
    semver:module-version "1.0.0";
  }
  revision 2018-12-07 {
    description
      "Moved group numbers to a range.";
  }
  revision 2017-09-07 {
    description
      "Fixed type translation error.";
  }
  revision 2015-11-09 {
    description
      "IOS XR 6.0 revision.";
  }

  typedef ncs_template_Hsrp-group {
    type string;
    description
      "Hsrp group";
  }

  typedef ncs_rpc_notif_Hsrp-group {
    type uint32 {
      range "0..4095";
    }
    description
      "Hsrp group";
  }

  typedef live_ncs_Hsrp-group {
    type uint32 {
      range "0..4095";
    }
    description
      "Hsrp group";
  }

  typedef Hsrp-group {
    type uint32 {
      range "0..4095";
    }
    description
      "Hsrp group";
  }

  augment "/ncs:devices/ncs:device/ncs:config" {
    // NCS drop config false container hsrp
  }
  augment "/ncs:devices/ncs:device/ncs:live-status" {
    container hsrp {
      tailf:ncs-device-type "netconf";
      tailf:display-when "not(../../ncs:module) or ../../ncs:module[ncs:name='Cisco-IOS-XR-ipv4-hsrp-oper'] or (../../ncs:live-status-protocol[not(ncs:capability)]) or (../../ncs:live-status-protocol/ncs:capability/ncs:module[.='Cisco-IOS-XR-ipv4-hsrp-oper'])";
      description
        "HSRP operational data";
      container ipv4 {
        description
          "IPv4 HSRP information";
        container groups {
          description
            "The HSRP standby group table";
          list group {
            key "interface-name group-number";
            description
              "An HSRP standby group";
            leaf interface-name {
              type xr:live_ncs_Interface-name;
              description
                "The interface name";
            }
            leaf group-number {
              type live_ncs_Hsrp-group;
              description
                "The HSRP group number";
            }
            uses live_ncs_STANDBY-GRP-INFO;
          }
        }
        container tracked-interfaces {
          description
            "The HSRP tracked interfaces table";
          list tracked-interface {
            key "interface-name group-number tracked-interface-name";
            description
              "An HSRP tracked interface entry";
            leaf interface-name {
              type xr:live_ncs_Interface-name;
              description
                "The interface name of the interface";
            }
            leaf group-number {
              type live_ncs_Hsrp-group;
              description
                "The HSRP group number";
            }
            leaf tracked-interface-name {
              type xr:live_ncs_Interface-name;
              description
                "The interface name of the interface being
                 tracked";
            }
            uses live_ncs_STANDBY-TRACKEDIF-INFO;
          }
        }
        container interfaces {
          description
            "The HSRP interface information table";
          list interface {
            key "interface-name";
            description
              "A HSRP interface entry";
            leaf interface-name {
              type xr:live_ncs_Interface-name;
              description
                "The interface name";
            }
            uses live_ncs_STANDBY-IF-INFO;
          }
        }
      }
      container mgo-sessions {
        description
          "HSRP MGO session table";
        list mgo-session {
          key "session-name";
          description
            "HSRP MGO session";
          leaf session-name {
            type xr:live_ncs_Cisco-ios-xr-string;
            description
              "HSRP MGO session name";
          }
          uses live_ncs_HSRP-MGO-INFO;
        }
      }
      container ipv6 {
        description
          "IPv6 HSRP information";
        container tracked-interfaces {
          description
            "The HSRP tracked interfaces table";
          list tracked-interface {
            key "interface-name group-number tracked-interface-name";
            description
              "An HSRP tracked interface entry";
            leaf interface-name {
              type xr:live_ncs_Interface-name;
              description
                "The interface name of the interface";
            }
            leaf group-number {
              type live_ncs_Hsrp-group;
              description
                "The HSRP group number";
            }
            leaf tracked-interface-name {
              type xr:live_ncs_Interface-name;
              description
                "The interface name of the interface being
                 tracked";
            }
            uses live_ncs_STANDBY-TRACKEDIF-INFO;
          }
        }
        container groups {
          description
            "The HSRP standby group table";
          list group {
            key "interface-name group-number";
            description
              "An HSRP standby group";
            leaf interface-name {
              type xr:live_ncs_Interface-name;
              description
                "The interface name";
            }
            leaf group-number {
              type live_ncs_Hsrp-group;
              description
                "The HSRP group number";
            }
            uses live_ncs_STANDBY-GRP-INFO;
          }
        }
        container interfaces {
          description
            "The HSRP interface information table";
          list interface {
            key "interface-name";
            description
              "A HSRP interface entry";
            leaf interface-name {
              type xr:live_ncs_Interface-name;
              description
                "The interface name";
            }
            uses live_ncs_STANDBY-IF-INFO;
          }
        }
      }
      container bfd-sessions {
        description
          "The table of HSRP BFD Sessions";
        list bfd-session {
          key "interface-name ip-address";
          description
            "An HSRP BFD Session";
          leaf interface-name {
            type xr:live_ncs_Interface-name;
            description
              "The interface name";
          }
          leaf ip-address {
            type inet:ip-address-no-zone;
            description
              "Destination IP Address of BFD Session";
          }
          uses live_ncs_STANDBY-BFD-INFO;
        }
      }
      container summary {
        description
          "HSRP summary statistics";
        uses live_ncs_HSRP-SUMMARY-INFO;
      }
    }
  }
  augment "/ncs:devices/ncs:template/ncs:ned-id/ncs:config" {
    // NCS drop config false container hsrp
  }
}

module Cisco-IOS-XR-sysadmin-ethsw-esdma-mlap {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-mlap";
  prefix esdma_mlap;

  import ietf-yang-types {
    prefix ietf;
  }
  import Cisco-IOS-XR-sysadmin-ethsw-esdma-types {
    prefix esdma_types;
  }
  import Cisco-IOS-XR-sysadmin-show-trace {
    prefix show_trace;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch mlap' commands.

     Copyright(c) 2020 by Cisco Systems, Inc.
     All rights reserved.

     Copyright (c) 2012-2020 by Cisco Systems, Inc.
     All rights reserved.";

  revision 2020-01-10 {
    description
      "Changes for whitebox esdma-mlap cli outputs";
    semver:module-version "1.1.0";
  }
  revision 2019-04-15 {
    description
      "Establish semantic version baseline.";
    semver:module-version "1.0.0";
  }
  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping ncs_template_mlap-endpoint-state-info {
    leaf valid {
      type string;
      description
        "Indicates whether this endpoint information contains valid data.";
    }
    leaf chassis-type {
      // NCS drop when statement
      type esdma_types:ncs_template_esdma-rack-type-enum;
      description
        "The chassis type of this endpoint is in";
    }
    leaf endpoint-type {
      // NCS drop when statement
      type esdma_types:ncs_template_esdma-switch-type-enum;
      description
        "The type of endpoint this endpoint switch is on";
    }
    leaf endpoint-slot-number {
      // NCS drop when statement
      type string;
      description
        "Slot number of this endpoint";
    }
    leaf endpoint-switch-number {
      // NCS drop when statement
      type string;
      description
        "Switch number for the endpoint";
    }
    leaf endpoint-switch-port-number {
      // NCS drop when statement
      type string;
      description
        "Port number on the switch for the endpoint";
    }
    leaf endpoint-switch-port-name {
      type string;
      description
        "Port number on the switch for the endpoint";
    }
    leaf endpoint-chassis-serial-number {
      // NCS drop when statement
      type string;
      description
        "Serial number for the endpoint";
    }
    leaf mlap-state {
      // NCS drop when statement
      type esdma_types:ncs_template_mlap-state-enum;
      description
        "Protocol invoked port state";
    }
    leaf inter-fcc_sw-port {
      // NCS drop when statement
      type string;
      description
        "Indicates whether this port is used for an inter-F-SW connection";
    }
    leaf fcc_sw-indirectly-reachable {
      // NCS drop when statement
      type string;
      description
        "Indicates whether this port can indirectly reach an F-SW";
    }
  }

  grouping ncs_template_mlap-internal-details {
    container mlap-internal-details {
      container info {
        leaf port-owner {
          type esdma_types:ncs_template_esdma-cpu;
          description
            "Indicates which switch data path the port belongs to";
        }
        leaf current-active-owner {
          type esdma_types:ncs_template_esdma-cpu;
          description
            "Indicates which switch is currently mastering chassis data";
        }
        leaf mlap-peer-flags {
          type string;
          description
            "Peer's port MLAP protocol flags";
        }
        leaf mlap-peer-idle-count {
          type string;
          description
            "Time intervals peer has not updated information";
        }
        leaf my-connection-active-mask {
          type string;
          description
            "My port active mask view";
        }
        leaf peer-connection-active-mask {
          type string;
          description
            "Peer's port active mask view";
        }
        leaf endpoint-card-type {
          type esdma_types:ncs_template_mlap-ep-type;
          description
            "Indicates the high-level card type this switch port is peering with";
        }
        leaf endpoint-mac-address {
          type string;
          description
            "MAC addess of device of the protocol peer for this switch port";
        }
      }
    }
  }

  grouping ncs_template_mlap-external-details {
    container mlap-external-details {
      container local-state-information {
        description
          "MLAP state information from this port's perspective";
        uses ncs_template_mlap-endpoint-state-info;
      }
      container peer-state-information {
        description
          "MLAP state information from peer port's perspective";
        uses ncs_template_mlap-endpoint-state-info;
      }
      container peer-other-link-state-information {
        description
          "MLAP state information for peer's other uplink perspective (RP/SC only)";
        uses ncs_template_mlap-endpoint-state-info;
      }
    }
  }

  grouping ncs_template_mlap-detail-data {
    container detail {
      list location {
        // NCS patched for predictable order
        ordered-by user;
        key "rack card switch-id";
        leaf rack {
          type esdma_types:ncs_template_esdma-rack-num-enum;
        }
        leaf card {
          type esdma_types:ncs_template_esdma-cpu;
        }
        leaf switch-id {
          type esdma_types:ncs_template_esdma-switch-type-enum;
          description
            "Switch type";
        }
        list port-iter {
          // NCS patched for predictable order
          ordered-by user;
          key "port";
          leaf port {
            type esdma_types:ncs_template_esdma-switch-port-type;
            description
              "Switch port";
          }
          container gen-data {
            leaf serial-num {
              type string;
              description
                "Rack serial number";
            }
            leaf connects-to {
              type string;
              description
                "Indicates what this port connects to";
            }
            leaf phys-state {
              type esdma_types:ncs_template_esdma-switch-port-state;
              description
                "Physical port state";
            }
            leaf admin-state {
              type esdma_types:ncs_template_esdma-switch-port-state;
              description
                "Administrative port state";
            }
            leaf protocol-state {
              type esdma_types:ncs_template_mlap-state-enum;
              description
                "Protocol invoked port state";
            }
            leaf forwarding {
              type esdma_types:ncs_template_switch-forwarding-state;
              description
                "Indicates whether this port is allowed to forward traffic";
            }
            leaf mlap-protocol {
              type esdma_types:ncs_template_mlap-protocol-enum;
              description
                "Indicates whether the internal or external MLAP protocol is active on this port";
            }
            leaf protocol-pkt-sent {
              type string;
              description
                "Number of protocol packets sent";
            }
            leaf protocol-pkt-recv {
              type string;
              description
                "Number of protocol packets received";
            }
            leaf protocol-set-color-pkts-sent {
              type string;
              description
                "Number of set-active-VLAN requests";
            }
            leaf protocol-set-color-pkts-recv {
              type string;
              description
                "Number of set-active-VLAN responses";
            }
            leaf protocol-send-error {
              type string;
              description
                "Number of protocol packet send errors";
            }
            leaf protocol-recv-error {
              type string;
              description
                "Number of protocol packet receive errors";
            }
            leaf protocol-state-changes {
              type string;
              description
                "Number of state changes";
            }
          }
          choice detail-type {
            case internal-detail {
              uses ncs_template_mlap-internal-details;
            }
            case external-detail {
              uses ncs_template_mlap-external-details;
            }
          }
        }
      }
    }
  }

  grouping ncs_template_mlap-summary-data {
    container summary-data {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest";
        }
        leaf switch-id {
          type esdma_types:ncs_template_esdma-switch-type-enum;
          description
            "Switch type";
        }
        leaf serial-num {
          type string;
          description
            "Rack serial number";
        }
        list port-iter {
          // NCS patched for predictable order
          ordered-by user;
          key "port";
          leaf port {
            type esdma_types:ncs_template_esdma-switch-port-type;
            description
              "Switch port";
          }
          leaf port-name {
            type string;
            description
              "Switch port";
          }
          leaf phys-state {
            type esdma_types:ncs_template_esdma-switch-port-state;
            description
              "Physical port state";
          }
          leaf admin-state {
            type esdma_types:ncs_template_esdma-switch-port-state;
            description
              "Administrative port state";
          }
          leaf protocol-state {
            type esdma_types:ncs_template_mlap-state-enum;
            description
              "Protocol invoked port state";
          }
          leaf forwarding {
            type esdma_types:ncs_template_switch-forwarding-state;
            description
              "Indicates whether this port is allowed to forward traffic";
          }
          leaf mlap-protocol {
            type esdma_types:ncs_template_mlap-protocol-enum;
            description
              "Indicates whether the internal or external MLAP protocol is active on this port";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping ncs_template_mlap-statistics-data {
    container statistics {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest";
        }
        leaf switch-id {
          type esdma_types:ncs_template_esdma-switch-type-enum;
          description
            "Switch type";
        }
        leaf serial-num {
          type string;
          description
            "Rack serial number";
        }
        list port-iter {
          // NCS patched for predictable order
          ordered-by user;
          key "port";
          leaf port {
            type esdma_types:ncs_template_esdma-switch-port-type;
            description
              "Switch port";
          }
          leaf port-name {
            type string;
            description
              "Switch port";
          }
          leaf protocol-state {
            type esdma_types:ncs_template_mlap-state-enum;
            description
              "Protocol invoked port state";
          }
          leaf protocol-state-changes {
            type string;
            description
              "Number of state changes";
          }
          leaf protocol-pkt-sent {
            type string;
            description
              "Number of protocol packets sent";
          }
          leaf protocol-pkt-recv {
            type string;
            description
              "Number of protocol packets received";
          }
          leaf protocol-set-color-pkts-sent {
            type string;
            description
              "Number of set-active-VLAN requests";
          }
          leaf protocol-set-color-pkts-recv {
            type string;
            description
              "Number of set-active-VLAN responses";
          }
          leaf protocol-send-error {
            type string;
            description
              "Number of protocol packet send errors";
          }
          leaf protocol-recv-error {
            type string;
            description
              "Number of protocol packet receive errors";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping ncs_template_mlap-reachable-data {
    container reachable {
      list location {
        // NCS patched for predictable order
        ordered-by user;
        key "rack card switch-id";
        leaf rack {
          type esdma_types:ncs_template_esdma-rack-num-enum;
        }
        leaf card {
          type esdma_types:ncs_template_esdma-cpu;
        }
        leaf switch-id {
          type esdma_types:ncs_template_esdma-switch-type-enum;
        }
      }
    }
  }

  grouping ncs_template_mlap-debug-counters {
    container debug {
      container counters {
        list location {
          // NCS patched for predictable order
          ordered-by user;
          key "rack card switch-id";
          leaf rack {
            type esdma_types:ncs_template_esdma-rack-num-enum;
          }
          leaf card {
            type esdma_types:ncs_template_esdma-cpu;
          }
          leaf switch-id {
            type esdma_types:ncs_template_esdma-switch-type-enum;
          }
          container counters {
            leaf eval-all-links-called {
              type string;
            }
            leaf timer-event-queued {
              type string;
            }
            leaf rx-packet-event-queued {
              type string;
            }
            leaf eval-all-links-queued {
              type string;
            }
            leaf link-status-queued {
              type string;
            }
            leaf admin-status-queued {
              type string;
            }
            leaf fwd-status-queued {
              type string;
            }
            leaf current-fifo-depth {
              type string;
            }
            leaf max-fifo-depth {
              type string;
            }
            leaf vlan-color-changes {
              type string;
            }
            leaf current-mlap-timeout-ms-interval {
              type string;
            }
            leaf aging-debug-enabled {
              type string;
            }
            leaf trace-verbosity {
              type esdma_types:ncs_template_mlap-trace-verbosity;
            }
          }
        }
      }
    }
  }

  grouping ncs_template_mlap-oper-group {
    container mlap {
      description
        "MLAP switch data";
      uses ncs_template_mlap-reachable-data;
      uses ncs_template_mlap-detail-data;
      uses ncs_template_mlap-statistics-data;
      uses ncs_template_mlap-summary-data;
      uses ncs_template_mlap-debug-counters;
      uses show_trace:ncs_template_traceable;
    }
  }

  grouping ncs_rpc_notif_mlap-endpoint-state-info {
    leaf valid {
      type boolean;
      description
        "Indicates whether this endpoint information contains valid data.";
    }
    leaf chassis-type {
      when "../valid = 'true'" {
        tailf:xpath-root 3;
      }
      type esdma_types:ncs_rpc_notif_esdma-rack-type-enum;
      description
        "The chassis type of this endpoint is in";
    }
    leaf endpoint-type {
      when "../valid = 'true'" {
        tailf:xpath-root 3;
      }
      type esdma_types:ncs_rpc_notif_esdma-switch-type-enum;
      description
        "The type of endpoint this endpoint switch is on";
    }
    leaf endpoint-slot-number {
      when "../valid = 'true'" {
        tailf:xpath-root 3;
      }
      type uint32;
      description
        "Slot number of this endpoint";
    }
    leaf endpoint-switch-number {
      when "../valid = 'true'" {
        tailf:xpath-root 3;
      }
      type uint32;
      description
        "Switch number for the endpoint";
    }
    leaf endpoint-switch-port-number {
      when "../valid = 'true'" {
        tailf:xpath-root 3;
      }
      type uint32;
      description
        "Port number on the switch for the endpoint";
    }
    leaf endpoint-switch-port-name {
      type string;
      description
        "Port number on the switch for the endpoint";
    }
    leaf endpoint-chassis-serial-number {
      when "../valid = 'true'" {
        tailf:xpath-root 3;
      }
      type string;
      description
        "Serial number for the endpoint";
    }
    leaf mlap-state {
      when "../valid = 'true'" {
        tailf:xpath-root 3;
      }
      type esdma_types:ncs_rpc_notif_mlap-state-enum;
      description
        "Protocol invoked port state";
    }
    leaf inter-fcc_sw-port {
      when "../valid = 'true'" {
        tailf:xpath-root 3;
      }
      type boolean;
      description
        "Indicates whether this port is used for an inter-F-SW connection";
    }
    leaf fcc_sw-indirectly-reachable {
      when "../valid = 'true'" {
        tailf:xpath-root 3;
      }
      type boolean;
      description
        "Indicates whether this port can indirectly reach an F-SW";
    }
  }

  grouping ncs_rpc_notif_mlap-internal-details {
    container mlap-internal-details {
      container info {
        leaf port-owner {
          type esdma_types:ncs_rpc_notif_esdma-cpu;
          description
            "Indicates which switch data path the port belongs to";
        }
        leaf current-active-owner {
          type esdma_types:ncs_rpc_notif_esdma-cpu;
          description
            "Indicates which switch is currently mastering chassis data";
        }
        leaf mlap-peer-flags {
          type bits {
            bit Valid {
              position 0;
            }
            bit FCC-Active {
              position 1;
            }
            bit Force-Active {
              position 2;
            }
            bit Ignore-Data {
              position 31;
            }
          }
          description
            "Peer's port MLAP protocol flags";
        }
        leaf mlap-peer-idle-count {
          type uint32;
          description
            "Time intervals peer has not updated information";
        }
        leaf my-connection-active-mask {
          type uint64;
          description
            "My port active mask view";
        }
        leaf peer-connection-active-mask {
          type uint64;
          description
            "Peer's port active mask view";
        }
        leaf endpoint-card-type {
          type esdma_types:ncs_rpc_notif_mlap-ep-type;
          description
            "Indicates the high-level card type this switch port is peering with";
        }
        leaf endpoint-mac-address {
          type ietf:mac-address;
          description
            "MAC addess of device of the protocol peer for this switch port";
        }
      }
    }
  }

  grouping ncs_rpc_notif_mlap-external-details {
    container mlap-external-details {
      container local-state-information {
        description
          "MLAP state information from this port's perspective";
        uses ncs_rpc_notif_mlap-endpoint-state-info;
      }
      container peer-state-information {
        description
          "MLAP state information from peer port's perspective";
        uses ncs_rpc_notif_mlap-endpoint-state-info;
      }
      container peer-other-link-state-information {
        description
          "MLAP state information for peer's other uplink perspective (RP/SC only)";
        uses ncs_rpc_notif_mlap-endpoint-state-info;
      }
    }
  }

  grouping ncs_rpc_notif_mlap-detail-data {
    container detail {
      list location {
        key "rack card switch-id";
        leaf rack {
          type esdma_types:ncs_rpc_notif_esdma-rack-num-enum;
        }
        leaf card {
          type esdma_types:ncs_rpc_notif_esdma-cpu;
        }
        leaf switch-id {
          type esdma_types:ncs_rpc_notif_esdma-switch-type-enum;
          description
            "Switch type";
        }
        list port-iter {
          key "port";
          leaf port {
            type esdma_types:ncs_rpc_notif_esdma-switch-port-type;
            description
              "Switch port";
          }
          container gen-data {
            leaf serial-num {
              type string;
              description
                "Rack serial number";
            }
            leaf connects-to {
              type string;
              description
                "Indicates what this port connects to";
            }
            leaf phys-state {
              type esdma_types:ncs_rpc_notif_esdma-switch-port-state;
              description
                "Physical port state";
            }
            leaf admin-state {
              type esdma_types:ncs_rpc_notif_esdma-switch-port-state;
              description
                "Administrative port state";
            }
            leaf protocol-state {
              type esdma_types:ncs_rpc_notif_mlap-state-enum;
              description
                "Protocol invoked port state";
            }
            leaf forwarding {
              type esdma_types:ncs_rpc_notif_switch-forwarding-state;
              description
                "Indicates whether this port is allowed to forward traffic";
            }
            leaf mlap-protocol {
              type esdma_types:ncs_rpc_notif_mlap-protocol-enum;
              description
                "Indicates whether the internal or external MLAP protocol is active on this port";
            }
            leaf protocol-pkt-sent {
              type uint64;
              description
                "Number of protocol packets sent";
            }
            leaf protocol-pkt-recv {
              type uint64;
              description
                "Number of protocol packets received";
            }
            leaf protocol-set-color-pkts-sent {
              type uint64;
              description
                "Number of set-active-VLAN requests";
            }
            leaf protocol-set-color-pkts-recv {
              type uint64;
              description
                "Number of set-active-VLAN responses";
            }
            leaf protocol-send-error {
              type uint64;
              description
                "Number of protocol packet send errors";
            }
            leaf protocol-recv-error {
              type uint64;
              description
                "Number of protocol packet receive errors";
            }
            leaf protocol-state-changes {
              type uint32;
              description
                "Number of state changes";
            }
          }
          choice detail-type {
            case internal-detail {
              uses ncs_rpc_notif_mlap-internal-details;
            }
            case external-detail {
              uses ncs_rpc_notif_mlap-external-details;
            }
          }
        }
      }
    }
  }

  grouping ncs_rpc_notif_mlap-summary-data {
    container summary-data {
      list location {
        key "rack card switch-id";
        leaf rack {
          type esdma_types:ncs_rpc_notif_esdma-rack-num-enum;
        }
        leaf card {
          type esdma_types:ncs_rpc_notif_esdma-cpu;
          description
            "Card that owns a switch of interest";
        }
        leaf switch-id {
          type esdma_types:ncs_rpc_notif_esdma-switch-type-enum;
          description
            "Switch type";
        }
        leaf serial-num {
          type string;
          description
            "Rack serial number";
        }
        list port-iter {
          key "port";
          leaf port {
            type esdma_types:ncs_rpc_notif_esdma-switch-port-type;
            description
              "Switch port";
          }
          leaf port-name {
            type string;
            description
              "Switch port";
          }
          leaf phys-state {
            type esdma_types:ncs_rpc_notif_esdma-switch-port-state;
            description
              "Physical port state";
          }
          leaf admin-state {
            type esdma_types:ncs_rpc_notif_esdma-switch-port-state;
            description
              "Administrative port state";
          }
          leaf protocol-state {
            type esdma_types:ncs_rpc_notif_mlap-state-enum;
            description
              "Protocol invoked port state";
          }
          leaf forwarding {
            type esdma_types:ncs_rpc_notif_switch-forwarding-state;
            description
              "Indicates whether this port is allowed to forward traffic";
          }
          leaf mlap-protocol {
            type esdma_types:ncs_rpc_notif_mlap-protocol-enum;
            description
              "Indicates whether the internal or external MLAP protocol is active on this port";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping ncs_rpc_notif_mlap-statistics-data {
    container statistics {
      list location {
        key "rack card switch-id";
        leaf rack {
          type esdma_types:ncs_rpc_notif_esdma-rack-num-enum;
        }
        leaf card {
          type esdma_types:ncs_rpc_notif_esdma-cpu;
          description
            "Card that owns a switch of interest";
        }
        leaf switch-id {
          type esdma_types:ncs_rpc_notif_esdma-switch-type-enum;
          description
            "Switch type";
        }
        leaf serial-num {
          type string;
          description
            "Rack serial number";
        }
        list port-iter {
          key "port";
          leaf port {
            type esdma_types:ncs_rpc_notif_esdma-switch-port-type;
            description
              "Switch port";
          }
          leaf port-name {
            type string;
            description
              "Switch port";
          }
          leaf protocol-state {
            type esdma_types:ncs_rpc_notif_mlap-state-enum;
            description
              "Protocol invoked port state";
          }
          leaf protocol-state-changes {
            type uint32;
            description
              "Number of state changes";
          }
          leaf protocol-pkt-sent {
            type uint64;
            description
              "Number of protocol packets sent";
          }
          leaf protocol-pkt-recv {
            type uint64;
            description
              "Number of protocol packets received";
          }
          leaf protocol-set-color-pkts-sent {
            type uint64;
            description
              "Number of set-active-VLAN requests";
          }
          leaf protocol-set-color-pkts-recv {
            type uint64;
            description
              "Number of set-active-VLAN responses";
          }
          leaf protocol-send-error {
            type uint64;
            description
              "Number of protocol packet send errors";
          }
          leaf protocol-recv-error {
            type uint64;
            description
              "Number of protocol packet receive errors";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping ncs_rpc_notif_mlap-reachable-data {
    container reachable {
      list location {
        key "rack card switch-id";
        leaf rack {
          type esdma_types:ncs_rpc_notif_esdma-rack-num-enum;
        }
        leaf card {
          type esdma_types:ncs_rpc_notif_esdma-cpu;
        }
        leaf switch-id {
          type esdma_types:ncs_rpc_notif_esdma-switch-type-enum;
        }
      }
    }
  }

  grouping ncs_rpc_notif_mlap-debug-counters {
    container debug {
      container counters {
        list location {
          key "rack card switch-id";
          leaf rack {
            type esdma_types:ncs_rpc_notif_esdma-rack-num-enum;
          }
          leaf card {
            type esdma_types:ncs_rpc_notif_esdma-cpu;
          }
          leaf switch-id {
            type esdma_types:ncs_rpc_notif_esdma-switch-type-enum;
          }
          container counters {
            leaf eval-all-links-called {
              type uint64;
            }
            leaf timer-event-queued {
              type uint64;
            }
            leaf rx-packet-event-queued {
              type uint64;
            }
            leaf eval-all-links-queued {
              type uint64;
            }
            leaf link-status-queued {
              type uint64;
            }
            leaf admin-status-queued {
              type uint64;
            }
            leaf fwd-status-queued {
              type uint64;
            }
            leaf current-fifo-depth {
              type uint64;
            }
            leaf max-fifo-depth {
              type uint64;
            }
            leaf vlan-color-changes {
              type uint32;
            }
            leaf current-mlap-timeout-ms-interval {
              type uint32;
            }
            leaf aging-debug-enabled {
              type boolean;
            }
            leaf trace-verbosity {
              type esdma_types:ncs_rpc_notif_mlap-trace-verbosity;
            }
          }
        }
      }
    }
  }

  grouping ncs_rpc_notif_mlap-oper-group {
    container mlap {
      description
        "MLAP switch data";
      uses ncs_rpc_notif_mlap-reachable-data;
      uses ncs_rpc_notif_mlap-detail-data;
      uses ncs_rpc_notif_mlap-statistics-data;
      uses ncs_rpc_notif_mlap-summary-data;
      uses ncs_rpc_notif_mlap-debug-counters;
      uses show_trace:ncs_rpc_notif_traceable;
    }
  }

  grouping live_ncs_mlap-endpoint-state-info {
    leaf valid {
      type boolean;
      description
        "Indicates whether this endpoint information contains valid data.";
    }
    leaf chassis-type {
      // NCS drop when statement
      type esdma_types:live_ncs_esdma-rack-type-enum;
      description
        "The chassis type of this endpoint is in";
    }
    leaf endpoint-type {
      // NCS drop when statement
      type esdma_types:live_ncs_esdma-switch-type-enum;
      description
        "The type of endpoint this endpoint switch is on";
    }
    leaf endpoint-slot-number {
      // NCS drop when statement
      type uint32;
      description
        "Slot number of this endpoint";
    }
    leaf endpoint-switch-number {
      // NCS drop when statement
      type uint32;
      description
        "Switch number for the endpoint";
    }
    leaf endpoint-switch-port-number {
      // NCS drop when statement
      type uint32;
      description
        "Port number on the switch for the endpoint";
    }
    leaf endpoint-switch-port-name {
      type string;
      description
        "Port number on the switch for the endpoint";
    }
    leaf endpoint-chassis-serial-number {
      // NCS drop when statement
      type string;
      description
        "Serial number for the endpoint";
    }
    leaf mlap-state {
      // NCS drop when statement
      type esdma_types:live_ncs_mlap-state-enum;
      description
        "Protocol invoked port state";
    }
    leaf inter-fcc_sw-port {
      // NCS drop when statement
      type boolean;
      description
        "Indicates whether this port is used for an inter-F-SW connection";
    }
    leaf fcc_sw-indirectly-reachable {
      // NCS drop when statement
      type boolean;
      description
        "Indicates whether this port can indirectly reach an F-SW";
    }
  }

  grouping live_ncs_mlap-internal-details {
    container mlap-internal-details {
      container info {
        leaf port-owner {
          type esdma_types:live_ncs_esdma-cpu;
          description
            "Indicates which switch data path the port belongs to";
        }
        leaf current-active-owner {
          type esdma_types:live_ncs_esdma-cpu;
          description
            "Indicates which switch is currently mastering chassis data";
        }
        leaf mlap-peer-flags {
          type bits {
            bit Valid {
              position 0;
            }
            bit FCC-Active {
              position 1;
            }
            bit Force-Active {
              position 2;
            }
            bit Ignore-Data {
              position 31;
            }
          }
          description
            "Peer's port MLAP protocol flags";
        }
        leaf mlap-peer-idle-count {
          type uint32;
          description
            "Time intervals peer has not updated information";
        }
        leaf my-connection-active-mask {
          type uint64;
          description
            "My port active mask view";
        }
        leaf peer-connection-active-mask {
          type uint64;
          description
            "Peer's port active mask view";
        }
        leaf endpoint-card-type {
          type esdma_types:live_ncs_mlap-ep-type;
          description
            "Indicates the high-level card type this switch port is peering with";
        }
        leaf endpoint-mac-address {
          type ietf:mac-address;
          description
            "MAC addess of device of the protocol peer for this switch port";
        }
      }
    }
  }

  grouping live_ncs_mlap-external-details {
    container mlap-external-details {
      container local-state-information {
        description
          "MLAP state information from this port's perspective";
        uses live_ncs_mlap-endpoint-state-info;
      }
      container peer-state-information {
        description
          "MLAP state information from peer port's perspective";
        uses live_ncs_mlap-endpoint-state-info;
      }
      container peer-other-link-state-information {
        description
          "MLAP state information for peer's other uplink perspective (RP/SC only)";
        uses live_ncs_mlap-endpoint-state-info;
      }
    }
  }

  grouping live_ncs_mlap-detail-data {
    container detail {
      list location {
        key "rack card switch-id";
        leaf rack {
          type esdma_types:live_ncs_esdma-rack-num-enum;
        }
        leaf card {
          type esdma_types:live_ncs_esdma-cpu;
        }
        leaf switch-id {
          type esdma_types:live_ncs_esdma-switch-type-enum;
          description
            "Switch type";
        }
        list port-iter {
          key "port";
          leaf port {
            type esdma_types:live_ncs_esdma-switch-port-type;
            description
              "Switch port";
          }
          container gen-data {
            leaf serial-num {
              type string;
              description
                "Rack serial number";
            }
            leaf connects-to {
              type string;
              description
                "Indicates what this port connects to";
            }
            leaf phys-state {
              type esdma_types:live_ncs_esdma-switch-port-state;
              description
                "Physical port state";
            }
            leaf admin-state {
              type esdma_types:live_ncs_esdma-switch-port-state;
              description
                "Administrative port state";
            }
            leaf protocol-state {
              type esdma_types:live_ncs_mlap-state-enum;
              description
                "Protocol invoked port state";
            }
            leaf forwarding {
              type esdma_types:live_ncs_switch-forwarding-state;
              description
                "Indicates whether this port is allowed to forward traffic";
            }
            leaf mlap-protocol {
              type esdma_types:live_ncs_mlap-protocol-enum;
              description
                "Indicates whether the internal or external MLAP protocol is active on this port";
            }
            leaf protocol-pkt-sent {
              type uint64;
              description
                "Number of protocol packets sent";
            }
            leaf protocol-pkt-recv {
              type uint64;
              description
                "Number of protocol packets received";
            }
            leaf protocol-set-color-pkts-sent {
              type uint64;
              description
                "Number of set-active-VLAN requests";
            }
            leaf protocol-set-color-pkts-recv {
              type uint64;
              description
                "Number of set-active-VLAN responses";
            }
            leaf protocol-send-error {
              type uint64;
              description
                "Number of protocol packet send errors";
            }
            leaf protocol-recv-error {
              type uint64;
              description
                "Number of protocol packet receive errors";
            }
            leaf protocol-state-changes {
              type uint32;
              description
                "Number of state changes";
            }
          }
          choice detail-type {
            case internal-detail {
              uses live_ncs_mlap-internal-details;
            }
            case external-detail {
              uses live_ncs_mlap-external-details;
            }
          }
        }
      }
    }
  }

  grouping live_ncs_mlap-summary-data {
    container summary-data {
      list location {
        key "rack card switch-id";
        leaf rack {
          type esdma_types:live_ncs_esdma-rack-num-enum;
        }
        leaf card {
          type esdma_types:live_ncs_esdma-cpu;
          description
            "Card that owns a switch of interest";
        }
        leaf switch-id {
          type esdma_types:live_ncs_esdma-switch-type-enum;
          description
            "Switch type";
        }
        leaf serial-num {
          type string;
          description
            "Rack serial number";
        }
        list port-iter {
          key "port";
          leaf port {
            type esdma_types:live_ncs_esdma-switch-port-type;
            description
              "Switch port";
          }
          leaf port-name {
            type string;
            description
              "Switch port";
          }
          leaf phys-state {
            type esdma_types:live_ncs_esdma-switch-port-state;
            description
              "Physical port state";
          }
          leaf admin-state {
            type esdma_types:live_ncs_esdma-switch-port-state;
            description
              "Administrative port state";
          }
          leaf protocol-state {
            type esdma_types:live_ncs_mlap-state-enum;
            description
              "Protocol invoked port state";
          }
          leaf forwarding {
            type esdma_types:live_ncs_switch-forwarding-state;
            description
              "Indicates whether this port is allowed to forward traffic";
          }
          leaf mlap-protocol {
            type esdma_types:live_ncs_mlap-protocol-enum;
            description
              "Indicates whether the internal or external MLAP protocol is active on this port";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping live_ncs_mlap-statistics-data {
    container statistics {
      list location {
        key "rack card switch-id";
        leaf rack {
          type esdma_types:live_ncs_esdma-rack-num-enum;
        }
        leaf card {
          type esdma_types:live_ncs_esdma-cpu;
          description
            "Card that owns a switch of interest";
        }
        leaf switch-id {
          type esdma_types:live_ncs_esdma-switch-type-enum;
          description
            "Switch type";
        }
        leaf serial-num {
          type string;
          description
            "Rack serial number";
        }
        list port-iter {
          key "port";
          leaf port {
            type esdma_types:live_ncs_esdma-switch-port-type;
            description
              "Switch port";
          }
          leaf port-name {
            type string;
            description
              "Switch port";
          }
          leaf protocol-state {
            type esdma_types:live_ncs_mlap-state-enum;
            description
              "Protocol invoked port state";
          }
          leaf protocol-state-changes {
            type uint32;
            description
              "Number of state changes";
          }
          leaf protocol-pkt-sent {
            type uint64;
            description
              "Number of protocol packets sent";
          }
          leaf protocol-pkt-recv {
            type uint64;
            description
              "Number of protocol packets received";
          }
          leaf protocol-set-color-pkts-sent {
            type uint64;
            description
              "Number of set-active-VLAN requests";
          }
          leaf protocol-set-color-pkts-recv {
            type uint64;
            description
              "Number of set-active-VLAN responses";
          }
          leaf protocol-send-error {
            type uint64;
            description
              "Number of protocol packet send errors";
          }
          leaf protocol-recv-error {
            type uint64;
            description
              "Number of protocol packet receive errors";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping live_ncs_mlap-reachable-data {
    container reachable {
      list location {
        key "rack card switch-id";
        leaf rack {
          type esdma_types:live_ncs_esdma-rack-num-enum;
        }
        leaf card {
          type esdma_types:live_ncs_esdma-cpu;
        }
        leaf switch-id {
          type esdma_types:live_ncs_esdma-switch-type-enum;
        }
      }
    }
  }

  grouping live_ncs_mlap-debug-counters {
    container debug {
      container counters {
        list location {
          key "rack card switch-id";
          leaf rack {
            type esdma_types:live_ncs_esdma-rack-num-enum;
          }
          leaf card {
            type esdma_types:live_ncs_esdma-cpu;
          }
          leaf switch-id {
            type esdma_types:live_ncs_esdma-switch-type-enum;
          }
          container counters {
            leaf eval-all-links-called {
              type uint64;
            }
            leaf timer-event-queued {
              type uint64;
            }
            leaf rx-packet-event-queued {
              type uint64;
            }
            leaf eval-all-links-queued {
              type uint64;
            }
            leaf link-status-queued {
              type uint64;
            }
            leaf admin-status-queued {
              type uint64;
            }
            leaf fwd-status-queued {
              type uint64;
            }
            leaf current-fifo-depth {
              type uint64;
            }
            leaf max-fifo-depth {
              type uint64;
            }
            leaf vlan-color-changes {
              type uint32;
            }
            leaf current-mlap-timeout-ms-interval {
              type uint32;
            }
            leaf aging-debug-enabled {
              type boolean;
            }
            leaf trace-verbosity {
              type esdma_types:live_ncs_mlap-trace-verbosity;
            }
          }
        }
      }
    }
  }

  grouping live_ncs_mlap-oper-group {
    container mlap {
      description
        "MLAP switch data";
      uses live_ncs_mlap-reachable-data;
      uses live_ncs_mlap-detail-data;
      uses live_ncs_mlap-statistics-data;
      uses live_ncs_mlap-summary-data;
      uses live_ncs_mlap-debug-counters;
      uses show_trace:live_ncs_traceable;
    }
  }

  grouping mlap-endpoint-state-info {
    leaf valid {
      type boolean;
      description
        "Indicates whether this endpoint information contains valid data.";
    }
    leaf chassis-type {
      when "../valid = 'true'" {
        tailf:xpath-root 3;
      }
      type esdma_types:esdma-rack-type-enum;
      description
        "The chassis type of this endpoint is in";
    }
    leaf endpoint-type {
      when "../valid = 'true'" {
        tailf:xpath-root 3;
      }
      type esdma_types:esdma-switch-type-enum;
      description
        "The type of endpoint this endpoint switch is on";
    }
    leaf endpoint-slot-number {
      when "../valid = 'true'" {
        tailf:xpath-root 3;
      }
      type uint32;
      description
        "Slot number of this endpoint";
    }
    leaf endpoint-switch-number {
      when "../valid = 'true'" {
        tailf:xpath-root 3;
      }
      type uint32;
      description
        "Switch number for the endpoint";
    }
    leaf endpoint-switch-port-number {
      when "../valid = 'true'" {
        tailf:xpath-root 3;
      }
      type uint32;
      description
        "Port number on the switch for the endpoint";
    }
    leaf endpoint-switch-port-name {
      type string;
      description
        "Port number on the switch for the endpoint";
    }
    leaf endpoint-chassis-serial-number {
      when "../valid = 'true'" {
        tailf:xpath-root 3;
      }
      type string;
      description
        "Serial number for the endpoint";
    }
    leaf mlap-state {
      when "../valid = 'true'" {
        tailf:xpath-root 3;
      }
      type esdma_types:mlap-state-enum;
      description
        "Protocol invoked port state";
    }
    leaf inter-fcc_sw-port {
      when "../valid = 'true'" {
        tailf:xpath-root 3;
      }
      type boolean;
      description
        "Indicates whether this port is used for an inter-F-SW connection";
    }
    leaf fcc_sw-indirectly-reachable {
      when "../valid = 'true'" {
        tailf:xpath-root 3;
      }
      type boolean;
      description
        "Indicates whether this port can indirectly reach an F-SW";
    }
  }

  grouping mlap-internal-details {
    container mlap-internal-details {
      container info {
        leaf port-owner {
          type esdma_types:esdma-cpu;
          description
            "Indicates which switch data path the port belongs to";
        }
        leaf current-active-owner {
          type esdma_types:esdma-cpu;
          description
            "Indicates which switch is currently mastering chassis data";
        }
        leaf mlap-peer-flags {
          type bits {
            bit Valid {
              position 0;
            }
            bit FCC-Active {
              position 1;
            }
            bit Force-Active {
              position 2;
            }
            bit Ignore-Data {
              position 31;
            }
          }
          description
            "Peer's port MLAP protocol flags";
        }
        leaf mlap-peer-idle-count {
          type uint32;
          description
            "Time intervals peer has not updated information";
        }
        leaf my-connection-active-mask {
          type uint64;
          description
            "My port active mask view";
        }
        leaf peer-connection-active-mask {
          type uint64;
          description
            "Peer's port active mask view";
        }
        leaf endpoint-card-type {
          type esdma_types:mlap-ep-type;
          description
            "Indicates the high-level card type this switch port is peering with";
        }
        leaf endpoint-mac-address {
          type ietf:mac-address;
          description
            "MAC addess of device of the protocol peer for this switch port";
        }
      }
    }
  }

  grouping mlap-external-details {
    container mlap-external-details {
      container local-state-information {
        description
          "MLAP state information from this port's perspective";
        uses mlap-endpoint-state-info;
      }
      container peer-state-information {
        description
          "MLAP state information from peer port's perspective";
        uses mlap-endpoint-state-info;
      }
      container peer-other-link-state-information {
        description
          "MLAP state information for peer's other uplink perspective (RP/SC only)";
        uses mlap-endpoint-state-info;
      }
    }
  }

  grouping mlap-detail-data {
    container detail {
      list location {
        key "rack card switch-id";
        leaf rack {
          type esdma_types:esdma-rack-num-enum;
        }
        leaf card {
          type esdma_types:esdma-cpu;
        }
        leaf switch-id {
          type esdma_types:esdma-switch-type-enum;
          description
            "Switch type";
        }
        list port-iter {
          key "port";
          leaf port {
            type esdma_types:esdma-switch-port-type;
            description
              "Switch port";
          }
          container gen-data {
            leaf serial-num {
              type string;
              description
                "Rack serial number";
            }
            leaf connects-to {
              type string;
              description
                "Indicates what this port connects to";
            }
            leaf phys-state {
              type esdma_types:esdma-switch-port-state;
              description
                "Physical port state";
            }
            leaf admin-state {
              type esdma_types:esdma-switch-port-state;
              description
                "Administrative port state";
            }
            leaf protocol-state {
              type esdma_types:mlap-state-enum;
              description
                "Protocol invoked port state";
            }
            leaf forwarding {
              type esdma_types:switch-forwarding-state;
              description
                "Indicates whether this port is allowed to forward traffic";
            }
            leaf mlap-protocol {
              type esdma_types:mlap-protocol-enum;
              description
                "Indicates whether the internal or external MLAP protocol is active on this port";
            }
            leaf protocol-pkt-sent {
              type uint64;
              description
                "Number of protocol packets sent";
            }
            leaf protocol-pkt-recv {
              type uint64;
              description
                "Number of protocol packets received";
            }
            leaf protocol-set-color-pkts-sent {
              type uint64;
              description
                "Number of set-active-VLAN requests";
            }
            leaf protocol-set-color-pkts-recv {
              type uint64;
              description
                "Number of set-active-VLAN responses";
            }
            leaf protocol-send-error {
              type uint64;
              description
                "Number of protocol packet send errors";
            }
            leaf protocol-recv-error {
              type uint64;
              description
                "Number of protocol packet receive errors";
            }
            leaf protocol-state-changes {
              type uint32;
              description
                "Number of state changes";
            }
          }
          choice detail-type {
            case internal-detail {
              uses mlap-internal-details;
            }
            case external-detail {
              uses mlap-external-details;
            }
          }
        }
      }
    }
  }

  grouping mlap-summary-data {
    container summary-data {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter {
          key "port";
          leaf port {
            type esdma_types:esdma-switch-port-type;
            description
              "Switch port";
          }
          leaf port-name {
            type string;
            description
              "Switch port";
          }
          leaf phys-state {
            type esdma_types:esdma-switch-port-state;
            description
              "Physical port state";
          }
          leaf admin-state {
            type esdma_types:esdma-switch-port-state;
            description
              "Administrative port state";
          }
          leaf protocol-state {
            type esdma_types:mlap-state-enum;
            description
              "Protocol invoked port state";
          }
          leaf forwarding {
            type esdma_types:switch-forwarding-state;
            description
              "Indicates whether this port is allowed to forward traffic";
          }
          leaf mlap-protocol {
            type esdma_types:mlap-protocol-enum;
            description
              "Indicates whether the internal or external MLAP protocol is active on this port";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping mlap-statistics-data {
    container statistics {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter {
          key "port";
          leaf port {
            type esdma_types:esdma-switch-port-type;
            description
              "Switch port";
          }
          leaf port-name {
            type string;
            description
              "Switch port";
          }
          leaf protocol-state {
            type esdma_types:mlap-state-enum;
            description
              "Protocol invoked port state";
          }
          leaf protocol-state-changes {
            type uint32;
            description
              "Number of state changes";
          }
          leaf protocol-pkt-sent {
            type uint64;
            description
              "Number of protocol packets sent";
          }
          leaf protocol-pkt-recv {
            type uint64;
            description
              "Number of protocol packets received";
          }
          leaf protocol-set-color-pkts-sent {
            type uint64;
            description
              "Number of set-active-VLAN requests";
          }
          leaf protocol-set-color-pkts-recv {
            type uint64;
            description
              "Number of set-active-VLAN responses";
          }
          leaf protocol-send-error {
            type uint64;
            description
              "Number of protocol packet send errors";
          }
          leaf protocol-recv-error {
            type uint64;
            description
              "Number of protocol packet receive errors";
          }
          leaf connects-to {
            type string;
            description
              "Indicates what this port connects to";
          }
          leaf expected-endpoint {
            type string;
            description
              "Indicates what this port is expected to connect to";
          }
          leaf mismatch-string {
            type string;
            description
              "Indicates whether there is a mismatch";
          }
        }
      }
    }
  }

  grouping mlap-reachable-data {
    container reachable {
      list location {
        key "rack card switch-id";
        leaf rack {
          type esdma_types:esdma-rack-num-enum;
        }
        leaf card {
          type esdma_types:esdma-cpu;
        }
        leaf switch-id {
          type esdma_types:esdma-switch-type-enum;
        }
      }
    }
  }

  grouping mlap-debug-counters {
    container debug {
      container counters {
        list location {
          key "rack card switch-id";
          leaf rack {
            type esdma_types:esdma-rack-num-enum;
          }
          leaf card {
            type esdma_types:esdma-cpu;
          }
          leaf switch-id {
            type esdma_types:esdma-switch-type-enum;
          }
          container counters {
            leaf eval-all-links-called {
              type uint64;
            }
            leaf timer-event-queued {
              type uint64;
            }
            leaf rx-packet-event-queued {
              type uint64;
            }
            leaf eval-all-links-queued {
              type uint64;
            }
            leaf link-status-queued {
              type uint64;
            }
            leaf admin-status-queued {
              type uint64;
            }
            leaf fwd-status-queued {
              type uint64;
            }
            leaf current-fifo-depth {
              type uint64;
            }
            leaf max-fifo-depth {
              type uint64;
            }
            leaf vlan-color-changes {
              type uint32;
            }
            leaf current-mlap-timeout-ms-interval {
              type uint32;
            }
            leaf aging-debug-enabled {
              type boolean;
            }
            leaf trace-verbosity {
              type esdma_types:mlap-trace-verbosity;
            }
          }
        }
      }
    }
  }

  grouping mlap-oper-group {
    container mlap {
      description
        "MLAP switch data";
      uses mlap-reachable-data;
      uses mlap-detail-data;
      uses mlap-statistics-data;
      uses mlap-summary-data;
      uses mlap-debug-counters;
      uses show_trace:traceable;
    }
  }
}

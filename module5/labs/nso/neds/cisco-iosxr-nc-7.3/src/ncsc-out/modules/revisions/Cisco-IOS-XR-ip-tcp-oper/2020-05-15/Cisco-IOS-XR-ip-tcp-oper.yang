module Cisco-IOS-XR-ip-tcp-oper {
  // Generated by yanger -t ncs
  tailf:mount-id "cisco-iosxr-nc-7.3:cisco-iosxr-nc-7.3";
  tailf:ncs-device-type "netconf";

  namespace "http://cisco.com/ns/yang/Cisco-IOS-XR-ip-tcp-oper";
  prefix ip-tcp-oper;

  import Cisco-IOS-XR-types {
    prefix xr;
  }
  import cisco-semver {
    prefix semver;
  }
  include Cisco-IOS-XR-ip-tcp-oper-sub5 {
    revision-date 2020-05-15;
  }
  include Cisco-IOS-XR-ip-tcp-oper-sub4 {
    revision-date 2020-05-15;
  }
  include Cisco-IOS-XR-ip-tcp-oper-sub3 {
    revision-date 2020-05-15;
  }
  include Cisco-IOS-XR-ip-tcp-oper-sub2 {
    revision-date 2020-05-15;
  }
  include Cisco-IOS-XR-ip-tcp-oper-sub1 {
    revision-date 2020-05-15;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-tcp package operational data.

     This module contains definitions
     for the following management objects:
       tcp-connection: TCP connection operational data
       tcp: IP TCP Operational Data
       tcp-nsr: TCP NSR operational data

     Copyright (c) 2013-2020 by Cisco Systems, Inc.
     All rights reserved.";

  revision 2020-05-15 {
    description
      "First SYN delay timer added";
    semver:module-version "1.1.0";
  }
  revision 2019-04-05 {
    description
      "Establish semantic version baseline.";
    semver:module-version "1.0.0";
  }
  revision 2018-11-01 {
    description
      "Added socket async double free prevention count in tcp statistics summary";
  }
  revision 2018-02-14 {
    description
      "PCB_ID argument is passed in string format.";
  }
  revision 2018-02-14 {
    description
      "Added support for TCP-AO feature.";
  }
  revision 2017-05-01 {
    description
      "Fixing backward compatibility error in module.";
  }
  revision 2016-02-26 {
    description
      "Descriptions updated.";
  }
  revision 2015-11-09 {
    description
      "IOS XR 6.0 revision.";
  }

  typedef ncs_template_Show {
    type string;
    description
      "Show";
  }

  typedef ncs_rpc_notif_Show {
    type enumeration {
      enum "all" {
        value 0;
        description
          "To dispay all";
      }
      enum "static-policy" {
        value 1;
        description
          "To display static policy";
      }
      enum "interface-filter" {
        value 2;
        description
          "To display interface filter";
      }
      enum "packet-filter" {
        value 3;
        description
          "To display packet type filter";
      }
    }
    description
      "Show";
  }

  typedef live_ncs_Show {
    type enumeration {
      enum "all" {
        value 0;
        description
          "To dispay all";
      }
      enum "static-policy" {
        value 1;
        description
          "To display static policy";
      }
      enum "interface-filter" {
        value 2;
        description
          "To display interface filter";
      }
      enum "packet-filter" {
        value 3;
        description
          "To display packet type filter";
      }
    }
    description
      "Show";
  }

  typedef Show {
    type enumeration {
      enum "all" {
        value 0;
        description
          "To dispay all";
      }
      enum "static-policy" {
        value 1;
        description
          "To display static policy";
      }
      enum "interface-filter" {
        value 2;
        description
          "To display interface filter";
      }
      enum "packet-filter" {
        value 3;
        description
          "To display packet type filter";
      }
    }
    description
      "Show";
  }

  augment "/ncs:devices/ncs:device/ncs:config" {
    // NCS drop config false container 'tcp-connection'
    // NCS drop config false container tcp
    // NCS drop config false container 'tcp-nsr'
  }
  augment "/ncs:devices/ncs:device/ncs:live-status" {
    container tcp-connection {
      tailf:ncs-device-type "netconf";
      tailf:display-when "not(../../ncs:module) or ../../ncs:module[ncs:name='Cisco-IOS-XR-ip-tcp-oper'] or (../../ncs:live-status-protocol[not(ncs:capability)]) or (../../ncs:live-status-protocol/ncs:capability/ncs:module[.='Cisco-IOS-XR-ip-tcp-oper'])";
      description
        "TCP connection operational data";
      container nodes {
        description
          "Table of information about all nodes present on
           the system";
        list node {
          key "id";
          description
            "Information about a single node";
          container statistics {
            description
              "Statistics of all TCP connections";
            container clients {
              description
                "Table listing clients";
              list client {
                key "client-id";
                description
                  "Describing Client ID";
                leaf client-id {
                  type uint32 {
                    range "0..4294967295";
                  }
                  description
                    "Displaying client's aggregated statistics";
                }
                uses live_ncs_TRANSP-CLIENT-STATS-BAG;
              }
            }
            container pcbs {
              description
                "Table listing the TCP connections for which
                 statistics are provided";
              list pcb {
                key "id";
                description
                  "Protocol Control Block ID";
                leaf id {
                  type xr:live_ncs_Cisco-ios-xr-string;
                  description
                    "Displaying statistics associated with a
                     particular PCB";
                }
                uses live_ncs_TCP-SH-PCB-STATS-BAG;
              }
            }
            container summary {
              description
                "Summary statistics across all TCP connections";
              uses live_ncs_TCP-SH-STATS-BAG;
            }
          }
          container extended-information {
            description
              "Extended Filter related Information";
            container display-types {
              description
                "Table listing display types";
              list display-type {
                key "disp-type";
                description
                  "Describing particular display type";
                leaf disp-type {
                  type live_ncs_Show;
                  description
                    "Specifying display type";
                }
                list connection-id {
                  key "pcb-id";
                  description
                    "Describing connection ID";
                  leaf pcb-id {
                    type xr:live_ncs_Cisco-ios-xr-string;
                    description
                      "Displaying inforamtion based on selected
                       display type associatedwith a particular
                       PCB";
                  }
                  uses live_ncs_SHOW-PCB-INFO;
                }
              }
            }
          }
          container detail-informations {
            description
              "Table listing TCP connections for which
               detailed information is provided";
            list detail-information {
              key "pcb-id";
              description
                "Protocol Control Block ID";
              leaf pcb-id {
                type xr:live_ncs_Cisco-ios-xr-string;
                description
                  "Detail information about TCP connection, put
                   null for all";
              }
              uses live_ncs_TCP-SH-TABLE-BAG;
            }
          }
          container keychains {
            description
              "Table listing keychains configured for TCP-AO.";
            list keychain {
              key "keychain-name";
              description
                "Details of a keychain";
              leaf keychain-name {
                type xr:live_ncs_Cisco-ios-xr-string;
                description
                  "Keychain name";
              }
              uses live_ncs_TCP-SH-KEYCHAIN-BAG;
            }
          }
          container brief-informations {
            description
              "Table listing connections for which brief
               information is provided.Note that not all
               connections are listed in the brief table.";
            list brief-information {
              key "pcb-id";
              description
                "Brief information about a TCP connection";
              leaf pcb-id {
                type xr:live_ncs_Cisco-ios-xr-string;
                description
                  "Protocol Control Block ID";
              }
              uses live_ncs_TCP-SH-BRIEF-BAG;
            }
          }
          leaf id {
            type xr:live_ncs_Node-id;
            description
              "Describing a location";
          }
        }
      }
    }
    container tcp {
      tailf:ncs-device-type "netconf";
      tailf:display-when "not(../../ncs:module) or ../../ncs:module[ncs:name='Cisco-IOS-XR-ip-tcp-oper'] or (../../ncs:live-status-protocol[not(ncs:capability)]) or (../../ncs:live-status-protocol/ncs:capability/ncs:module[.='Cisco-IOS-XR-ip-tcp-oper'])";
      description
        "IP TCP Operational Data";
      container nodes {
        description
          "Node-specific TCP operational data";
        list node {
          key "node-name";
          description
            "TCP operational data for a particular node";
          container statistics {
            description
              "Statistical TCP operational data for a node";
            container ipv4-traffic {
              description
                "TCP Traffic statistics for IPv4";
              uses live_ncs_IP-TCP;
            }
            container ipv6-traffic {
              description
                "TCP Traffic statistics for IPv6";
              uses live_ncs_IP-TCP;
            }
          }
          leaf node-name {
            type xr:live_ncs_Node-id;
            description
              "Node name";
          }
        }
      }
    }
    container tcp-nsr {
      tailf:ncs-device-type "netconf";
      tailf:display-when "not(../../ncs:module) or ../../ncs:module[ncs:name='Cisco-IOS-XR-ip-tcp-oper'] or (../../ncs:live-status-protocol[not(ncs:capability)]) or (../../ncs:live-status-protocol/ncs:capability/ncs:module[.='Cisco-IOS-XR-ip-tcp-oper'])";
      description
        "TCP NSR operational data";
      container nodes {
        description
          "Table of information about all nodes present on
           the system";
        list node {
          key "id";
          description
            "Information about a single node";
          container session {
            description
              "Information about TCP NSR Sessions";
            container brief-sessions {
              description
                "Information about TCP NSR Sessions";
              list brief-session {
                key "id";
                description
                  "Brief information about NSR Sessions";
                leaf id {
                  type xr:live_ncs_Hex-integer;
                  description
                    "ID of NSR Sesison";
                }
                uses live_ncs_TCP-NSR-PCB-BRIEF-BAG;
              }
            }
            container detail-sessions {
              description
                "Table about TCP NSR Sessions details";
              list detail-session {
                key "id";
                description
                  "showing detailed information of NSR Sessions";
                leaf id {
                  type xr:live_ncs_Hex-integer;
                  description
                    "ID of NSR Sesison";
                }
                uses live_ncs_TCP-NSR-PCB-DETAILED-BAG;
              }
            }
          }
          container client {
            description
              "Information about TCP NSR Client";
            container detail-clients {
              description
                "Table about TCP NSR Client details";
              list detail-client {
                key "id";
                description
                  "showing detailed information of NSR Clients";
                leaf id {
                  type xr:live_ncs_Hex-integer;
                  description
                    "ID of NSR client";
                }
                uses live_ncs_TCP-NSR-CCB-DETAILED-BAG;
              }
            }
            container brief-clients {
              description
                "Information about TCP NSR Client";
              list brief-client {
                key "id";
                description
                  "Brief information about NSR Client";
                leaf id {
                  type xr:live_ncs_Hex-integer;
                  description
                    "ID of NSR client";
                }
                uses live_ncs_TCP-NSR-CCB-BRIEF-BAG;
              }
            }
          }
          container session-set {
            description
              "Information about TCP NSR Session Sets";
            container detail-sets {
              description
                "Table about TCP NSR Session Sets details";
              list detail-set {
                key "id";
                description
                  "showing detailed information of NSR Session
                   Sets";
                leaf id {
                  type xr:live_ncs_Hex-integer;
                  description
                    "ID of NSR Sesison Set";
                }
                uses live_ncs_TCP-NSR-SSCB-DETAILED-BAG;
              }
            }
            container brief-sets {
              description
                "Information about TCP NSR Session Sets";
              list brief-set {
                key "id";
                description
                  "Brief information about NSR Session Sets";
                leaf id {
                  type xr:live_ncs_Hex-integer;
                  description
                    "ID of NSR Session Set";
                }
                uses live_ncs_TCP-NSR-SSCB-BRIEF-BAG;
              }
            }
          }
          container statistics {
            description
              "Statis Information about TCP NSR connections";
            container summary {
              description
                "Summary statistics across all NSR connections";
              uses live_ncs_TCP-NSR-SUMMARY-STATS-BAG;
            }
            container statistic-clients {
              description
                "Table listing NSR connections for which
                 statistic information is provided";
              list statistic-client {
                key "id";
                description
                  "showing statistic information of NSR Clients";
                leaf id {
                  type xr:live_ncs_Hex-integer;
                  description
                    "ID of NSR Client";
                }
                uses live_ncs_TCP-NSR-CCB-STATS-BAG;
              }
            }
            container statistic-sets {
              description
                "Table listing NSR connections for which
                 statistic information is provided";
              list statistic-set {
                key "id";
                description
                  "showing statistic information of NSR Session
                   Set";
                leaf id {
                  type xr:live_ncs_Hex-integer;
                  description
                    "ID of NSR Session Set";
                }
                uses live_ncs_TCP-NSR-SSCB-STATS-BAG;
              }
            }
            container statistic-sessions {
              description
                "Table listing NSR connections for which
                 statistic information is provided";
              list statistic-session {
                key "id";
                description
                  "showing statistic information of TCP
                   connections";
                leaf id {
                  type xr:live_ncs_Hex-integer;
                  description
                    "ID of TCP connection";
                }
                uses live_ncs_TCP-NSR-PCB-STATS-BAG;
              }
            }
          }
          leaf id {
            type xr:live_ncs_Node-id;
            description
              "Describing a location";
          }
        }
      }
    }
  }
  augment "/ncs:devices/ncs:template/ncs:ned-id/ncs:config" {
    // NCS drop config false container 'tcp-connection'
    // NCS drop config false container tcp
    // NCS drop config false container 'tcp-nsr'
  }
}

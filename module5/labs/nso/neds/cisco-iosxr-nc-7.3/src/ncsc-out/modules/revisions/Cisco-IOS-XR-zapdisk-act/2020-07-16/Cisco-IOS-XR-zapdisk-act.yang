module Cisco-IOS-XR-zapdisk-act {
  // Generated by yanger -t ncs
  tailf:mount-id "cisco-iosxr-nc-7.3:cisco-iosxr-nc-7.3";
  tailf:ncs-device-type "netconf";

  namespace "http://cisco.com/ns/yang/Cisco-IOS-XR-zapdisk-act";
  prefix zapdisk-act;

  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2020 by Cisco Systems, Inc.
     All rights reserved.";

  revision 2020-07-16 {
    description
      "IOS XR 7.1.2 revision.";
  }

  augment "/ncs:devices/ncs:device/ncs:rpc" {
    container rpc-zapdisk-start {
      tailf:ncs-device-type "netconf";
      tailf:display-when "not(../../ncs:module) or ../../ncs:module[ncs:name='Cisco-IOS-XR-zapdisk-act']";
      tailf:action zapdisk-start {
        tailf:actionpoint ncsproxy {
          tailf:internal;
        }
        description
          "Action to start zapdisk operation";
        input {
          leaf location {
            type string;
            mandatory true;
            description
              "Location string to start zapdisk operation";
          }
        }
        output {
          leaf result {
            type string;
            mandatory true;
            description
              "Result of zapdisk operation";
          }
        }
      }
    }
  }
  augment "/ncs:devices/ncs:device-group/ncs:ned-id/ncs:rpc" {
    container rpc-zapdisk-start {
      tailf:ncs-device-type "netconf";
      tailf:display-when "/ncs:devices/ncs:device[ncs:name=current()/../../../ncs:member]/ncs:module[ncs:name='Cisco-IOS-XR-zapdisk-act']";
      tailf:action zapdisk-start {
        tailf:actionpoint ncsproxy {
          tailf:internal;
        }
        description
          "Action to start zapdisk operation";
        input {
          leaf location {
            type string;
            mandatory true;
            description
              "Location string to start zapdisk operation";
          }
        }
        output {
          container "device" {
            leaf "name" {
              type string;
            }
            leaf "info" {
              type string;
            }
            container "result" {
              leaf result {
                type string;
                mandatory true;
                description
                  "Result of zapdisk operation";
              }
            }
          }
        }
      }
    }
  }
  augment "/ncs:devices/ncs:device/ncs:rpc" {
    container rpc-zapdisk-show {
      tailf:ncs-device-type "netconf";
      tailf:display-when "not(../../ncs:module) or ../../ncs:module[ncs:name='Cisco-IOS-XR-zapdisk-act']";
      tailf:action zapdisk-show {
        tailf:actionpoint ncsproxy {
          tailf:internal;
        }
        description
          "Action to list zapdisk locations";
        output {
          leaf location {
            type string;
            mandatory true;
            description
              "Result of zapdisk show location";
          }
        }
      }
    }
  }
  augment "/ncs:devices/ncs:device-group/ncs:ned-id/ncs:rpc" {
    container rpc-zapdisk-show {
      tailf:ncs-device-type "netconf";
      tailf:display-when "/ncs:devices/ncs:device[ncs:name=current()/../../../ncs:member]/ncs:module[ncs:name='Cisco-IOS-XR-zapdisk-act']";
      tailf:action zapdisk-show {
        tailf:actionpoint ncsproxy {
          tailf:internal;
        }
        description
          "Action to list zapdisk locations";
        output {
          container "device" {
            leaf "name" {
              type string;
            }
            leaf "info" {
              type string;
            }
            container "result" {
              leaf location {
                type string;
                mandatory true;
                description
                  "Result of zapdisk show location";
              }
            }
          }
        }
      }
    }
  }
}

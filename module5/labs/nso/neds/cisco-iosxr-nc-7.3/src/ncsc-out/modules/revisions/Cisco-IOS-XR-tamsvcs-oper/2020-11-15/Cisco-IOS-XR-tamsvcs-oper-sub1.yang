submodule Cisco-IOS-XR-tamsvcs-oper-sub1 {
  // Generated by yanger -t ncs
  tailf:mount-id "cisco-iosxr-nc-7.3:cisco-iosxr-nc-7.3";

  belongs-to Cisco-IOS-XR-tamsvcs-oper {
    prefix Cisco-IOS-XR-tamsvcs-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tamsvcs package operational data.

     Copyright (c) 2013-2020 by Cisco Systems, Inc.
     All rights reserved.";

  revision 2020-11-15 {
    description
      "Show device info and sudi certs support for tam";
    semver:module-version "1.1.0";
  }
  revision 2019-04-05 {
    description
      "Establish semantic version baseline.";
    semver:module-version "1.0.1";
  }
  revision 2015-11-09 {
    description
      "IOS XR 6.0 revision.";
  }

  grouping ncs_template_TAMSVCS-SUDI-CERTS {
    description
      "Tam Sudi certs bag";
    leaf sudi-root-cert {
      type string;
      description
        "Sudi Root Certificate";
    }
    leaf sudi-subca-cert {
      type string;
      description
        "Sudi SubCA Certificate";
    }
    leaf sudi-cert {
      type string;
      description
        "Sudi Certificate of Tam Device";
    }
  }

  grouping ncs_template_TAMSVCS-DEVICE-INFO {
    description
      "Tam device info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
  }

  grouping ncs_template_TAMSVCS-INFO-ALL {
    description
      "Tam All info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
  }

  grouping ncs_rpc_notif_TAMSVCS-SUDI-CERTS {
    description
      "Tam Sudi certs bag";
    leaf sudi-root-cert {
      type string;
      description
        "Sudi Root Certificate";
    }
    leaf sudi-subca-cert {
      type string;
      description
        "Sudi SubCA Certificate";
    }
    leaf sudi-cert {
      type string;
      description
        "Sudi Certificate of Tam Device";
    }
  }

  grouping ncs_rpc_notif_TAMSVCS-DEVICE-INFO {
    description
      "Tam device info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
  }

  grouping ncs_rpc_notif_TAMSVCS-INFO-ALL {
    description
      "Tam All info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
  }

  grouping live_ncs_TAMSVCS-SUDI-CERTS {
    description
      "Tam Sudi certs bag";
    leaf sudi-root-cert {
      type string;
      description
        "Sudi Root Certificate";
    }
    leaf sudi-subca-cert {
      type string;
      description
        "Sudi SubCA Certificate";
    }
    leaf sudi-cert {
      type string;
      description
        "Sudi Certificate of Tam Device";
    }
  }

  grouping live_ncs_TAMSVCS-DEVICE-INFO {
    description
      "Tam device info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
  }

  grouping live_ncs_TAMSVCS-INFO-ALL {
    description
      "Tam All info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
  }

  grouping TAMSVCS-SUDI-CERTS {
    description
      "Tam Sudi certs bag";
    leaf sudi-root-cert {
      type string;
      description
        "Sudi Root Certificate";
    }
    leaf sudi-subca-cert {
      type string;
      description
        "Sudi SubCA Certificate";
    }
    leaf sudi-cert {
      type string;
      description
        "Sudi Certificate of Tam Device";
    }
  }

  grouping TAMSVCS-DEVICE-INFO {
    description
      "Tam device info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
  }

  grouping TAMSVCS-INFO-ALL {
    description
      "Tam All info bag";
    leaf device-type {
      type string;
      description
        "Type of Tam Device";
    }
    leaf device-pid {
      type string;
      description
        "Pid of Tam Device";
    }
    leaf device-serial {
      type string;
      description
        "Serial Number of Tam Device";
    }
    leaf device-firware-version {
      type string;
      description
        "Firmware version of the device";
    }
    leaf server-version {
      type string;
      description
        "Tam Server Version";
    }
    leaf server-package-version {
      type string;
      description
        "Tam Services Server Package Version";
    }
    leaf client-package-version {
      type string;
      description
        "Tam Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
  }
}

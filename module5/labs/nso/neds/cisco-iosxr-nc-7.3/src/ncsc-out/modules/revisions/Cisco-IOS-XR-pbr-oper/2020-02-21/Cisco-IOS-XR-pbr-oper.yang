module Cisco-IOS-XR-pbr-oper {
  // Generated by yanger -t ncs
  tailf:mount-id "cisco-iosxr-nc-7.3:cisco-iosxr-nc-7.3";
  tailf:ncs-device-type "netconf";

  namespace "http://cisco.com/ns/yang/Cisco-IOS-XR-pbr-oper";
  prefix pbr-oper;

  import Cisco-IOS-XR-types {
    prefix xr;
  }
  import cisco-semver {
    prefix semver;
  }
  include Cisco-IOS-XR-pbr-oper-sub1 {
    revision-date 2020-02-21;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr package operational data.

     This module contains definitions
     for the following management objects:
       pbr: PBR operational data

     Copyright (c) 2013-2020 by Cisco Systems, Inc.
     All rights reserved.";

  revision 2020-02-21 {
    description
      "Adding HTTP Redirect stats per subs interface";
    semver:module-version "1.1.0";
  }
  revision 2019-04-05 {
    description
      "Establish semantic version baseline.";
    semver:module-version "1.0.1";
  }
  revision 2015-11-09 {
    description
      "IOS XR 6.0 revision.";
  }

  augment "/ncs:devices/ncs:device/ncs:config" {
    // NCS drop config false container pbr
  }
  augment "/ncs:devices/ncs:device/ncs:live-status" {
    container pbr {
      tailf:ncs-device-type "netconf";
      tailf:display-when "not(../../ncs:module) or ../../ncs:module[ncs:name='Cisco-IOS-XR-pbr-oper'] or (../../ncs:live-status-protocol[not(ncs:capability)]) or (../../ncs:live-status-protocol/ncs:capability/ncs:module[.='Cisco-IOS-XR-pbr-oper'])";
      description
        "PBR operational data";
      container nodes {
        description
          "Node-specific PBR operational data";
        list node {
          key "node-name";
          description
            "PBR operational data for a particular node";
          container policy-map {
            description
              "Operational data for policymaps";
            container interfaces {
              description
                "Operational data for all interfaces";
              list interface {
                key "interface-name";
                description
                  "PBR action data for a particular interface";
                container direction {
                  description
                    "PBR direction";
                  container input {
                    description
                      "PBR policy statistics";
                    uses live_ncs_PBR-STATS;
                  }
                }
                leaf interface-name {
                  type xr:live_ncs_Interface-name;
                  description
                    "Name of the interface";
                }
              }
            }
          }
          leaf node-name {
            type xr:live_ncs_Node-id;
            description
              "The node";
          }
        }
      }
    }
  }
  augment "/ncs:devices/ncs:template/ncs:ned-id/ncs:config" {
    // NCS drop config false container pbr
  }
}

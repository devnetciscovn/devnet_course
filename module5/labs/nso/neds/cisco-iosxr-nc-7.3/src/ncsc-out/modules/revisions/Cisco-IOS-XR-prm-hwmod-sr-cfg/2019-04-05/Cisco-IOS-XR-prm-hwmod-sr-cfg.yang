module Cisco-IOS-XR-prm-hwmod-sr-cfg {
  // Generated by yanger -t ncs
  tailf:mount-id "cisco-iosxr-nc-7.3:cisco-iosxr-nc-7.3";
  tailf:ncs-device-type "netconf";

  namespace "http://cisco.com/ns/yang/Cisco-IOS-XR-prm-hwmod-sr-cfg";
  prefix prm-hwmod-sr-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR prm-hwmod-sr package configuration.

     This module contains definitions
     for the following management objects:
       hardware-module: HardwareModule

     Copyright (c) 2013-2019 by Cisco Systems, Inc.
     All rights reserved.";

  revision 2019-04-05 {
    description
      "Establish semantic version baseline.";
    semver:module-version "1.0.0";
  }
  revision 2017-04-12 {
    description
      "Implementing Conf Yang Model for Service label reservation for SR label stack limit";
  }
  revision 2015-11-09 {
    description
      "IOS XR 6.0 revision.";
  }

  augment "/ncs:devices/ncs:device/ncs:config" {
    container hardware-module {
      tailf:ncs-device-type "netconf";
      tailf:display-when "not(../../ncs:module) or ../../ncs:module[ncs:name='Cisco-IOS-XR-prm-hwmod-sr-cfg']";
      description
        "HardwareModule";
      container segment-routing {
        description
          "Segment Routing";
        container reserve {
          description
            "Reserve";
          container service-label {
            description
              "Service Label";
            leaf enable {
              type empty;
              description
                "Enable";
            }
          }
        }
      }
    }
  }
  augment "/ncs:devices/ncs:device/ncs:live-status" {
    container hardware-module {
      tailf:ncs-device-type "netconf";
      tailf:display-when "not(../../ncs:module) or ../../ncs:module[ncs:name='Cisco-IOS-XR-prm-hwmod-sr-cfg'] or (../../ncs:live-status-protocol[not(ncs:capability)]) or (../../ncs:live-status-protocol/ncs:capability/ncs:module[.='Cisco-IOS-XR-prm-hwmod-sr-cfg'])";
      description
        "HardwareModule";
      container segment-routing {
        description
          "Segment Routing";
        container reserve {
          description
            "Reserve";
          container service-label {
            description
              "Service Label";
            leaf enable {
              type empty;
              description
                "Enable";
            }
          }
        }
      }
    }
  }
  augment "/ncs:devices/ncs:template/ncs:ned-id/ncs:config" {
    container hardware-module {
      description
        "HardwareModule";
      container segment-routing {
        description
          "Segment Routing";
        container reserve {
          description
            "Reserve";
          container service-label {
            description
              "Service Label";
            leaf enable {
              type empty;
              description
                "Enable";
            }
          }
        }
      }
    }
  }
}

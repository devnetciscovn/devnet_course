module Cisco-IOS-XR-sysadmin-skywarp-envmon-ui {
  // Generated by yanger -t ncs
  tailf:mount-id "cisco-iosxr-nc-7.3:cisco-iosxr-nc-7.3";
  tailf:ncs-device-type "netconf";

  namespace "http://www.cisco.com/ns/yang/Cisco-IOS-XR-sysadmin-skywarp-envmon-ui";
  prefix envmon;

  import Cisco-IOS-XR-sysadmin-show-trace {
    prefix show_trace;
  }
  import tailf-xsd-types {
    prefix xs;
  }
  import Cisco-IOS-XR-sysadmin-types {
    prefix calvados;
  }
  import Cisco-IOS-XR-sysadmin-skywarp-envmon-types {
    prefix envmon-types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module holds chassis, cards Enviroment data.

     Copyright (c) 2012-2020 by Cisco Systems, Inc.
     All rights reserved.";

  revision 2020-05-12 {
    description
      "Required changes to add single mode config location specific";
    semver:module-version "1.0.0";
  }
  revision 2020-05-05 {
    description
      "Adjusting power consumed due to multi output for 9903";
  }
  revision 2019-04-15 {
    description
      "Establish semantic version baseline.";
  }
  revision 2018-04-09 {
    description
      "Required changes for ConfD 6.4.5";
  }
  revision 2018-02-06 {
    description
      "Adding CLI input validation for LC priority shutdown feature";
  }
  revision 2018-01-25 {
    description
      "Initial revision of LC priority shutdown feature";
  }
  revision 2017-11-27 {
    description
      "Add graceful shutdown disable CLI.";
  }
  revision 2017-07-31 {
    description
      "Changing the namespace to follow Cisco guidelines on naming convention";
  }
  revision 2017-04-10 {
    description
      "Adding the source leaf to altitude value,
       this is to distinguish the source of the altitude value ";
  }
  revision 2017-03-31 {
    description
      "Renamed module and namespace";
  }
  revision 2017-03-30 {
    description
      "commenting the sensor_attributes callpoints for the oper sensors,
       using only the location based callpoints for sensor_attributes ";
  }
  revision 2016-10-12 {
    description
      "unhide commands and configs. moved to advanced-grp";
  }
  revision 2011-11-24 {
    description
      "Initial revision of show environment commands";
  }

  grouping ncs_template_pm-location {
    leaf all {
      type empty;
    }
    list location {
      // NCS patched for predictable order
      ordered-by user;
      key "pmId";
      leaf pmId {
        type string;
      }
    }
  }

  grouping ncs_template_temp-data {
    // NCS drop config false container temperatures
  }

  grouping ncs_template_all-temp-data {
    // NCS drop config false list temperatures
  }

  grouping ncs_template_volt-data {
    // NCS drop config false container voltages
  }

  grouping ncs_template_all-volt-data {
    // NCS drop config false list voltages
  }

  grouping ncs_template_current-data {
    // NCS drop config false container current
  }

  grouping ncs_template_all-current-data {
    // NCS drop config false list current
  }

  grouping ncs_template_fan-data {
    // NCS drop config false container fan
  }

  grouping ncs_template_all-fan-data {
    // NCS drop config false list fan
  }

  grouping ncs_template_power-data {
    // NCS drop config false container power
  }

  grouping ncs_template_all-power-data {
    // NCS drop config false list power
  }

  grouping ncs_template_altitude-data {
    // NCS drop config false container altitude
  }

  grouping ncs_template_all-altitude-data {
    // NCS drop config false list altitude
  }

  grouping ncs_template_rack-location {
    leaf all {
      type empty;
    }
    list location {
      // NCS patched for predictable order
      ordered-by user;
      key "rackId";
      leaf rackId {
        type calvados:ncs_template_rack-id;
      }
    }
  }

  grouping ncs_template_router-group {
    container router {
      container altitude {
        container all {
          leaf num_meters {
            type string;
          }
        }
        container rack_loc {
          list location {
            // NCS patched for predictable order
            ordered-by user;
            key "rackId";
            leaf rackId {
              type calvados:ncs_template_rack-id;
            }
            leaf num_meters {
              type string;
            }
          }
        }
      }
    }
  }

  grouping ncs_template_air-filter-group {
    container air-filter {
      container replaced {
        container all {
          leaf date {
            type string;
          }
        }
        container rack_loc {
          list location {
            // NCS patched for predictable order
            ordered-by user;
            key "rackId";
            leaf rackId {
              type calvados:ncs_template_rack-id;
            }
            leaf date {
              type string;
            }
          }
        }
      }
    }
  }

  grouping ncs_template_fan-ctrl-group {
    container fan-ctrl {
      container disable {
        container rack_loc {
          uses ncs_template_rack-location;
        }
      }
    }
  }

  grouping ncs_template_temp-monitor-group {
    container temperature {
      container disable {
        container rack_loc {
          uses ncs_template_rack-location;
        }
      }
    }
  }

  grouping ncs_template_env-monitor-group {
    container monitoring {
      container disable {
        container rack_loc {
          uses ncs_template_rack-location;
        }
      }
    }
  }

  grouping ncs_template_power-mgmt-group {
    container action {
      container disable {
        container rack_loc {
          uses ncs_template_rack-location;
        }
      }
    }
    container single-feed-mode {
      container enable {
        container pm_loc {
          uses ncs_template_pm-location;
        }
      }
    }
    container extended-temp {
      container enable {
        container rack_loc {
          uses ncs_template_rack-location;
        }
      }
    }
    container redundancy-num-pms {
      container all {
        leaf num_pm {
          type envmon-types:ncs_template_num_pm;
        }
      }
      container rack_loc {
        list location {
          // NCS patched for predictable order
          ordered-by user;
          key "rackId";
          leaf rackId {
            type calvados:ncs_template_rack-id;
          }
          leaf num_pm {
            type envmon-types:ncs_template_num_pm;
          }
        }
      }
    }
    container progressive {
      list enable {
        // NCS patched for predictable order
        ordered-by user;
        key "enabled";
        leaf enabled {
          type string;
          // NCS dropped explicit config true
        }
        leaf syslog-threshold {
          type string;
          // NCS dropped explicit config true
        }
        leaf shutdown-threshold {
          type string;
          // NCS dropped explicit config true
        }
        container priority {
          list location {
            // NCS patched for predictable order
            ordered-by user;
            key "loc";
            leaf loc {
              type string;
            }
            leaf prior {
              type string;
            }
          }
        }
      }
    }
  }

  grouping ncs_template_cmd_types {
    // NCS drop config false container oper
    // NCS drop config false container all
    container config {
      description
        "environment configurational data";
      uses ncs_template_router-group;
      uses ncs_template_air-filter-group;
      uses ncs_template_fan-ctrl-group;
      uses ncs_template_temp-monitor-group;
      uses ncs_template_env-monitor-group;
      uses envmon-types:ncs_template_fan-speed-group;
      uses envmon-types:ncs_template_fan-ctrl-optics-group;
      uses envmon-types:ncs_template_vin-uv-shut-group;
    }
  }

  grouping ncs_rpc_notif_pm-location {
    leaf all {
      type empty;
    }
    list location {
      key "pmId";
      leaf pmId {
        type string {
          pattern '0/PT[0-3]-PM[0-3]';
        }
      }
    }
  }

  grouping ncs_rpc_notif_temp-data {
    container temperatures {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf temperature_value {
            type string;
          }
          leaf value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping ncs_rpc_notif_all-temp-data {
    list temperatures {
      key "loc_iden";
      config false;
      leaf loc_iden {
        type string;
      }
      leaf print_header {
        type boolean;
        default "false";
      }
      list sensor_attributes {
        key "sensor";
        leaf sensor {
          type string;
        }
        leaf sensor_id {
          type string;
        }
        leaf alarm {
          type string;
        }
        leaf temperature_value {
          type string;
        }
        leaf value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping ncs_rpc_notif_volt-data {
    container voltages {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf value {
            type string;
          }
          leaf temperature_value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping ncs_rpc_notif_all-volt-data {
    list voltages {
      key "loc_iden";
      config false;
      leaf loc_iden {
        type string;
      }
      leaf print_header {
        type boolean;
        default "false";
      }
      list sensor_attributes {
        key "sensor";
        leaf sensor {
          type string;
        }
        leaf sensor_id {
          type string;
        }
        leaf alarm {
          type string;
        }
        leaf value {
          type string;
        }
        leaf temperature_value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping ncs_rpc_notif_current-data {
    container current {
      config false;
      list location {
        key "location";
        leaf location {
          type string;
        }
        list sensor_attributes {
          key "sensor";
          leaf loc_header {
            type boolean;
            default "false";
          }
          leaf print_header {
            type boolean;
            default "false";
          }
          leaf location {
            type string;
          }
          leaf sensor {
            type string;
          }
          leaf sensor_id {
            type string;
          }
          leaf alarm {
            type string;
          }
          leaf value {
            type string;
          }
          leaf temperature_value {
            type int32;
          }
        }
      }
    }
  }

  grouping ncs_rpc_notif_all-current-data {
    list current {
      key "loc_iden";
      config false;
      leaf loc_iden {
        type string;
      }
      leaf print_header {
        type boolean;
        default "false";
      }
      list sensor_attributes {
        key "sensor";
        leaf sensor {
          type string;
        }
        leaf sensor_id {
          type string;
        }
        leaf value {
          type string;
        }
      }
    }
  }

  grouping ncs_rpc_notif_fan-data {
    container fan {
      config false;
      list location {
        key "location";
        leaf location {
          type string;
        }
        leaf print_header {
          type boolean;
          default "false";
        }
        leaf loc_header {
          type uint32;
        }
        list fan_attributes {
          key "logical_slot";
          leaf print_fan_header {
            type string;
          }
          leaf location {
            type string;
          }
          leaf logical_slot {
            type string;
          }
          leaf fru_PID {
            type string;
          }
          leaf fans_speed {
            type string;
          }
          leaf fan_header {
            type uint32;
          }
          leaf speed_space {
            type uint32;
          }
        }
      }
    }
  }

  grouping ncs_rpc_notif_all-fan-data {
    list fan {
      key "loc_iden";
      config false;
      leaf loc_iden {
        type string;
      }
      list fan_attributes {
        key "logical_slot";
        leaf print_fan_header {
          type string;
        }
        leaf location {
          type string;
        }
        leaf logical_slot {
          type string;
        }
        leaf fru_PID {
          type string;
        }
        leaf fans_speed {
          type string;
        }
        leaf fan_header {
          type uint32;
        }
        leaf speed_space {
          type uint32;
        }
      }
    }
  }

  grouping ncs_rpc_notif_power-data {
    container power {
      config false;
      list location {
        key "location";
        leaf location {
          type string;
        }
        list pem_attributes {
          key "pem";
          leaf pem {
            type string;
          }
          leaf pem_id {
            type string;
          }
          leaf card_type {
            type string;
          }
          leaf ps_type {
            type string;
          }
          leaf shelf_num {
            type uint16;
          }
          leaf supply_type {
            type string;
          }
          leaf input_voltage {
            type string;
          }
          leaf input_current {
            type string;
          }
          leaf output_voltage {
            type xs:double;
          }
          leaf output_current {
            type xs:double;
          }
          leaf status {
            type string;
          }
          leaf input_power_to_ps {
            type uint32;
          }
          leaf input_current_to_ps {
            type string;
          }
          leaf output_power_from_ps {
            type uint32;
          }
          leaf output_current_from_ps {
            type xs:double;
          }
          leaf power_allocated {
            type uint32;
          }
          leaf power_consumed {
            type string;
          }
          leaf power_status {
            type string;
          }
          leaf confgd_power_redundancy_mode {
            type string;
          }
          leaf usable_power_capacity {
            type uint32;
          }
          leaf protection_power_capacity {
            type uint32;
          }
          leaf power_resrv_and_alloc {
            type uint32;
          }
          leaf system_power_used {
            type uint32;
          }
          leaf system_power_input {
            type uint32;
          }
          leaf power_level {
            type uint16;
          }
          leaf output_header {
            type uint16;
          }
          leaf output_footer {
            type uint16;
          }
          leaf ps_sum_footer {
            type uint16;
          }
        }
      }
    }
  }

  grouping ncs_rpc_notif_all-power-data {
    list power {
      key "loc_iden";
      config false;
      leaf loc_iden {
        type string;
      }
      list pem_attributes {
        key "pem";
        leaf pem {
          type string;
        }
        leaf pem_id {
          type string;
        }
        leaf card_type {
          type string;
        }
        leaf ps_type {
          type string;
        }
        leaf shelf_num {
          type uint16;
        }
        leaf supply_type {
          type string;
        }
        leaf input_voltage {
          type string;
        }
        leaf input_current {
          type string;
        }
        leaf output_voltage {
          type xs:double;
        }
        leaf output_current {
          type xs:double;
        }
        leaf status {
          type string;
        }
        leaf input_power_to_ps {
          type uint32;
        }
        leaf input_current_to_ps {
          type string;
        }
        leaf output_power_from_ps {
          type uint32;
        }
        leaf output_current_from_ps {
          type xs:double;
        }
        leaf power_allocated {
          type uint32;
        }
        leaf power_consumed {
          type string;
        }
        leaf power_status {
          type string;
        }
        leaf confgd_power_redundancy_mode {
          type string;
        }
        leaf usable_power_capacity {
          type uint32;
        }
        leaf protection_power_capacity {
          type uint32;
        }
        leaf power_resrv_and_alloc {
          type uint32;
        }
        leaf system_power_used {
          type uint32;
        }
        leaf system_power_input {
          type uint32;
        }
        leaf power_level {
          type uint16;
        }
        leaf output_header {
          type uint16;
        }
        leaf output_footer {
          type uint16;
        }
        leaf ps_sum_footer {
          type uint16;
        }
      }
    }
  }

  grouping ncs_rpc_notif_altitude-data {
    container altitude {
      config false;
      list location {
        key "location";
        leaf location {
          type string;
        }
        list alt_attributes {
          key "sensor";
          leaf sensor {
            type string;
          }
          leaf rack {
            type uint32;
          }
          leaf sensor_value {
            type string;
          }
          leaf source {
            type string;
          }
          leaf print_header {
            type boolean;
            default "false";
          }
        }
      }
    }
  }

  grouping ncs_rpc_notif_all-altitude-data {
    list altitude {
      key "loc_iden";
      config false;
      leaf loc_iden {
        type string;
      }
      list alt_attributes {
        key "sensor";
        leaf print_header {
          type boolean;
          default "false";
        }
        leaf sensor {
          type string;
        }
        leaf rack {
          type uint32;
        }
        leaf sensor_value {
          type string;
        }
        leaf source {
          type string;
        }
      }
    }
  }

  grouping ncs_rpc_notif_rack-location {
    leaf all {
      type empty;
    }
    list location {
      key "rackId";
      leaf rackId {
        type calvados:ncs_rpc_notif_rack-id;
      }
    }
  }

  grouping ncs_rpc_notif_router-group {
    container router {
      container altitude {
        container all {
          leaf num_meters {
            type uint32 {
              range "1..4000";
            }
          }
        }
        container rack_loc {
          list location {
            key "rackId";
            leaf rackId {
              type calvados:ncs_rpc_notif_rack-id;
            }
            leaf num_meters {
              type uint32 {
                range "1..4000";
              }
            }
          }
        }
      }
    }
  }

  grouping ncs_rpc_notif_air-filter-group {
    container air-filter {
      container replaced {
        container all {
          leaf date {
            type xs:date;
          }
        }
        container rack_loc {
          list location {
            key "rackId";
            leaf rackId {
              type calvados:ncs_rpc_notif_rack-id;
            }
            leaf date {
              type xs:date;
            }
          }
        }
      }
    }
  }

  grouping ncs_rpc_notif_fan-ctrl-group {
    container fan-ctrl {
      container disable {
        container rack_loc {
          uses ncs_rpc_notif_rack-location;
        }
      }
    }
  }

  grouping ncs_rpc_notif_temp-monitor-group {
    container temperature {
      container disable {
        container rack_loc {
          uses ncs_rpc_notif_rack-location;
        }
      }
    }
  }

  grouping ncs_rpc_notif_env-monitor-group {
    container monitoring {
      container disable {
        container rack_loc {
          uses ncs_rpc_notif_rack-location;
        }
      }
    }
  }

  grouping ncs_rpc_notif_power-mgmt-group {
    container action {
      container disable {
        container rack_loc {
          uses ncs_rpc_notif_rack-location;
        }
      }
    }
    container single-feed-mode {
      container enable {
        container pm_loc {
          uses ncs_rpc_notif_pm-location;
        }
      }
    }
    container extended-temp {
      container enable {
        container rack_loc {
          uses ncs_rpc_notif_rack-location;
        }
      }
    }
    container redundancy-num-pms {
      container all {
        leaf num_pm {
          type envmon-types:ncs_rpc_notif_num_pm;
        }
      }
      container rack_loc {
        list location {
          key "rackId";
          leaf rackId {
            type calvados:ncs_rpc_notif_rack-id;
          }
          leaf num_pm {
            type envmon-types:ncs_rpc_notif_num_pm;
          }
        }
      }
    }
    container progressive {
      list enable {
        key "enabled";
        leaf enabled {
          type enumeration {
            enum "enable";
          }
          // NCS dropped explicit config true
        }
        leaf syslog-threshold {
          type uint32 {
            range "3000 .. 72000";
          }
          // NCS dropped explicit config true
        }
        leaf shutdown-threshold {
          type uint32 {
            range "3000 .. 72000";
          }
          // NCS dropped explicit config true
        }
        container priority {
          list location {
            key "loc";
            leaf loc {
              type string {
                pattern '0/([0-9]|1[0-9])';
              }
            }
            leaf prior {
              type uint32 {
                range "0 .. 19";
              }
            }
          }
        }
      }
    }
  }

  grouping ncs_rpc_notif_cmd_types {
    container oper {
      config false;
      description
        "environment operational (show) data";
      uses ncs_rpc_notif_temp-data;
      uses ncs_rpc_notif_volt-data;
      uses ncs_rpc_notif_current-data;
      uses ncs_rpc_notif_fan-data;
      uses ncs_rpc_notif_power-data;
      uses ncs_rpc_notif_altitude-data;
    }
    container all {
      config false;
      list location {
        key "location";
        leaf location {
          type string;
        }
        uses ncs_rpc_notif_all-temp-data;
        uses ncs_rpc_notif_all-volt-data;
        uses ncs_rpc_notif_all-current-data;
        uses ncs_rpc_notif_all-fan-data;
        uses ncs_rpc_notif_all-power-data;
        uses ncs_rpc_notif_all-altitude-data;
      }
    }
    container config {
      description
        "environment configurational data";
      uses ncs_rpc_notif_router-group;
      uses ncs_rpc_notif_air-filter-group;
      uses ncs_rpc_notif_fan-ctrl-group;
      uses ncs_rpc_notif_temp-monitor-group;
      uses ncs_rpc_notif_env-monitor-group;
      uses envmon-types:ncs_rpc_notif_fan-speed-group;
      uses envmon-types:ncs_rpc_notif_fan-ctrl-optics-group;
      uses envmon-types:ncs_rpc_notif_vin-uv-shut-group;
    }
  }

  grouping live_ncs_pm-location {
    leaf all {
      type empty;
    }
    list location {
      key "pmId";
      leaf pmId {
        type string {
          pattern '0/PT[0-3]-PM[0-3]';
        }
      }
    }
  }

  grouping live_ncs_temp-data {
    container temperatures {
      list location {
        key "location";
        leaf location {
          type string;
        }
        list sensor_attributes {
          key "sensor";
          leaf loc_header {
            type boolean;
            // NCS drop default statement
          }
          leaf print_header {
            type boolean;
            // NCS drop default statement
          }
          leaf location {
            type string;
          }
          leaf sensor {
            type string;
          }
          leaf sensor_id {
            type string;
          }
          leaf alarm {
            type string;
          }
          leaf temperature_value {
            type string;
          }
          leaf value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping live_ncs_all-temp-data {
    list temperatures {
      key "loc_iden";
      leaf loc_iden {
        type string;
      }
      leaf print_header {
        type boolean;
        // NCS drop default statement
      }
      list sensor_attributes {
        key "sensor";
        leaf sensor {
          type string;
        }
        leaf sensor_id {
          type string;
        }
        leaf alarm {
          type string;
        }
        leaf temperature_value {
          type string;
        }
        leaf value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping live_ncs_volt-data {
    container voltages {
      list location {
        key "location";
        leaf location {
          type string;
        }
        list sensor_attributes {
          key "sensor";
          leaf loc_header {
            type boolean;
            // NCS drop default statement
          }
          leaf print_header {
            type boolean;
            // NCS drop default statement
          }
          leaf location {
            type string;
          }
          leaf sensor {
            type string;
          }
          leaf sensor_id {
            type string;
          }
          leaf alarm {
            type string;
          }
          leaf value {
            type string;
          }
          leaf temperature_value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping live_ncs_all-volt-data {
    list voltages {
      key "loc_iden";
      leaf loc_iden {
        type string;
      }
      leaf print_header {
        type boolean;
        // NCS drop default statement
      }
      list sensor_attributes {
        key "sensor";
        leaf sensor {
          type string;
        }
        leaf sensor_id {
          type string;
        }
        leaf alarm {
          type string;
        }
        leaf value {
          type string;
        }
        leaf temperature_value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping live_ncs_current-data {
    container current {
      list location {
        key "location";
        leaf location {
          type string;
        }
        list sensor_attributes {
          key "sensor";
          leaf loc_header {
            type boolean;
            // NCS drop default statement
          }
          leaf print_header {
            type boolean;
            // NCS drop default statement
          }
          leaf location {
            type string;
          }
          leaf sensor {
            type string;
          }
          leaf sensor_id {
            type string;
          }
          leaf alarm {
            type string;
          }
          leaf value {
            type string;
          }
          leaf temperature_value {
            type int32;
          }
        }
      }
    }
  }

  grouping live_ncs_all-current-data {
    list current {
      key "loc_iden";
      leaf loc_iden {
        type string;
      }
      leaf print_header {
        type boolean;
        // NCS drop default statement
      }
      list sensor_attributes {
        key "sensor";
        leaf sensor {
          type string;
        }
        leaf sensor_id {
          type string;
        }
        leaf value {
          type string;
        }
      }
    }
  }

  grouping live_ncs_fan-data {
    container fan {
      list location {
        key "location";
        leaf location {
          type string;
        }
        leaf print_header {
          type boolean;
          // NCS drop default statement
        }
        leaf loc_header {
          type uint32;
        }
        list fan_attributes {
          key "logical_slot";
          leaf print_fan_header {
            type string;
          }
          leaf location {
            type string;
          }
          leaf logical_slot {
            type string;
          }
          leaf fru_PID {
            type string;
          }
          leaf fans_speed {
            type string;
          }
          leaf fan_header {
            type uint32;
          }
          leaf speed_space {
            type uint32;
          }
        }
      }
    }
  }

  grouping live_ncs_all-fan-data {
    list fan {
      key "loc_iden";
      leaf loc_iden {
        type string;
      }
      list fan_attributes {
        key "logical_slot";
        leaf print_fan_header {
          type string;
        }
        leaf location {
          type string;
        }
        leaf logical_slot {
          type string;
        }
        leaf fru_PID {
          type string;
        }
        leaf fans_speed {
          type string;
        }
        leaf fan_header {
          type uint32;
        }
        leaf speed_space {
          type uint32;
        }
      }
    }
  }

  grouping live_ncs_power-data {
    container power {
      list location {
        key "location";
        leaf location {
          type string;
        }
        list pem_attributes {
          key "pem";
          leaf pem {
            type string;
          }
          leaf pem_id {
            type string;
          }
          leaf card_type {
            type string;
          }
          leaf ps_type {
            type string;
          }
          leaf shelf_num {
            type uint16;
          }
          leaf supply_type {
            type string;
          }
          leaf input_voltage {
            type string;
          }
          leaf input_current {
            type string;
          }
          leaf output_voltage {
            type xs:double;
          }
          leaf output_current {
            type xs:double;
          }
          leaf status {
            type string;
          }
          leaf input_power_to_ps {
            type uint32;
          }
          leaf input_current_to_ps {
            type string;
          }
          leaf output_power_from_ps {
            type uint32;
          }
          leaf output_current_from_ps {
            type xs:double;
          }
          leaf power_allocated {
            type uint32;
          }
          leaf power_consumed {
            type string;
          }
          leaf power_status {
            type string;
          }
          leaf confgd_power_redundancy_mode {
            type string;
          }
          leaf usable_power_capacity {
            type uint32;
          }
          leaf protection_power_capacity {
            type uint32;
          }
          leaf power_resrv_and_alloc {
            type uint32;
          }
          leaf system_power_used {
            type uint32;
          }
          leaf system_power_input {
            type uint32;
          }
          leaf power_level {
            type uint16;
          }
          leaf output_header {
            type uint16;
          }
          leaf output_footer {
            type uint16;
          }
          leaf ps_sum_footer {
            type uint16;
          }
        }
      }
    }
  }

  grouping live_ncs_all-power-data {
    list power {
      key "loc_iden";
      leaf loc_iden {
        type string;
      }
      list pem_attributes {
        key "pem";
        leaf pem {
          type string;
        }
        leaf pem_id {
          type string;
        }
        leaf card_type {
          type string;
        }
        leaf ps_type {
          type string;
        }
        leaf shelf_num {
          type uint16;
        }
        leaf supply_type {
          type string;
        }
        leaf input_voltage {
          type string;
        }
        leaf input_current {
          type string;
        }
        leaf output_voltage {
          type xs:double;
        }
        leaf output_current {
          type xs:double;
        }
        leaf status {
          type string;
        }
        leaf input_power_to_ps {
          type uint32;
        }
        leaf input_current_to_ps {
          type string;
        }
        leaf output_power_from_ps {
          type uint32;
        }
        leaf output_current_from_ps {
          type xs:double;
        }
        leaf power_allocated {
          type uint32;
        }
        leaf power_consumed {
          type string;
        }
        leaf power_status {
          type string;
        }
        leaf confgd_power_redundancy_mode {
          type string;
        }
        leaf usable_power_capacity {
          type uint32;
        }
        leaf protection_power_capacity {
          type uint32;
        }
        leaf power_resrv_and_alloc {
          type uint32;
        }
        leaf system_power_used {
          type uint32;
        }
        leaf system_power_input {
          type uint32;
        }
        leaf power_level {
          type uint16;
        }
        leaf output_header {
          type uint16;
        }
        leaf output_footer {
          type uint16;
        }
        leaf ps_sum_footer {
          type uint16;
        }
      }
    }
  }

  grouping live_ncs_altitude-data {
    container altitude {
      list location {
        key "location";
        leaf location {
          type string;
        }
        list alt_attributes {
          key "sensor";
          leaf sensor {
            type string;
          }
          leaf rack {
            type uint32;
          }
          leaf sensor_value {
            type string;
          }
          leaf source {
            type string;
          }
          leaf print_header {
            type boolean;
            // NCS drop default statement
          }
        }
      }
    }
  }

  grouping live_ncs_all-altitude-data {
    list altitude {
      key "loc_iden";
      leaf loc_iden {
        type string;
      }
      list alt_attributes {
        key "sensor";
        leaf print_header {
          type boolean;
          // NCS drop default statement
        }
        leaf sensor {
          type string;
        }
        leaf rack {
          type uint32;
        }
        leaf sensor_value {
          type string;
        }
        leaf source {
          type string;
        }
      }
    }
  }

  grouping live_ncs_rack-location {
    leaf all {
      type empty;
    }
    list location {
      key "rackId";
      leaf rackId {
        type calvados:live_ncs_rack-id;
      }
    }
  }

  grouping live_ncs_router-group {
    container router {
      container altitude {
        container all {
          leaf num_meters {
            type uint32 {
              range "1..4000";
            }
          }
        }
        container rack_loc {
          list location {
            key "rackId";
            leaf rackId {
              type calvados:live_ncs_rack-id;
            }
            leaf num_meters {
              type uint32 {
                range "1..4000";
              }
            }
          }
        }
      }
    }
  }

  grouping live_ncs_air-filter-group {
    container air-filter {
      container replaced {
        container all {
          leaf date {
            type xs:date;
          }
        }
        container rack_loc {
          list location {
            key "rackId";
            leaf rackId {
              type calvados:live_ncs_rack-id;
            }
            leaf date {
              type xs:date;
            }
          }
        }
      }
    }
  }

  grouping live_ncs_fan-ctrl-group {
    container fan-ctrl {
      container disable {
        container rack_loc {
          uses live_ncs_rack-location;
        }
      }
    }
  }

  grouping live_ncs_temp-monitor-group {
    container temperature {
      container disable {
        container rack_loc {
          uses live_ncs_rack-location;
        }
      }
    }
  }

  grouping live_ncs_env-monitor-group {
    container monitoring {
      container disable {
        container rack_loc {
          uses live_ncs_rack-location;
        }
      }
    }
  }

  grouping live_ncs_power-mgmt-group {
    container action {
      container disable {
        container rack_loc {
          uses live_ncs_rack-location;
        }
      }
    }
    container single-feed-mode {
      container enable {
        container pm_loc {
          uses live_ncs_pm-location;
        }
      }
    }
    container extended-temp {
      container enable {
        container rack_loc {
          uses live_ncs_rack-location;
        }
      }
    }
    container redundancy-num-pms {
      container all {
        leaf num_pm {
          type envmon-types:live_ncs_num_pm;
        }
      }
      container rack_loc {
        list location {
          key "rackId";
          leaf rackId {
            type calvados:live_ncs_rack-id;
          }
          leaf num_pm {
            type envmon-types:live_ncs_num_pm;
          }
        }
      }
    }
    container progressive {
      list enable {
        key "enabled";
        leaf enabled {
          type enumeration {
            enum "enable";
          }
        }
        leaf syslog-threshold {
          type uint32 {
            range "3000 .. 72000";
          }
        }
        leaf shutdown-threshold {
          type uint32 {
            range "3000 .. 72000";
          }
        }
        container priority {
          list location {
            key "loc";
            leaf loc {
              type string {
                pattern '0/([0-9]|1[0-9])';
              }
            }
            leaf prior {
              type uint32 {
                range "0 .. 19";
              }
            }
          }
        }
      }
    }
  }

  grouping live_ncs_cmd_types {
    container oper {
      description
        "environment operational (show) data";
      uses live_ncs_temp-data;
      uses live_ncs_volt-data;
      uses live_ncs_current-data;
      uses live_ncs_fan-data;
      uses live_ncs_power-data;
      uses live_ncs_altitude-data;
    }
    container all {
      list location {
        key "location";
        leaf location {
          type string;
        }
        uses live_ncs_all-temp-data;
        uses live_ncs_all-volt-data;
        uses live_ncs_all-current-data;
        uses live_ncs_all-fan-data;
        uses live_ncs_all-power-data;
        uses live_ncs_all-altitude-data;
      }
    }
    container config {
      description
        "environment configurational data";
      uses live_ncs_router-group;
      uses live_ncs_air-filter-group;
      uses live_ncs_fan-ctrl-group;
      uses live_ncs_temp-monitor-group;
      uses live_ncs_env-monitor-group;
      uses envmon-types:live_ncs_fan-speed-group;
      uses envmon-types:live_ncs_fan-ctrl-optics-group;
      uses envmon-types:live_ncs_vin-uv-shut-group;
    }
  }

  grouping pm-location {
    leaf all {
      type empty;
    }
    list location {
      key "pmId";
      leaf pmId {
        type string {
          pattern '0/PT[0-3]-PM[0-3]';
        }
      }
    }
  }

  grouping temp-data {
    // NCS drop config false container temperatures
  }

  grouping all-temp-data {
    // NCS drop config false list temperatures
  }

  grouping volt-data {
    // NCS drop config false container voltages
  }

  grouping all-volt-data {
    // NCS drop config false list voltages
  }

  grouping current-data {
    // NCS drop config false container current
  }

  grouping all-current-data {
    // NCS drop config false list current
  }

  grouping fan-data {
    // NCS drop config false container fan
  }

  grouping all-fan-data {
    // NCS drop config false list fan
  }

  grouping power-data {
    // NCS drop config false container power
  }

  grouping all-power-data {
    // NCS drop config false list power
  }

  grouping altitude-data {
    // NCS drop config false container altitude
  }

  grouping all-altitude-data {
    // NCS drop config false list altitude
  }

  grouping rack-location {
    leaf all {
      type empty;
    }
    list location {
      key "rackId";
      leaf rackId {
        type calvados:rack-id;
      }
    }
  }

  grouping router-group {
    container router {
      container altitude {
        container all {
          leaf num_meters {
            type uint32 {
              range "1..4000";
            }
          }
        }
        container rack_loc {
          list location {
            key "rackId";
            leaf rackId {
              type calvados:rack-id;
            }
            leaf num_meters {
              type uint32 {
                range "1..4000";
              }
            }
          }
        }
      }
    }
  }

  grouping air-filter-group {
    container air-filter {
      container replaced {
        container all {
          leaf date {
            type xs:date;
          }
        }
        container rack_loc {
          list location {
            key "rackId";
            leaf rackId {
              type calvados:rack-id;
            }
            leaf date {
              type xs:date;
            }
          }
        }
      }
    }
  }

  grouping fan-ctrl-group {
    container fan-ctrl {
      container disable {
        container rack_loc {
          uses rack-location;
        }
      }
    }
  }

  grouping temp-monitor-group {
    container temperature {
      container disable {
        container rack_loc {
          uses rack-location;
        }
      }
    }
  }

  grouping env-monitor-group {
    container monitoring {
      container disable {
        container rack_loc {
          uses rack-location;
        }
      }
    }
  }

  grouping power-mgmt-group {
    container action {
      container disable {
        container rack_loc {
          uses rack-location;
        }
      }
    }
    container single-feed-mode {
      container enable {
        container pm_loc {
          uses pm-location;
        }
      }
    }
    container extended-temp {
      container enable {
        container rack_loc {
          uses rack-location;
        }
      }
    }
    container redundancy-num-pms {
      container all {
        leaf num_pm {
          type envmon-types:num_pm;
        }
      }
      container rack_loc {
        list location {
          key "rackId";
          leaf rackId {
            type calvados:rack-id;
          }
          leaf num_pm {
            type envmon-types:num_pm;
          }
        }
      }
    }
    container progressive {
      list enable {
        key "enabled";
        leaf enabled {
          type enumeration {
            enum "enable";
          }
          // NCS dropped explicit config true
        }
        leaf syslog-threshold {
          type uint32 {
            range "3000 .. 72000";
          }
          // NCS dropped explicit config true
        }
        leaf shutdown-threshold {
          type uint32 {
            range "3000 .. 72000";
          }
          // NCS dropped explicit config true
        }
        container priority {
          list location {
            key "loc";
            leaf loc {
              type string {
                pattern '0/([0-9]|1[0-9])';
              }
            }
            leaf prior {
              type uint32 {
                range "0 .. 19";
              }
            }
          }
        }
      }
    }
  }

  grouping cmd_types {
    // NCS drop config false container oper
    // NCS drop config false container all
    container config {
      description
        "environment configurational data";
      uses router-group;
      uses air-filter-group;
      uses fan-ctrl-group;
      uses temp-monitor-group;
      uses env-monitor-group;
      uses envmon-types:fan-speed-group;
      uses envmon-types:fan-ctrl-optics-group;
      uses envmon-types:vin-uv-shut-group;
    }
  }

  augment "/ncs:devices/ncs:device/ncs:config" {
    container environment {
      tailf:ncs-device-type "netconf";
      tailf:display-when "not(../../ncs:module) or ../../ncs:module[ncs:name='Cisco-IOS-XR-sysadmin-skywarp-envmon-ui']";
      uses cmd_types;
      uses show_trace:traceable;
    }
    container power-mgmt {
      tailf:ncs-device-type "netconf";
      tailf:display-when "not(../../ncs:module) or ../../ncs:module[ncs:name='Cisco-IOS-XR-sysadmin-skywarp-envmon-ui']";
      container config {
        description
          "Power Trays and PEMs configurational data";
        uses power-mgmt-group;
      }
    }
  }
  augment "/ncs:devices/ncs:device/ncs:live-status" {
    container environment {
      tailf:ncs-device-type "netconf";
      tailf:display-when "not(../../ncs:module) or ../../ncs:module[ncs:name='Cisco-IOS-XR-sysadmin-skywarp-envmon-ui'] or (../../ncs:live-status-protocol[not(ncs:capability)]) or (../../ncs:live-status-protocol/ncs:capability/ncs:module[.='Cisco-IOS-XR-sysadmin-skywarp-envmon-ui'])";
      uses live_ncs_cmd_types;
      uses show_trace:live_ncs_traceable;
    }
    container power-mgmt {
      tailf:ncs-device-type "netconf";
      tailf:display-when "not(../../ncs:module) or ../../ncs:module[ncs:name='Cisco-IOS-XR-sysadmin-skywarp-envmon-ui'] or (../../ncs:live-status-protocol[not(ncs:capability)]) or (../../ncs:live-status-protocol/ncs:capability/ncs:module[.='Cisco-IOS-XR-sysadmin-skywarp-envmon-ui'])";
      container config {
        description
          "Power Trays and PEMs configurational data";
        uses live_ncs_power-mgmt-group;
      }
    }
  }
  augment "/ncs:devices/ncs:template/ncs:ned-id/ncs:config" {
    container environment {
      uses ncs_template_cmd_types;
      uses show_trace:ncs_template_traceable;
    }
    container power-mgmt {
      container config {
        description
          "Power Trays and PEMs configurational data";
        uses ncs_template_power-mgmt-group;
      }
    }
  }
}

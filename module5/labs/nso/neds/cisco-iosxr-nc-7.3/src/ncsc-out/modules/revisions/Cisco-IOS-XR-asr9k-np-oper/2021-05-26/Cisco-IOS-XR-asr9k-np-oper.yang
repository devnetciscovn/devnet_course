module Cisco-IOS-XR-asr9k-np-oper {
  // Generated by yanger -t ncs
  tailf:mount-id "cisco-iosxr-nc-7.3:cisco-iosxr-nc-7.3";
  tailf:ncs-device-type "netconf";

  namespace "http://cisco.com/ns/yang/Cisco-IOS-XR-asr9k-np-oper";
  prefix asr9k-np-oper;

  import Cisco-IOS-XR-types {
    prefix xr;
  }
  import cisco-semver {
    prefix semver;
  }
  include Cisco-IOS-XR-asr9k-np-oper-sub1 {
    revision-date 2021-05-26;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-np package operational data.

     This module contains definitions
     for the following management objects:
       hardware-module-np: Hardware NP Counters

     Copyright (c) 2013-2021 by Cisco Systems, Inc.
     All rights reserved.";

  revision 2021-05-26 {
    description
      "add support for NP ucode counter query by index";
    semver:module-version "1.1.0";
  }
  revision 2019-10-29 {
    description
      "Add more specific descriptions to address Good description issue";
    semver:module-version "1.0.0";
  }
  revision 2019-04-05 {
    description
      "Establish semantic version baseline.";
  }
  revision 2015-11-09 {
    description
      "IOS XR 6.0 revision.";
  }

  typedef ncs_template_Np {
    type string;
    description
      "np0:NP0, np1:NP1, np2:NP2, np3:NP3, np4:NP4, np5
       :NP5, np6:NP6, np7:NP7";
  }

  typedef ncs_rpc_notif_Np {
    type string {
      pattern '(np0)|(np1)|(np2)|(np3)|(np4)|(np5)|(np6)|(np7)';
    }
    description
      "np0:NP0, np1:NP1, np2:NP2, np3:NP3, np4:NP4, np5
       :NP5, np6:NP6, np7:NP7";
  }

  typedef live_ncs_Np {
    type string {
      pattern '(np0)|(np1)|(np2)|(np3)|(np4)|(np5)|(np6)|(np7)';
    }
    description
      "np0:NP0, np1:NP1, np2:NP2, np3:NP3, np4:NP4, np5
       :NP5, np6:NP6, np7:NP7";
  }

  typedef Np {
    type string {
      pattern '(np0)|(np1)|(np2)|(np3)|(np4)|(np5)|(np6)|(np7)';
    }
    description
      "np0:NP0, np1:NP1, np2:NP2, np3:NP3, np4:NP4, np5
       :NP5, np6:NP6, np7:NP7";
  }

  augment "/ncs:devices/ncs:device/ncs:config" {
    // NCS drop config false container 'hardware-module-np'
  }
  augment "/ncs:devices/ncs:device/ncs:live-status" {
    container hardware-module-np {
      tailf:ncs-device-type "netconf";
      tailf:display-when "not(../../ncs:module) or ../../ncs:module[ncs:name='Cisco-IOS-XR-asr9k-np-oper'] or (../../ncs:live-status-protocol[not(ncs:capability)]) or (../../ncs:live-status-protocol/ncs:capability/ncs:module[.='Cisco-IOS-XR-asr9k-np-oper'])";
      description
        "Hardware NP Counters";
      container nodes {
        description
          "Table of nodes";
        list node {
          key "node-name";
          description
            "Number";
          container nps {
            description
              "List of all NP";
            list np {
              key "np-name";
              description
                "np0 to np7";
              container np-uidb {
                description
                  "Hardware np uidb";
                uses live_ncs_PRM-NP-UIDB;
              }
              container tcam-region-summary {
                description
                  "Information of the TCAM region";
                uses live_ncs_TCAM-INFO-SHOW-SUM-REGION;
              }
              container chn-load {
                description
                  "prm channel load info";
                uses live_ncs_PRM-NP-CHN-LOAD;
              }
              container load-utilization {
                description
                  "Hardware np load or utilization";
                uses live_ncs_PRM-NP-LOAD;
              }
              container tcam-summary {
                description
                  "prm tcam summary info";
                uses live_ncs_TCAM-INFO-SHOW-SUM;
              }
              container l2rm-hw-resource {
                description
                  "L2rm Hardware Resources";
                uses live_ncs_PRM-NP-L2RM-HW-RSC;
              }
              container profile {
                description
                  "Hardware Profile";
                uses live_ncs_PRM-NP-PROFILE;
              }
              container counters {
                description
                  "prm counters info";
                uses live_ncs_PRM-NP-COUNTERS;
              }
              container indexed-counters {
                description
                  "PRM NP counters info by index";
                list indexed-counter {
                  key "counter-index";
                  description
                    "List of NP ucode Counters";
                  container ucode-counter {
                    description
                      "PRM indexed counter info";
                    uses live_ncs_PRM-NP-INDEXED-COUNTER;
                  }
                  leaf counter-index {
                    type uint32;
                    description
                      "Indexed Counter Key";
                  }
                }
              }
              container fast-drop {
                description
                  "prm fast drop counters info";
                uses live_ncs_PRM-NP-FAST-DROP;
              }
              container efd {
                description
                  "EFD COS to Priority Mapping";
                uses live_ncs_PRM-EFD;
              }
              leaf np-name {
                type live_ncs_Np;
                description
                  "NP name";
              }
            }
          }
          leaf node-name {
            type xr:live_ncs_Node-id;
            description
              "node number";
          }
        }
      }
    }
  }
  augment "/ncs:devices/ncs:template/ncs:ned-id/ncs:config" {
    // NCS drop config false container 'hardware-module-np'
  }
}

module Cisco-IOS-XR-hw-module-cfg {
  // Generated by yanger -t ncs
  tailf:mount-id "cisco-iosxr-nc-7.3:cisco-iosxr-nc-7.3";
  tailf:ncs-device-type "netconf";

  namespace "http://cisco.com/ns/yang/Cisco-IOS-XR-hw-module-cfg";
  prefix hw-module-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hw-module package configuration.

     This module contains definitions
     for the following management objects:
       hw-module: Hardware module information

     Copyright (c) 2013-2020 by Cisco Systems, Inc.
     All rights reserved.";

  revision 2020-05-27 {
    description
      "Addition of attention-led and auto-reset-disable leaves to eXR model.";
    semver:module-version "3.0.0";
  }
  revision 2019-10-15 {
    description
      "IOS XR 7.0.12 revision.";
    semver:module-version "2.0.0";
  }
  revision 2019-04-05 {
    description
      "Establish semantic version baseline.";
    semver:module-version "1.0.0";
  }
  revision 2015-11-09 {
    description
      "IOS XR 6.0 revision.";
  }

  typedef ncs_template_Admin-state {
    type string;
    description
      "Admin state";
  }

  typedef ncs_rpc_notif_Admin-state {
    type enumeration {
      enum "unshut" {
        value 0;
        description
          "Power On";
      }
      enum "shut" {
        value 1;
        description
          "Power Off";
      }
    }
    description
      "Admin state";
  }

  typedef live_ncs_Admin-state {
    type enumeration {
      enum "unshut" {
        value 0;
        description
          "Power On";
      }
      enum "shut" {
        value 1;
        description
          "Power Off";
      }
    }
    description
      "Admin state";
  }

  typedef Admin-state {
    type enumeration {
      enum "unshut" {
        value 0;
        description
          "Power On";
      }
      enum "shut" {
        value 1;
        description
          "Power Off";
      }
    }
    description
      "Admin state";
  }

  augment "/ncs:devices/ncs:device/ncs:config" {
    container hw-module {
      tailf:ncs-device-type "netconf";
      tailf:display-when "not(../../ncs:module) or ../../ncs:module[ncs:name='Cisco-IOS-XR-hw-module-cfg']";
      description
        "Hardware module information";
      container nodes {
        description
          "List of nodes";
        list node {
          key "location";
          description
            "Node object";
          container config {
            must 'attention-led or admin-state or auto-reset-disable' {
              tailf:xpath-root 3;
              error-message "Hw-module config containers cannot be empty";
              description
                "At least one configuration parameter must be set";
            }
            description
              "Configuration data for hw-module";
            leaf auto-reset-disable {
              type boolean;
              description
                "Do not automatically reset the hw-module on
                 failure";
            }
            leaf attention-led {
              type boolean;
              description
                "Enable hw-module attention LED (Blue)";
            }
            leaf admin-state {
              type Admin-state;
              description
                "Set the admin state of the hw-module";
            }
          }
          leaf location {
            type string;
            description
              "Location string";
          }
        }
      }
    }
  }
  augment "/ncs:devices/ncs:device/ncs:live-status" {
    container hw-module {
      tailf:ncs-device-type "netconf";
      tailf:display-when "not(../../ncs:module) or ../../ncs:module[ncs:name='Cisco-IOS-XR-hw-module-cfg'] or (../../ncs:live-status-protocol[not(ncs:capability)]) or (../../ncs:live-status-protocol/ncs:capability/ncs:module[.='Cisco-IOS-XR-hw-module-cfg'])";
      description
        "Hardware module information";
      container nodes {
        description
          "List of nodes";
        list node {
          key "location";
          description
            "Node object";
          container config {
            // NCS drop must statement
            description
              "Configuration data for hw-module";
            leaf auto-reset-disable {
              type boolean;
              description
                "Do not automatically reset the hw-module on
                 failure";
            }
            leaf attention-led {
              type boolean;
              description
                "Enable hw-module attention LED (Blue)";
            }
            leaf admin-state {
              type live_ncs_Admin-state;
              description
                "Set the admin state of the hw-module";
            }
          }
          leaf location {
            type string;
            description
              "Location string";
          }
        }
      }
    }
  }
  augment "/ncs:devices/ncs:template/ncs:ned-id/ncs:config" {
    container hw-module {
      description
        "Hardware module information";
      container nodes {
        description
          "List of nodes";
        list node {
          // NCS patched for predictable order
          ordered-by user;
          key "location";
          description
            "Node object";
          container config {
            // NCS drop must statement
            description
              "Configuration data for hw-module";
            leaf auto-reset-disable {
              type string;
              description
                "Do not automatically reset the hw-module on
                 failure";
            }
            leaf attention-led {
              type string;
              description
                "Enable hw-module attention LED (Blue)";
            }
            leaf admin-state {
              type ncs_template_Admin-state;
              description
                "Set the admin state of the hw-module";
            }
          }
          leaf location {
            type string;
            description
              "Location string";
          }
        }
      }
    }
  }
}

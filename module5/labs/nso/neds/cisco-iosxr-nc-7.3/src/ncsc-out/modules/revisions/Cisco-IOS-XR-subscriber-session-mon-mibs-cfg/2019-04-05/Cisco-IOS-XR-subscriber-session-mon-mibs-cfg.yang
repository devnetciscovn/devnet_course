module Cisco-IOS-XR-subscriber-session-mon-mibs-cfg {
  // Generated by yanger -t ncs
  tailf:mount-id "cisco-iosxr-nc-7.3:cisco-iosxr-nc-7.3";
  tailf:ncs-device-type "netconf";

  namespace "http://cisco.com/ns/yang/Cisco-IOS-XR-subscriber-session-mon-mibs-cfg";
  prefix subscriber-session-mon-mibs-cfg;

  import Cisco-IOS-XR-types {
    prefix xr;
  }
  import cisco-semver {
    prefix semver;
  }
  import Cisco-IOS-XR-snmp-agent-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-session-mon-mibs package configuration.

     This YANG module augments the
       Cisco-IOS-XR-snmp-agent-cfg
     module with configuration data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_NODE-TABLE {
    description
      "Common node of rising, falling, percent,
       evaluation";
    container nodes {
      description
        "Table of Node";
      list node {
        // NCS patched for predictable order
        ordered-by user;
        key "node-name";
        description
          "Rising node level";
        leaf session-count {
          type string;
          description
            "Session count";
        }
        leaf interval {
          type string;
          description
            "interval value in multiples of 10";
        }
        leaf node-name {
          type xr:ncs_template_Node-id;
          description
            "location";
        }
      }
    }
  }

  grouping ncs_template_ACCESS-INTERFACE-TABLE {
    description
      "Common node of rising, falling, percent,
       evaluation";
    container access-interfaces {
      description
        "Table of AccessInterface";
      list access-interface {
        // NCS patched for predictable order
        ordered-by user;
        key "interface-name";
        description
          "Access interface";
        leaf session-count {
          type string;
          description
            "Session count";
        }
        leaf interval {
          type string;
          description
            "Interval value in multiples of 10";
        }
        leaf interface-name {
          type xr:ncs_template_Interface-name;
          description
            "Interface name";
        }
      }
    }
  }

  grouping ncs_rpc_notif_NODE-TABLE {
    description
      "Common node of rising, falling, percent,
       evaluation";
    container nodes {
      description
        "Table of Node";
      list node {
        key "node-name";
        description
          "Rising node level";
        leaf session-count {
          type uint32 {
            range "1..4294967294";
          }
          description
            "Session count";
        }
        leaf interval {
          type uint32 {
            range "30..3600";
          }
          description
            "interval value in multiples of 10";
        }
        leaf node-name {
          type xr:ncs_rpc_notif_Node-id;
          description
            "location";
        }
      }
    }
  }

  grouping ncs_rpc_notif_ACCESS-INTERFACE-TABLE {
    description
      "Common node of rising, falling, percent,
       evaluation";
    container access-interfaces {
      description
        "Table of AccessInterface";
      list access-interface {
        key "interface-name";
        description
          "Access interface";
        leaf session-count {
          type uint32 {
            range "1..4294967294";
          }
          description
            "Session count";
        }
        leaf interval {
          type uint32 {
            range "30..3600";
          }
          description
            "Interval value in multiples of 10";
        }
        leaf interface-name {
          type xr:ncs_rpc_notif_Interface-name;
          description
            "Interface name";
        }
      }
    }
  }

  grouping live_ncs_NODE-TABLE {
    description
      "Common node of rising, falling, percent,
       evaluation";
    container nodes {
      description
        "Table of Node";
      list node {
        key "node-name";
        description
          "Rising node level";
        leaf session-count {
          type uint32 {
            range "1..4294967294";
          }
          description
            "Session count";
        }
        leaf interval {
          type uint32 {
            range "30..3600";
          }
          description
            "interval value in multiples of 10";
        }
        leaf node-name {
          type xr:live_ncs_Node-id;
          description
            "location";
        }
      }
    }
  }

  grouping live_ncs_ACCESS-INTERFACE-TABLE {
    description
      "Common node of rising, falling, percent,
       evaluation";
    container access-interfaces {
      description
        "Table of AccessInterface";
      list access-interface {
        key "interface-name";
        description
          "Access interface";
        leaf session-count {
          type uint32 {
            range "1..4294967294";
          }
          description
            "Session count";
        }
        leaf interval {
          type uint32 {
            range "30..3600";
          }
          description
            "Interval value in multiples of 10";
        }
        leaf interface-name {
          type xr:live_ncs_Interface-name;
          description
            "Interface name";
        }
      }
    }
  }

  grouping NODE-TABLE {
    description
      "Common node of rising, falling, percent,
       evaluation";
    container nodes {
      description
        "Table of Node";
      list node {
        key "node-name";
        description
          "Rising node level";
        leaf session-count {
          type uint32 {
            range "1..4294967294";
          }
          description
            "Session count";
        }
        leaf interval {
          type uint32 {
            range "30..3600";
          }
          description
            "interval value in multiples of 10";
        }
        leaf node-name {
          type xr:Node-id;
          description
            "location";
        }
      }
    }
  }

  grouping ACCESS-INTERFACE-TABLE {
    description
      "Common node of rising, falling, percent,
       evaluation";
    container access-interfaces {
      description
        "Table of AccessInterface";
      list access-interface {
        key "interface-name";
        description
          "Access interface";
        leaf session-count {
          type uint32 {
            range "1..4294967294";
          }
          description
            "Session count";
        }
        leaf interval {
          type uint32 {
            range "30..3600";
          }
          description
            "Interval value in multiples of 10";
        }
        leaf interface-name {
          type xr:Interface-name;
          description
            "Interface name";
        }
      }
    }
  }

  augment "/ncs:devices/ncs:template/ncs:ned-id/ncs:config/a1:mib" {
    description
      "This augment extends the configuration data of
       'Cisco-IOS-XR-snmp-agent-cfg'";
    container subscriber {
      description
        "Subscriber threshold commands";
      container threshold {
        description
          "Subscriber threshold commands";
        container delta {
          description
            "Delta loss keyword";
          container evaluation {
            description
              "Evaluation keyword";
            uses ncs_template_ACCESS-INTERFACE-TABLE;
            uses ncs_template_NODE-TABLE;
          }
          container percent {
            description
              "Delta loss percent";
            uses ncs_template_ACCESS-INTERFACE-TABLE;
            uses ncs_template_NODE-TABLE;
          }
        }
        container access-interface-sub {
          description
            "Access interface for regular expression";
          container subsets {
            description
              "Table of Subset";
            list subset {
              // NCS patched for predictable order
              ordered-by user;
              key "subset-id";
              description
                "Subset command";
              container regular-expression {
                description
                  "Regular expression";
                container notification {
                  description
                    "Notification keyword";
                  container rising-falling {
                    description
                      "Rising-falling threshold";
                    leaf disable {
                      type string;
                      description
                        "Disable the notifications on access
                         interfaces";
                    }
                  }
                }
              }
              leaf subset-id {
                type string;
                description
                  "Subset number";
              }
            }
          }
        }
        container falling {
          description
            "Falling threshold";
          uses ncs_template_ACCESS-INTERFACE-TABLE;
          uses ncs_template_NODE-TABLE;
        }
        container rising {
          description
            "Rising threshold";
          uses ncs_template_ACCESS-INTERFACE-TABLE;
          uses ncs_template_NODE-TABLE;
        }
      }
    }
  }
  augment "/ncs:devices/ncs:device/ncs:live-status/a1:mib" {
    description
      "This augment extends the configuration data of
       'Cisco-IOS-XR-snmp-agent-cfg'";
    container subscriber {
      tailf:ncs-device-type "netconf";
      tailf:display-when "not(../../../ncs:module) or ../../../ncs:module[ncs:name='Cisco-IOS-XR-subscriber-session-mon-mibs-cfg'] or (../../../ncs:live-status-protocol[not(ncs:capability)]) or (../../../ncs:live-status-protocol/ncs:capability/ncs:module[.='Cisco-IOS-XR-subscriber-session-mon-mibs-cfg'])";
      description
        "Subscriber threshold commands";
      container threshold {
        description
          "Subscriber threshold commands";
        container delta {
          description
            "Delta loss keyword";
          container evaluation {
            description
              "Evaluation keyword";
            uses live_ncs_ACCESS-INTERFACE-TABLE;
            uses live_ncs_NODE-TABLE;
          }
          container percent {
            description
              "Delta loss percent";
            uses live_ncs_ACCESS-INTERFACE-TABLE;
            uses live_ncs_NODE-TABLE;
          }
        }
        container access-interface-sub {
          description
            "Access interface for regular expression";
          container subsets {
            description
              "Table of Subset";
            list subset {
              key "subset-id";
              description
                "Subset command";
              container regular-expression {
                description
                  "Regular expression";
                container notification {
                  description
                    "Notification keyword";
                  container rising-falling {
                    description
                      "Rising-falling threshold";
                    leaf disable {
                      type string;
                      description
                        "Disable the notifications on access
                         interfaces";
                    }
                  }
                }
              }
              leaf subset-id {
                type uint32 {
                  range "1..255";
                }
                description
                  "Subset number";
              }
            }
          }
        }
        container falling {
          description
            "Falling threshold";
          uses live_ncs_ACCESS-INTERFACE-TABLE;
          uses live_ncs_NODE-TABLE;
        }
        container rising {
          description
            "Rising threshold";
          uses live_ncs_ACCESS-INTERFACE-TABLE;
          uses live_ncs_NODE-TABLE;
        }
      }
    }
  }
  augment "/ncs:devices/ncs:device/ncs:config/a1:mib" {
    description
      "This augment extends the configuration data of
       'Cisco-IOS-XR-snmp-agent-cfg'";
    container subscriber {
      tailf:ncs-device-type "netconf";
      tailf:display-when "not(../../../ncs:module) or ../../../ncs:module[ncs:name='Cisco-IOS-XR-subscriber-session-mon-mibs-cfg']";
      description
        "Subscriber threshold commands";
      container threshold {
        description
          "Subscriber threshold commands";
        container delta {
          description
            "Delta loss keyword";
          container evaluation {
            description
              "Evaluation keyword";
            uses ACCESS-INTERFACE-TABLE;
            uses NODE-TABLE;
          }
          container percent {
            description
              "Delta loss percent";
            uses ACCESS-INTERFACE-TABLE;
            uses NODE-TABLE;
          }
        }
        container access-interface-sub {
          description
            "Access interface for regular expression";
          container subsets {
            description
              "Table of Subset";
            list subset {
              key "subset-id";
              description
                "Subset command";
              container regular-expression {
                description
                  "Regular expression";
                container notification {
                  description
                    "Notification keyword";
                  container rising-falling {
                    description
                      "Rising-falling threshold";
                    leaf disable {
                      type string;
                      description
                        "Disable the notifications on access
                         interfaces";
                    }
                  }
                }
              }
              leaf subset-id {
                type uint32 {
                  range "1..255";
                }
                description
                  "Subset number";
              }
            }
          }
        }
        container falling {
          description
            "Falling threshold";
          uses ACCESS-INTERFACE-TABLE;
          uses NODE-TABLE;
        }
        container rising {
          description
            "Rising threshold";
          uses ACCESS-INTERFACE-TABLE;
          uses NODE-TABLE;
        }
      }
    }
  }
  augment "/ncs:devices/ncs:template/ncs:ned-id/ncs:config/a1:snmp/a1:notification" {
    description
      "This augment extends the configuration data of
       'Cisco-IOS-XR-snmp-agent-cfg'";
    container subscriber-mib {
      description
        "Subscriber notification commands";
      container session-aggregate {
        description
          "Session aggregation";
        leaf node {
          type empty;
          description
            "Subscriber notification at node level";
        }
        leaf access-interface {
          type empty;
          description
            "Subscriber notification at access interface
             level";
        }
      }
    }
  }
  augment "/ncs:devices/ncs:device/ncs:live-status/a1:snmp/a1:notification" {
    description
      "This augment extends the configuration data of
       'Cisco-IOS-XR-snmp-agent-cfg'";
    container subscriber-mib {
      tailf:ncs-device-type "netconf";
      tailf:display-when "not(../../../../ncs:module) or ../../../../ncs:module[ncs:name='Cisco-IOS-XR-subscriber-session-mon-mibs-cfg'] or (../../../../ncs:live-status-protocol[not(ncs:capability)]) or (../../../../ncs:live-status-protocol/ncs:capability/ncs:module[.='Cisco-IOS-XR-subscriber-session-mon-mibs-cfg'])";
      description
        "Subscriber notification commands";
      container session-aggregate {
        description
          "Session aggregation";
        leaf node {
          type empty;
          description
            "Subscriber notification at node level";
        }
        leaf access-interface {
          type empty;
          description
            "Subscriber notification at access interface
             level";
        }
      }
    }
  }
  augment "/ncs:devices/ncs:device/ncs:config/a1:snmp/a1:notification" {
    description
      "This augment extends the configuration data of
       'Cisco-IOS-XR-snmp-agent-cfg'";
    container subscriber-mib {
      tailf:ncs-device-type "netconf";
      tailf:display-when "not(../../../../ncs:module) or ../../../../ncs:module[ncs:name='Cisco-IOS-XR-subscriber-session-mon-mibs-cfg']";
      description
        "Subscriber notification commands";
      container session-aggregate {
        description
          "Session aggregation";
        leaf node {
          type empty;
          description
            "Subscriber notification at node level";
        }
        leaf access-interface {
          type empty;
          description
            "Subscriber notification at access interface
             level";
        }
      }
    }
  }
}

module Cisco-IOS-XR-qos-mibs-cfg {
  // Generated by yanger -t ncs
  tailf:mount-id "cisco-iosxr-nc-7.3:cisco-iosxr-nc-7.3";
  tailf:ncs-device-type "netconf";

  namespace "http://cisco.com/ns/yang/Cisco-IOS-XR-qos-mibs-cfg";
  prefix qos-mibs-cfg;

  import cisco-semver {
    prefix semver;
  }
  import Cisco-IOS-XR-snmp-agent-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR qos-mibs package configuration.

     This YANG module augments the
       Cisco-IOS-XR-snmp-agent-cfg
     module with configuration data.

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-11-09 {
    description
      "IOS XR 6.0 revision.";
  }

  augment "/ncs:devices/ncs:template/ncs:ned-id/ncs:config/a1:mib" {
    description
      "This augment extends the configuration data of
       'Cisco-IOS-XR-snmp-agent-cfg'";
    container cb-qosmib {
      description
        "CBQoSMIB configuration";
      container cache {
        description
          "CBQoSMIB statistics data caching";
        leaf enable {
          type empty;
          description
            "Enable CBQoSMIB statistics data caching";
        }
        leaf refresh-time {
          type string;
          units "second";
          description
            "Cache refresh time in seconds";
        }
        leaf service-policy-count {
          type string;
          description
            "Maximum number of service policies to cache
             the statistics for";
        }
      }
      leaf member-interface-stats {
        type empty;
        description
          "Enable bundle member interface statistics
           retrieval.";
      }
      leaf persist {
        type empty;
        description
          "Persist CBQoSMIB config, service-policy and
           object indices";
      }
    }
  }
  augment "/ncs:devices/ncs:device/ncs:live-status/a1:mib" {
    description
      "This augment extends the configuration data of
       'Cisco-IOS-XR-snmp-agent-cfg'";
    container cb-qosmib {
      tailf:ncs-device-type "netconf";
      tailf:display-when "not(../../../ncs:module) or ../../../ncs:module[ncs:name='Cisco-IOS-XR-qos-mibs-cfg'] or (../../../ncs:live-status-protocol[not(ncs:capability)]) or (../../../ncs:live-status-protocol/ncs:capability/ncs:module[.='Cisco-IOS-XR-qos-mibs-cfg'])";
      description
        "CBQoSMIB configuration";
      container cache {
        description
          "CBQoSMIB statistics data caching";
        leaf enable {
          type empty;
          description
            "Enable CBQoSMIB statistics data caching";
        }
        leaf refresh-time {
          type uint32 {
            range "5..60";
          }
          units "second";
          description
            "Cache refresh time in seconds";
        }
        leaf service-policy-count {
          type uint32 {
            range "1..5000";
          }
          description
            "Maximum number of service policies to cache
             the statistics for";
        }
      }
      leaf member-interface-stats {
        type empty;
        description
          "Enable bundle member interface statistics
           retrieval.";
      }
      leaf persist {
        type empty;
        description
          "Persist CBQoSMIB config, service-policy and
           object indices";
      }
    }
  }
  augment "/ncs:devices/ncs:device/ncs:config/a1:mib" {
    description
      "This augment extends the configuration data of
       'Cisco-IOS-XR-snmp-agent-cfg'";
    container cb-qosmib {
      tailf:ncs-device-type "netconf";
      tailf:display-when "not(../../../ncs:module) or ../../../ncs:module[ncs:name='Cisco-IOS-XR-qos-mibs-cfg']";
      description
        "CBQoSMIB configuration";
      container cache {
        description
          "CBQoSMIB statistics data caching";
        leaf enable {
          type empty;
          description
            "Enable CBQoSMIB statistics data caching";
        }
        leaf refresh-time {
          type uint32 {
            range "5..60";
          }
          units "second";
          description
            "Cache refresh time in seconds";
        }
        leaf service-policy-count {
          type uint32 {
            range "1..5000";
          }
          description
            "Maximum number of service policies to cache
             the statistics for";
        }
      }
      leaf member-interface-stats {
        type empty;
        description
          "Enable bundle member interface statistics
           retrieval.";
      }
      leaf persist {
        type empty;
        description
          "Persist CBQoSMIB config, service-policy and
           object indices";
      }
    }
  }
}

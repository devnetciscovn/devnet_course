module Cisco-IOS-XR-invmgr-diag-oper {
  // Generated by yanger -t ncs
  tailf:mount-id "cisco-iosxr-nc-7.3:cisco-iosxr-nc-7.3";
  tailf:ncs-device-type "netconf";

  namespace "http://cisco.com/ns/yang/Cisco-IOS-XR-invmgr-diag-oper";
  prefix invmgr-diag-oper;

  import Cisco-IOS-XR-types {
    prefix xr;
  }
  import cisco-semver {
    prefix semver;
  }
  include Cisco-IOS-XR-invmgr-diag-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR invmgr-diag package operational data.

     This module contains definitions
     for the following management objects:
       diag: Diag information

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_INSTANCE-TABLE {
    description
      "Common node of slot, fan-tray, power-shelf";
    container instances {
      description
        "Table of instances";
      list instance {
        // NCS patched for predictable order
        ordered-by user;
        key "name";
        description
          "instance number";
        leaf name {
          type xr:ncs_template_Cisco-ios-xr-string;
          description
            "Instance name";
        }
        uses ncs_template_DETAIL;
      }
    }
  }

  grouping ncs_template_DETAIL {
    description
      "Common node of instance, chassis";
    container detail {
      description
        "Detail information";
      uses ncs_template_INVMGR-DIAG-DETAIL-FORMAT;
    }
  }

  grouping ncs_rpc_notif_INSTANCE-TABLE {
    description
      "Common node of slot, fan-tray, power-shelf";
    container instances {
      description
        "Table of instances";
      list instance {
        key "name";
        description
          "instance number";
        leaf name {
          type xr:ncs_rpc_notif_Cisco-ios-xr-string;
          description
            "Instance name";
        }
        uses ncs_rpc_notif_DETAIL;
      }
    }
  }

  grouping ncs_rpc_notif_DETAIL {
    description
      "Common node of instance, chassis";
    container detail {
      description
        "Detail information";
      uses ncs_rpc_notif_INVMGR-DIAG-DETAIL-FORMAT;
    }
  }

  grouping live_ncs_INSTANCE-TABLE {
    description
      "Common node of slot, fan-tray, power-shelf";
    container instances {
      description
        "Table of instances";
      list instance {
        key "name";
        description
          "instance number";
        leaf name {
          type xr:live_ncs_Cisco-ios-xr-string;
          description
            "Instance name";
        }
        uses live_ncs_DETAIL;
      }
    }
  }

  grouping live_ncs_DETAIL {
    description
      "Common node of instance, chassis";
    container detail {
      description
        "Detail information";
      uses live_ncs_INVMGR-DIAG-DETAIL-FORMAT;
    }
  }

  grouping INSTANCE-TABLE {
    description
      "Common node of slot, fan-tray, power-shelf";
    container instances {
      description
        "Table of instances";
      list instance {
        key "name";
        description
          "instance number";
        leaf name {
          type xr:Cisco-ios-xr-string;
          description
            "Instance name";
        }
        uses DETAIL;
      }
    }
  }

  grouping DETAIL {
    description
      "Common node of instance, chassis";
    container detail {
      description
        "Detail information";
      uses INVMGR-DIAG-DETAIL-FORMAT;
    }
  }

  augment "/ncs:devices/ncs:device/ncs:config" {
    // NCS drop config false container diag
  }
  augment "/ncs:devices/ncs:device/ncs:live-status" {
    container diag {
      tailf:ncs-device-type "netconf";
      tailf:display-when "not(../../ncs:module) or ../../ncs:module[ncs:name='Cisco-IOS-XR-invmgr-diag-oper'] or (../../ncs:live-status-protocol[not(ncs:capability)]) or (../../ncs:live-status-protocol/ncs:capability/ncs:module[.='Cisco-IOS-XR-invmgr-diag-oper'])";
      description
        "Diag information";
      container racks {
        description
          "Table of racks";
        list rack {
          key "rack-name";
          description
            "Rack name";
          container power-shelfs {
            description
              "Table for rack power shelf ";
            list power-shelf {
              key "power-shelf-name";
              description
                "Power shelf name";
              leaf power-shelf-name {
                type xr:live_ncs_Cisco-ios-xr-string;
                description
                  "Power Shelf name";
              }
              uses live_ncs_INSTANCE-TABLE;
            }
          }
          container fan-trays {
            description
              "Table for rack fan trays";
            list fan-tray {
              key "fan-tray-name";
              description
                "Fan tray name";
              leaf fan-tray-name {
                type xr:live_ncs_Cisco-ios-xr-string;
                description
                  "Fan tray name";
              }
              uses live_ncs_INSTANCE-TABLE;
            }
          }
          container slots {
            description
              "Table of slots";
            list slot {
              key "slot-name";
              description
                "Slot name";
              leaf slot-name {
                type xr:live_ncs_Cisco-ios-xr-string;
                description
                  "Slot name";
              }
              uses live_ncs_INSTANCE-TABLE;
            }
          }
          container chassis {
            description
              "Chassis information";
            uses live_ncs_DETAIL;
          }
          leaf rack-name {
            type xr:live_ncs_Cisco-ios-xr-string;
            description
              "Rack name";
          }
        }
      }
    }
  }
  augment "/ncs:devices/ncs:template/ncs:ned-id/ncs:config" {
    // NCS drop config false container diag
  }
}

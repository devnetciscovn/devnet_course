submodule Cisco-IOS-XR-clns-isis-oper-sub2 {
  // Generated by yanger -t ncs
  tailf:mount-id "cisco-iosxr-nc-7.3:cisco-iosxr-nc-7.3";

  belongs-to Cisco-IOS-XR-clns-isis-oper {
    prefix Cisco-IOS-XR-clns-isis-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR clns-isis package operational data.

     Copyright (c) 2013-2021 by Cisco Systems, Inc.
     All rights reserved.";

  revision 2021-03-13 {
    description
      "Interface bandwidth changed from uint32_t to uint64_t
       2021-01-04
         Add private adjacency bag";
    semver:module-version "4.1.0";
  }
  revision 2020-11-05 {
    description
      "Flex-algo extension for show isis topology.
       2020-10-20
       Change in Yang tool corrected strings repair-s-rv6* to repair-srv6*, end-xsid* to end-x-sid*, and is-s-rv6 to is-srv6. Changed avg-dela-rawy to avg-delay-raw to fix misspelling via CSCvu63930. Changed SRv6 function-type to sid-behavior, uint32_t to mgmt_srv6_sid_fmt, and num-sid to num-sids for consistency and to comply with current IETF ISIS SRv6 draft via CSCvu06764.";
    semver:module-version "4.0.0";
  }
  revision 2020-05-12 {
    description
      "Added SRLG and SRLG Static
       2020-03-25
       Added operational data for new features.";
    semver:module-version "3.0.0";
  }
  revision 2019-09-25 {
    description
      "Added operational data for new features
       2019-05-14
       Conditional Advertise-prefix support
       2019-05-03
       move ocni-isis opencfg model from native model to private oper model";
    semver:module-version "2.0.0";
  }
  revision 2019-04-05 {
    description
      "Establish semantic version baseline.";
    semver:module-version "1.0.0";
  }
  revision 2019-03-28 {
    description
      "Upgrade ocni-isis to opencfg model version 0.4.2";
  }
  revision 2019-02-23 {
    description
      "Added is_srv6 flag to ISIS IPv6 route";
  }
  revision 2019-02-16 {
    description
      "Added interface link-group name";
  }
  revision 2018-10-15 {
    description
      "Add SRv6 configured locators";
  }
  revision 2018-10-04 {
    description
      "Update SRv6 locator table";
  }
  revision 2018-05-17 {
    description
      "Update opencfg isis model";
  }
  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  typedef ncs_template_Srms-mi-flag-e-b {
    type string;
    description
      "Srms mi flag e b";
  }

  typedef ncs_template_In6-addr-t-b {
    type string;
    description
      "In6 addr t b";
  }

  typedef ncs_template_Srms-mi-af-e-b {
    type string;
    description
      "Srms mi af e b";
  }

  typedef ncs_template_Srms-mi-src-e-b {
    type string;
    description
      "Srms mi src e b";
  }

  typedef ncs_rpc_notif_Srms-mi-flag-e-b {
    type enumeration {
      enum "false" {
        value 0;
        description
          "False";
      }
      enum "true" {
        value 1;
        description
          "True";
      }
    }
    description
      "Srms mi flag e b";
  }

  typedef ncs_rpc_notif_In6-addr-t-b {
    type inet:ipv6-address;
    description
      "In6 addr t b";
  }

  typedef ncs_rpc_notif_Srms-mi-af-e-b {
    type enumeration {
      enum "none" {
        value 0;
        description
          "None";
      }
      enum "ipv4" {
        value 1;
        description
          "IPv4";
      }
      enum "ipv6" {
        value 2;
        description
          "IPv6";
      }
    }
    description
      "Srms mi af e b";
  }

  typedef ncs_rpc_notif_Srms-mi-src-e-b {
    type enumeration {
      enum "none" {
        value 0;
        description
          "None";
      }
      enum "local" {
        value 1;
        description
          "Local";
      }
      enum "remote" {
        value 2;
        description
          "Remote";
      }
    }
    description
      "Srms mi src e b";
  }

  typedef live_ncs_Srms-mi-flag-e-b {
    type enumeration {
      enum "false" {
        value 0;
        description
          "False";
      }
      enum "true" {
        value 1;
        description
          "True";
      }
    }
    description
      "Srms mi flag e b";
  }

  typedef live_ncs_In6-addr-t-b {
    type inet:ipv6-address;
    description
      "In6 addr t b";
  }

  typedef live_ncs_Srms-mi-af-e-b {
    type enumeration {
      enum "none" {
        value 0;
        description
          "None";
      }
      enum "ipv4" {
        value 1;
        description
          "IPv4";
      }
      enum "ipv6" {
        value 2;
        description
          "IPv6";
      }
    }
    description
      "Srms mi af e b";
  }

  typedef live_ncs_Srms-mi-src-e-b {
    type enumeration {
      enum "none" {
        value 0;
        description
          "None";
      }
      enum "local" {
        value 1;
        description
          "Local";
      }
      enum "remote" {
        value 2;
        description
          "Remote";
      }
    }
    description
      "Srms mi src e b";
  }

  typedef Srms-mi-flag-e-b {
    type enumeration {
      enum "false" {
        value 0;
        description
          "False";
      }
      enum "true" {
        value 1;
        description
          "True";
      }
    }
    description
      "Srms mi flag e b";
  }

  typedef In6-addr-t-b {
    type inet:ipv6-address;
    description
      "In6 addr t b";
  }

  typedef Srms-mi-af-e-b {
    type enumeration {
      enum "none" {
        value 0;
        description
          "None";
      }
      enum "ipv4" {
        value 1;
        description
          "IPv4";
      }
      enum "ipv6" {
        value 2;
        description
          "IPv6";
      }
    }
    description
      "Srms mi af e b";
  }

  typedef Srms-mi-src-e-b {
    type enumeration {
      enum "none" {
        value 0;
        description
          "None";
      }
      enum "local" {
        value 1;
        description
          "Local";
      }
      enum "remote" {
        value 2;
        description
          "Remote";
      }
    }
    description
      "Srms mi src e b";
  }

  grouping ncs_template_ADDR {
    description
      "ADDR";
    leaf af {
      type ncs_template_Srms-mi-af-e-b;
      description
        "AF";
    }
    leaf ipv4 {
      // NCS drop when statement
      type string;
      description
        "IPv4";
    }
    leaf ipv6 {
      // NCS drop when statement
      type ncs_template_In6-addr-t-b;
      description
        "IPv6";
    }
  }

  grouping ncs_template_SRMS-MI-T-B {
    description
      "SRMS show bag";
    container addr {
      description
        "Ipv4 address";
      uses ncs_template_ADDR;
    }
    leaf src {
      type ncs_template_Srms-mi-src-e-b;
      description
        "Source of this prefix, whether local or remote";
    }
    leaf router {
      type string;
      description
        "Router ID";
    }
    leaf area {
      type string;
      description
        "Area (OSPF) or Level (ISIS)";
    }
    leaf prefixlen {
      type string;
      description
        "Prefix length";
    }
    leaf sid-start {
      type string;
      description
        "Starting SID";
    }
    leaf sid-count {
      type string;
      description
        "SID range";
    }
    leaf last-prefix {
      type string;
      description
        "Last IP Prefix";
    }
    leaf last-sid-index {
      type string;
      description
        "Last SID Index";
    }
    leaf flag-attached {
      type ncs_template_Srms-mi-flag-e-b;
      description
        "Attached flag";
    }
  }

  grouping ncs_rpc_notif_ADDR {
    description
      "ADDR";
    leaf af {
      type ncs_rpc_notif_Srms-mi-af-e-b;
      description
        "AF";
    }
    leaf ipv4 {
      when "../af = 'ipv4'" {
        tailf:xpath-root 3;
        description
          "../AF = 'IPv4'";
      }
      type inet:ipv4-address;
      description
        "IPv4";
    }
    leaf ipv6 {
      when "../af = 'ipv6'" {
        tailf:xpath-root 3;
        description
          "../AF = 'IPv6'";
      }
      type ncs_rpc_notif_In6-addr-t-b;
      description
        "IPv6";
    }
  }

  grouping ncs_rpc_notif_SRMS-MI-T-B {
    description
      "SRMS show bag";
    container addr {
      description
        "Ipv4 address";
      uses ncs_rpc_notif_ADDR;
    }
    leaf src {
      type ncs_rpc_notif_Srms-mi-src-e-b;
      description
        "Source of this prefix, whether local or remote";
    }
    leaf router {
      type string {
        length "0..30";
      }
      description
        "Router ID";
    }
    leaf area {
      type string {
        length "0..30";
      }
      description
        "Area (OSPF) or Level (ISIS)";
    }
    leaf prefixlen {
      type uint8;
      description
        "Prefix length";
    }
    leaf sid-start {
      type uint32;
      description
        "Starting SID";
    }
    leaf sid-count {
      type uint32;
      description
        "SID range";
    }
    leaf last-prefix {
      type string {
        length "0..50";
      }
      description
        "Last IP Prefix";
    }
    leaf last-sid-index {
      type uint32;
      description
        "Last SID Index";
    }
    leaf flag-attached {
      type ncs_rpc_notif_Srms-mi-flag-e-b;
      description
        "Attached flag";
    }
  }

  grouping live_ncs_ADDR {
    description
      "ADDR";
    leaf af {
      type live_ncs_Srms-mi-af-e-b;
      description
        "AF";
    }
    leaf ipv4 {
      // NCS drop when statement
      type inet:ipv4-address;
      description
        "IPv4";
    }
    leaf ipv6 {
      // NCS drop when statement
      type live_ncs_In6-addr-t-b;
      description
        "IPv6";
    }
  }

  grouping live_ncs_SRMS-MI-T-B {
    description
      "SRMS show bag";
    container addr {
      description
        "Ipv4 address";
      uses live_ncs_ADDR;
    }
    leaf src {
      type live_ncs_Srms-mi-src-e-b;
      description
        "Source of this prefix, whether local or remote";
    }
    leaf router {
      type string {
        length "0..30";
      }
      description
        "Router ID";
    }
    leaf area {
      type string {
        length "0..30";
      }
      description
        "Area (OSPF) or Level (ISIS)";
    }
    leaf prefixlen {
      type uint8;
      description
        "Prefix length";
    }
    leaf sid-start {
      type uint32;
      description
        "Starting SID";
    }
    leaf sid-count {
      type uint32;
      description
        "SID range";
    }
    leaf last-prefix {
      type string {
        length "0..50";
      }
      description
        "Last IP Prefix";
    }
    leaf last-sid-index {
      type uint32;
      description
        "Last SID Index";
    }
    leaf flag-attached {
      type live_ncs_Srms-mi-flag-e-b;
      description
        "Attached flag";
    }
  }

  grouping ADDR {
    description
      "ADDR";
    leaf af {
      type Srms-mi-af-e-b;
      description
        "AF";
    }
    leaf ipv4 {
      when "../af = 'ipv4'" {
        tailf:xpath-root 3;
        description
          "../AF = 'IPv4'";
      }
      type inet:ipv4-address;
      description
        "IPv4";
    }
    leaf ipv6 {
      when "../af = 'ipv6'" {
        tailf:xpath-root 3;
        description
          "../AF = 'IPv6'";
      }
      type In6-addr-t-b;
      description
        "IPv6";
    }
  }

  grouping SRMS-MI-T-B {
    description
      "SRMS show bag";
    container addr {
      description
        "Ipv4 address";
      uses ADDR;
    }
    leaf src {
      type Srms-mi-src-e-b;
      description
        "Source of this prefix, whether local or remote";
    }
    leaf router {
      type string {
        length "0..30";
      }
      description
        "Router ID";
    }
    leaf area {
      type string {
        length "0..30";
      }
      description
        "Area (OSPF) or Level (ISIS)";
    }
    leaf prefixlen {
      type uint8;
      description
        "Prefix length";
    }
    leaf sid-start {
      type uint32;
      description
        "Starting SID";
    }
    leaf sid-count {
      type uint32;
      description
        "SID range";
    }
    leaf last-prefix {
      type string {
        length "0..50";
      }
      description
        "Last IP Prefix";
    }
    leaf last-sid-index {
      type uint32;
      description
        "Last SID Index";
    }
    leaf flag-attached {
      type Srms-mi-flag-e-b;
      description
        "Attached flag";
    }
  }
}

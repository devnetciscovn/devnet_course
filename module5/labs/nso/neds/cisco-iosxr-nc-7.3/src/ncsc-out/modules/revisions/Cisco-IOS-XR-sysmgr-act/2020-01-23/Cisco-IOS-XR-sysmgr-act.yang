module Cisco-IOS-XR-sysmgr-act {
  // Generated by yanger -t ncs
  tailf:mount-id "cisco-iosxr-nc-7.3:cisco-iosxr-nc-7.3";
  tailf:ncs-device-type "netconf";

  namespace "http://cisco.com/ns/yang/Cisco-IOS-XR-sysmgr-act";
  prefix sysmgr-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sysmgr action package configuration.

     Copyright (c) 2016-2020 by Cisco Systems, Inc.
     All rights reserved.";

  revision 2020-01-23 {
    description
      "Added support for process crash from XR.";
    semver:module-version "1.1.0";
  }
  revision 2019-10-01 {
    description
      "Made changes to be RFC6087 compliant";
    semver:module-version "1.0.1";
  }
  revision 2019-04-05 {
    description
      "Establish semantic version baseline.";
    semver:module-version "1.0.0";
  }
  revision 2017-03-03 {
    description
      "IOS XR 6.3.1 revision.";
  }

  augment "/ncs:devices/ncs:device/ncs:rpc" {
    container rpc-sysmgr-process-shutdown {
      tailf:ncs-device-type "netconf";
      tailf:display-when "not(../../ncs:module) or ../../ncs:module[ncs:name='Cisco-IOS-XR-sysmgr-act']";
      tailf:action sysmgr-process-shutdown {
        tailf:actionpoint ncsproxy {
          tailf:internal;
        }
        description
          "Shutdown an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device-group/ncs:ned-id/ncs:rpc" {
    container rpc-sysmgr-process-shutdown {
      tailf:ncs-device-type "netconf";
      tailf:display-when "/ncs:devices/ncs:device[ncs:name=current()/../../../ncs:member]/ncs:module[ncs:name='Cisco-IOS-XR-sysmgr-act']";
      tailf:action sysmgr-process-shutdown {
        tailf:actionpoint ncsproxy {
          tailf:internal;
        }
        description
          "Shutdown an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device/ncs:rpc" {
    container rpc-sysmgr-process-crash {
      tailf:ncs-device-type "netconf";
      tailf:display-when "not(../../ncs:module) or ../../ncs:module[ncs:name='Cisco-IOS-XR-sysmgr-act']";
      tailf:action sysmgr-process-crash {
        tailf:actionpoint ncsproxy {
          tailf:internal;
        }
        description
          "Crash an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device-group/ncs:ned-id/ncs:rpc" {
    container rpc-sysmgr-process-crash {
      tailf:ncs-device-type "netconf";
      tailf:display-when "/ncs:devices/ncs:device[ncs:name=current()/../../../ncs:member]/ncs:module[ncs:name='Cisco-IOS-XR-sysmgr-act']";
      tailf:action sysmgr-process-crash {
        tailf:actionpoint ncsproxy {
          tailf:internal;
        }
        description
          "Crash an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device/ncs:rpc" {
    container rpc-sysmgr-process-start {
      tailf:ncs-device-type "netconf";
      tailf:display-when "not(../../ncs:module) or ../../ncs:module[ncs:name='Cisco-IOS-XR-sysmgr-act']";
      tailf:action sysmgr-process-start {
        tailf:actionpoint ncsproxy {
          tailf:internal;
        }
        description
          "Start an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device-group/ncs:ned-id/ncs:rpc" {
    container rpc-sysmgr-process-start {
      tailf:ncs-device-type "netconf";
      tailf:display-when "/ncs:devices/ncs:device[ncs:name=current()/../../../ncs:member]/ncs:module[ncs:name='Cisco-IOS-XR-sysmgr-act']";
      tailf:action sysmgr-process-start {
        tailf:actionpoint ncsproxy {
          tailf:internal;
        }
        description
          "Start an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device/ncs:rpc" {
    container rpc-sysmgr-process-restart {
      tailf:ncs-device-type "netconf";
      tailf:display-when "not(../../ncs:module) or ../../ncs:module[ncs:name='Cisco-IOS-XR-sysmgr-act']";
      tailf:action sysmgr-process-restart {
        tailf:actionpoint ncsproxy {
          tailf:internal;
        }
        description
          "Restart an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
  augment "/ncs:devices/ncs:device-group/ncs:ned-id/ncs:rpc" {
    container rpc-sysmgr-process-restart {
      tailf:ncs-device-type "netconf";
      tailf:display-when "/ncs:devices/ncs:device[ncs:name=current()/../../../ncs:member]/ncs:module[ncs:name='Cisco-IOS-XR-sysmgr-act']";
      tailf:action sysmgr-process-restart {
        tailf:actionpoint ncsproxy {
          tailf:internal;
        }
        description
          "Restart an XR process";
        input {
          leaf process-name {
            type string;
            mandatory true;
            description
              "XR process name or Job Id e.g. bgp, ospf";
          }
          leaf location {
            type string;
            description
              "XR node identifier e.g. 0/RP0/CPU0, 0/0/CPU0";
          }
        }
      }
    }
  }
}

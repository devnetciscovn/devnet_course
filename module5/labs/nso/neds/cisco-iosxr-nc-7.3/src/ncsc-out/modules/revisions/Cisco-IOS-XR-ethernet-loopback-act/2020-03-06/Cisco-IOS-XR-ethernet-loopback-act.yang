module Cisco-IOS-XR-ethernet-loopback-act {
  // Generated by yanger -t ncs
  tailf:mount-id "cisco-iosxr-nc-7.3:cisco-iosxr-nc-7.3";
  tailf:ncs-device-type "netconf";

  namespace "http://cisco.com/ns/yang/Cisco-IOS-XR-ethernet-loopback-act";
  prefix ethernet-loopback-act;

  import ietf-yang-types {
    prefix yang;
  }
  import Cisco-IOS-XR-types {
    prefix xr;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet loopback actions.

     Copyright (c) 2020 by Cisco Systems, Inc.
     All rights reserved.";

  revision 2020-03-06 {
    description
      "IOS XR 7.4.1 revision.";
  }

  typedef ncs_template_loopback-direction {
    type string;
    description
      "Direction of loopback";
  }

  typedef ncs_template_loopback-status {
    type string;
    description
      "Status of loopback session";
  }

  typedef ncs_template_vlan-type {
    type string;
    description
      "Type of the outer VLAN ID";
  }

  typedef ncs_rpc_notif_loopback-direction {
    type enumeration {
      enum "external" {
        description
          "External loopback (wire loopback)";
      }
      enum "internal" {
        description
          "Internal loopback (bridge loopback)";
      }
    }
    description
      "Direction of loopback";
  }

  typedef ncs_rpc_notif_loopback-status {
    type enumeration {
      enum "inactive" {
        description
          "Loopback is not active";
      }
      enum "active" {
        description
          "Loopback is active";
      }
    }
    description
      "Status of loopback session";
  }

  typedef ncs_rpc_notif_vlan-type {
    type enumeration {
      enum "dot1q" {
        description
          "Dot1q outer VLAN type";
      }
      enum "dot1ad" {
        description
          "Dot1ad outer VLAN type";
      }
    }
    description
      "Type of the outer VLAN ID";
  }

  typedef live_ncs_loopback-direction {
    type enumeration {
      enum "external" {
        description
          "External loopback (wire loopback)";
      }
      enum "internal" {
        description
          "Internal loopback (bridge loopback)";
      }
    }
    description
      "Direction of loopback";
  }

  typedef live_ncs_loopback-status {
    type enumeration {
      enum "inactive" {
        description
          "Loopback is not active";
      }
      enum "active" {
        description
          "Loopback is active";
      }
    }
    description
      "Status of loopback session";
  }

  typedef live_ncs_vlan-type {
    type enumeration {
      enum "dot1q" {
        description
          "Dot1q outer VLAN type";
      }
      enum "dot1ad" {
        description
          "Dot1ad outer VLAN type";
      }
    }
    description
      "Type of the outer VLAN ID";
  }

  typedef loopback-direction {
    type enumeration {
      enum "external" {
        description
          "External loopback (wire loopback)";
      }
      enum "internal" {
        description
          "Internal loopback (bridge loopback)";
      }
    }
    description
      "Direction of loopback";
  }

  typedef loopback-status {
    type enumeration {
      enum "inactive" {
        description
          "Loopback is not active";
      }
      enum "active" {
        description
          "Loopback is active";
      }
    }
    description
      "Status of loopback session";
  }

  typedef vlan-type {
    type enumeration {
      enum "dot1q" {
        description
          "Dot1q outer VLAN type";
      }
      enum "dot1ad" {
        description
          "Dot1ad outer VLAN type";
      }
    }
    description
      "Type of the outer VLAN ID";
  }

  grouping ncs_template_EDPL-REMOTE-VLAN-TYPE {
    description
      "Encapsulation specification for remote loopback commands";
    leaf outer-type {
      type ncs_template_vlan-type;
      description
        "Type of outer VLAN ID";
    }
    leaf outer-vlan-ids {
      type string;
      description
        "Outer VLAN ID";
    }
    leaf inner-vlan-ids {
      type string;
      description
        "Inner VLAN ID";
    }
    leaf all-vlans {
      type string;
      description
        "Include the all-vlans flag in the remote request";
    }
  }

  grouping ncs_template_EDPL-CFM-INFO-TYPE {
    description
      "CFM domain and service specification";
    leaf domain {
      type string;
      // NCS drop mandatory statement
      description
        "CFM domain name";
    }
    leaf service {
      type string;
      // NCS drop mandatory statement
      description
        "CFM service name";
    }
  }

  grouping ncs_template_EDPL-REMOTE-TARGET-TYPE {
    description
      "Information on remote session target";
    leaf mac {
      type string;
      description
        "Target remote mac address";
    }
    leaf mep {
      type string;
      description
        "ID of target remote MEP";
    }
  }

  grouping ncs_template_EDPL-REMOTE-SESSION-LIST-TYPE {
    description
      "List of remote sessions";
    list session {
      // NCS patched for predictable order
      ordered-by user;
      description
        "List of remote sessions";
      leaf mac {
        type string;
        description
          "Remote mac address";
      }
      leaf direction {
        type ncs_template_loopback-direction;
        description
          "Loopback session direction";
      }
      leaf timer {
        type string;
        description
          "Remaining session time, in seconds";
      }
      leaf status {
        type ncs_template_loopback-status;
        description
          "Loopback session status";
      }
    }
  }

  grouping ncs_rpc_notif_EDPL-REMOTE-VLAN-TYPE {
    description
      "Encapsulation specification for remote loopback commands";
    leaf outer-type {
      type ncs_rpc_notif_vlan-type;
      description
        "Type of outer VLAN ID";
    }
    leaf outer-vlan-ids {
      type string;
      description
        "Outer VLAN ID";
    }
    leaf inner-vlan-ids {
      type string;
      description
        "Inner VLAN ID";
    }
    leaf all-vlans {
      type boolean;
      description
        "Include the all-vlans flag in the remote request";
    }
  }

  grouping ncs_rpc_notif_EDPL-CFM-INFO-TYPE {
    description
      "CFM domain and service specification";
    leaf domain {
      type string;
      mandatory true;
      description
        "CFM domain name";
    }
    leaf service {
      type string;
      mandatory true;
      description
        "CFM service name";
    }
  }

  grouping ncs_rpc_notif_EDPL-REMOTE-TARGET-TYPE {
    description
      "Information on remote session target";
    leaf mac {
      type yang:mac-address;
      description
        "Target remote mac address";
    }
    leaf mep {
      type uint16;
      description
        "ID of target remote MEP";
    }
  }

  grouping ncs_rpc_notif_EDPL-REMOTE-SESSION-LIST-TYPE {
    description
      "List of remote sessions";
    list session {
      description
        "List of remote sessions";
      leaf mac {
        type yang:mac-address;
        description
          "Remote mac address";
      }
      leaf direction {
        type ncs_rpc_notif_loopback-direction;
        description
          "Loopback session direction";
      }
      leaf timer {
        type uint32;
        description
          "Remaining session time, in seconds";
      }
      leaf status {
        type ncs_rpc_notif_loopback-status;
        description
          "Loopback session status";
      }
    }
  }

  grouping live_ncs_EDPL-REMOTE-VLAN-TYPE {
    description
      "Encapsulation specification for remote loopback commands";
    leaf outer-type {
      type live_ncs_vlan-type;
      description
        "Type of outer VLAN ID";
    }
    leaf outer-vlan-ids {
      type string;
      description
        "Outer VLAN ID";
    }
    leaf inner-vlan-ids {
      type string;
      description
        "Inner VLAN ID";
    }
    leaf all-vlans {
      type boolean;
      description
        "Include the all-vlans flag in the remote request";
    }
  }

  grouping live_ncs_EDPL-CFM-INFO-TYPE {
    description
      "CFM domain and service specification";
    leaf domain {
      type string;
      // NCS drop mandatory statement
      description
        "CFM domain name";
    }
    leaf service {
      type string;
      // NCS drop mandatory statement
      description
        "CFM service name";
    }
  }

  grouping live_ncs_EDPL-REMOTE-TARGET-TYPE {
    description
      "Information on remote session target";
    leaf mac {
      type yang:mac-address;
      description
        "Target remote mac address";
    }
    leaf mep {
      type uint16;
      description
        "ID of target remote MEP";
    }
  }

  grouping live_ncs_EDPL-REMOTE-SESSION-LIST-TYPE {
    description
      "List of remote sessions";
    list session {
      description
        "List of remote sessions";
      leaf mac {
        type yang:mac-address;
        description
          "Remote mac address";
      }
      leaf direction {
        type live_ncs_loopback-direction;
        description
          "Loopback session direction";
      }
      leaf timer {
        type uint32;
        description
          "Remaining session time, in seconds";
      }
      leaf status {
        type live_ncs_loopback-status;
        description
          "Loopback session status";
      }
    }
  }

  grouping EDPL-REMOTE-VLAN-TYPE {
    description
      "Encapsulation specification for remote loopback commands";
    leaf outer-type {
      type vlan-type;
      description
        "Type of outer VLAN ID";
    }
    leaf outer-vlan-ids {
      type string;
      description
        "Outer VLAN ID";
    }
    leaf inner-vlan-ids {
      type string;
      description
        "Inner VLAN ID";
    }
    leaf all-vlans {
      type boolean;
      description
        "Include the all-vlans flag in the remote request";
    }
  }

  grouping EDPL-CFM-INFO-TYPE {
    description
      "CFM domain and service specification";
    leaf domain {
      type string;
      mandatory true;
      description
        "CFM domain name";
    }
    leaf service {
      type string;
      mandatory true;
      description
        "CFM service name";
    }
  }

  grouping EDPL-REMOTE-TARGET-TYPE {
    description
      "Information on remote session target";
    leaf mac {
      type yang:mac-address;
      description
        "Target remote mac address";
    }
    leaf mep {
      type uint16;
      description
        "ID of target remote MEP";
    }
  }

  grouping EDPL-REMOTE-SESSION-LIST-TYPE {
    description
      "List of remote sessions";
    list session {
      description
        "List of remote sessions";
      leaf mac {
        type yang:mac-address;
        description
          "Remote mac address";
      }
      leaf direction {
        type loopback-direction;
        description
          "Loopback session direction";
      }
      leaf timer {
        type uint32;
        description
          "Remaining session time, in seconds";
      }
      leaf status {
        type loopback-status;
        description
          "Loopback session status";
      }
    }
  }

  augment "/ncs:devices/ncs:device/ncs:rpc" {
    container rpc-ethernet-loopback-discover-remote {
      tailf:ncs-device-type "netconf";
      tailf:display-when "not(../../ncs:module) or ../../ncs:module[ncs:name='Cisco-IOS-XR-ethernet-loopback-act']";
      tailf:action ethernet-loopback-discover-remote {
        tailf:actionpoint ncsproxy {
          tailf:internal;
        }
        description
          "Send a discovery request to retrieve information on remote loopback sessions";
        input {
          leaf interface {
            type xr:ncs_rpc_notif_Interface-name;
            mandatory true;
            description
              "Interface on which to send the request";
          }
          uses ncs_rpc_notif_EDPL-CFM-INFO-TYPE;
          uses ncs_rpc_notif_EDPL-REMOTE-VLAN-TYPE;
        }
        output {
          uses ncs_rpc_notif_EDPL-REMOTE-SESSION-LIST-TYPE;
        }
      }
    }
  }
  augment "/ncs:devices/ncs:device-group/ncs:ned-id/ncs:rpc" {
    container rpc-ethernet-loopback-discover-remote {
      tailf:ncs-device-type "netconf";
      tailf:display-when "/ncs:devices/ncs:device[ncs:name=current()/../../../ncs:member]/ncs:module[ncs:name='Cisco-IOS-XR-ethernet-loopback-act']";
      tailf:action ethernet-loopback-discover-remote {
        tailf:actionpoint ncsproxy {
          tailf:internal;
        }
        description
          "Send a discovery request to retrieve information on remote loopback sessions";
        input {
          leaf interface {
            type xr:ncs_rpc_notif_Interface-name;
            mandatory true;
            description
              "Interface on which to send the request";
          }
          uses ncs_rpc_notif_EDPL-CFM-INFO-TYPE;
          uses ncs_rpc_notif_EDPL-REMOTE-VLAN-TYPE;
        }
        output {
          container "device" {
            leaf "name" {
              type string;
            }
            leaf "info" {
              type string;
            }
            container "result" {
              uses ncs_rpc_notif_EDPL-REMOTE-SESSION-LIST-TYPE;
            }
          }
        }
      }
    }
  }
  augment "/ncs:devices/ncs:device/ncs:rpc" {
    container rpc-ethernet-loopback-get-state-remote {
      tailf:ncs-device-type "netconf";
      tailf:display-when "not(../../ncs:module) or ../../ncs:module[ncs:name='Cisco-IOS-XR-ethernet-loopback-act']";
      tailf:action ethernet-loopback-get-state-remote {
        tailf:actionpoint ncsproxy {
          tailf:internal;
        }
        description
          "Retrieve the state of a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
        }
        output {
          uses ncs_rpc_notif_EDPL-REMOTE-SESSION-LIST-TYPE;
        }
      }
    }
  }
  augment "/ncs:devices/ncs:device-group/ncs:ned-id/ncs:rpc" {
    container rpc-ethernet-loopback-get-state-remote {
      tailf:ncs-device-type "netconf";
      tailf:display-when "/ncs:devices/ncs:device[ncs:name=current()/../../../ncs:member]/ncs:module[ncs:name='Cisco-IOS-XR-ethernet-loopback-act']";
      tailf:action ethernet-loopback-get-state-remote {
        tailf:actionpoint ncsproxy {
          tailf:internal;
        }
        description
          "Retrieve the state of a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
        }
        output {
          container "device" {
            leaf "name" {
              type string;
            }
            leaf "info" {
              type string;
            }
            container "result" {
              uses ncs_rpc_notif_EDPL-REMOTE-SESSION-LIST-TYPE;
            }
          }
        }
      }
    }
  }
  augment "/ncs:devices/ncs:device/ncs:rpc" {
    container rpc-ethernet-loopback-extend-remote {
      tailf:ncs-device-type "netconf";
      tailf:display-when "not(../../ncs:module) or ../../ncs:module[ncs:name='Cisco-IOS-XR-ethernet-loopback-act']";
      tailf:action ethernet-loopback-extend-remote {
        tailf:actionpoint ncsproxy {
          tailf:internal;
        }
        description
          "Extend a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
          leaf timeout {
            type uint32 {
              range "1..604800";
            }
            mandatory true;
            description
              "Loopback duration in seconds";
          }
        }
      }
    }
  }
  augment "/ncs:devices/ncs:device-group/ncs:ned-id/ncs:rpc" {
    container rpc-ethernet-loopback-extend-remote {
      tailf:ncs-device-type "netconf";
      tailf:display-when "/ncs:devices/ncs:device[ncs:name=current()/../../../ncs:member]/ncs:module[ncs:name='Cisco-IOS-XR-ethernet-loopback-act']";
      tailf:action ethernet-loopback-extend-remote {
        tailf:actionpoint ncsproxy {
          tailf:internal;
        }
        description
          "Extend a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
          leaf timeout {
            type uint32 {
              range "1..604800";
            }
            mandatory true;
            description
              "Loopback duration in seconds";
          }
        }
      }
    }
  }
  augment "/ncs:devices/ncs:device/ncs:rpc" {
    container rpc-ethernet-loopback-stop-remote {
      tailf:ncs-device-type "netconf";
      tailf:display-when "not(../../ncs:module) or ../../ncs:module[ncs:name='Cisco-IOS-XR-ethernet-loopback-act']";
      tailf:action ethernet-loopback-stop-remote {
        tailf:actionpoint ncsproxy {
          tailf:internal;
        }
        description
          "Stop a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
        }
      }
    }
  }
  augment "/ncs:devices/ncs:device-group/ncs:ned-id/ncs:rpc" {
    container rpc-ethernet-loopback-stop-remote {
      tailf:ncs-device-type "netconf";
      tailf:display-when "/ncs:devices/ncs:device[ncs:name=current()/../../../ncs:member]/ncs:module[ncs:name='Cisco-IOS-XR-ethernet-loopback-act']";
      tailf:action ethernet-loopback-stop-remote {
        tailf:actionpoint ncsproxy {
          tailf:internal;
        }
        description
          "Stop a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
        }
      }
    }
  }
  augment "/ncs:devices/ncs:device/ncs:rpc" {
    container rpc-ethernet-loopback-start-remote {
      tailf:ncs-device-type "netconf";
      tailf:display-when "not(../../ncs:module) or ../../ncs:module[ncs:name='Cisco-IOS-XR-ethernet-loopback-act']";
      tailf:action ethernet-loopback-start-remote {
        tailf:actionpoint ncsproxy {
          tailf:internal;
        }
        description
          "Start a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
          leaf timeout {
            type uint32 {
              range "1..604800";
            }
            mandatory true;
            description
              "Loopback duration in seconds";
          }
        }
      }
    }
  }
  augment "/ncs:devices/ncs:device-group/ncs:ned-id/ncs:rpc" {
    container rpc-ethernet-loopback-start-remote {
      tailf:ncs-device-type "netconf";
      tailf:display-when "/ncs:devices/ncs:device[ncs:name=current()/../../../ncs:member]/ncs:module[ncs:name='Cisco-IOS-XR-ethernet-loopback-act']";
      tailf:action ethernet-loopback-start-remote {
        tailf:actionpoint ncsproxy {
          tailf:internal;
        }
        description
          "Start a remote ethernet loopback session";
        input {
          leaf interface {
            type xr:ncs_rpc_notif_Interface-name;
            mandatory true;
            description
              "Interface on which to send the request";
          }
          uses ncs_rpc_notif_EDPL-REMOTE-TARGET-TYPE;
          uses ncs_rpc_notif_EDPL-CFM-INFO-TYPE;
          uses ncs_rpc_notif_EDPL-REMOTE-VLAN-TYPE;
          leaf timeout {
            type uint32 {
              range "1..604800";
            }
            mandatory true;
            description
              "Loopback duration in seconds";
          }
        }
      }
    }
  }
  augment "/ncs:devices/ncs:device/ncs:rpc" {
    container rpc-ethernet-loopback-extend-local {
      tailf:ncs-device-type "netconf";
      tailf:display-when "not(../../ncs:module) or ../../ncs:module[ncs:name='Cisco-IOS-XR-ethernet-loopback-act']";
      tailf:action ethernet-loopback-extend-local {
        tailf:actionpoint ncsproxy {
          tailf:internal;
        }
        description
          "Extend a local ethernet loopback session";
        input {
          leaf interface {
            type xr:ncs_rpc_notif_Interface-name;
            mandatory true;
            description
              "Interface on which the loopback session is running";
          }
          leaf id {
            type uint32;
            mandatory true;
            description
              "ID of session to extend";
          }
          leaf timeout {
            type uint32 {
              range "0..604800";
            }
            description
              "Loopback duration in seconds";
          }
        }
      }
    }
  }
  augment "/ncs:devices/ncs:device-group/ncs:ned-id/ncs:rpc" {
    container rpc-ethernet-loopback-extend-local {
      tailf:ncs-device-type "netconf";
      tailf:display-when "/ncs:devices/ncs:device[ncs:name=current()/../../../ncs:member]/ncs:module[ncs:name='Cisco-IOS-XR-ethernet-loopback-act']";
      tailf:action ethernet-loopback-extend-local {
        tailf:actionpoint ncsproxy {
          tailf:internal;
        }
        description
          "Extend a local ethernet loopback session";
        input {
          leaf interface {
            type xr:ncs_rpc_notif_Interface-name;
            mandatory true;
            description
              "Interface on which the loopback session is running";
          }
          leaf id {
            type uint32;
            mandatory true;
            description
              "ID of session to extend";
          }
          leaf timeout {
            type uint32 {
              range "0..604800";
            }
            description
              "Loopback duration in seconds";
          }
        }
      }
    }
  }
  augment "/ncs:devices/ncs:device/ncs:rpc" {
    container rpc-ethernet-loopback-stop-local {
      tailf:ncs-device-type "netconf";
      tailf:display-when "not(../../ncs:module) or ../../ncs:module[ncs:name='Cisco-IOS-XR-ethernet-loopback-act']";
      tailf:action ethernet-loopback-stop-local {
        tailf:actionpoint ncsproxy {
          tailf:internal;
        }
        description
          "Stop a local ethernet loopback session";
        input {
          leaf interface {
            type xr:ncs_rpc_notif_Interface-name;
            mandatory true;
            description
              "Interface on which the loopback session is running";
          }
          leaf id {
            type uint32;
            mandatory true;
            description
              "ID of session to stop";
          }
        }
      }
    }
  }
  augment "/ncs:devices/ncs:device-group/ncs:ned-id/ncs:rpc" {
    container rpc-ethernet-loopback-stop-local {
      tailf:ncs-device-type "netconf";
      tailf:display-when "/ncs:devices/ncs:device[ncs:name=current()/../../../ncs:member]/ncs:module[ncs:name='Cisco-IOS-XR-ethernet-loopback-act']";
      tailf:action ethernet-loopback-stop-local {
        tailf:actionpoint ncsproxy {
          tailf:internal;
        }
        description
          "Stop a local ethernet loopback session";
        input {
          leaf interface {
            type xr:ncs_rpc_notif_Interface-name;
            mandatory true;
            description
              "Interface on which the loopback session is running";
          }
          leaf id {
            type uint32;
            mandatory true;
            description
              "ID of session to stop";
          }
        }
      }
    }
  }
  augment "/ncs:devices/ncs:device/ncs:rpc" {
    container rpc-ethernet-loopback-start-local {
      tailf:ncs-device-type "netconf";
      tailf:display-when "not(../../ncs:module) or ../../ncs:module[ncs:name='Cisco-IOS-XR-ethernet-loopback-act']";
      tailf:action ethernet-loopback-start-local {
        tailf:actionpoint ncsproxy {
          tailf:internal;
        }
        description
          "Start a local ethernet loopback session";
        input {
          leaf interface {
            type xr:ncs_rpc_notif_Interface-name;
            mandatory true;
            description
              "Interface on which to start the loopback";
          }
          leaf direction {
            type ncs_rpc_notif_loopback-direction;
            mandatory true;
            description
              "Loopback direction";
          }
          leaf source-mac {
            type yang:mac-address;
            description
              "Source mac to filter on";
          }
          leaf dest-mac {
            type yang:mac-address;
            description
              "Destination mac to filter on";
          }
          leaf outer-type {
            type ncs_rpc_notif_vlan-type;
            description
              "Type of outer VLAN ID to filter on";
          }
          leaf outer-vlan-ids {
            type string;
            description
              "Outer VLAN ID or IDs to filter on";
          }
          leaf inner-vlan-ids {
            type string;
            description
              "Inner VLAN ID or IDs to filter on";
          }
          leaf ether-type {
            type uint16;
            description
              "Ether-type to filter";
          }
          leaf cos {
            type uint8 {
              range "0..7";
            }
            description
              "Class of service to filter on";
          }
          leaf llc-oui {
            type uint32 {
              range "0..16777215";
            }
            description
              "LLC-OUI to filter on";
          }
          leaf timeout {
            type uint32 {
              range "0..604800";
            }
            description
              "Loopback duration in seconds";
          }
        }
        output {
          leaf id {
            type uint32;
            description
              "Session ID";
          }
        }
      }
    }
  }
  augment "/ncs:devices/ncs:device-group/ncs:ned-id/ncs:rpc" {
    container rpc-ethernet-loopback-start-local {
      tailf:ncs-device-type "netconf";
      tailf:display-when "/ncs:devices/ncs:device[ncs:name=current()/../../../ncs:member]/ncs:module[ncs:name='Cisco-IOS-XR-ethernet-loopback-act']";
      tailf:action ethernet-loopback-start-local {
        tailf:actionpoint ncsproxy {
          tailf:internal;
        }
        description
          "Start a local ethernet loopback session";
        input {
          leaf interface {
            type xr:ncs_rpc_notif_Interface-name;
            mandatory true;
            description
              "Interface on which to start the loopback";
          }
          leaf direction {
            type ncs_rpc_notif_loopback-direction;
            mandatory true;
            description
              "Loopback direction";
          }
          leaf source-mac {
            type yang:mac-address;
            description
              "Source mac to filter on";
          }
          leaf dest-mac {
            type yang:mac-address;
            description
              "Destination mac to filter on";
          }
          leaf outer-type {
            type ncs_rpc_notif_vlan-type;
            description
              "Type of outer VLAN ID to filter on";
          }
          leaf outer-vlan-ids {
            type string;
            description
              "Outer VLAN ID or IDs to filter on";
          }
          leaf inner-vlan-ids {
            type string;
            description
              "Inner VLAN ID or IDs to filter on";
          }
          leaf ether-type {
            type uint16;
            description
              "Ether-type to filter";
          }
          leaf cos {
            type uint8 {
              range "0..7";
            }
            description
              "Class of service to filter on";
          }
          leaf llc-oui {
            type uint32 {
              range "0..16777215";
            }
            description
              "LLC-OUI to filter on";
          }
          leaf timeout {
            type uint32 {
              range "0..604800";
            }
            description
              "Loopback duration in seconds";
          }
        }
        output {
          container "device" {
            leaf "name" {
              type string;
            }
            leaf "info" {
              type string;
            }
            container "result" {
              leaf id {
                type uint32;
                description
                  "Session ID";
              }
            }
          }
        }
      }
    }
  }
}

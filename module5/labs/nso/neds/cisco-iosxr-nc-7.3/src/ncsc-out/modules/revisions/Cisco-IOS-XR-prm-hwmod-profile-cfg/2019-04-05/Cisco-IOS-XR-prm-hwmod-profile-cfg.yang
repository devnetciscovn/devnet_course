module Cisco-IOS-XR-prm-hwmod-profile-cfg {
  // Generated by yanger -t ncs
  tailf:mount-id "cisco-iosxr-nc-7.3:cisco-iosxr-nc-7.3";
  tailf:ncs-device-type "netconf";

  namespace "http://cisco.com/ns/yang/Cisco-IOS-XR-prm-hwmod-profile-cfg";
  prefix prm-hwmod-profile-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR prm-hwmod-profile package configuration.

     This module contains definitions
     for the following management objects:
       hardware-module: HardwareModule

     Copyright (c) 2013-2019 by Cisco Systems, Inc.
     All rights reserved.";

  revision 2019-04-05 {
    description
      "Establish semantic version baseline.";
    semver:module-version "1.0.0";
  }
  revision 2017-12-05 {
    description
      "Implementing Conf Yang Model for profile selection";
  }
  revision 2015-11-09 {
    description
      "IOS XR 6.0 revision.";
  }

  typedef ncs_template_Profile-type-data {
    type string;
    description
      "Profile type data";
  }

  typedef ncs_rpc_notif_Profile-type-data {
    type enumeration {
      enum "sp" {
        value 1;
        description
          "SP Profile";
      }
      enum "dc" {
        value 2;
        description
          "DC Profile";
      }
    }
    description
      "Profile type data";
  }

  typedef live_ncs_Profile-type-data {
    type enumeration {
      enum "sp" {
        value 1;
        description
          "SP Profile";
      }
      enum "dc" {
        value 2;
        description
          "DC Profile";
      }
    }
    description
      "Profile type data";
  }

  typedef Profile-type-data {
    type enumeration {
      enum "sp" {
        value 1;
        description
          "SP Profile";
      }
      enum "dc" {
        value 2;
        description
          "DC Profile";
      }
    }
    description
      "Profile type data";
  }

  augment "/ncs:devices/ncs:device/ncs:config" {
    container hardware-module {
      tailf:ncs-device-type "netconf";
      tailf:display-when "not(../../ncs:module) or ../../ncs:module[ncs:name='Cisco-IOS-XR-prm-hwmod-profile-cfg']";
      description
        "HardwareModule";
      leaf profile {
        type Profile-type-data;
        description
          "Specify Profile type";
      }
    }
  }
  augment "/ncs:devices/ncs:device/ncs:live-status" {
    container hardware-module {
      tailf:ncs-device-type "netconf";
      tailf:display-when "not(../../ncs:module) or ../../ncs:module[ncs:name='Cisco-IOS-XR-prm-hwmod-profile-cfg'] or (../../ncs:live-status-protocol[not(ncs:capability)]) or (../../ncs:live-status-protocol/ncs:capability/ncs:module[.='Cisco-IOS-XR-prm-hwmod-profile-cfg'])";
      description
        "HardwareModule";
      leaf profile {
        type live_ncs_Profile-type-data;
        description
          "Specify Profile type";
      }
    }
  }
  augment "/ncs:devices/ncs:template/ncs:ned-id/ncs:config" {
    container hardware-module {
      description
        "HardwareModule";
      leaf profile {
        type ncs_template_Profile-type-data;
        description
          "Specify Profile type";
      }
    }
  }
}

module Cisco-IOS-XR-procmem-oper {
  // Generated by yanger -t ncs
  tailf:mount-id "cisco-iosxr-nc-7.3:cisco-iosxr-nc-7.3";
  tailf:ncs-device-type "netconf";

  namespace "http://cisco.com/ns/yang/Cisco-IOS-XR-procmem-oper";
  prefix procmem-oper;

  import Cisco-IOS-XR-types {
    prefix xr;
  }
  import cisco-semver {
    prefix semver;
  }
  include Cisco-IOS-XR-procmem-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR procmem package operational data.

     This module contains definitions
     for the following management objects:
       processes-memory: Process statistics

     Copyright (c) 2013-2019 by Cisco Systems, Inc.
     All rights reserved.";

  revision 2019-04-05 {
    description
      "Establish semantic version baseline.";
    semver:module-version "1.0.0";
  }
  revision 2019-03-04 {
    description
      "Moved proccess id from integer to range.";
  }
  revision 2017-09-07 {
    description
      "Fixed type translation error.";
  }
  revision 2017-05-01 {
    description
      "Fixing backward compatibility error in module.";
  }
  revision 2015-11-09 {
    description
      "IOS XR 6.0 revision.";
  }
  revision 2015-07-30 {
    description
      "IOS XR 6.0.0 revision.";
  }

  typedef ncs_template_Proc-mem-pid-range {
    type string;
    description
      "Proc mem pid range";
  }

  typedef ncs_rpc_notif_Proc-mem-pid-range {
    type uint32 {
      range "1..2147483647";
    }
    description
      "Proc mem pid range";
  }

  typedef live_ncs_Proc-mem-pid-range {
    type uint32 {
      range "1..2147483647";
    }
    description
      "Proc mem pid range";
  }

  typedef Proc-mem-pid-range {
    type uint32 {
      range "1..2147483647";
    }
    description
      "Proc mem pid range";
  }

  augment "/ncs:devices/ncs:device/ncs:config" {
    // NCS drop config false container 'processes-memory'
  }
  augment "/ncs:devices/ncs:device/ncs:live-status" {
    container processes-memory {
      tailf:ncs-device-type "netconf";
      tailf:display-when "not(../../ncs:module) or ../../ncs:module[ncs:name='Cisco-IOS-XR-procmem-oper'] or (../../ncs:live-status-protocol[not(ncs:capability)]) or (../../ncs:live-status-protocol/ncs:capability/ncs:module[.='Cisco-IOS-XR-procmem-oper'])";
      description
        "Process statistics";
      container nodes {
        description
          "List of nodes";
        list node {
          key "node-name";
          description
            "Node ID";
          container process-ids {
            description
              "List of jobs";
            list process-id {
              key "process-id";
              description
                "Process Id";
              leaf process-id {
                type live_ncs_Proc-mem-pid-range;
                description
                  "Process Id";
              }
              uses live_ncs_PROCESSESMEMORY-ENTRY;
            }
          }
          leaf node-name {
            type xr:live_ncs_Node-id;
            description
              "Node name";
          }
        }
      }
    }
  }
  augment "/ncs:devices/ncs:template/ncs:ned-id/ncs:config" {
    // NCS drop config false container 'processes-memory'
  }
}

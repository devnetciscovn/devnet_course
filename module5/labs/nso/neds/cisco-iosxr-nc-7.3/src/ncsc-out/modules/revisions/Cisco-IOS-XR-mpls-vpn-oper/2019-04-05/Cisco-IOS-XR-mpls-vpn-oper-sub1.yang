submodule Cisco-IOS-XR-mpls-vpn-oper-sub1 {
  // Generated by yanger -t ncs
  tailf:mount-id "cisco-iosxr-nc-7.3:cisco-iosxr-nc-7.3";

  belongs-to Cisco-IOS-XR-mpls-vpn-oper {
    prefix Cisco-IOS-XR-mpls-vpn-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-vpn package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Mpls-vpn-rt {
    type string;
    description
      "Layer 3 VPN Route Target Type";
  }

  typedef ncs_template_Mpls-vpn-safi {
    type string;
    description
      "Layer 3 VPN Sub-Address Family Type";
  }

  typedef ncs_template_Mpls-vpn-afi {
    type string;
    description
      "Layer 3 VPN Address Family Type";
  }

  typedef ncs_rpc_notif_Mpls-vpn-rt {
    type enumeration {
      enum "import" {
        value 1;
        description
          "VRF Route Target Type Import";
      }
      enum "export" {
        value 2;
        description
          "VRF Route Target Type Export";
      }
      enum "both" {
        value 3;
        description
          "VRF Route Target Type Import and Export";
      }
    }
    description
      "Layer 3 VPN Route Target Type";
  }

  typedef ncs_rpc_notif_Mpls-vpn-safi {
    type enumeration {
      enum "unicast" {
        value 1;
        description
          "VRF Unicast sub-address family";
      }
      enum "multicast" {
        value 2;
        description
          "VRF Multicast sub-address family";
      }
      enum "flowspec" {
        value 133;
        description
          "VRF Flowspec sub-address family";
      }
    }
    description
      "Layer 3 VPN Sub-Address Family Type";
  }

  typedef ncs_rpc_notif_Mpls-vpn-afi {
    type enumeration {
      enum "ipv4" {
        value 1;
        description
          "VRF IPv4 address family";
      }
      enum "ipv6" {
        value 2;
        description
          "VRF IPv6 address family";
      }
    }
    description
      "Layer 3 VPN Address Family Type";
  }

  typedef live_ncs_Mpls-vpn-rt {
    type enumeration {
      enum "import" {
        value 1;
        description
          "VRF Route Target Type Import";
      }
      enum "export" {
        value 2;
        description
          "VRF Route Target Type Export";
      }
      enum "both" {
        value 3;
        description
          "VRF Route Target Type Import and Export";
      }
    }
    description
      "Layer 3 VPN Route Target Type";
  }

  typedef live_ncs_Mpls-vpn-safi {
    type enumeration {
      enum "unicast" {
        value 1;
        description
          "VRF Unicast sub-address family";
      }
      enum "multicast" {
        value 2;
        description
          "VRF Multicast sub-address family";
      }
      enum "flowspec" {
        value 133;
        description
          "VRF Flowspec sub-address family";
      }
    }
    description
      "Layer 3 VPN Sub-Address Family Type";
  }

  typedef live_ncs_Mpls-vpn-afi {
    type enumeration {
      enum "ipv4" {
        value 1;
        description
          "VRF IPv4 address family";
      }
      enum "ipv6" {
        value 2;
        description
          "VRF IPv6 address family";
      }
    }
    description
      "Layer 3 VPN Address Family Type";
  }

  typedef Mpls-vpn-rt {
    type enumeration {
      enum "import" {
        value 1;
        description
          "VRF Route Target Type Import";
      }
      enum "export" {
        value 2;
        description
          "VRF Route Target Type Export";
      }
      enum "both" {
        value 3;
        description
          "VRF Route Target Type Import and Export";
      }
    }
    description
      "Layer 3 VPN Route Target Type";
  }

  typedef Mpls-vpn-safi {
    type enumeration {
      enum "unicast" {
        value 1;
        description
          "VRF Unicast sub-address family";
      }
      enum "multicast" {
        value 2;
        description
          "VRF Multicast sub-address family";
      }
      enum "flowspec" {
        value 133;
        description
          "VRF Flowspec sub-address family";
      }
    }
    description
      "Layer 3 VPN Sub-Address Family Type";
  }

  typedef Mpls-vpn-afi {
    type enumeration {
      enum "ipv4" {
        value 1;
        description
          "VRF IPv4 address family";
      }
      enum "ipv6" {
        value 2;
        description
          "VRF IPv6 address family";
      }
    }
    description
      "Layer 3 VPN Address Family Type";
  }

  grouping ncs_template_MPLS-VPN-RT {
    description
      "Layer 3 VPN Route Target";
    leaf route-target-type {
      type ncs_template_Mpls-vpn-rt;
      description
        "Route Target Type";
    }
    leaf route-target-value {
      type string;
      description
        "Route Target Value";
    }
    leaf af-name {
      type ncs_template_Mpls-vpn-afi;
      description
        "AF name";
    }
    leaf saf-name {
      type ncs_template_Mpls-vpn-safi;
      description
        "SAF name";
    }
  }

  grouping ncs_template_MPLS-VPN-AFI-SAFI {
    description
      "Layer 3 VPN AFI/SAFI Info";
    leaf af-name {
      type ncs_template_Mpls-vpn-afi;
      description
        "AF name";
    }
    leaf saf-name {
      type ncs_template_Mpls-vpn-safi;
      description
        "SAF name";
    }
    leaf import-route-policy {
      type string;
      description
        "Import Route Policy";
    }
    leaf export-route-policy {
      type string;
      description
        "Export Route Policy";
    }
    list route-target {
      // NCS patched for predictable order
      ordered-by user;
      description
        "Route Targets";
      uses ncs_template_MPLS-VPN-RT;
    }
  }

  grouping ncs_template_MPLS-VPN-INTERFACES {
    description
      "Layer 3 VPN Interface Names";
    leaf interface-name {
      type string;
      description
        "Interface Name";
    }
  }

  grouping ncs_template_MPLS-VPN-VRF {
    description
      "Layer 3 VPN VRF";
    leaf vrf-name-xr {
      type string;
      description
        "VRF Name";
    }
    leaf vrf-description {
      type string;
      description
        "VRF Description";
    }
    leaf route-distinguisher {
      type string;
      description
        "Route Distinguisher";
    }
    leaf is-big-vrf {
      type string;
      description
        "VRF mode information";
    }
    list interface {
      // NCS patched for predictable order
      ordered-by user;
      description
        "Interfaces in VRF";
      uses ncs_template_MPLS-VPN-INTERFACES;
    }
    list af {
      // NCS patched for predictable order
      ordered-by user;
      description
        "AF/SAF information";
      uses ncs_template_MPLS-VPN-AFI-SAFI;
    }
  }

  grouping ncs_rpc_notif_MPLS-VPN-RT {
    description
      "Layer 3 VPN Route Target";
    leaf route-target-type {
      type ncs_rpc_notif_Mpls-vpn-rt;
      description
        "Route Target Type";
    }
    leaf route-target-value {
      type string;
      description
        "Route Target Value";
    }
    leaf af-name {
      type ncs_rpc_notif_Mpls-vpn-afi;
      description
        "AF name";
    }
    leaf saf-name {
      type ncs_rpc_notif_Mpls-vpn-safi;
      description
        "SAF name";
    }
  }

  grouping ncs_rpc_notif_MPLS-VPN-AFI-SAFI {
    description
      "Layer 3 VPN AFI/SAFI Info";
    leaf af-name {
      type ncs_rpc_notif_Mpls-vpn-afi;
      description
        "AF name";
    }
    leaf saf-name {
      type ncs_rpc_notif_Mpls-vpn-safi;
      description
        "SAF name";
    }
    leaf import-route-policy {
      type string;
      description
        "Import Route Policy";
    }
    leaf export-route-policy {
      type string;
      description
        "Export Route Policy";
    }
    list route-target {
      description
        "Route Targets";
      uses ncs_rpc_notif_MPLS-VPN-RT;
    }
  }

  grouping ncs_rpc_notif_MPLS-VPN-INTERFACES {
    description
      "Layer 3 VPN Interface Names";
    leaf interface-name {
      type string;
      description
        "Interface Name";
    }
  }

  grouping ncs_rpc_notif_MPLS-VPN-VRF {
    description
      "Layer 3 VPN VRF";
    leaf vrf-name-xr {
      type string;
      description
        "VRF Name";
    }
    leaf vrf-description {
      type string;
      description
        "VRF Description";
    }
    leaf route-distinguisher {
      type string;
      description
        "Route Distinguisher";
    }
    leaf is-big-vrf {
      type boolean;
      description
        "VRF mode information";
    }
    list interface {
      description
        "Interfaces in VRF";
      uses ncs_rpc_notif_MPLS-VPN-INTERFACES;
    }
    list af {
      description
        "AF/SAF information";
      uses ncs_rpc_notif_MPLS-VPN-AFI-SAFI;
    }
  }

  grouping live_ncs_MPLS-VPN-RT {
    description
      "Layer 3 VPN Route Target";
    leaf route-target-type {
      type live_ncs_Mpls-vpn-rt;
      description
        "Route Target Type";
    }
    leaf route-target-value {
      type string;
      description
        "Route Target Value";
    }
    leaf af-name {
      type live_ncs_Mpls-vpn-afi;
      description
        "AF name";
    }
    leaf saf-name {
      type live_ncs_Mpls-vpn-safi;
      description
        "SAF name";
    }
  }

  grouping live_ncs_MPLS-VPN-AFI-SAFI {
    description
      "Layer 3 VPN AFI/SAFI Info";
    leaf af-name {
      type live_ncs_Mpls-vpn-afi;
      description
        "AF name";
    }
    leaf saf-name {
      type live_ncs_Mpls-vpn-safi;
      description
        "SAF name";
    }
    leaf import-route-policy {
      type string;
      description
        "Import Route Policy";
    }
    leaf export-route-policy {
      type string;
      description
        "Export Route Policy";
    }
    list route-target {
      description
        "Route Targets";
      uses live_ncs_MPLS-VPN-RT;
    }
  }

  grouping live_ncs_MPLS-VPN-INTERFACES {
    description
      "Layer 3 VPN Interface Names";
    leaf interface-name {
      type string;
      description
        "Interface Name";
    }
  }

  grouping live_ncs_MPLS-VPN-VRF {
    description
      "Layer 3 VPN VRF";
    leaf vrf-name-xr {
      type string;
      description
        "VRF Name";
    }
    leaf vrf-description {
      type string;
      description
        "VRF Description";
    }
    leaf route-distinguisher {
      type string;
      description
        "Route Distinguisher";
    }
    leaf is-big-vrf {
      type boolean;
      description
        "VRF mode information";
    }
    list interface {
      description
        "Interfaces in VRF";
      uses live_ncs_MPLS-VPN-INTERFACES;
    }
    list af {
      description
        "AF/SAF information";
      uses live_ncs_MPLS-VPN-AFI-SAFI;
    }
  }

  grouping MPLS-VPN-RT {
    description
      "Layer 3 VPN Route Target";
    leaf route-target-type {
      type Mpls-vpn-rt;
      description
        "Route Target Type";
    }
    leaf route-target-value {
      type string;
      description
        "Route Target Value";
    }
    leaf af-name {
      type Mpls-vpn-afi;
      description
        "AF name";
    }
    leaf saf-name {
      type Mpls-vpn-safi;
      description
        "SAF name";
    }
  }

  grouping MPLS-VPN-AFI-SAFI {
    description
      "Layer 3 VPN AFI/SAFI Info";
    leaf af-name {
      type Mpls-vpn-afi;
      description
        "AF name";
    }
    leaf saf-name {
      type Mpls-vpn-safi;
      description
        "SAF name";
    }
    leaf import-route-policy {
      type string;
      description
        "Import Route Policy";
    }
    leaf export-route-policy {
      type string;
      description
        "Export Route Policy";
    }
    list route-target {
      description
        "Route Targets";
      uses MPLS-VPN-RT;
    }
  }

  grouping MPLS-VPN-INTERFACES {
    description
      "Layer 3 VPN Interface Names";
    leaf interface-name {
      type string;
      description
        "Interface Name";
    }
  }

  grouping MPLS-VPN-VRF {
    description
      "Layer 3 VPN VRF";
    leaf vrf-name-xr {
      type string;
      description
        "VRF Name";
    }
    leaf vrf-description {
      type string;
      description
        "VRF Description";
    }
    leaf route-distinguisher {
      type string;
      description
        "Route Distinguisher";
    }
    leaf is-big-vrf {
      type boolean;
      description
        "VRF mode information";
    }
    list interface {
      description
        "Interfaces in VRF";
      uses MPLS-VPN-INTERFACES;
    }
    list af {
      description
        "AF/SAF information";
      uses MPLS-VPN-AFI-SAFI;
    }
  }
}

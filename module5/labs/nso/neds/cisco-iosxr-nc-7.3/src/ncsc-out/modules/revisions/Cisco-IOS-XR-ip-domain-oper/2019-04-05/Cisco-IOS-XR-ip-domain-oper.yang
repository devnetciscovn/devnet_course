module Cisco-IOS-XR-ip-domain-oper {
  // Generated by yanger -t ncs
  tailf:mount-id "cisco-iosxr-nc-7.3:cisco-iosxr-nc-7.3";
  tailf:ncs-device-type "netconf";

  namespace "http://cisco.com/ns/yang/Cisco-IOS-XR-ip-domain-oper";
  prefix ip-domain-oper;

  import Cisco-IOS-XR-types {
    prefix xr;
  }
  import cisco-semver {
    prefix semver;
  }
  include Cisco-IOS-XR-ip-domain-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-domain package operational data.

     This module contains definitions
     for the following management objects:
       ip-domain: Domain server and host data

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-09-29 {
    description
      "IOS XR 6.0.0 revision.";
  }
  revision 2015-01-07 {
    description
      "IOS XR 5.3.1 revision.";
  }

  augment "/ncs:devices/ncs:device/ncs:config" {
    // NCS drop config false container 'ip-domain'
  }
  augment "/ncs:devices/ncs:device/ncs:live-status" {
    container ip-domain {
      tailf:ncs-device-type "netconf";
      tailf:display-when "not(../../ncs:module) or ../../ncs:module[ncs:name='Cisco-IOS-XR-ip-domain-oper'] or (../../ncs:live-status-protocol[not(ncs:capability)]) or (../../ncs:live-status-protocol/ncs:capability/ncs:module[.='Cisco-IOS-XR-ip-domain-oper'])";
      description
        "Domain server and host data";
      container vrfs {
        description
          "List of VRFs";
        list vrf {
          key "vrf-name";
          description
            "VRF instance";
          container server {
            description
              "Domain server data";
            uses live_ncs_DOMAIN-SH-SERVER-BAG;
          }
          container hosts {
            description
              "List of domain hosts";
            list host {
              key "host-name";
              description
                "IP domain-name, lookup style, nameservers for
                 specific host";
              leaf host-name {
                type string;
                description
                  "Hostname";
              }
              uses live_ncs_DOMAIN-SH-HOSTS-BAG;
            }
          }
          leaf vrf-name {
            type xr:live_ncs_Cisco-ios-xr-string;
            description
              "VRF name";
          }
        }
      }
    }
  }
  augment "/ncs:devices/ncs:template/ncs:ned-id/ncs:config" {
    // NCS drop config false container 'ip-domain'
  }
}

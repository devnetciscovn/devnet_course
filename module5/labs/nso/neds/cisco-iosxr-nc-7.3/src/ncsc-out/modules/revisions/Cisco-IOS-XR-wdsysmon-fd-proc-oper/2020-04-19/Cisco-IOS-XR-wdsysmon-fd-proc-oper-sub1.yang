submodule Cisco-IOS-XR-wdsysmon-fd-proc-oper-sub1 {
  // Generated by yanger -t ncs
  tailf:mount-id "cisco-iosxr-nc-7.3:cisco-iosxr-nc-7.3";

  belongs-to Cisco-IOS-XR-wdsysmon-fd-proc-oper {
    prefix Cisco-IOS-XR-wdsysmon-fd-proc-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR wdsysmon-fd-proc package operational data.

     Copyright (c) 2013-2020 by Cisco Systems, Inc.
     All rights reserved.";

  revision 2020-04-19 {
    description
      "Initial version.";
    semver:module-version "1.0.0";
  }
  revision 2019-04-05 {
    description
      "Establish semantic version baseline.";
  }
  revision 2015-11-09 {
    description
      "IOS XR 6.0 revision.";
  }

  grouping ncs_template_THREAD-CPU-UTIL {
    description
      "Thread CPU utilization information";
    leaf thread-name {
      type string;
      description
        "Thread name";
    }
    leaf thread-id {
      type string;
      description
        "Thread ID";
    }
    leaf process-cpu-one-minute {
      type string;
      units "percentage";
      description
        "Thread CPU utilization in percent for past 1
         minute";
    }
    leaf process-cpu-five-minute {
      type string;
      units "percentage";
      description
        "Thread CPU utilization in percent for past 5
         minute";
    }
    leaf process-cpu-fifteen-minute {
      type string;
      units "percentage";
      description
        "Thread CPU utilization in percent for past 15
         minute";
    }
  }

  grouping ncs_template_PROCESS-CPU-UTIL {
    description
      "Process CPU utilization information";
    leaf process-name {
      type string;
      description
        "Process name";
    }
    leaf process-id {
      type string;
      description
        "Process ID";
    }
    leaf process-cpu-one-minute {
      type string;
      units "percentage";
      description
        "Process CPU utilization in percent for past 1
         minute";
    }
    leaf process-cpu-five-minute {
      type string;
      units "percentage";
      description
        "Process CPU utilization in percent for past 5
         minute";
    }
    leaf process-cpu-fifteen-minute {
      type string;
      units "percentage";
      description
        "Process CPU utilization in percent for past 15
         minute";
    }
    list thread-cpu {
      // NCS patched for predictable order
      ordered-by user;
      description
        "Threads Per process CPU utilization";
      uses ncs_template_THREAD-CPU-UTIL;
    }
  }

  grouping ncs_template_NODE-CPU-UTIL {
    description
      "Node CPU utilization information";
    leaf total-cpu-one-minute {
      type string;
      description
        "Total CPU utilization in past 1 minute";
    }
    leaf total-cpu-five-minute {
      type string;
      description
        "Total CPU utilization in past 5 minute";
    }
    leaf total-cpu-fifteen-minute {
      type string;
      description
        "Total CPU utilization in past 15 minute";
    }
    list process-cpu {
      // NCS patched for predictable order
      ordered-by user;
      description
        "Per process CPU utilization";
      uses ncs_template_PROCESS-CPU-UTIL;
    }
  }

  grouping ncs_rpc_notif_THREAD-CPU-UTIL {
    description
      "Thread CPU utilization information";
    leaf thread-name {
      type string;
      description
        "Thread name";
    }
    leaf thread-id {
      type uint32;
      description
        "Thread ID";
    }
    leaf process-cpu-one-minute {
      type uint32;
      units "percentage";
      description
        "Thread CPU utilization in percent for past 1
         minute";
    }
    leaf process-cpu-five-minute {
      type uint32;
      units "percentage";
      description
        "Thread CPU utilization in percent for past 5
         minute";
    }
    leaf process-cpu-fifteen-minute {
      type uint32;
      units "percentage";
      description
        "Thread CPU utilization in percent for past 15
         minute";
    }
  }

  grouping ncs_rpc_notif_PROCESS-CPU-UTIL {
    description
      "Process CPU utilization information";
    leaf process-name {
      type string;
      description
        "Process name";
    }
    leaf process-id {
      type uint32;
      description
        "Process ID";
    }
    leaf process-cpu-one-minute {
      type uint32;
      units "percentage";
      description
        "Process CPU utilization in percent for past 1
         minute";
    }
    leaf process-cpu-five-minute {
      type uint32;
      units "percentage";
      description
        "Process CPU utilization in percent for past 5
         minute";
    }
    leaf process-cpu-fifteen-minute {
      type uint32;
      units "percentage";
      description
        "Process CPU utilization in percent for past 15
         minute";
    }
    list thread-cpu {
      description
        "Threads Per process CPU utilization";
      uses ncs_rpc_notif_THREAD-CPU-UTIL;
    }
  }

  grouping ncs_rpc_notif_NODE-CPU-UTIL {
    description
      "Node CPU utilization information";
    leaf total-cpu-one-minute {
      type uint32;
      description
        "Total CPU utilization in past 1 minute";
    }
    leaf total-cpu-five-minute {
      type uint32;
      description
        "Total CPU utilization in past 5 minute";
    }
    leaf total-cpu-fifteen-minute {
      type uint32;
      description
        "Total CPU utilization in past 15 minute";
    }
    list process-cpu {
      description
        "Per process CPU utilization";
      uses ncs_rpc_notif_PROCESS-CPU-UTIL;
    }
  }

  grouping live_ncs_THREAD-CPU-UTIL {
    description
      "Thread CPU utilization information";
    leaf thread-name {
      type string;
      description
        "Thread name";
    }
    leaf thread-id {
      type uint32;
      description
        "Thread ID";
    }
    leaf process-cpu-one-minute {
      type uint32;
      units "percentage";
      description
        "Thread CPU utilization in percent for past 1
         minute";
    }
    leaf process-cpu-five-minute {
      type uint32;
      units "percentage";
      description
        "Thread CPU utilization in percent for past 5
         minute";
    }
    leaf process-cpu-fifteen-minute {
      type uint32;
      units "percentage";
      description
        "Thread CPU utilization in percent for past 15
         minute";
    }
  }

  grouping live_ncs_PROCESS-CPU-UTIL {
    description
      "Process CPU utilization information";
    leaf process-name {
      type string;
      description
        "Process name";
    }
    leaf process-id {
      type uint32;
      description
        "Process ID";
    }
    leaf process-cpu-one-minute {
      type uint32;
      units "percentage";
      description
        "Process CPU utilization in percent for past 1
         minute";
    }
    leaf process-cpu-five-minute {
      type uint32;
      units "percentage";
      description
        "Process CPU utilization in percent for past 5
         minute";
    }
    leaf process-cpu-fifteen-minute {
      type uint32;
      units "percentage";
      description
        "Process CPU utilization in percent for past 15
         minute";
    }
    list thread-cpu {
      description
        "Threads Per process CPU utilization";
      uses live_ncs_THREAD-CPU-UTIL;
    }
  }

  grouping live_ncs_NODE-CPU-UTIL {
    description
      "Node CPU utilization information";
    leaf total-cpu-one-minute {
      type uint32;
      description
        "Total CPU utilization in past 1 minute";
    }
    leaf total-cpu-five-minute {
      type uint32;
      description
        "Total CPU utilization in past 5 minute";
    }
    leaf total-cpu-fifteen-minute {
      type uint32;
      description
        "Total CPU utilization in past 15 minute";
    }
    list process-cpu {
      description
        "Per process CPU utilization";
      uses live_ncs_PROCESS-CPU-UTIL;
    }
  }

  grouping THREAD-CPU-UTIL {
    description
      "Thread CPU utilization information";
    leaf thread-name {
      type string;
      description
        "Thread name";
    }
    leaf thread-id {
      type uint32;
      description
        "Thread ID";
    }
    leaf process-cpu-one-minute {
      type uint32;
      units "percentage";
      description
        "Thread CPU utilization in percent for past 1
         minute";
    }
    leaf process-cpu-five-minute {
      type uint32;
      units "percentage";
      description
        "Thread CPU utilization in percent for past 5
         minute";
    }
    leaf process-cpu-fifteen-minute {
      type uint32;
      units "percentage";
      description
        "Thread CPU utilization in percent for past 15
         minute";
    }
  }

  grouping PROCESS-CPU-UTIL {
    description
      "Process CPU utilization information";
    leaf process-name {
      type string;
      description
        "Process name";
    }
    leaf process-id {
      type uint32;
      description
        "Process ID";
    }
    leaf process-cpu-one-minute {
      type uint32;
      units "percentage";
      description
        "Process CPU utilization in percent for past 1
         minute";
    }
    leaf process-cpu-five-minute {
      type uint32;
      units "percentage";
      description
        "Process CPU utilization in percent for past 5
         minute";
    }
    leaf process-cpu-fifteen-minute {
      type uint32;
      units "percentage";
      description
        "Process CPU utilization in percent for past 15
         minute";
    }
    list thread-cpu {
      description
        "Threads Per process CPU utilization";
      uses THREAD-CPU-UTIL;
    }
  }

  grouping NODE-CPU-UTIL {
    description
      "Node CPU utilization information";
    leaf total-cpu-one-minute {
      type uint32;
      description
        "Total CPU utilization in past 1 minute";
    }
    leaf total-cpu-five-minute {
      type uint32;
      description
        "Total CPU utilization in past 5 minute";
    }
    leaf total-cpu-fifteen-minute {
      type uint32;
      description
        "Total CPU utilization in past 15 minute";
    }
    list process-cpu {
      description
        "Per process CPU utilization";
      uses PROCESS-CPU-UTIL;
    }
  }
}

submodule Cisco-IOS-XR-Subscriber-infra-subdb-oper-sub2 {
  // Generated by yanger -t ncs
  tailf:mount-id "cisco-iosxr-nc-7.3:cisco-iosxr-nc-7.3";

  belongs-to Cisco-IOS-XR-Subscriber-infra-subdb-oper {
    prefix Cisco-IOS-XR-Subscriber-infra-subdb-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR Subscriber-infra-subdb package operational data.

     Copyright (c) 2013-2020 by Cisco Systems, Inc.
     All rights reserved.";

  revision 2020-04-02 {
    description
      "Added new bag for Subscriber database transition states and cfg object types.";
    semver:module-version "2.0.0";
  }
  revision 2019-04-05 {
    description
      "Establish semantic version baseline.";
    semver:module-version "1.0.1";
  }
  revision 2018-09-28 {
    description
      "Fixed Subscriber database Association.";
  }
  revision 2015-11-09 {
    description
      "IOS XR 6.0 revision.";
  }

  grouping ncs_template_SUBDB-SUBSCRIBER-IN-STATE-COUNTS {
    description
      "SUBDB SUBSCRIBER IN STATE COUNTS";
    leaf init-state {
      type string;
      description
        "Sessions in initialized state";
    }
    leaf destroying-state {
      type string;
      description
        "Sessions in Destroying state";
    }
    leaf config-gen-state {
      type string;
      description
        "Sessions in Config gen state";
    }
    leaf fat-gen-state {
      type string;
      description
        "Sessions in Fat gen state";
    }
    leaf config-apply-state {
      type string;
      description
        "Sessions in Config apply state";
    }
    leaf config-done-state {
      type string;
      description
        "Sessions in Config done state";
    }
    leaf config-unapply-state {
      type string;
      description
        "Sessions in Config unapply state";
    }
    leaf config-error-state {
      type string;
      description
        "Sessions in Config error state";
    }
    leaf error-state {
      type string;
      description
        "Sessions in error state";
    }
    leaf pre-sync-state {
      type string;
      description
        "Sessions in pre sync state";
    }
    leaf sync-state {
      type string;
      description
        "Sessions in sync state";
    }
  }

  grouping ncs_template_SUBDB-CFG-OBJECT-TYPE {
    description
      "SUBDB CFG OBJECT TYPE";
    leaf object-type-min {
      type string;
      description
        "Object type min";
    }
    leaf object-type-user-profile {
      type string;
      description
        "Object type user profile";
    }
    leaf object-type-service-profile {
      type string;
      description
        "Object type service profile";
    }
    leaf object-type-subsc-svc-template {
      type string;
      description
        "Object type subsc svc template";
    }
    leaf object-type-ppp-template {
      type string;
      description
        "Object type ppp template";
    }
    leaf object-type-ip-sub-template {
      type string;
      description
        "Object type ipsub template";
    }
    leaf object-type-sub-template {
      type string;
      description
        "Object type sub template";
    }
  }

  grouping ncs_template_SUBDB-SUMMARY-COUNTS-BAG {
    description
      "SUBDB SUMMARY COUNTS BAG";
    container subdb-obj-counts-by-type {
      description
        "The count of the various configuration objects
         by type";
      uses ncs_template_SUBDB-CFG-OBJECT-TYPE;
    }
    container subscribers-in-state {
      description
        "Number of subscribers in the various states";
      uses ncs_template_SUBDB-SUBSCRIBER-IN-STATE-COUNTS;
    }
    container num-transitions-through-state {
      description
        "Cumulative number of transitions through the
         various states";
      uses ncs_template_SUBDB-SUBSCRIBER-IN-STATE-COUNTS;
    }
    leaf assoc-db-entries {
      type string;
      description
        "Number of Entries in Association DB";
    }
    leaf assoc-db-associations {
      type string;
      description
        "Number of Associations in Association DB";
    }
    leaf derived-db-entries {
      type string;
      description
        "Number of Entries in Derived DB";
    }
    leaf config-db-entries {
      type string;
      description
        "Number of Entries in Configuration DB";
    }
    leaf interface-db-entries {
      type string;
      description
        "Number of Entries in Interface DB";
    }
    leaf num-ipsub-dhcp {
      type string;
      description
        "Number of IPSUB DHCP subscribers";
    }
    leaf num-ipsub-inband {
      type string;
      description
        "Number of IPSUB Inband subscribers";
    }
    leaf num-pppoe {
      type string;
      description
        "Number of PPPOE subscribers";
    }
  }

  grouping ncs_rpc_notif_SUBDB-SUBSCRIBER-IN-STATE-COUNTS {
    description
      "SUBDB SUBSCRIBER IN STATE COUNTS";
    leaf init-state {
      type uint32;
      description
        "Sessions in initialized state";
    }
    leaf destroying-state {
      type uint32;
      description
        "Sessions in Destroying state";
    }
    leaf config-gen-state {
      type uint32;
      description
        "Sessions in Config gen state";
    }
    leaf fat-gen-state {
      type uint32;
      description
        "Sessions in Fat gen state";
    }
    leaf config-apply-state {
      type uint32;
      description
        "Sessions in Config apply state";
    }
    leaf config-done-state {
      type uint32;
      description
        "Sessions in Config done state";
    }
    leaf config-unapply-state {
      type uint32;
      description
        "Sessions in Config unapply state";
    }
    leaf config-error-state {
      type uint32;
      description
        "Sessions in Config error state";
    }
    leaf error-state {
      type uint32;
      description
        "Sessions in error state";
    }
    leaf pre-sync-state {
      type uint32;
      description
        "Sessions in pre sync state";
    }
    leaf sync-state {
      type uint32;
      description
        "Sessions in sync state";
    }
  }

  grouping ncs_rpc_notif_SUBDB-CFG-OBJECT-TYPE {
    description
      "SUBDB CFG OBJECT TYPE";
    leaf object-type-min {
      type uint32;
      description
        "Object type min";
    }
    leaf object-type-user-profile {
      type uint32;
      description
        "Object type user profile";
    }
    leaf object-type-service-profile {
      type uint32;
      description
        "Object type service profile";
    }
    leaf object-type-subsc-svc-template {
      type uint32;
      description
        "Object type subsc svc template";
    }
    leaf object-type-ppp-template {
      type uint32;
      description
        "Object type ppp template";
    }
    leaf object-type-ip-sub-template {
      type uint32;
      description
        "Object type ipsub template";
    }
    leaf object-type-sub-template {
      type uint32;
      description
        "Object type sub template";
    }
  }

  grouping ncs_rpc_notif_SUBDB-SUMMARY-COUNTS-BAG {
    description
      "SUBDB SUMMARY COUNTS BAG";
    container subdb-obj-counts-by-type {
      description
        "The count of the various configuration objects
         by type";
      uses ncs_rpc_notif_SUBDB-CFG-OBJECT-TYPE;
    }
    container subscribers-in-state {
      description
        "Number of subscribers in the various states";
      uses ncs_rpc_notif_SUBDB-SUBSCRIBER-IN-STATE-COUNTS;
    }
    container num-transitions-through-state {
      description
        "Cumulative number of transitions through the
         various states";
      uses ncs_rpc_notif_SUBDB-SUBSCRIBER-IN-STATE-COUNTS;
    }
    leaf assoc-db-entries {
      type uint32;
      description
        "Number of Entries in Association DB";
    }
    leaf assoc-db-associations {
      type uint32;
      description
        "Number of Associations in Association DB";
    }
    leaf derived-db-entries {
      type uint32;
      description
        "Number of Entries in Derived DB";
    }
    leaf config-db-entries {
      type uint32;
      description
        "Number of Entries in Configuration DB";
    }
    leaf interface-db-entries {
      type uint32;
      description
        "Number of Entries in Interface DB";
    }
    leaf num-ipsub-dhcp {
      type uint32;
      description
        "Number of IPSUB DHCP subscribers";
    }
    leaf num-ipsub-inband {
      type uint32;
      description
        "Number of IPSUB Inband subscribers";
    }
    leaf num-pppoe {
      type uint32;
      description
        "Number of PPPOE subscribers";
    }
  }

  grouping live_ncs_SUBDB-SUBSCRIBER-IN-STATE-COUNTS {
    description
      "SUBDB SUBSCRIBER IN STATE COUNTS";
    leaf init-state {
      type uint32;
      description
        "Sessions in initialized state";
    }
    leaf destroying-state {
      type uint32;
      description
        "Sessions in Destroying state";
    }
    leaf config-gen-state {
      type uint32;
      description
        "Sessions in Config gen state";
    }
    leaf fat-gen-state {
      type uint32;
      description
        "Sessions in Fat gen state";
    }
    leaf config-apply-state {
      type uint32;
      description
        "Sessions in Config apply state";
    }
    leaf config-done-state {
      type uint32;
      description
        "Sessions in Config done state";
    }
    leaf config-unapply-state {
      type uint32;
      description
        "Sessions in Config unapply state";
    }
    leaf config-error-state {
      type uint32;
      description
        "Sessions in Config error state";
    }
    leaf error-state {
      type uint32;
      description
        "Sessions in error state";
    }
    leaf pre-sync-state {
      type uint32;
      description
        "Sessions in pre sync state";
    }
    leaf sync-state {
      type uint32;
      description
        "Sessions in sync state";
    }
  }

  grouping live_ncs_SUBDB-CFG-OBJECT-TYPE {
    description
      "SUBDB CFG OBJECT TYPE";
    leaf object-type-min {
      type uint32;
      description
        "Object type min";
    }
    leaf object-type-user-profile {
      type uint32;
      description
        "Object type user profile";
    }
    leaf object-type-service-profile {
      type uint32;
      description
        "Object type service profile";
    }
    leaf object-type-subsc-svc-template {
      type uint32;
      description
        "Object type subsc svc template";
    }
    leaf object-type-ppp-template {
      type uint32;
      description
        "Object type ppp template";
    }
    leaf object-type-ip-sub-template {
      type uint32;
      description
        "Object type ipsub template";
    }
    leaf object-type-sub-template {
      type uint32;
      description
        "Object type sub template";
    }
  }

  grouping live_ncs_SUBDB-SUMMARY-COUNTS-BAG {
    description
      "SUBDB SUMMARY COUNTS BAG";
    container subdb-obj-counts-by-type {
      description
        "The count of the various configuration objects
         by type";
      uses live_ncs_SUBDB-CFG-OBJECT-TYPE;
    }
    container subscribers-in-state {
      description
        "Number of subscribers in the various states";
      uses live_ncs_SUBDB-SUBSCRIBER-IN-STATE-COUNTS;
    }
    container num-transitions-through-state {
      description
        "Cumulative number of transitions through the
         various states";
      uses live_ncs_SUBDB-SUBSCRIBER-IN-STATE-COUNTS;
    }
    leaf assoc-db-entries {
      type uint32;
      description
        "Number of Entries in Association DB";
    }
    leaf assoc-db-associations {
      type uint32;
      description
        "Number of Associations in Association DB";
    }
    leaf derived-db-entries {
      type uint32;
      description
        "Number of Entries in Derived DB";
    }
    leaf config-db-entries {
      type uint32;
      description
        "Number of Entries in Configuration DB";
    }
    leaf interface-db-entries {
      type uint32;
      description
        "Number of Entries in Interface DB";
    }
    leaf num-ipsub-dhcp {
      type uint32;
      description
        "Number of IPSUB DHCP subscribers";
    }
    leaf num-ipsub-inband {
      type uint32;
      description
        "Number of IPSUB Inband subscribers";
    }
    leaf num-pppoe {
      type uint32;
      description
        "Number of PPPOE subscribers";
    }
  }

  grouping SUBDB-SUBSCRIBER-IN-STATE-COUNTS {
    description
      "SUBDB SUBSCRIBER IN STATE COUNTS";
    leaf init-state {
      type uint32;
      description
        "Sessions in initialized state";
    }
    leaf destroying-state {
      type uint32;
      description
        "Sessions in Destroying state";
    }
    leaf config-gen-state {
      type uint32;
      description
        "Sessions in Config gen state";
    }
    leaf fat-gen-state {
      type uint32;
      description
        "Sessions in Fat gen state";
    }
    leaf config-apply-state {
      type uint32;
      description
        "Sessions in Config apply state";
    }
    leaf config-done-state {
      type uint32;
      description
        "Sessions in Config done state";
    }
    leaf config-unapply-state {
      type uint32;
      description
        "Sessions in Config unapply state";
    }
    leaf config-error-state {
      type uint32;
      description
        "Sessions in Config error state";
    }
    leaf error-state {
      type uint32;
      description
        "Sessions in error state";
    }
    leaf pre-sync-state {
      type uint32;
      description
        "Sessions in pre sync state";
    }
    leaf sync-state {
      type uint32;
      description
        "Sessions in sync state";
    }
  }

  grouping SUBDB-CFG-OBJECT-TYPE {
    description
      "SUBDB CFG OBJECT TYPE";
    leaf object-type-min {
      type uint32;
      description
        "Object type min";
    }
    leaf object-type-user-profile {
      type uint32;
      description
        "Object type user profile";
    }
    leaf object-type-service-profile {
      type uint32;
      description
        "Object type service profile";
    }
    leaf object-type-subsc-svc-template {
      type uint32;
      description
        "Object type subsc svc template";
    }
    leaf object-type-ppp-template {
      type uint32;
      description
        "Object type ppp template";
    }
    leaf object-type-ip-sub-template {
      type uint32;
      description
        "Object type ipsub template";
    }
    leaf object-type-sub-template {
      type uint32;
      description
        "Object type sub template";
    }
  }

  grouping SUBDB-SUMMARY-COUNTS-BAG {
    description
      "SUBDB SUMMARY COUNTS BAG";
    container subdb-obj-counts-by-type {
      description
        "The count of the various configuration objects
         by type";
      uses SUBDB-CFG-OBJECT-TYPE;
    }
    container subscribers-in-state {
      description
        "Number of subscribers in the various states";
      uses SUBDB-SUBSCRIBER-IN-STATE-COUNTS;
    }
    container num-transitions-through-state {
      description
        "Cumulative number of transitions through the
         various states";
      uses SUBDB-SUBSCRIBER-IN-STATE-COUNTS;
    }
    leaf assoc-db-entries {
      type uint32;
      description
        "Number of Entries in Association DB";
    }
    leaf assoc-db-associations {
      type uint32;
      description
        "Number of Associations in Association DB";
    }
    leaf derived-db-entries {
      type uint32;
      description
        "Number of Entries in Derived DB";
    }
    leaf config-db-entries {
      type uint32;
      description
        "Number of Entries in Configuration DB";
    }
    leaf interface-db-entries {
      type uint32;
      description
        "Number of Entries in Interface DB";
    }
    leaf num-ipsub-dhcp {
      type uint32;
      description
        "Number of IPSUB DHCP subscribers";
    }
    leaf num-ipsub-inband {
      type uint32;
      description
        "Number of IPSUB Inband subscribers";
    }
    leaf num-pppoe {
      type uint32;
      description
        "Number of PPPOE subscribers";
    }
  }
}

module vplatform {
  // Generated by yanger -t ncs
  tailf:mount-id "cisco-iosxr-nc-7.3:cisco-iosxr-nc-7.3";
  tailf:ncs-device-type "netconf";

  namespace "http://cisco.com/panini/calvados/vplatform";
  prefix vplatform;

  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2015-08-30 {
    description
      "Initial version.";
  }

  augment "/ncs:devices/ncs:device/ncs:config" {
    // NCS drop config false container 'virtual-platform'
  }
  augment "/ncs:devices/ncs:device/ncs:live-status" {
    container virtual-platform {
      presence "In NCS this node is optional";
      tailf:ncs-device-type "netconf";
      tailf:display-when "not(../../ncs:module) or ../../ncs:module[ncs:name='vplatform'] or (../../ncs:live-status-protocol[not(ncs:capability)]) or (../../ncs:live-status-protocol/ncs:capability/ncs:module[.='vplatform'])";
      container vplatform {
        list summary {
          leaf lines {
            type string;
          }
        }
      }
      container udi {
        container history {
          list udi_his {
            leaf history_records {
              type string;
            }
          }
        }
      }
      container cpu {
        container history {
          list cpu_utl {
            leaf history_records {
              type string;
            }
          }
        }
      }
      container processor {
        container history {
          list proc_info {
            leaf history_records {
              type string;
            }
          }
        }
      }
      container memory {
        container history {
          list mem_usg {
            leaf history_records {
              type string;
            }
          }
        }
      }
      container disk {
        container history {
          list disk_utl {
            leaf history_records {
              type string;
            }
          }
        }
      }
      container Action {
        list udi {
          // NCS drop min-elements statement
          // NCS drop max-elements statement
          description
            "UDI Operations";
        }
      }
    }
  }
  augment "/ncs:devices/ncs:template/ncs:ned-id/ncs:config" {
    // NCS drop config false container 'virtual-platform'
  }
}

module Cisco-IOS-XR-cdp-cfg {
  // Generated by yanger -t ncs
  tailf:mount-id "cisco-iosxr-nc-7.3:cisco-iosxr-nc-7.3";
  tailf:ncs-device-type "netconf";

  namespace "http://cisco.com/ns/yang/Cisco-IOS-XR-cdp-cfg";
  prefix cdp-cfg;

  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cdp package configuration.

     This module contains definitions
     for the following management objects:
       cdp: Global CDP configuration data

     This YANG module augments the
       Cisco-IOS-XR-ifmgr-cfg
     module with configuration data.

     Copyright (c) 2013-2019 by Cisco Systems, Inc.
     All rights reserved.";

  revision 2019-04-05 {
    description
      "Establish semantic version baseline.";
    semver:module-version "1.0.1";
  }
  revision 2017-08-16 {
    description
      "Descriptions updated.";
  }
  revision 2015-01-07 {
    description
      "IOS XR 5.3.1 revision.";
  }

  augment "/ncs:devices/ncs:device/ncs:config" {
    container cdp {
      tailf:ncs-device-type "netconf";
      tailf:display-when "not(../../ncs:module) or ../../ncs:module[ncs:name='Cisco-IOS-XR-cdp-cfg']";
      description
        "Global CDP configuration data";
      leaf timer {
        type uint32 {
          range "5..254";
        }
        default "60";
        description
          "Specify the rate at which CDP packets are sent";
      }
      leaf advertise-v1-only {
        type empty;
        description
          "Enable CDPv1 only advertisements";
      }
      leaf enable {
        type boolean;
        default "true";
        description
          "Enable or disable CDP globally";
      }
      leaf hold-time {
        type uint32 {
          range "10..255";
        }
        default "180";
        description
          "Length of time (in sec) that the receiver must
           keep a CDP packet";
      }
      leaf log-adjacency {
        type empty;
        description
          "Enable logging of adjacency changes";
      }
    }
  }
  augment "/ncs:devices/ncs:device/ncs:live-status" {
    container cdp {
      tailf:ncs-device-type "netconf";
      tailf:display-when "not(../../ncs:module) or ../../ncs:module[ncs:name='Cisco-IOS-XR-cdp-cfg'] or (../../ncs:live-status-protocol[not(ncs:capability)]) or (../../ncs:live-status-protocol/ncs:capability/ncs:module[.='Cisco-IOS-XR-cdp-cfg'])";
      description
        "Global CDP configuration data";
      leaf timer {
        type uint32 {
          range "5..254";
        }
        // NCS drop default statement
        description
          "Specify the rate at which CDP packets are sent";
      }
      leaf advertise-v1-only {
        type empty;
        description
          "Enable CDPv1 only advertisements";
      }
      leaf enable {
        type boolean;
        // NCS drop default statement
        description
          "Enable or disable CDP globally";
      }
      leaf hold-time {
        type uint32 {
          range "10..255";
        }
        // NCS drop default statement
        description
          "Length of time (in sec) that the receiver must
           keep a CDP packet";
      }
      leaf log-adjacency {
        type empty;
        description
          "Enable logging of adjacency changes";
      }
    }
  }
  augment "/ncs:devices/ncs:template/ncs:ned-id/ncs:config" {
    container cdp {
      description
        "Global CDP configuration data";
      leaf timer {
        type string;
        // NCS drop default statement
        description
          "Specify the rate at which CDP packets are sent";
      }
      leaf advertise-v1-only {
        type empty;
        description
          "Enable CDPv1 only advertisements";
      }
      leaf enable {
        type string;
        // NCS drop default statement
        description
          "Enable or disable CDP globally";
      }
      leaf hold-time {
        type string;
        // NCS drop default statement
        description
          "Length of time (in sec) that the receiver must
           keep a CDP packet";
      }
      leaf log-adjacency {
        type empty;
        description
          "Enable logging of adjacency changes";
      }
    }
  }
  augment "/ncs:devices/ncs:template/ncs:ned-id/ncs:config/a1:interface-configurations/a1:interface-configuration" {
    description
      "This augment extends the configuration data of
       'Cisco-IOS-XR-ifmgr-cfg'";
    container cdp {
      description
        "Interface specific CDP configuration";
      leaf enable {
        type empty;
        description
          "Enable or disable CDP on an interface";
      }
    }
  }
  augment "/ncs:devices/ncs:device/ncs:live-status/a1:interface-configurations/a1:interface-configuration" {
    description
      "This augment extends the configuration data of
       'Cisco-IOS-XR-ifmgr-cfg'";
    container cdp {
      tailf:ncs-device-type "netconf";
      tailf:display-when "not(../../../../ncs:module) or ../../../../ncs:module[ncs:name='Cisco-IOS-XR-cdp-cfg'] or (../../../../ncs:live-status-protocol[not(ncs:capability)]) or (../../../../ncs:live-status-protocol/ncs:capability/ncs:module[.='Cisco-IOS-XR-cdp-cfg'])";
      description
        "Interface specific CDP configuration";
      leaf enable {
        type empty;
        description
          "Enable or disable CDP on an interface";
      }
    }
  }
  augment "/ncs:devices/ncs:device/ncs:config/a1:interface-configurations/a1:interface-configuration" {
    description
      "This augment extends the configuration data of
       'Cisco-IOS-XR-ifmgr-cfg'";
    container cdp {
      tailf:ncs-device-type "netconf";
      tailf:display-when "not(../../../../ncs:module) or ../../../../ncs:module[ncs:name='Cisco-IOS-XR-cdp-cfg']";
      description
        "Interface specific CDP configuration";
      leaf enable {
        type empty;
        description
          "Enable or disable CDP on an interface";
      }
    }
  }
}

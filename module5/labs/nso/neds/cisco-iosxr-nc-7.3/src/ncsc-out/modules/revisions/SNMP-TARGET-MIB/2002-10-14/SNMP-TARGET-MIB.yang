module SNMP-TARGET-MIB {
  // Generated by yanger -t ncs
  tailf:mount-id "cisco-iosxr-nc-7.3:cisco-iosxr-nc-7.3";
  tailf:ncs-device-type "netconf";

  namespace "http://tail-f.com/ns/mibs/SNMP-TARGET-MIB/200210140000Z";
  prefix SNMP_TARGET_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }
  import tailf-ncs {
    prefix ncs;
  }

  revision 2002-10-14 {
    description
      "";
  }

  typedef ncs_template_UDPIPv4TAddress {
    type string;
  }

  typedef ncs_template_UDPIPv6TAddress {
    type string;
  }

  typedef ncs_template_UDPTAddress {
    type string;
  }

  typedef ncs_template_EmptyOctetList {
    type string;
  }

  typedef ncs_template_UDPTMask {
    type string;
  }

  typedef ncs_template_snmpTargetAddrEngineIDType {
    type string;
  }

  typedef ncs_template_snmpTargetAddrMMSType {
    type string;
  }

  typedef ncs_template_SnmpTagValue {
    type string;
  }

  typedef ncs_template_SnmpTagList {
    type string;
  }

  typedef ncs_template_snmpTargetAddrNameType {
    type string;
  }

  typedef ncs_template_snmpTargetAddrRetryCountType {
    type string;
  }

  typedef ncs_template_snmpTargetAddrParamsType {
    type string;
  }

  typedef ncs_template_snmpTargetParamsNameType {
    type string;
  }

  typedef ncs_template_snmpTargetParamsSecurityModelType {
    type string;
  }

  typedef ncs_rpc_notif_UDPIPv4TAddress {
    tailf:info
      "ipv4+port (6 dot-separated octets)";
    type tailf:octet-list;
  }

  typedef ncs_rpc_notif_UDPIPv6TAddress {
    tailf:info
      "ipv6+port (18 dot-separated octets)";
    type tailf:octet-list;
  }

  typedef ncs_rpc_notif_UDPTAddress {
    type union {
      type ncs_rpc_notif_UDPIPv4TAddress;
      type ncs_rpc_notif_UDPIPv6TAddress;
    }
  }

  typedef ncs_rpc_notif_EmptyOctetList {
    type tailf:octet-list;
  }

  typedef ncs_rpc_notif_UDPTMask {
    tailf:info
      "octectList, 0, 6 or 18 octets long";
    type union {
      type ncs_rpc_notif_UDPTAddress;
      type ncs_rpc_notif_EmptyOctetList;
    }
  }

  typedef ncs_rpc_notif_snmpTargetAddrEngineIDType {
    type tailf:hex-list {
      pattern '(((([0-9A-Fa-f]{2}):){4,31})([0-9A-Fa-f]{2}))?';
      tailf:value-length "min .. 32";
    }
  }

  typedef ncs_rpc_notif_snmpTargetAddrMMSType {
    type int32 {
      range "0 | 484 .. 2147483647";
    }
  }

  typedef ncs_rpc_notif_SnmpTagValue {
    type string {
      length "min .. 255";
    }
  }

  typedef ncs_rpc_notif_SnmpTagList {
    type string {
      length "min .. 255";
    }
  }

  typedef ncs_rpc_notif_snmpTargetAddrNameType {
    type string {
      length "1 .. 32";
    }
  }

  typedef ncs_rpc_notif_snmpTargetAddrRetryCountType {
    type int32 {
      range "0 .. 255";
    }
  }

  typedef ncs_rpc_notif_snmpTargetAddrParamsType {
    type string {
      length "1 .. 32";
    }
  }

  typedef ncs_rpc_notif_snmpTargetParamsNameType {
    type string {
      length "1 .. 32";
    }
  }

  typedef ncs_rpc_notif_snmpTargetParamsSecurityModelType {
    type int32 {
      range "1 .. 2147483647";
    }
  }

  typedef live_ncs_UDPIPv4TAddress {
    tailf:info
      "ipv4+port (6 dot-separated octets)";
    type tailf:octet-list;
  }

  typedef live_ncs_UDPIPv6TAddress {
    tailf:info
      "ipv6+port (18 dot-separated octets)";
    type tailf:octet-list;
  }

  typedef live_ncs_UDPTAddress {
    type union {
      type live_ncs_UDPIPv4TAddress;
      type live_ncs_UDPIPv6TAddress;
    }
  }

  typedef live_ncs_EmptyOctetList {
    type tailf:octet-list;
  }

  typedef live_ncs_UDPTMask {
    tailf:info
      "octectList, 0, 6 or 18 octets long";
    type union {
      type live_ncs_UDPTAddress;
      type live_ncs_EmptyOctetList;
    }
  }

  typedef live_ncs_snmpTargetAddrEngineIDType {
    type tailf:hex-list {
      pattern '(((([0-9A-Fa-f]{2}):){4,31})([0-9A-Fa-f]{2}))?';
      tailf:value-length "min .. 32";
    }
  }

  typedef live_ncs_snmpTargetAddrMMSType {
    type int32 {
      range "0 | 484 .. 2147483647";
    }
  }

  typedef live_ncs_SnmpTagValue {
    type string {
      length "min .. 255";
    }
  }

  typedef live_ncs_SnmpTagList {
    type string {
      length "min .. 255";
    }
  }

  typedef live_ncs_snmpTargetAddrNameType {
    type string {
      length "1 .. 32";
    }
  }

  typedef live_ncs_snmpTargetAddrRetryCountType {
    type int32 {
      range "0 .. 255";
    }
  }

  typedef live_ncs_snmpTargetAddrParamsType {
    type string {
      length "1 .. 32";
    }
  }

  typedef live_ncs_snmpTargetParamsNameType {
    type string {
      length "1 .. 32";
    }
  }

  typedef live_ncs_snmpTargetParamsSecurityModelType {
    type int32 {
      range "1 .. 2147483647";
    }
  }

  typedef UDPIPv4TAddress {
    tailf:info
      "ipv4+port (6 dot-separated octets)";
    type tailf:octet-list;
  }

  typedef UDPIPv6TAddress {
    tailf:info
      "ipv6+port (18 dot-separated octets)";
    type tailf:octet-list;
  }

  typedef UDPTAddress {
    type union {
      type UDPIPv4TAddress;
      type UDPIPv6TAddress;
    }
  }

  typedef EmptyOctetList {
    type tailf:octet-list;
  }

  typedef UDPTMask {
    tailf:info
      "octectList, 0, 6 or 18 octets long";
    type union {
      type UDPTAddress;
      type EmptyOctetList;
    }
  }

  typedef snmpTargetAddrEngineIDType {
    type tailf:hex-list {
      pattern '(((([0-9A-Fa-f]{2}):){4,31})([0-9A-Fa-f]{2}))?';
      tailf:value-length "min .. 32";
    }
  }

  typedef snmpTargetAddrMMSType {
    type int32 {
      range "0 | 484 .. 2147483647";
    }
  }

  typedef SnmpTagValue {
    type string {
      length "min .. 255";
    }
  }

  typedef SnmpTagList {
    type string {
      length "min .. 255";
    }
  }

  typedef snmpTargetAddrNameType {
    type string {
      length "1 .. 32";
    }
  }

  typedef snmpTargetAddrRetryCountType {
    type int32 {
      range "0 .. 255";
    }
  }

  typedef snmpTargetAddrParamsType {
    type string {
      length "1 .. 32";
    }
  }

  typedef snmpTargetParamsNameType {
    type string {
      length "1 .. 32";
    }
  }

  typedef snmpTargetParamsSecurityModelType {
    type int32 {
      range "1 .. 2147483647";
    }
  }

  augment "/ncs:devices/ncs:device/ncs:config" {
    container SNMP-TARGET-MIB {
      tailf:ncs-device-type "netconf";
      tailf:display-when "not(../../ncs:module) or ../../ncs:module[ncs:name='SNMP-TARGET-MIB']";
      // NCS drop config false container snmpTargetObjects
      container snmpTargetAddrTable {
        list snmpTargetAddrEntry {
          key "snmpTargetAddrName";
          leaf snmpTargetAddrName {
            type snmpTargetAddrNameType;
          }
          leaf snmpTargetAddrTDomain {
            type SNMPv2_TC:TDomain;
            mandatory true;
          }
          leaf snmpTargetAddrTAddress {
            type UDPTAddress;
            mandatory true;
          }
          leaf snmpTargetAddrTimeout {
            type SNMPv2_TC:TimeInterval;
            default "1500";
          }
          leaf snmpTargetAddrRetryCount {
            type snmpTargetAddrRetryCountType;
            default "3";
          }
          leaf snmpTargetAddrTagList {
            type SnmpTagList;
            default "";
          }
          leaf snmpTargetAddrParams {
            type snmpTargetAddrParamsType;
            mandatory true;
          }
          leaf snmpTargetAddrStorageType {
            type SNMPv2_TC:StorageType;
            default "nonVolatile";
          }
          leaf snmpTargetAddrEngineID {
            type snmpTargetAddrEngineIDType;
            default "";
          }
          leaf snmpTargetAddrTMask {
            type UDPTMask;
            default "";
          }
          leaf snmpTargetAddrMMS {
            type snmpTargetAddrMMSType;
            default "2048";
          }
          leaf enabled {
            type boolean;
            default "true";
          }
        }
      }
      container snmpTargetParamsTable {
        list snmpTargetParamsEntry {
          key "snmpTargetParamsName";
          leaf snmpTargetParamsName {
            type snmpTargetParamsNameType;
          }
          leaf snmpTargetParamsMPModel {
            type SNMP_FRAMEWORK_MIB:SnmpMessageProcessingModel;
            mandatory true;
          }
          leaf snmpTargetParamsSecurityModel {
            type snmpTargetParamsSecurityModelType;
            mandatory true;
          }
          leaf snmpTargetParamsSecurityName {
            type SNMP_FRAMEWORK_MIB:SnmpAdminString;
            mandatory true;
          }
          leaf snmpTargetParamsSecurityLevel {
            type SNMP_FRAMEWORK_MIB:SnmpSecurityLevel;
            mandatory true;
          }
          leaf snmpTargetParamsStorageType {
            type SNMPv2_TC:StorageType;
            default "nonVolatile";
          }
        }
      }
    }
  }
  augment "/ncs:devices/ncs:device/ncs:live-status" {
    container SNMP-TARGET-MIB {
      tailf:ncs-device-type "netconf";
      tailf:display-when "not(../../ncs:module) or ../../ncs:module[ncs:name='SNMP-TARGET-MIB'] or (../../ncs:live-status-protocol[not(ncs:capability)]) or (../../ncs:live-status-protocol/ncs:capability/ncs:module[.='SNMP-TARGET-MIB'])";
      container snmpTargetObjects {
        leaf snmpUnavailableContexts {
          type yang:counter32;
        }
        leaf snmpUnknownContexts {
          type yang:counter32;
        }
      }
      container snmpTargetAddrTable {
        list snmpTargetAddrEntry {
          key "snmpTargetAddrName";
          leaf snmpTargetAddrName {
            type live_ncs_snmpTargetAddrNameType;
          }
          leaf snmpTargetAddrTDomain {
            type SNMPv2_TC:live_ncs_TDomain;
            // NCS drop mandatory statement
          }
          leaf snmpTargetAddrTAddress {
            type live_ncs_UDPTAddress;
            // NCS drop mandatory statement
          }
          leaf snmpTargetAddrTimeout {
            type SNMPv2_TC:live_ncs_TimeInterval;
            // NCS drop default statement
          }
          leaf snmpTargetAddrRetryCount {
            type live_ncs_snmpTargetAddrRetryCountType;
            // NCS drop default statement
          }
          leaf snmpTargetAddrTagList {
            type live_ncs_SnmpTagList;
            // NCS drop default statement
          }
          leaf snmpTargetAddrParams {
            type live_ncs_snmpTargetAddrParamsType;
            // NCS drop mandatory statement
          }
          leaf snmpTargetAddrStorageType {
            type SNMPv2_TC:live_ncs_StorageType;
            // NCS drop default statement
          }
          leaf snmpTargetAddrEngineID {
            type live_ncs_snmpTargetAddrEngineIDType;
            // NCS drop default statement
          }
          leaf snmpTargetAddrTMask {
            type live_ncs_UDPTMask;
            // NCS drop default statement
          }
          leaf snmpTargetAddrMMS {
            type live_ncs_snmpTargetAddrMMSType;
            // NCS drop default statement
          }
          leaf enabled {
            type boolean;
            // NCS drop default statement
          }
        }
      }
      container snmpTargetParamsTable {
        list snmpTargetParamsEntry {
          key "snmpTargetParamsName";
          leaf snmpTargetParamsName {
            type live_ncs_snmpTargetParamsNameType;
          }
          leaf snmpTargetParamsMPModel {
            type SNMP_FRAMEWORK_MIB:live_ncs_SnmpMessageProcessingModel;
            // NCS drop mandatory statement
          }
          leaf snmpTargetParamsSecurityModel {
            type live_ncs_snmpTargetParamsSecurityModelType;
            // NCS drop mandatory statement
          }
          leaf snmpTargetParamsSecurityName {
            type SNMP_FRAMEWORK_MIB:live_ncs_SnmpAdminString;
            // NCS drop mandatory statement
          }
          leaf snmpTargetParamsSecurityLevel {
            type SNMP_FRAMEWORK_MIB:live_ncs_SnmpSecurityLevel;
            // NCS drop mandatory statement
          }
          leaf snmpTargetParamsStorageType {
            type SNMPv2_TC:live_ncs_StorageType;
            // NCS drop default statement
          }
        }
      }
    }
  }
  augment "/ncs:devices/ncs:template/ncs:ned-id/ncs:config" {
    container SNMP-TARGET-MIB {
      // NCS drop config false container snmpTargetObjects
      container snmpTargetAddrTable {
        list snmpTargetAddrEntry {
          // NCS patched for predictable order
          ordered-by user;
          key "snmpTargetAddrName";
          leaf snmpTargetAddrName {
            type ncs_template_snmpTargetAddrNameType;
          }
          leaf snmpTargetAddrTDomain {
            type SNMPv2_TC:ncs_template_TDomain;
            // NCS drop mandatory statement
          }
          leaf snmpTargetAddrTAddress {
            type ncs_template_UDPTAddress;
            // NCS drop mandatory statement
          }
          leaf snmpTargetAddrTimeout {
            type SNMPv2_TC:ncs_template_TimeInterval;
            // NCS drop default statement
          }
          leaf snmpTargetAddrRetryCount {
            type ncs_template_snmpTargetAddrRetryCountType;
            // NCS drop default statement
          }
          leaf snmpTargetAddrTagList {
            type ncs_template_SnmpTagList;
            // NCS drop default statement
          }
          leaf snmpTargetAddrParams {
            type ncs_template_snmpTargetAddrParamsType;
            // NCS drop mandatory statement
          }
          leaf snmpTargetAddrStorageType {
            type SNMPv2_TC:ncs_template_StorageType;
            // NCS drop default statement
          }
          leaf snmpTargetAddrEngineID {
            type ncs_template_snmpTargetAddrEngineIDType;
            // NCS drop default statement
          }
          leaf snmpTargetAddrTMask {
            type ncs_template_UDPTMask;
            // NCS drop default statement
          }
          leaf snmpTargetAddrMMS {
            type ncs_template_snmpTargetAddrMMSType;
            // NCS drop default statement
          }
          leaf enabled {
            type string;
            // NCS drop default statement
          }
        }
      }
      container snmpTargetParamsTable {
        list snmpTargetParamsEntry {
          // NCS patched for predictable order
          ordered-by user;
          key "snmpTargetParamsName";
          leaf snmpTargetParamsName {
            type ncs_template_snmpTargetParamsNameType;
          }
          leaf snmpTargetParamsMPModel {
            type SNMP_FRAMEWORK_MIB:ncs_template_SnmpMessageProcessingModel;
            // NCS drop mandatory statement
          }
          leaf snmpTargetParamsSecurityModel {
            type ncs_template_snmpTargetParamsSecurityModelType;
            // NCS drop mandatory statement
          }
          leaf snmpTargetParamsSecurityName {
            type SNMP_FRAMEWORK_MIB:ncs_template_SnmpAdminString;
            // NCS drop mandatory statement
          }
          leaf snmpTargetParamsSecurityLevel {
            type SNMP_FRAMEWORK_MIB:ncs_template_SnmpSecurityLevel;
            // NCS drop mandatory statement
          }
          leaf snmpTargetParamsStorageType {
            type SNMPv2_TC:ncs_template_StorageType;
            // NCS drop default statement
          }
        }
      }
    }
  }
}

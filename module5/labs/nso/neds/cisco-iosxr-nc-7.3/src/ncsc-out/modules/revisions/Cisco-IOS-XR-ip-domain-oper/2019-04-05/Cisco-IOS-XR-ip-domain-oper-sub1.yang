submodule Cisco-IOS-XR-ip-domain-oper-sub1 {
  // Generated by yanger -t ncs
  tailf:mount-id "cisco-iosxr-nc-7.3:cisco-iosxr-nc-7.3";

  belongs-to Cisco-IOS-XR-ip-domain-oper {
    prefix Cisco-IOS-XR-ip-domain-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-domain package operational data.

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-09-29 {
    description
      "IOS XR 6.0.0 revision.";
  }
  revision 2015-01-07 {
    description
      "IOS XR 5.3.1 revision.";
  }

  typedef ncs_template_String1 {
    type string;
    description
      "String1";
  }

  typedef ncs_template_Domain-ipv6-address {
    type string;
    description
      "Domain ipv6 address";
  }

  typedef ncs_template_Host-address {
    type string;
    description
      "Host Address Type";
  }

  typedef ncs_template_Server-domain-lkup {
    type string;
    description
      "Domain look up";
  }

  typedef ncs_rpc_notif_String1 {
    type string {
      length "0..256";
    }
    description
      "String1";
  }

  typedef ncs_rpc_notif_Domain-ipv6-address {
    type inet:ipv6-address;
    description
      "Domain ipv6 address";
  }

  typedef ncs_rpc_notif_Host-address {
    type identityref {
      base Host-address-base;
    }
    description
      "Host Address Type";
  }

  typedef ncs_rpc_notif_Server-domain-lkup {
    type enumeration {
      enum "static-mapping" {
        value 0;
        description
          "Static mapping";
      }
      enum "domain-service" {
        value 1;
        description
          "Domain service";
      }
    }
    description
      "Domain look up";
  }

  typedef live_ncs_String1 {
    type string {
      length "0..256";
    }
    description
      "String1";
  }

  typedef live_ncs_Domain-ipv6-address {
    type inet:ipv6-address;
    description
      "Domain ipv6 address";
  }

  typedef live_ncs_Host-address {
    type identityref {
      base Host-address-base;
    }
    description
      "Host Address Type";
  }

  typedef live_ncs_Server-domain-lkup {
    type enumeration {
      enum "static-mapping" {
        value 0;
        description
          "Static mapping";
      }
      enum "domain-service" {
        value 1;
        description
          "Domain service";
      }
    }
    description
      "Domain look up";
  }

  typedef String1 {
    type string {
      length "0..256";
    }
    description
      "String1";
  }

  typedef Domain-ipv6-address {
    type inet:ipv6-address;
    description
      "Domain ipv6 address";
  }

  typedef Host-address {
    type identityref {
      base Host-address-base;
    }
    description
      "Host Address Type";
  }

  typedef Server-domain-lkup {
    type enumeration {
      enum "static-mapping" {
        value 0;
        description
          "Static mapping";
      }
      enum "domain-service" {
        value 1;
        description
          "Domain service";
      }
    }
    description
      "Domain look up";
  }

  grouping ncs_template_DOMAIN-HOST-ALIAS-BAG {
    description
      "Domain host alias";
    leaf-list host-alias {
      // NCS patched for predictable order
      ordered-by user;
      type ncs_template_String1;
      description
        "Host alias list";
    }
  }

  grouping ncs_template_DOMAIN-SH-HOSTS-BAG {
    description
      "Domain hosts";
    container host-alias-list {
      description
        "Host alias";
      uses ncs_template_DOMAIN-HOST-ALIAS-BAG;
    }
    leaf af-name {
      type ncs_template_Host-address;
      description
        "Address type";
    }
    leaf age {
      type string;
      units "hour";
      description
        "Age in hours";
    }
    list host-address {
      // NCS patched for predictable order
      ordered-by user;
      description
        "Host address list";
      uses ncs_template_DOMAIN-IPADDRESS;
    }
  }

  grouping ncs_template_DOMAIN-IPADDRESS {
    description
      "IP Address";
    leaf af-name {
      type ncs_template_Host-address;
      description
        "AFName";
    }
    leaf ipv4-address {
      // NCS drop when statement
      type string;
      description
        "IPv4 address";
    }
    leaf ipv6-address {
      // NCS drop when statement
      type ncs_template_Domain-ipv6-address;
      description
        "IPv6 address";
    }
  }

  grouping ncs_template_DOMAIN-SH-SERVER-BAG {
    description
      "Domain servers";
    leaf domain-lookup {
      type ncs_template_Server-domain-lkup;
      description
        "Domain lookup";
    }
    leaf domain-name {
      type string;
      description
        "Domain name";
    }
    leaf-list domain {
      // NCS patched for predictable order
      ordered-by user;
      type ncs_template_String1;
      description
        "Domain list";
    }
    list server-address {
      // NCS patched for predictable order
      ordered-by user;
      description
        "Server address list";
      uses ncs_template_DOMAIN-IPADDRESS;
    }
  }

  grouping ncs_rpc_notif_DOMAIN-HOST-ALIAS-BAG {
    description
      "Domain host alias";
    leaf-list host-alias {
      type ncs_rpc_notif_String1;
      description
        "Host alias list";
    }
  }

  grouping ncs_rpc_notif_DOMAIN-SH-HOSTS-BAG {
    description
      "Domain hosts";
    container host-alias-list {
      description
        "Host alias";
      uses ncs_rpc_notif_DOMAIN-HOST-ALIAS-BAG;
    }
    leaf af-name {
      type ncs_rpc_notif_Host-address;
      description
        "Address type";
    }
    leaf age {
      type uint16;
      units "hour";
      description
        "Age in hours";
    }
    list host-address {
      description
        "Host address list";
      uses ncs_rpc_notif_DOMAIN-IPADDRESS;
    }
  }

  grouping ncs_rpc_notif_DOMAIN-IPADDRESS {
    description
      "IP Address";
    leaf af-name {
      type ncs_rpc_notif_Host-address;
      description
        "AFName";
    }
    leaf ipv4-address {
      when "../af-name = 'ipv4'" {
        tailf:xpath-root 3;
        description
          "../AFName = 'IPv4'";
      }
      type inet:ipv4-address;
      description
        "IPv4 address";
    }
    leaf ipv6-address {
      when "../af-name = 'ipv6'" {
        tailf:xpath-root 3;
        description
          "../AFName = 'IPv6'";
      }
      type ncs_rpc_notif_Domain-ipv6-address;
      description
        "IPv6 address";
    }
  }

  grouping ncs_rpc_notif_DOMAIN-SH-SERVER-BAG {
    description
      "Domain servers";
    leaf domain-lookup {
      type ncs_rpc_notif_Server-domain-lkup;
      description
        "Domain lookup";
    }
    leaf domain-name {
      type string {
        length "0..256";
      }
      description
        "Domain name";
    }
    leaf-list domain {
      type ncs_rpc_notif_String1;
      description
        "Domain list";
    }
    list server-address {
      description
        "Server address list";
      uses ncs_rpc_notif_DOMAIN-IPADDRESS;
    }
  }

  grouping live_ncs_DOMAIN-HOST-ALIAS-BAG {
    description
      "Domain host alias";
    leaf-list host-alias {
      type live_ncs_String1;
      description
        "Host alias list";
    }
  }

  grouping live_ncs_DOMAIN-SH-HOSTS-BAG {
    description
      "Domain hosts";
    container host-alias-list {
      description
        "Host alias";
      uses live_ncs_DOMAIN-HOST-ALIAS-BAG;
    }
    leaf af-name {
      type live_ncs_Host-address;
      description
        "Address type";
    }
    leaf age {
      type uint16;
      units "hour";
      description
        "Age in hours";
    }
    list host-address {
      description
        "Host address list";
      uses live_ncs_DOMAIN-IPADDRESS;
    }
  }

  grouping live_ncs_DOMAIN-IPADDRESS {
    description
      "IP Address";
    leaf af-name {
      type live_ncs_Host-address;
      description
        "AFName";
    }
    leaf ipv4-address {
      // NCS drop when statement
      type inet:ipv4-address;
      description
        "IPv4 address";
    }
    leaf ipv6-address {
      // NCS drop when statement
      type live_ncs_Domain-ipv6-address;
      description
        "IPv6 address";
    }
  }

  grouping live_ncs_DOMAIN-SH-SERVER-BAG {
    description
      "Domain servers";
    leaf domain-lookup {
      type live_ncs_Server-domain-lkup;
      description
        "Domain lookup";
    }
    leaf domain-name {
      type string {
        length "0..256";
      }
      description
        "Domain name";
    }
    leaf-list domain {
      type live_ncs_String1;
      description
        "Domain list";
    }
    list server-address {
      description
        "Server address list";
      uses live_ncs_DOMAIN-IPADDRESS;
    }
  }

  grouping DOMAIN-HOST-ALIAS-BAG {
    description
      "Domain host alias";
    leaf-list host-alias {
      type String1;
      description
        "Host alias list";
    }
  }

  grouping DOMAIN-SH-HOSTS-BAG {
    description
      "Domain hosts";
    container host-alias-list {
      description
        "Host alias";
      uses DOMAIN-HOST-ALIAS-BAG;
    }
    leaf af-name {
      type Host-address;
      description
        "Address type";
    }
    leaf age {
      type uint16;
      units "hour";
      description
        "Age in hours";
    }
    list host-address {
      description
        "Host address list";
      uses DOMAIN-IPADDRESS;
    }
  }

  grouping DOMAIN-IPADDRESS {
    description
      "IP Address";
    leaf af-name {
      type Host-address;
      description
        "AFName";
    }
    leaf ipv4-address {
      when "../af-name = 'ipv4'" {
        tailf:xpath-root 3;
        description
          "../AFName = 'IPv4'";
      }
      type inet:ipv4-address;
      description
        "IPv4 address";
    }
    leaf ipv6-address {
      when "../af-name = 'ipv6'" {
        tailf:xpath-root 3;
        description
          "../AFName = 'IPv6'";
      }
      type Domain-ipv6-address;
      description
        "IPv6 address";
    }
  }

  grouping DOMAIN-SH-SERVER-BAG {
    description
      "Domain servers";
    leaf domain-lookup {
      type Server-domain-lkup;
      description
        "Domain lookup";
    }
    leaf domain-name {
      type string {
        length "0..256";
      }
      description
        "Domain name";
    }
    leaf-list domain {
      type String1;
      description
        "Domain list";
    }
    list server-address {
      description
        "Server address list";
      uses DOMAIN-IPADDRESS;
    }
  }

  identity ipv6 {
    base Host-address-base;
    description
      "IPv6 family address";
  }

  identity ipv4 {
    base Host-address-base;
    description
      "IPv4 family address";
  }

  identity Host-address-base {
    description
      "Base identity for Host-address";
  }
}

module Cisco-IOS-XR-sysadmin-tacacs-test-tacacs {
  // Generated by yanger -t ncs
  tailf:mount-id "cisco-iosxr-nc-7.3:cisco-iosxr-nc-7.3";
  tailf:ncs-device-type "netconf";

  namespace "http://www.cisco.com/ns/yang/Cisco-IOS-XR-sysadmin-tacacs-test-tacacs";
  prefix test_tacacs;

  import Cisco-IOS-XR-sysadmin-tacacs-tacacs-server {
    prefix tacacs-server;
  }
  import cisco-semver {
    prefix semver;
  }
  import tailf-common {
    prefix tailf;
  }
  import tailf-ncs {
    prefix ncs;
  }

  organization
    "Cisco Systems Inc.";
  contact
    "aaa-ng-tacacs-dev@cisco.com";
  description
    "This clie part is for test commands for tacacs

     Copyright (c) 2012-2020 by Cisco Systems, Inc.
     All rights reserved.";

  revision 2021-02-26 {
    description
      "Updated presence string to command containers";
    semver:module-version "1.1.0";
  }
  revision 2019-04-15 {
    description
      "Establish semantic version baseline.";
    semver:module-version "1.0.0";
  }
  revision 2017-05-10 {
    description
      "Namespace changed from test_tacacs to Cisco-IOS-XR-sysadmin-tacacs-test-tacacs";
  }
  revision 2015-07-07 {
    description
      "Initial revision";
  }

  augment "/ncs:devices/ncs:template/ncs:ned-id/ncs:config/tacacs-server:tacacs-server" {
    // NCS drop config false container 'test-authentication'
    // NCS drop config false container 'test-authorization'
    // NCS drop config false container 'test-accounting'
  }
  augment "/ncs:devices/ncs:device/ncs:live-status/tacacs-server:tacacs-server" {
    container test-authentication {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "Indicates test-authentication is configured";
      leaf authentication {
        type string;
        // NCS drop mandatory statement
        description
          "Authentication";
      }
    }
    container test-authorization {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "Indicates test-authorization is configured";
      leaf authorization {
        type string;
        // NCS drop mandatory statement
        description
          "Authorization";
      }
    }
    container test-accounting {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "Indicates test-accounting is configured";
      leaf accounting {
        type string;
        // NCS drop mandatory statement
        description
          "Accounting";
      }
    }
  }
  augment "/ncs:devices/ncs:device/ncs:config/tacacs-server:tacacs-server" {
    // NCS drop config false container 'test-authentication'
    // NCS drop config false container 'test-authorization'
    // NCS drop config false container 'test-accounting'
  }
}

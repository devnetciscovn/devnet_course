module Cisco-IOS-XR-lcmode-cfg {
  // Generated by yanger -t ncs
  tailf:mount-id "cisco-iosxr-nc-7.3:cisco-iosxr-nc-7.3";
  tailf:ncs-device-type "netconf";

  namespace "http://cisco.com/ns/yang/Cisco-IOS-XR-lcmode-cfg";
  prefix lcmode-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lcmode package configuration.

     This module contains definitions
     for the following management objects:
       lcmode-oc: LC MODE OC configuration
       lcmode-cli: LC MODE CLI configuration

     Copyright (c) 2013-2020 by Cisco Systems, Inc.
     All rights reserved.";

  revision 2020-03-19 {
    description
      "Initial Revision.";
    semver:module-version "1.0.0";
  }
  revision 2019-04-05 {
    description
      "Establish semantic version baseline.";
  }
  revision 2015-11-09 {
    description
      "IOS XR 6.0 revision.";
  }

  typedef ncs_template_Lc-mode {
    type string;
    description
      "Lc mode";
  }

  typedef ncs_rpc_notif_Lc-mode {
    type enumeration {
      enum "10g-grey-mxp" {
        value 1;
        description
          "LCMODE for 10G GREY MXP with QSFP28 Trunk";
      }
      enum "100g-txp" {
        value 2;
        description
          "LCMODE for 100G TXP";
      }
      enum "4x100g-mxp-400g-txp" {
        value 3;
        description
          "LCMODE for 100G MXP and 400G TXP with CFP2 DCO
           Trunk";
      }
      enum "40x10g-4x100g-mxp" {
        value 4;
        description
          "LCMODE for 10G/100G MXP With CFP2 DCO Trunk";
      }
      enum "4x100ge-mxp-dd" {
        value 5;
        description
          "LCMODE for 100GE MXP with QSFP-DD-ZR Trunk";
      }
      enum "400ge-txp-dd" {
        value 6;
        description
          "LCMODE for 400GE TXP with QSFP-DD-ZR Trunk";
      }
    }
    description
      "Lc mode";
  }

  typedef live_ncs_Lc-mode {
    type enumeration {
      enum "10g-grey-mxp" {
        value 1;
        description
          "LCMODE for 10G GREY MXP with QSFP28 Trunk";
      }
      enum "100g-txp" {
        value 2;
        description
          "LCMODE for 100G TXP";
      }
      enum "4x100g-mxp-400g-txp" {
        value 3;
        description
          "LCMODE for 100G MXP and 400G TXP with CFP2 DCO
           Trunk";
      }
      enum "40x10g-4x100g-mxp" {
        value 4;
        description
          "LCMODE for 10G/100G MXP With CFP2 DCO Trunk";
      }
      enum "4x100ge-mxp-dd" {
        value 5;
        description
          "LCMODE for 100GE MXP with QSFP-DD-ZR Trunk";
      }
      enum "400ge-txp-dd" {
        value 6;
        description
          "LCMODE for 400GE TXP with QSFP-DD-ZR Trunk";
      }
    }
    description
      "Lc mode";
  }

  typedef Lc-mode {
    type enumeration {
      enum "10g-grey-mxp" {
        value 1;
        description
          "LCMODE for 10G GREY MXP with QSFP28 Trunk";
      }
      enum "100g-txp" {
        value 2;
        description
          "LCMODE for 100G TXP";
      }
      enum "4x100g-mxp-400g-txp" {
        value 3;
        description
          "LCMODE for 100G MXP and 400G TXP with CFP2 DCO
           Trunk";
      }
      enum "40x10g-4x100g-mxp" {
        value 4;
        description
          "LCMODE for 10G/100G MXP With CFP2 DCO Trunk";
      }
      enum "4x100ge-mxp-dd" {
        value 5;
        description
          "LCMODE for 100GE MXP with QSFP-DD-ZR Trunk";
      }
      enum "400ge-txp-dd" {
        value 6;
        description
          "LCMODE for 400GE TXP with QSFP-DD-ZR Trunk";
      }
    }
    description
      "Lc mode";
  }

  augment "/ncs:devices/ncs:device/ncs:config" {
    container lcmode-oc {
      tailf:ncs-device-type "netconf";
      tailf:display-when "not(../../ncs:module) or ../../ncs:module[ncs:name='Cisco-IOS-XR-lcmode-cfg']";
      description
        "LC MODE OC configuration";
      list slot-info-oc {
        key "lc-slot";
        description
          "location of LC";
        leaf lcmode-type-oc {
          type Lc-mode;
          description
            "LCMODE config type";
        }
        leaf lc-slot {
          type xr:Cisco-ios-xr-string;
          description
            "LC location";
        }
      }
    }
    container lcmode-cli {
      tailf:ncs-device-type "netconf";
      tailf:display-when "not(../../ncs:module) or ../../ncs:module[ncs:name='Cisco-IOS-XR-lcmode-cfg']";
      description
        "LC MODE CLI configuration";
      list slot-info-cli {
        key "lc-slot";
        description
          "location of LC";
        leaf lcmode-type-cli {
          type Lc-mode;
          description
            "LCMODE config type";
        }
        leaf lc-slot {
          type xr:Cisco-ios-xr-string;
          description
            "LC location";
        }
      }
    }
  }
  augment "/ncs:devices/ncs:device/ncs:live-status" {
    container lcmode-oc {
      tailf:ncs-device-type "netconf";
      tailf:display-when "not(../../ncs:module) or ../../ncs:module[ncs:name='Cisco-IOS-XR-lcmode-cfg'] or (../../ncs:live-status-protocol[not(ncs:capability)]) or (../../ncs:live-status-protocol/ncs:capability/ncs:module[.='Cisco-IOS-XR-lcmode-cfg'])";
      description
        "LC MODE OC configuration";
      list slot-info-oc {
        key "lc-slot";
        description
          "location of LC";
        leaf lcmode-type-oc {
          type live_ncs_Lc-mode;
          description
            "LCMODE config type";
        }
        leaf lc-slot {
          type xr:live_ncs_Cisco-ios-xr-string;
          description
            "LC location";
        }
      }
    }
    container lcmode-cli {
      tailf:ncs-device-type "netconf";
      tailf:display-when "not(../../ncs:module) or ../../ncs:module[ncs:name='Cisco-IOS-XR-lcmode-cfg'] or (../../ncs:live-status-protocol[not(ncs:capability)]) or (../../ncs:live-status-protocol/ncs:capability/ncs:module[.='Cisco-IOS-XR-lcmode-cfg'])";
      description
        "LC MODE CLI configuration";
      list slot-info-cli {
        key "lc-slot";
        description
          "location of LC";
        leaf lcmode-type-cli {
          type live_ncs_Lc-mode;
          description
            "LCMODE config type";
        }
        leaf lc-slot {
          type xr:live_ncs_Cisco-ios-xr-string;
          description
            "LC location";
        }
      }
    }
  }
  augment "/ncs:devices/ncs:template/ncs:ned-id/ncs:config" {
    container lcmode-oc {
      description
        "LC MODE OC configuration";
      list slot-info-oc {
        // NCS patched for predictable order
        ordered-by user;
        key "lc-slot";
        description
          "location of LC";
        leaf lcmode-type-oc {
          type ncs_template_Lc-mode;
          description
            "LCMODE config type";
        }
        leaf lc-slot {
          type xr:ncs_template_Cisco-ios-xr-string;
          description
            "LC location";
        }
      }
    }
    container lcmode-cli {
      description
        "LC MODE CLI configuration";
      list slot-info-cli {
        // NCS patched for predictable order
        ordered-by user;
        key "lc-slot";
        description
          "location of LC";
        leaf lcmode-type-cli {
          type ncs_template_Lc-mode;
          description
            "LCMODE config type";
        }
        leaf lc-slot {
          type xr:ncs_template_Cisco-ios-xr-string;
          description
            "LC location";
        }
      }
    }
  }
}

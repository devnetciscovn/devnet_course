module Cisco-IOS-XR-ncs5500-coherent-node-oper {
  // Generated by yanger -t ncs
  tailf:mount-id "cisco-iosxr-nc-7.3:cisco-iosxr-nc-7.3";
  tailf:ncs-device-type "netconf";

  namespace "http://cisco.com/ns/yang/Cisco-IOS-XR-ncs5500-coherent-node-oper";
  prefix ncs5500-coherent-node-oper;

  import Cisco-IOS-XR-types {
    prefix xr;
  }
  import cisco-semver {
    prefix semver;
  }
  include Cisco-IOS-XR-ncs5500-coherent-node-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs5500-coherent-node package operational data.

     This module contains definitions
     for the following management objects:
       coherent: Coherent node  operational data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container coherent
  }
  augment "/ncs:devices/ncs:device/ncs:live-status" {
    container coherent {
      tailf:ncs-device-type "netconf";
      tailf:display-when "not(../../ncs:module) or ../../ncs:module[ncs:name='Cisco-IOS-XR-ncs5500-coherent-node-oper'] or (../../ncs:live-status-protocol[not(ncs:capability)]) or (../../ncs:live-status-protocol/ncs:capability/ncs:module[.='Cisco-IOS-XR-ncs5500-coherent-node-oper'])";
      description
        "Coherent node  operational data";
      container nodes {
        description
          "Coherent list of nodes";
        list node {
          key "node-name";
          description
            "Coherent discovery operational data for a
             particular node";
          container coherent-time-stats {
            description
              "Coherent driver performace information";
            uses live_ncs_COH-TIME-STATS;
          }
          container coherenthealth {
            description
              "Coherent node data for driver health";
            uses live_ncs_COH-HEALTH-DATA;
          }
          leaf node-name {
            type xr:live_ncs_Node-id;
            description
              "The node name";
          }
        }
      }
    }
  }
  augment "/ncs:devices/ncs:template/ncs:ned-id/ncs:config" {
    // NCS drop config false container coherent
  }
}

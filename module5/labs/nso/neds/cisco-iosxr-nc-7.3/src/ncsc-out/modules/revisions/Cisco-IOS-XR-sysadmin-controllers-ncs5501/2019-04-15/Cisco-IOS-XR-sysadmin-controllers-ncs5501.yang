module Cisco-IOS-XR-sysadmin-controllers-ncs5501 {
  // Generated by yanger -t ncs
  tailf:mount-id "cisco-iosxr-nc-7.3:cisco-iosxr-nc-7.3";
  tailf:ncs-device-type "netconf";

  namespace "http://www.cisco.com/ns/yang/Cisco-IOS-XR-sysadmin-controllers-NCS5501";
  prefix calvados_controllers;

  import Cisco-IOS-XR-sysadmin-fabric-ncs5501 {
    prefix fabric;
  }
  import Cisco-IOS-XR-sysadmin-card-mgr {
    prefix card_mgr;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the top level container for
     all hardware devices managed in Sysadmin.

     Copyright (c) 2015-2020 by Cisco Systems, Inc.
     All rights reserved.";

  revision 2019-04-15 {
    description
      "Establish semantic version baseline.";
    semver:module-version "1.0.0";
  }
  revision 2017-10-11 {
    description
      "Changed the namespace to unique namespace per unique model";
  }
  revision 2017-01-31 {
    description
      "Changed the namespace and module name";
  }
  revision 2016-01-12 {
    description
      "Created initial 'controller' implementation for Turin";
  }

  augment "/ncs:devices/ncs:device/ncs:config" {
    container controller {
      tailf:ncs-device-type "netconf";
      tailf:display-when "not(../../ncs:module) or ../../ncs:module[ncs:name='Cisco-IOS-XR-sysadmin-controllers-ncs5501']";
      uses fabric:fabric;
      uses card_mgr:card_mgr-group;
    }
  }
  augment "/ncs:devices/ncs:device/ncs:live-status" {
    container controller {
      tailf:ncs-device-type "netconf";
      tailf:display-when "not(../../ncs:module) or ../../ncs:module[ncs:name='Cisco-IOS-XR-sysadmin-controllers-ncs5501'] or (../../ncs:live-status-protocol[not(ncs:capability)]) or (../../ncs:live-status-protocol/ncs:capability/ncs:module[.='Cisco-IOS-XR-sysadmin-controllers-ncs5501'])";
      uses fabric:live_ncs_fabric;
      uses card_mgr:live_ncs_card_mgr-group;
    }
  }
  augment "/ncs:devices/ncs:template/ncs:ned-id/ncs:config" {
    container controller {
      uses fabric:ncs_template_fabric;
      uses card_mgr:ncs_template_card_mgr-group;
    }
  }
}

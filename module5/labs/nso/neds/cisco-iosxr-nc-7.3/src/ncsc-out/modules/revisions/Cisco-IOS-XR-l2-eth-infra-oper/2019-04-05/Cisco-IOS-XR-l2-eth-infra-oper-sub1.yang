submodule Cisco-IOS-XR-l2-eth-infra-oper-sub1 {
  // Generated by yanger -t ncs
  tailf:mount-id "cisco-iosxr-nc-7.3:cisco-iosxr-nc-7.3";

  belongs-to Cisco-IOS-XR-l2-eth-infra-oper {
    prefix Cisco-IOS-XR-l2-eth-infra-oper;
  }

  import ietf-yang-types {
    prefix yang;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR l2-eth-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Eth-caps-ucast-mac-mode {
    type string;
    description
      "Eth caps ucast mac mode";
  }

  typedef ncs_rpc_notif_Eth-caps-ucast-mac-mode {
    type enumeration {
      enum "reserved" {
        value 0;
        description
          "Reserved";
      }
      enum "permit" {
        value 1;
        description
          "Permit";
      }
    }
    description
      "Eth caps ucast mac mode";
  }

  typedef live_ncs_Eth-caps-ucast-mac-mode {
    type enumeration {
      enum "reserved" {
        value 0;
        description
          "Reserved";
      }
      enum "permit" {
        value 1;
        description
          "Permit";
      }
    }
    description
      "Eth caps ucast mac mode";
  }

  typedef Eth-caps-ucast-mac-mode {
    type enumeration {
      enum "reserved" {
        value 0;
        description
          "Reserved";
      }
      enum "permit" {
        value 1;
        description
          "Permit";
      }
    }
    description
      "Eth caps ucast mac mode";
  }

  grouping ncs_template_ETH-CAPS-UCAST-MAC-ENTRY-TYPE {
    description
      "ETH CAPS UCAST MAC ENTRY TYPE";
    leaf mac-address {
      type string;
      description
        "MAC address";
    }
    leaf mode {
      type ncs_template_Eth-caps-ucast-mac-mode;
      description
        "Unicast MAC mode";
    }
  }

  grouping ncs_template_ETHER-CAPS-UCAST-FILTER {
    description
      "Per interface unicast MAC filter information";
    list unicast-filter {
      // NCS patched for predictable order
      ordered-by user;
      description
        "Unicast MAC filter information";
      uses ncs_template_ETH-CAPS-UCAST-MAC-ENTRY-TYPE;
    }
  }

  grouping ncs_rpc_notif_ETH-CAPS-UCAST-MAC-ENTRY-TYPE {
    description
      "ETH CAPS UCAST MAC ENTRY TYPE";
    leaf mac-address {
      type yang:mac-address;
      description
        "MAC address";
    }
    leaf mode {
      type ncs_rpc_notif_Eth-caps-ucast-mac-mode;
      description
        "Unicast MAC mode";
    }
  }

  grouping ncs_rpc_notif_ETHER-CAPS-UCAST-FILTER {
    description
      "Per interface unicast MAC filter information";
    list unicast-filter {
      description
        "Unicast MAC filter information";
      uses ncs_rpc_notif_ETH-CAPS-UCAST-MAC-ENTRY-TYPE;
    }
  }

  grouping live_ncs_ETH-CAPS-UCAST-MAC-ENTRY-TYPE {
    description
      "ETH CAPS UCAST MAC ENTRY TYPE";
    leaf mac-address {
      type yang:mac-address;
      description
        "MAC address";
    }
    leaf mode {
      type live_ncs_Eth-caps-ucast-mac-mode;
      description
        "Unicast MAC mode";
    }
  }

  grouping live_ncs_ETHER-CAPS-UCAST-FILTER {
    description
      "Per interface unicast MAC filter information";
    list unicast-filter {
      description
        "Unicast MAC filter information";
      uses live_ncs_ETH-CAPS-UCAST-MAC-ENTRY-TYPE;
    }
  }

  grouping ETH-CAPS-UCAST-MAC-ENTRY-TYPE {
    description
      "ETH CAPS UCAST MAC ENTRY TYPE";
    leaf mac-address {
      type yang:mac-address;
      description
        "MAC address";
    }
    leaf mode {
      type Eth-caps-ucast-mac-mode;
      description
        "Unicast MAC mode";
    }
  }

  grouping ETHER-CAPS-UCAST-FILTER {
    description
      "Per interface unicast MAC filter information";
    list unicast-filter {
      description
        "Unicast MAC filter information";
      uses ETH-CAPS-UCAST-MAC-ENTRY-TYPE;
    }
  }
}

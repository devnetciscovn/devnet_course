module Cisco-IOS-XR-ipv4-ospf-act {
  // Generated by yanger -t ncs
  tailf:mount-id "cisco-iosxr-nc-7.3:cisco-iosxr-nc-7.3";
  tailf:ncs-device-type "netconf";

  namespace "http://cisco.com/ns/yang/Cisco-IOS-XR-ipv4-ospf-act";
  prefix ospf-act;

  import cisco-semver {
    prefix semver;
  }
  import Cisco-IOS-XR-types {
    prefix xr;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR OSPF action package configuration.

     Copyright (c) 2016-2020 by Cisco Systems, Inc.
     All rights reserved.";

  revision 2020-08-13 {
    description
      "Added xr-task name ospf to restrict unlimited permission";
    semver:module-version "1.1.0";
  }
  revision 2019-10-01 {
    description
      "Made changes to be RFC6087 compliant";
    semver:module-version "1.1.0";
  }
  revision 2019-04-05 {
    description
      "Establish semantic version baseline.";
    semver:module-version "1.0.0";
  }
  revision 2016-09-14 {
    description
      "IOS XR 6.2.1 revision.";
  }

  grouping ncs_template_OSPF-STAT-ATTRIBUTES {
    description
      "OSPF Stat Attributes";
    leaf process {
      type empty;
      description
        "Reset OSPF process";
    }
    leaf redistribution {
      type empty;
      description
        "Clear OSPF route redistrbution";
    }
    leaf route {
      type empty;
      description
        "Clear OSPF route table";
    }
    container stats {
      description
        "OSPF counters and statistics";
      leaf spf {
        type empty;
        description
          "SPF statistics";
      }
      leaf message-queue {
        type empty;
        description
          "Message-queue statistics";
      }
      container interface {
        description
          "OSPF interface statistics";
        leaf interface-name {
          type xr:ncs_template_Interface-name;
          description
            "OSPF Interface name";
        }
      }
      container neighbor {
        description
          "Neighbor statistics per interface or neighbor id";
        leaf neighbor-id {
          type string;
          description
            "Neighbor ID";
        }
        container interface {
          description
            "OSPF Interface";
          leaf interface-name {
            type xr:ncs_template_Interface-name;
            description
              "OSPF interface statistics";
          }
        }
      }
    }
  }

  grouping ncs_rpc_notif_OSPF-STAT-ATTRIBUTES {
    description
      "OSPF Stat Attributes";
    leaf process {
      type empty;
      description
        "Reset OSPF process";
    }
    leaf redistribution {
      type empty;
      description
        "Clear OSPF route redistrbution";
    }
    leaf route {
      type empty;
      description
        "Clear OSPF route table";
    }
    container stats {
      description
        "OSPF counters and statistics";
      leaf spf {
        type empty;
        description
          "SPF statistics";
      }
      leaf message-queue {
        type empty;
        description
          "Message-queue statistics";
      }
      container interface {
        description
          "OSPF interface statistics";
        leaf interface-name {
          type xr:ncs_rpc_notif_Interface-name;
          description
            "OSPF Interface name";
        }
      }
      container neighbor {
        description
          "Neighbor statistics per interface or neighbor id";
        leaf neighbor-id {
          type inet:ipv4-address;
          description
            "Neighbor ID";
        }
        container interface {
          description
            "OSPF Interface";
          leaf interface-name {
            type xr:ncs_rpc_notif_Interface-name;
            description
              "OSPF interface statistics";
          }
        }
      }
    }
  }

  grouping live_ncs_OSPF-STAT-ATTRIBUTES {
    description
      "OSPF Stat Attributes";
    leaf process {
      type empty;
      description
        "Reset OSPF process";
    }
    leaf redistribution {
      type empty;
      description
        "Clear OSPF route redistrbution";
    }
    leaf route {
      type empty;
      description
        "Clear OSPF route table";
    }
    container stats {
      description
        "OSPF counters and statistics";
      leaf spf {
        type empty;
        description
          "SPF statistics";
      }
      leaf message-queue {
        type empty;
        description
          "Message-queue statistics";
      }
      container interface {
        description
          "OSPF interface statistics";
        leaf interface-name {
          type xr:live_ncs_Interface-name;
          description
            "OSPF Interface name";
        }
      }
      container neighbor {
        description
          "Neighbor statistics per interface or neighbor id";
        leaf neighbor-id {
          type inet:ipv4-address;
          description
            "Neighbor ID";
        }
        container interface {
          description
            "OSPF Interface";
          leaf interface-name {
            type xr:live_ncs_Interface-name;
            description
              "OSPF interface statistics";
          }
        }
      }
    }
  }

  grouping OSPF-STAT-ATTRIBUTES {
    description
      "OSPF Stat Attributes";
    leaf process {
      type empty;
      description
        "Reset OSPF process";
    }
    leaf redistribution {
      type empty;
      description
        "Clear OSPF route redistrbution";
    }
    leaf route {
      type empty;
      description
        "Clear OSPF route table";
    }
    container stats {
      description
        "OSPF counters and statistics";
      leaf spf {
        type empty;
        description
          "SPF statistics";
      }
      leaf message-queue {
        type empty;
        description
          "Message-queue statistics";
      }
      container interface {
        description
          "OSPF interface statistics";
        leaf interface-name {
          type xr:Interface-name;
          description
            "OSPF Interface name";
        }
      }
      container neighbor {
        description
          "Neighbor statistics per interface or neighbor id";
        leaf neighbor-id {
          type inet:ipv4-address;
          description
            "Neighbor ID";
        }
        container interface {
          description
            "OSPF Interface";
          leaf interface-name {
            type xr:Interface-name;
            description
              "OSPF interface statistics";
          }
        }
      }
    }
  }

  augment "/ncs:devices/ncs:device/ncs:rpc" {
    container rpc-clear-ospf-instance-vrf {
      tailf:ncs-device-type "netconf";
      tailf:display-when "not(../../ncs:module) or ../../ncs:module[ncs:name='Cisco-IOS-XR-ipv4-ospf-act']";
      tailf:action clear-ospf-instance-vrf {
        tailf:actionpoint ncsproxy {
          tailf:internal;
        }
        description
          "Clear one or more non-default OSPF VRFs in process";
        input {
          container instance {
            description
              "OSPF instance name";
            leaf instance-identifier {
              type string;
              mandatory true;
              description
                "OSPF process instance identifier";
            }
            container vrf {
              description
                "Clear one or more non-default OSPF VRFs in process";
              leaf vrf-name {
                type string;
                description
                  "OSPF VRF name";
              }
              uses ncs_rpc_notif_OSPF-STAT-ATTRIBUTES;
            }
            container all {
              description
                "Clear all non-default OSPF VRFs";
              uses ncs_rpc_notif_OSPF-STAT-ATTRIBUTES;
            }
            container all-inclusive {
              description
                "Clear all non-default and default OSPF VRFs";
              uses ncs_rpc_notif_OSPF-STAT-ATTRIBUTES;
            }
          }
        }
      }
    }
  }
  augment "/ncs:devices/ncs:device-group/ncs:ned-id/ncs:rpc" {
    container rpc-clear-ospf-instance-vrf {
      tailf:ncs-device-type "netconf";
      tailf:display-when "/ncs:devices/ncs:device[ncs:name=current()/../../../ncs:member]/ncs:module[ncs:name='Cisco-IOS-XR-ipv4-ospf-act']";
      tailf:action clear-ospf-instance-vrf {
        tailf:actionpoint ncsproxy {
          tailf:internal;
        }
        description
          "Clear one or more non-default OSPF VRFs in process";
        input {
          container instance {
            description
              "OSPF instance name";
            leaf instance-identifier {
              type string;
              mandatory true;
              description
                "OSPF process instance identifier";
            }
            container vrf {
              description
                "Clear one or more non-default OSPF VRFs in process";
              leaf vrf-name {
                type string;
                description
                  "OSPF VRF name";
              }
              uses ncs_rpc_notif_OSPF-STAT-ATTRIBUTES;
            }
            container all {
              description
                "Clear all non-default OSPF VRFs";
              uses ncs_rpc_notif_OSPF-STAT-ATTRIBUTES;
            }
            container all-inclusive {
              description
                "Clear all non-default and default OSPF VRFs";
              uses ncs_rpc_notif_OSPF-STAT-ATTRIBUTES;
            }
          }
        }
      }
    }
  }
  augment "/ncs:devices/ncs:device/ncs:rpc" {
    container rpc-clear-ospf-process {
      tailf:ncs-device-type "netconf";
      tailf:display-when "not(../../ncs:module) or ../../ncs:module[ncs:name='Cisco-IOS-XR-ipv4-ospf-act']";
      tailf:action clear-ospf-process {
        tailf:actionpoint ncsproxy {
          tailf:internal;
        }
        description
          "Clear (reset) OSPF process";
        input {
          container instance {
            description
              "Clear data from OSPF instance";
            leaf instance-identifier {
              type string;
              description
                "OSPF process instance identifier";
            }
          }
          leaf process {
            type empty;
            mandatory true;
            description
              "Reset OSPF process";
          }
        }
      }
    }
  }
  augment "/ncs:devices/ncs:device-group/ncs:ned-id/ncs:rpc" {
    container rpc-clear-ospf-process {
      tailf:ncs-device-type "netconf";
      tailf:display-when "/ncs:devices/ncs:device[ncs:name=current()/../../../ncs:member]/ncs:module[ncs:name='Cisco-IOS-XR-ipv4-ospf-act']";
      tailf:action clear-ospf-process {
        tailf:actionpoint ncsproxy {
          tailf:internal;
        }
        description
          "Clear (reset) OSPF process";
        input {
          container instance {
            description
              "Clear data from OSPF instance";
            leaf instance-identifier {
              type string;
              description
                "OSPF process instance identifier";
            }
          }
          leaf process {
            type empty;
            mandatory true;
            description
              "Reset OSPF process";
          }
        }
      }
    }
  }
  augment "/ncs:devices/ncs:device/ncs:rpc" {
    container rpc-clear-ospf-statistics-interface {
      tailf:ncs-device-type "netconf";
      tailf:display-when "not(../../ncs:module) or ../../ncs:module[ncs:name='Cisco-IOS-XR-ipv4-ospf-act']";
      tailf:action clear-ospf-statistics-interface {
        tailf:actionpoint ncsproxy {
          tailf:internal;
        }
        description
          "Clear OSPF interface statistics";
        input {
          container instance {
            description
              "Clear data from OSPF instance";
            leaf instance-identifier {
              type string;
              description
                "OSPF process instance identifier";
            }
          }
          container interface {
            description
              "OSPF interface";
            leaf interface-name {
              type xr:ncs_rpc_notif_Interface-name;
              description
                "OSPF interface statistics";
            }
          }
        }
      }
    }
  }
  augment "/ncs:devices/ncs:device-group/ncs:ned-id/ncs:rpc" {
    container rpc-clear-ospf-statistics-interface {
      tailf:ncs-device-type "netconf";
      tailf:display-when "/ncs:devices/ncs:device[ncs:name=current()/../../../ncs:member]/ncs:module[ncs:name='Cisco-IOS-XR-ipv4-ospf-act']";
      tailf:action clear-ospf-statistics-interface {
        tailf:actionpoint ncsproxy {
          tailf:internal;
        }
        description
          "Clear OSPF interface statistics";
        input {
          container instance {
            description
              "Clear data from OSPF instance";
            leaf instance-identifier {
              type string;
              description
                "OSPF process instance identifier";
            }
          }
          container interface {
            description
              "OSPF interface";
            leaf interface-name {
              type xr:ncs_rpc_notif_Interface-name;
              description
                "OSPF interface statistics";
            }
          }
        }
      }
    }
  }
  augment "/ncs:devices/ncs:device/ncs:rpc" {
    container rpc-clear-ospf-statistics-neighbor {
      tailf:ncs-device-type "netconf";
      tailf:display-when "not(../../ncs:module) or ../../ncs:module[ncs:name='Cisco-IOS-XR-ipv4-ospf-act']";
      tailf:action clear-ospf-statistics-neighbor {
        tailf:actionpoint ncsproxy {
          tailf:internal;
        }
        description
          "Clear OSPF neighbor statistics per interface or neighbor id";
        input {
          container instance {
            description
              "Clear data from OSPF instance";
            leaf instance-identifier {
              type string;
              description
                "OSPF process instance identifier";
            }
          }
          container neighbor {
            description
              "OSPF neighbor";
            leaf neighbor-id {
              type inet:ipv4-address;
              description
                "Neighbor ID";
            }
            leaf interface-name {
              type xr:ncs_rpc_notif_Interface-name;
              description
                "Interface";
            }
          }
        }
      }
    }
  }
  augment "/ncs:devices/ncs:device-group/ncs:ned-id/ncs:rpc" {
    container rpc-clear-ospf-statistics-neighbor {
      tailf:ncs-device-type "netconf";
      tailf:display-when "/ncs:devices/ncs:device[ncs:name=current()/../../../ncs:member]/ncs:module[ncs:name='Cisco-IOS-XR-ipv4-ospf-act']";
      tailf:action clear-ospf-statistics-neighbor {
        tailf:actionpoint ncsproxy {
          tailf:internal;
        }
        description
          "Clear OSPF neighbor statistics per interface or neighbor id";
        input {
          container instance {
            description
              "Clear data from OSPF instance";
            leaf instance-identifier {
              type string;
              description
                "OSPF process instance identifier";
            }
          }
          container neighbor {
            description
              "OSPF neighbor";
            leaf neighbor-id {
              type inet:ipv4-address;
              description
                "Neighbor ID";
            }
            leaf interface-name {
              type xr:ncs_rpc_notif_Interface-name;
              description
                "Interface";
            }
          }
        }
      }
    }
  }
  augment "/ncs:devices/ncs:device/ncs:rpc" {
    container rpc-clear-ospf-statistics {
      tailf:ncs-device-type "netconf";
      tailf:display-when "not(../../ncs:module) or ../../ncs:module[ncs:name='Cisco-IOS-XR-ipv4-ospf-act']";
      tailf:action clear-ospf-statistics {
        tailf:actionpoint ncsproxy {
          tailf:internal;
        }
        description
          "Clear OSPF counters and statistics";
        input {
          container instance {
            description
              "Clear data from OSPF instance";
            leaf instance-identifier {
              type string;
              description
                "OSPF process instance identifier";
            }
          }
          leaf all {
            type empty;
            description
              "All OSPF counters and statistics";
          }
          leaf message-queue {
            type empty;
            description
              "Message-queue statistics";
          }
          leaf spf {
            type empty;
            description
              "SPF statistics";
          }
          leaf neighbor {
            type empty;
            description
              "Neighbor statistics per neighbor id";
          }
          leaf interface-name {
            type empty;
            description
              "OSPF interface statistics";
          }
        }
      }
    }
  }
  augment "/ncs:devices/ncs:device-group/ncs:ned-id/ncs:rpc" {
    container rpc-clear-ospf-statistics {
      tailf:ncs-device-type "netconf";
      tailf:display-when "/ncs:devices/ncs:device[ncs:name=current()/../../../ncs:member]/ncs:module[ncs:name='Cisco-IOS-XR-ipv4-ospf-act']";
      tailf:action clear-ospf-statistics {
        tailf:actionpoint ncsproxy {
          tailf:internal;
        }
        description
          "Clear OSPF counters and statistics";
        input {
          container instance {
            description
              "Clear data from OSPF instance";
            leaf instance-identifier {
              type string;
              description
                "OSPF process instance identifier";
            }
          }
          leaf all {
            type empty;
            description
              "All OSPF counters and statistics";
          }
          leaf message-queue {
            type empty;
            description
              "Message-queue statistics";
          }
          leaf spf {
            type empty;
            description
              "SPF statistics";
          }
          leaf neighbor {
            type empty;
            description
              "Neighbor statistics per neighbor id";
          }
          leaf interface-name {
            type empty;
            description
              "OSPF interface statistics";
          }
        }
      }
    }
  }
  augment "/ncs:devices/ncs:device/ncs:rpc" {
    container rpc-clear-ospf-redistribution {
      tailf:ncs-device-type "netconf";
      tailf:display-when "not(../../ncs:module) or ../../ncs:module[ncs:name='Cisco-IOS-XR-ipv4-ospf-act']";
      tailf:action clear-ospf-redistribution {
        tailf:actionpoint ncsproxy {
          tailf:internal;
        }
        description
          "Clear OSPF route redistribution";
        input {
          container instance {
            description
              "Clear data from OSPF instance";
            leaf instance-identifier {
              type string;
              description
                "OSPF process instance identifier";
            }
          }
          leaf redistribution {
            type empty;
            mandatory true;
            description
              "Clear OSPF route redistribution";
          }
        }
      }
    }
  }
  augment "/ncs:devices/ncs:device-group/ncs:ned-id/ncs:rpc" {
    container rpc-clear-ospf-redistribution {
      tailf:ncs-device-type "netconf";
      tailf:display-when "/ncs:devices/ncs:device[ncs:name=current()/../../../ncs:member]/ncs:module[ncs:name='Cisco-IOS-XR-ipv4-ospf-act']";
      tailf:action clear-ospf-redistribution {
        tailf:actionpoint ncsproxy {
          tailf:internal;
        }
        description
          "Clear OSPF route redistribution";
        input {
          container instance {
            description
              "Clear data from OSPF instance";
            leaf instance-identifier {
              type string;
              description
                "OSPF process instance identifier";
            }
          }
          leaf redistribution {
            type empty;
            mandatory true;
            description
              "Clear OSPF route redistribution";
          }
        }
      }
    }
  }
  augment "/ncs:devices/ncs:device/ncs:rpc" {
    container rpc-clear-ospf-routes {
      tailf:ncs-device-type "netconf";
      tailf:display-when "not(../../ncs:module) or ../../ncs:module[ncs:name='Cisco-IOS-XR-ipv4-ospf-act']";
      tailf:action clear-ospf-routes {
        tailf:actionpoint ncsproxy {
          tailf:internal;
        }
        description
          "Clear OSPF route table";
        input {
          container instance {
            description
              "Clear data from OSPF instance";
            leaf instance-identifier {
              type string;
              description
                "OSPF process instance identifier";
            }
          }
          leaf route {
            type empty;
            mandatory true;
            description
              "Clear OSPF route table";
          }
        }
      }
    }
  }
  augment "/ncs:devices/ncs:device-group/ncs:ned-id/ncs:rpc" {
    container rpc-clear-ospf-routes {
      tailf:ncs-device-type "netconf";
      tailf:display-when "/ncs:devices/ncs:device[ncs:name=current()/../../../ncs:member]/ncs:module[ncs:name='Cisco-IOS-XR-ipv4-ospf-act']";
      tailf:action clear-ospf-routes {
        tailf:actionpoint ncsproxy {
          tailf:internal;
        }
        description
          "Clear OSPF route table";
        input {
          container instance {
            description
              "Clear data from OSPF instance";
            leaf instance-identifier {
              type string;
              description
                "OSPF process instance identifier";
            }
          }
          leaf route {
            type empty;
            mandatory true;
            description
              "Clear OSPF route table";
          }
        }
      }
    }
  }
}

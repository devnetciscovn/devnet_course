module Cisco-IOS-XR-optics-driver-quad-cfg {
  // Generated by yanger -t ncs
  tailf:mount-id "cisco-iosxr-nc-7.3:cisco-iosxr-nc-7.3";
  tailf:ncs-device-type "netconf";

  namespace "http://cisco.com/ns/yang/Cisco-IOS-XR-optics-driver-quad-cfg";
  prefix optics-driver-quad-cfg;

  import cisco-semver {
    prefix semver;
  }
  import Cisco-IOS-XR-config-mda-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-driver-quad package configuration.

     This YANG module augments the
       Cisco-IOS-XR-config-mda-cfg
     module with configuration data.

     Copyright (c) 2013-2020 by Cisco Systems, Inc.
     All rights reserved.";

  revision 2020-06-17 {
    description
      "Changed type of NodeName from String to StringNodeID, added pathformat of quad as decimal in schema file";
    semver:module-version "3.0.0";
  }
  revision 2019-04-05 {
    description
      "Establish semantic version baseline.";
    semver:module-version "1.0.1";
  }
  revision 2018-07-21 {
    description
      "Schema added.";
  }
  revision 2015-11-09 {
    description
      "IOS XR 6.0 revision.";
  }

  grouping ncs_template_QUAD-CONFIG-TABLE {
    description
      "Common node of active-node, preconfigured-node";
    container quad-configs {
      description
        "quad configuration";
      list quad-config {
        // NCS patched for predictable order
        ordered-by user;
        key "id1";
        description
          "none";
        container mode {
          description
            "select mode 10g or 25g for a quad(group of 4
             ports).";
          leaf speed {
            type string;
            description
              "speed 10g or 25g";
          }
        }
        leaf id1 {
          type string;
          description
            "none";
        }
      }
    }
  }

  grouping ncs_rpc_notif_QUAD-CONFIG-TABLE {
    description
      "Common node of active-node, preconfigured-node";
    container quad-configs {
      description
        "quad configuration";
      list quad-config {
        key "id1";
        description
          "none";
        container mode {
          description
            "select mode 10g or 25g for a quad(group of 4
             ports).";
          leaf speed {
            type string;
            description
              "speed 10g or 25g";
          }
        }
        leaf id1 {
          type uint32;
          description
            "none";
        }
      }
    }
  }

  grouping live_ncs_QUAD-CONFIG-TABLE {
    description
      "Common node of active-node, preconfigured-node";
    container quad-configs {
      description
        "quad configuration";
      list quad-config {
        key "id1";
        description
          "none";
        container mode {
          description
            "select mode 10g or 25g for a quad(group of 4
             ports).";
          leaf speed {
            type string;
            description
              "speed 10g or 25g";
          }
        }
        leaf id1 {
          type uint32;
          description
            "none";
        }
      }
    }
  }

  grouping QUAD-CONFIG-TABLE {
    description
      "Common node of active-node, preconfigured-node";
    container quad-configs {
      description
        "quad configuration";
      list quad-config {
        key "id1";
        description
          "none";
        container mode {
          description
            "select mode 10g or 25g for a quad(group of 4
             ports).";
          leaf speed {
            type string;
            description
              "speed 10g or 25g";
          }
        }
        leaf id1 {
          type uint32;
          description
            "none";
        }
      }
    }
  }

  augment "/ncs:devices/ncs:template/ncs:ned-id/ncs:config/a1:preconfigured-nodes/a1:preconfigured-node" {
    description
      "This augment extends the configuration data of
       'Cisco-IOS-XR-config-mda-cfg'";
    uses ncs_template_QUAD-CONFIG-TABLE;
  }
  augment "/ncs:devices/ncs:device/ncs:live-status/a1:preconfigured-nodes/a1:preconfigured-node" {
    description
      "This augment extends the configuration data of
       'Cisco-IOS-XR-config-mda-cfg'";
    uses live_ncs_QUAD-CONFIG-TABLE {
      refine quad-configs {
        tailf:ncs-device-type "netconf";
        tailf:display-when "not(../../../../ncs:module) or ../../../../ncs:module[ncs:name='Cisco-IOS-XR-optics-driver-quad-cfg'] or (../../../../ncs:live-status-protocol[not(ncs:capability)]) or (../../../../ncs:live-status-protocol/ncs:capability/ncs:module[.='Cisco-IOS-XR-optics-driver-quad-cfg'])";
      }
    }
  }
  augment "/ncs:devices/ncs:device/ncs:config/a1:preconfigured-nodes/a1:preconfigured-node" {
    description
      "This augment extends the configuration data of
       'Cisco-IOS-XR-config-mda-cfg'";
    uses QUAD-CONFIG-TABLE {
      refine quad-configs {
        tailf:ncs-device-type "netconf";
        tailf:display-when "not(../../../../ncs:module) or ../../../../ncs:module[ncs:name='Cisco-IOS-XR-optics-driver-quad-cfg']";
      }
    }
  }
  augment "/ncs:devices/ncs:template/ncs:ned-id/ncs:config/a1:active-nodes/a1:active-node" {
    description
      "This augment extends the configuration data of
       'Cisco-IOS-XR-config-mda-cfg'";
    uses ncs_template_QUAD-CONFIG-TABLE;
  }
  augment "/ncs:devices/ncs:device/ncs:live-status/a1:active-nodes/a1:active-node" {
    description
      "This augment extends the configuration data of
       'Cisco-IOS-XR-config-mda-cfg'";
    uses live_ncs_QUAD-CONFIG-TABLE {
      refine quad-configs {
        tailf:ncs-device-type "netconf";
        tailf:display-when "not(../../../../ncs:module) or ../../../../ncs:module[ncs:name='Cisco-IOS-XR-optics-driver-quad-cfg'] or (../../../../ncs:live-status-protocol[not(ncs:capability)]) or (../../../../ncs:live-status-protocol/ncs:capability/ncs:module[.='Cisco-IOS-XR-optics-driver-quad-cfg'])";
      }
    }
  }
  augment "/ncs:devices/ncs:device/ncs:config/a1:active-nodes/a1:active-node" {
    description
      "This augment extends the configuration data of
       'Cisco-IOS-XR-config-mda-cfg'";
    uses QUAD-CONFIG-TABLE {
      refine quad-configs {
        tailf:ncs-device-type "netconf";
        tailf:display-when "not(../../../../ncs:module) or ../../../../ncs:module[ncs:name='Cisco-IOS-XR-optics-driver-quad-cfg']";
      }
    }
  }
}

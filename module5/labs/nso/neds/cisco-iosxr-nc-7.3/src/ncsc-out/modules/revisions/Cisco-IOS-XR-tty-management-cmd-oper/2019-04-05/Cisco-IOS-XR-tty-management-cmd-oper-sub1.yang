submodule Cisco-IOS-XR-tty-management-cmd-oper-sub1 {
  // Generated by yanger -t ncs
  tailf:mount-id "cisco-iosxr-nc-7.3:cisco-iosxr-nc-7.3";

  belongs-to Cisco-IOS-XR-tty-management-cmd-oper {
    prefix Cisco-IOS-XR-tty-management-cmd-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tty-management-cmd package operational data.

     Copyright (c) 2013-2019 by Cisco Systems, Inc.
     All rights reserved.";

  revision 2019-04-05 {
    description
      "Establish semantic version baseline.";
    semver:module-version "1.0.1";
  }
  revision 2019-02-25 {
    description
      "Fixed unconstrained data type issues";
  }
  revision 2017-09-07 {
    description
      "Fixed type translation error.";
  }
  revision 2015-11-09 {
    description
      "IOS XR 6.0 revision.";
  }

  grouping ncs_template_SHOWUSERS-ENTRY {
    description
      " Per Line Information";
    leaf line {
      type string;
      description
        "Line Number";
    }
    leaf user {
      type string;
      description
        "User Name";
    }
    leaf service {
      type string;
      description
        "Service Name";
    }
    leaf conns {
      type string;
      description
        "No. of Connections";
    }
    leaf idle-string {
      type string;
      description
        "Idle Time";
    }
    leaf location {
      type string;
      description
        "IP address of remote login host";
    }
  }

  grouping ncs_rpc_notif_SHOWUSERS-ENTRY {
    description
      " Per Line Information";
    leaf line {
      type string;
      description
        "Line Number";
    }
    leaf user {
      type string;
      description
        "User Name";
    }
    leaf service {
      type string;
      description
        "Service Name";
    }
    leaf conns {
      type string;
      description
        "No. of Connections";
    }
    leaf idle-string {
      type string;
      description
        "Idle Time";
    }
    leaf location {
      type string;
      description
        "IP address of remote login host";
    }
  }

  grouping live_ncs_SHOWUSERS-ENTRY {
    description
      " Per Line Information";
    leaf line {
      type string;
      description
        "Line Number";
    }
    leaf user {
      type string;
      description
        "User Name";
    }
    leaf service {
      type string;
      description
        "Service Name";
    }
    leaf conns {
      type string;
      description
        "No. of Connections";
    }
    leaf idle-string {
      type string;
      description
        "Idle Time";
    }
    leaf location {
      type string;
      description
        "IP address of remote login host";
    }
  }

  grouping SHOWUSERS-ENTRY {
    description
      " Per Line Information";
    leaf line {
      type string;
      description
        "Line Number";
    }
    leaf user {
      type string;
      description
        "User Name";
    }
    leaf service {
      type string;
      description
        "Service Name";
    }
    leaf conns {
      type string;
      description
        "No. of Connections";
    }
    leaf idle-string {
      type string;
      description
        "Idle Time";
    }
    leaf location {
      type string;
      description
        "IP address of remote login host";
    }
  }
}

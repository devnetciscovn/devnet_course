submodule Cisco-IOS-XR-cnbng-nal-oper-sub2 {
  // Generated by yanger -t ncs
  tailf:mount-id "cisco-iosxr-nc-7.3:cisco-iosxr-nc-7.3";

  belongs-to Cisco-IOS-XR-cnbng-nal-oper {
    prefix Cisco-IOS-XR-cnbng-nal-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR cnbng-nal package operational data.

     Copyright (c) 2013-2021 by Cisco Systems, Inc.
     All rights reserved.";

  revision 2021-06-20 {
    description
      "Added new path for getting subscriber summary based on VRF name.";
    semver:module-version "1.1.0";
  }
  revision 2020-12-13 {
    description
      "NAL SVM service final timestamp.";
    semver:module-version "1.0.0";
  }
  revision 2020-12-10 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-19 {
    description
      "Added schema support for cnbng-nal filter oper commands.";
  }
  revision 2020-10-08 {
    description
      "Moved counter and AIPC stats to new bag files.";
  }
  revision 2020-10-05 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  grouping ncs_template_NAL-MAIN-EDM-HISTOGRAM-TABLE {
    description
      "NAL MAIN EDM HISTOGRAM TABLE";
    leaf api-name {
      type string;
      description
        "API name";
    }
    leaf req-count {
      type string;
      description
        "Request count";
    }
    leaf avg-time-sec {
      type string;
      units "second";
      description
        "Average time seconds";
    }
    leaf avg-time-nsec {
      type string;
      units "nanosecond";
      description
        "Average time nano-seconds";
    }
    leaf min-time-sec {
      type string;
      units "second";
      description
        "Minimum time seconds";
    }
    leaf min-time-nsec {
      type string;
      units "nanosecond";
      description
        "Minimum time nano-seconds";
    }
    leaf max-time-sec {
      type string;
      units "second";
      description
        "Maximum time seconds";
    }
    leaf max-time-nsec {
      type string;
      units "nanosecond";
      description
        "Maximum time nano-seconds";
    }
    leaf-list hist-array {
      // NCS patched for predictable order
      ordered-by user;
      type string;
      // NCS drop max-elements statement
      description
        "Histogram counters";
    }
  }

  grouping ncs_template_NAL-MAIN-EDM-32B-COUNTER {
    description
      "NAL MAIN EDM 32B COUNTER";
    leaf counter-name {
      type string;
      description
        "Counter name";
    }
    leaf counter {
      type string;
      description
        "Counter value";
    }
  }

  grouping ncs_template_NAL-MAIN-EDM-NAL-COUNTERS {
    description
      "NAL counter statistics";
    leaf-list spa-lib-counter {
      // NCS patched for predictable order
      ordered-by user;
      type string;
      description
        "SPA LIB Counters";
    }
    list subscriber-stat {
      // NCS patched for predictable order
      ordered-by user;
      // NCS drop max-elements statement
      description
        "Subscriber statistics";
      uses ncs_template_NAL-MAIN-EDM-32B-COUNTER;
    }
    list error-stat {
      // NCS patched for predictable order
      ordered-by user;
      // NCS drop max-elements statement
      description
        "Error statistics";
      uses ncs_template_NAL-MAIN-EDM-32B-COUNTER;
    }
    list acc-stat {
      // NCS patched for predictable order
      ordered-by user;
      // NCS drop max-elements statement
      description
        "Accounting statistics";
      uses ncs_template_NAL-MAIN-EDM-32B-COUNTER;
    }
    list svm-stat {
      // NCS patched for predictable order
      ordered-by user;
      // NCS drop max-elements statement
      description
        "SVM statistics";
      uses ncs_template_NAL-MAIN-EDM-32B-COUNTER;
    }
    list spa-stat {
      // NCS patched for predictable order
      ordered-by user;
      // NCS drop max-elements statement
      description
        "SPA statistics";
      uses ncs_template_NAL-MAIN-EDM-32B-COUNTER;
    }
    list hist-stat {
      // NCS patched for predictable order
      ordered-by user;
      // NCS drop max-elements statement
      description
        "Histogram statistics";
      uses ncs_template_NAL-MAIN-EDM-HISTOGRAM-TABLE;
    }
    list cp-recon-stat {
      // NCS patched for predictable order
      ordered-by user;
      // NCS drop max-elements statement
      description
        "CP Recon statistics";
      uses ncs_template_NAL-MAIN-EDM-32B-COUNTER;
    }
    list pkt-stat {
      // NCS patched for predictable order
      ordered-by user;
      // NCS drop max-elements statement
      description
        "Packet statistics";
      uses ncs_template_NAL-MAIN-EDM-32B-COUNTER;
    }
  }

  grouping ncs_rpc_notif_NAL-MAIN-EDM-HISTOGRAM-TABLE {
    description
      "NAL MAIN EDM HISTOGRAM TABLE";
    leaf api-name {
      type string {
        length "0..33";
      }
      description
        "API name";
    }
    leaf req-count {
      type uint32;
      description
        "Request count";
    }
    leaf avg-time-sec {
      type uint32;
      units "second";
      description
        "Average time seconds";
    }
    leaf avg-time-nsec {
      type uint32;
      units "nanosecond";
      description
        "Average time nano-seconds";
    }
    leaf min-time-sec {
      type uint32;
      units "second";
      description
        "Minimum time seconds";
    }
    leaf min-time-nsec {
      type uint32;
      units "nanosecond";
      description
        "Minimum time nano-seconds";
    }
    leaf max-time-sec {
      type uint32;
      units "second";
      description
        "Maximum time seconds";
    }
    leaf max-time-nsec {
      type uint32;
      units "nanosecond";
      description
        "Maximum time nano-seconds";
    }
    leaf-list hist-array {
      type uint32;
      max-elements 9;
      description
        "Histogram counters";
    }
  }

  grouping ncs_rpc_notif_NAL-MAIN-EDM-32B-COUNTER {
    description
      "NAL MAIN EDM 32B COUNTER";
    leaf counter-name {
      type string {
        length "0..33";
      }
      description
        "Counter name";
    }
    leaf counter {
      type uint32;
      description
        "Counter value";
    }
  }

  grouping ncs_rpc_notif_NAL-MAIN-EDM-NAL-COUNTERS {
    description
      "NAL counter statistics";
    leaf-list spa-lib-counter {
      type uint8;
      description
        "SPA LIB Counters";
    }
    list subscriber-stat {
      max-elements 150;
      description
        "Subscriber statistics";
      uses ncs_rpc_notif_NAL-MAIN-EDM-32B-COUNTER;
    }
    list error-stat {
      max-elements 119;
      description
        "Error statistics";
      uses ncs_rpc_notif_NAL-MAIN-EDM-32B-COUNTER;
    }
    list acc-stat {
      max-elements 39;
      description
        "Accounting statistics";
      uses ncs_rpc_notif_NAL-MAIN-EDM-32B-COUNTER;
    }
    list svm-stat {
      max-elements 112;
      description
        "SVM statistics";
      uses ncs_rpc_notif_NAL-MAIN-EDM-32B-COUNTER;
    }
    list spa-stat {
      max-elements 86;
      description
        "SPA statistics";
      uses ncs_rpc_notif_NAL-MAIN-EDM-32B-COUNTER;
    }
    list hist-stat {
      max-elements 43;
      description
        "Histogram statistics";
      uses ncs_rpc_notif_NAL-MAIN-EDM-HISTOGRAM-TABLE;
    }
    list cp-recon-stat {
      max-elements 92;
      description
        "CP Recon statistics";
      uses ncs_rpc_notif_NAL-MAIN-EDM-32B-COUNTER;
    }
    list pkt-stat {
      max-elements 26;
      description
        "Packet statistics";
      uses ncs_rpc_notif_NAL-MAIN-EDM-32B-COUNTER;
    }
  }

  grouping live_ncs_NAL-MAIN-EDM-HISTOGRAM-TABLE {
    description
      "NAL MAIN EDM HISTOGRAM TABLE";
    leaf api-name {
      type string {
        length "0..33";
      }
      description
        "API name";
    }
    leaf req-count {
      type uint32;
      description
        "Request count";
    }
    leaf avg-time-sec {
      type uint32;
      units "second";
      description
        "Average time seconds";
    }
    leaf avg-time-nsec {
      type uint32;
      units "nanosecond";
      description
        "Average time nano-seconds";
    }
    leaf min-time-sec {
      type uint32;
      units "second";
      description
        "Minimum time seconds";
    }
    leaf min-time-nsec {
      type uint32;
      units "nanosecond";
      description
        "Minimum time nano-seconds";
    }
    leaf max-time-sec {
      type uint32;
      units "second";
      description
        "Maximum time seconds";
    }
    leaf max-time-nsec {
      type uint32;
      units "nanosecond";
      description
        "Maximum time nano-seconds";
    }
    leaf-list hist-array {
      type uint32;
      // NCS drop max-elements statement
      description
        "Histogram counters";
    }
  }

  grouping live_ncs_NAL-MAIN-EDM-32B-COUNTER {
    description
      "NAL MAIN EDM 32B COUNTER";
    leaf counter-name {
      type string {
        length "0..33";
      }
      description
        "Counter name";
    }
    leaf counter {
      type uint32;
      description
        "Counter value";
    }
  }

  grouping live_ncs_NAL-MAIN-EDM-NAL-COUNTERS {
    description
      "NAL counter statistics";
    leaf-list spa-lib-counter {
      type uint8;
      description
        "SPA LIB Counters";
    }
    list subscriber-stat {
      // NCS drop max-elements statement
      description
        "Subscriber statistics";
      uses live_ncs_NAL-MAIN-EDM-32B-COUNTER;
    }
    list error-stat {
      // NCS drop max-elements statement
      description
        "Error statistics";
      uses live_ncs_NAL-MAIN-EDM-32B-COUNTER;
    }
    list acc-stat {
      // NCS drop max-elements statement
      description
        "Accounting statistics";
      uses live_ncs_NAL-MAIN-EDM-32B-COUNTER;
    }
    list svm-stat {
      // NCS drop max-elements statement
      description
        "SVM statistics";
      uses live_ncs_NAL-MAIN-EDM-32B-COUNTER;
    }
    list spa-stat {
      // NCS drop max-elements statement
      description
        "SPA statistics";
      uses live_ncs_NAL-MAIN-EDM-32B-COUNTER;
    }
    list hist-stat {
      // NCS drop max-elements statement
      description
        "Histogram statistics";
      uses live_ncs_NAL-MAIN-EDM-HISTOGRAM-TABLE;
    }
    list cp-recon-stat {
      // NCS drop max-elements statement
      description
        "CP Recon statistics";
      uses live_ncs_NAL-MAIN-EDM-32B-COUNTER;
    }
    list pkt-stat {
      // NCS drop max-elements statement
      description
        "Packet statistics";
      uses live_ncs_NAL-MAIN-EDM-32B-COUNTER;
    }
  }

  grouping NAL-MAIN-EDM-HISTOGRAM-TABLE {
    description
      "NAL MAIN EDM HISTOGRAM TABLE";
    leaf api-name {
      type string {
        length "0..33";
      }
      description
        "API name";
    }
    leaf req-count {
      type uint32;
      description
        "Request count";
    }
    leaf avg-time-sec {
      type uint32;
      units "second";
      description
        "Average time seconds";
    }
    leaf avg-time-nsec {
      type uint32;
      units "nanosecond";
      description
        "Average time nano-seconds";
    }
    leaf min-time-sec {
      type uint32;
      units "second";
      description
        "Minimum time seconds";
    }
    leaf min-time-nsec {
      type uint32;
      units "nanosecond";
      description
        "Minimum time nano-seconds";
    }
    leaf max-time-sec {
      type uint32;
      units "second";
      description
        "Maximum time seconds";
    }
    leaf max-time-nsec {
      type uint32;
      units "nanosecond";
      description
        "Maximum time nano-seconds";
    }
    leaf-list hist-array {
      type uint32;
      max-elements 9;
      description
        "Histogram counters";
    }
  }

  grouping NAL-MAIN-EDM-32B-COUNTER {
    description
      "NAL MAIN EDM 32B COUNTER";
    leaf counter-name {
      type string {
        length "0..33";
      }
      description
        "Counter name";
    }
    leaf counter {
      type uint32;
      description
        "Counter value";
    }
  }

  grouping NAL-MAIN-EDM-NAL-COUNTERS {
    description
      "NAL counter statistics";
    leaf-list spa-lib-counter {
      type uint8;
      description
        "SPA LIB Counters";
    }
    list subscriber-stat {
      max-elements 150;
      description
        "Subscriber statistics";
      uses NAL-MAIN-EDM-32B-COUNTER;
    }
    list error-stat {
      max-elements 119;
      description
        "Error statistics";
      uses NAL-MAIN-EDM-32B-COUNTER;
    }
    list acc-stat {
      max-elements 39;
      description
        "Accounting statistics";
      uses NAL-MAIN-EDM-32B-COUNTER;
    }
    list svm-stat {
      max-elements 112;
      description
        "SVM statistics";
      uses NAL-MAIN-EDM-32B-COUNTER;
    }
    list spa-stat {
      max-elements 86;
      description
        "SPA statistics";
      uses NAL-MAIN-EDM-32B-COUNTER;
    }
    list hist-stat {
      max-elements 43;
      description
        "Histogram statistics";
      uses NAL-MAIN-EDM-HISTOGRAM-TABLE;
    }
    list cp-recon-stat {
      max-elements 92;
      description
        "CP Recon statistics";
      uses NAL-MAIN-EDM-32B-COUNTER;
    }
    list pkt-stat {
      max-elements 26;
      description
        "Packet statistics";
      uses NAL-MAIN-EDM-32B-COUNTER;
    }
  }
}

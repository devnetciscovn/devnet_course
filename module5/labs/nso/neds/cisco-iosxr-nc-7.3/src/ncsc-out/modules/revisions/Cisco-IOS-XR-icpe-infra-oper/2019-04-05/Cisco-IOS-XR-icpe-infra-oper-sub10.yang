submodule Cisco-IOS-XR-icpe-infra-oper-sub10 {
  // Generated by yanger -t ncs
  tailf:mount-id "cisco-iosxr-nc-7.3:cisco-iosxr-nc-7.3";

  belongs-to Cisco-IOS-XR-icpe-infra-oper {
    prefix Cisco-IOS-XR-icpe-infra-oper;
  }

  import cisco-semver {
    prefix semver;
  }
  include Cisco-IOS-XR-icpe-infra-oper-sub4 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR icpe-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Icpe-install-sat-state {
    type string;
    description
      "Icpe install sat state";
  }

  typedef ncs_rpc_notif_Icpe-install-sat-state {
    type enumeration {
      enum "icpe-install-sat-state-unknown" {
        description
          "Unknown";
      }
      enum "icpe-install-sat-state-not-initiat-ed" {
        description
          "Not initiated";
      }
      enum "icpe-install-sat-state-transferring" {
        description
          "Transferring";
      }
      enum "icpe-install-sat-state-activating" {
        description
          "Activating";
      }
      enum "icpe-install-sat-state-updating" {
        description
          "Updating";
      }
      enum "icpe-install-sat-state-replacing" {
        description
          "Replacing";
      }
      enum "icpe-install-sat-state-deactivating" {
        description
          "Deactivating";
      }
      enum "icpe-install-sat-state-removing" {
        description
          "Removing";
      }
      enum "icpe-install-sat-state-success" {
        description
          "Success";
      }
      enum "icpe-install-sat-state-failure" {
        description
          "Failure";
      }
      enum "icpe-install-sat-state-multiple-ops" {
        description
          "Multiple ops";
      }
      enum "icpe-install-sat-state-aborted" {
        description
          "Aborted";
      }
      enum "icpe-install-sat-state-protocol-version" {
        description
          "Protocol version";
      }
      enum "icpe-install-sat-state-pkg-not-present" {
        description
          "Pkg not present";
      }
      enum "icpe-install-sat-state-no-image" {
        description
          "No image";
      }
      enum "icpe-install-sat-state-no-such-file" {
        description
          "No such file";
      }
      enum "icpe-install-sat-state-sat-uncfgd" {
        description
          "Sat uncfgd";
      }
      enum "icpe-install-sat-state-processing" {
        description
          "Processing";
      }
    }
    description
      "Icpe install sat state";
  }

  typedef live_ncs_Icpe-install-sat-state {
    type enumeration {
      enum "icpe-install-sat-state-unknown" {
        description
          "Unknown";
      }
      enum "icpe-install-sat-state-not-initiat-ed" {
        description
          "Not initiated";
      }
      enum "icpe-install-sat-state-transferring" {
        description
          "Transferring";
      }
      enum "icpe-install-sat-state-activating" {
        description
          "Activating";
      }
      enum "icpe-install-sat-state-updating" {
        description
          "Updating";
      }
      enum "icpe-install-sat-state-replacing" {
        description
          "Replacing";
      }
      enum "icpe-install-sat-state-deactivating" {
        description
          "Deactivating";
      }
      enum "icpe-install-sat-state-removing" {
        description
          "Removing";
      }
      enum "icpe-install-sat-state-success" {
        description
          "Success";
      }
      enum "icpe-install-sat-state-failure" {
        description
          "Failure";
      }
      enum "icpe-install-sat-state-multiple-ops" {
        description
          "Multiple ops";
      }
      enum "icpe-install-sat-state-aborted" {
        description
          "Aborted";
      }
      enum "icpe-install-sat-state-protocol-version" {
        description
          "Protocol version";
      }
      enum "icpe-install-sat-state-pkg-not-present" {
        description
          "Pkg not present";
      }
      enum "icpe-install-sat-state-no-image" {
        description
          "No image";
      }
      enum "icpe-install-sat-state-no-such-file" {
        description
          "No such file";
      }
      enum "icpe-install-sat-state-sat-uncfgd" {
        description
          "Sat uncfgd";
      }
      enum "icpe-install-sat-state-processing" {
        description
          "Processing";
      }
    }
    description
      "Icpe install sat state";
  }

  typedef Icpe-install-sat-state {
    type enumeration {
      enum "icpe-install-sat-state-unknown" {
        description
          "Unknown";
      }
      enum "icpe-install-sat-state-not-initiat-ed" {
        description
          "Not initiated";
      }
      enum "icpe-install-sat-state-transferring" {
        description
          "Transferring";
      }
      enum "icpe-install-sat-state-activating" {
        description
          "Activating";
      }
      enum "icpe-install-sat-state-updating" {
        description
          "Updating";
      }
      enum "icpe-install-sat-state-replacing" {
        description
          "Replacing";
      }
      enum "icpe-install-sat-state-deactivating" {
        description
          "Deactivating";
      }
      enum "icpe-install-sat-state-removing" {
        description
          "Removing";
      }
      enum "icpe-install-sat-state-success" {
        description
          "Success";
      }
      enum "icpe-install-sat-state-failure" {
        description
          "Failure";
      }
      enum "icpe-install-sat-state-multiple-ops" {
        description
          "Multiple ops";
      }
      enum "icpe-install-sat-state-aborted" {
        description
          "Aborted";
      }
      enum "icpe-install-sat-state-protocol-version" {
        description
          "Protocol version";
      }
      enum "icpe-install-sat-state-pkg-not-present" {
        description
          "Pkg not present";
      }
      enum "icpe-install-sat-state-no-image" {
        description
          "No image";
      }
      enum "icpe-install-sat-state-no-such-file" {
        description
          "No such file";
      }
      enum "icpe-install-sat-state-sat-uncfgd" {
        description
          "Sat uncfgd";
      }
      enum "icpe-install-sat-state-processing" {
        description
          "Processing";
      }
    }
    description
      "Icpe install sat state";
  }

  grouping ncs_template_ICPE-INSTALL-SHOW-DETAIL-SATELLITE-TYPE {
    description
      "ICPE INSTALL SHOW DETAIL SATELLITE TYPE";
    leaf satellite-id {
      type string;
      description
        "Satellite ID";
    }
    leaf state {
      type ncs_template_Icpe-install-sat-state;
      description
        "State";
    }
    leaf percentage {
      type string;
      units "percentage";
      description
        "Percentage";
    }
    leaf retries {
      type string;
      description
        "Retries";
    }
    leaf start-time {
      type string;
      description
        "Start time";
    }
    leaf end-time {
      type string;
      description
        "End time";
    }
    leaf info {
      type ncs_template_Xr-yang-string;
      description
        "Info";
    }
  }

  grouping ncs_template_ICPE-INSTALL-SHOW-DETAIL-TYPE {
    description
      "Detailed breakdown of install status";
    leaf operation-id-xr {
      type string;
      description
        "Operation ID";
    }
    leaf satellite-range {
      type ncs_template_Xr-yang-string;
      description
        "Satellite range";
    }
    leaf operation-type {
      type string;
      description
        "Operation type";
    }
    leaf progress-percentage {
      type string;
      units "percentage";
      description
        "Progress percentage";
    }
    leaf start-time {
      type string;
      description
        "Start time";
    }
    leaf end-time {
      type string;
      description
        "End time";
    }
    leaf reference-op {
      type string;
      description
        "Reference op";
    }
    leaf ref-type {
      type ncs_template_Icpe-oper-ref-type;
      description
        "Ref type";
    }
    leaf ref-name {
      type ncs_template_Xr-yang-string;
      description
        "Ref name";
    }
    leaf ref-state {
      type ncs_template_Icpe-install-sat-state;
      description
        "Ref state";
    }
    leaf-list sats-not-initiated {
      // NCS patched for predictable order
      ordered-by user;
      type string;
      description
        "Sats not initiated";
    }
    leaf-list sats-transferring {
      // NCS patched for predictable order
      ordered-by user;
      type string;
      description
        "Sats transferring";
    }
    leaf-list sats-activating {
      // NCS patched for predictable order
      ordered-by user;
      type string;
      description
        "Sats activating";
    }
    leaf-list sats-updating {
      // NCS patched for predictable order
      ordered-by user;
      type string;
      description
        "Sats updating";
    }
    leaf-list sats-replacing {
      // NCS patched for predictable order
      ordered-by user;
      type string;
      description
        "Sats replacing";
    }
    leaf-list sats-deactivating {
      // NCS patched for predictable order
      ordered-by user;
      type string;
      description
        "Sats deactivating";
    }
    leaf-list sats-removing {
      // NCS patched for predictable order
      ordered-by user;
      type string;
      description
        "Sats removing";
    }
    leaf-list sats-transfer-failed {
      // NCS patched for predictable order
      ordered-by user;
      type string;
      description
        "Sats transfer failed";
    }
    leaf-list sats-activate-failed {
      // NCS patched for predictable order
      ordered-by user;
      type string;
      description
        "Sats activate failed";
    }
    leaf-list sats-update-failed {
      // NCS patched for predictable order
      ordered-by user;
      type string;
      description
        "Sats update failed";
    }
    leaf-list sats-replace-failed {
      // NCS patched for predictable order
      ordered-by user;
      type string;
      description
        "Sats replace failed";
    }
    leaf-list sats-deactivate-failed {
      // NCS patched for predictable order
      ordered-by user;
      type string;
      description
        "Sats deactivate failed";
    }
    leaf-list sats-remove-failed {
      // NCS patched for predictable order
      ordered-by user;
      type string;
      description
        "Sats remove failed";
    }
    leaf-list sats-transfer-aborted {
      // NCS patched for predictable order
      ordered-by user;
      type string;
      description
        "Sats transfer aborted";
    }
    leaf-list sats-activate-aborted {
      // NCS patched for predictable order
      ordered-by user;
      type string;
      description
        "Sats activate aborted";
    }
    leaf-list sats-update-aborted {
      // NCS patched for predictable order
      ordered-by user;
      type string;
      description
        "Sats update aborted";
    }
    leaf-list sats-replace-aborted {
      // NCS patched for predictable order
      ordered-by user;
      type string;
      description
        "Sats replace aborted";
    }
    leaf-list sats-deactivate-aborted {
      // NCS patched for predictable order
      ordered-by user;
      type string;
      description
        "Sats deactivate aborted";
    }
    leaf-list sats-remove-aborted {
      // NCS patched for predictable order
      ordered-by user;
      type string;
      description
        "Sats remove aborted";
    }
    leaf-list sats-no-operation {
      // NCS patched for predictable order
      ordered-by user;
      type string;
      description
        "Sats no operation";
    }
    leaf-list sats-completed {
      // NCS patched for predictable order
      ordered-by user;
      type string;
      description
        "Sats completed";
    }
    leaf-list name-string {
      // NCS patched for predictable order
      ordered-by user;
      type ncs_template_Xr-yang-string;
      description
        "Name strings";
    }
    list satellite {
      // NCS patched for predictable order
      ordered-by user;
      description
        "Breakdown per satellite table";
      uses ncs_template_ICPE-INSTALL-SHOW-DETAIL-SATELLITE-TYPE;
    }
  }

  grouping ncs_rpc_notif_ICPE-INSTALL-SHOW-DETAIL-SATELLITE-TYPE {
    description
      "ICPE INSTALL SHOW DETAIL SATELLITE TYPE";
    leaf satellite-id {
      type uint16;
      description
        "Satellite ID";
    }
    leaf state {
      type ncs_rpc_notif_Icpe-install-sat-state;
      description
        "State";
    }
    leaf percentage {
      type uint16;
      units "percentage";
      description
        "Percentage";
    }
    leaf retries {
      type uint16;
      description
        "Retries";
    }
    leaf start-time {
      type uint32;
      description
        "Start time";
    }
    leaf end-time {
      type uint32;
      description
        "End time";
    }
    leaf info {
      type ncs_rpc_notif_Xr-yang-string;
      description
        "Info";
    }
  }

  grouping ncs_rpc_notif_ICPE-INSTALL-SHOW-DETAIL-TYPE {
    description
      "Detailed breakdown of install status";
    leaf operation-id-xr {
      type uint32;
      description
        "Operation ID";
    }
    leaf satellite-range {
      type ncs_rpc_notif_Xr-yang-string;
      description
        "Satellite range";
    }
    leaf operation-type {
      type uint16;
      description
        "Operation type";
    }
    leaf progress-percentage {
      type uint16;
      units "percentage";
      description
        "Progress percentage";
    }
    leaf start-time {
      type uint32;
      description
        "Start time";
    }
    leaf end-time {
      type uint32;
      description
        "End time";
    }
    leaf reference-op {
      type boolean;
      description
        "Reference op";
    }
    leaf ref-type {
      type ncs_rpc_notif_Icpe-oper-ref-type;
      description
        "Ref type";
    }
    leaf ref-name {
      type ncs_rpc_notif_Xr-yang-string;
      description
        "Ref name";
    }
    leaf ref-state {
      type ncs_rpc_notif_Icpe-install-sat-state;
      description
        "Ref state";
    }
    leaf-list sats-not-initiated {
      type uint16;
      description
        "Sats not initiated";
    }
    leaf-list sats-transferring {
      type uint16;
      description
        "Sats transferring";
    }
    leaf-list sats-activating {
      type uint16;
      description
        "Sats activating";
    }
    leaf-list sats-updating {
      type uint16;
      description
        "Sats updating";
    }
    leaf-list sats-replacing {
      type uint16;
      description
        "Sats replacing";
    }
    leaf-list sats-deactivating {
      type uint16;
      description
        "Sats deactivating";
    }
    leaf-list sats-removing {
      type uint16;
      description
        "Sats removing";
    }
    leaf-list sats-transfer-failed {
      type uint16;
      description
        "Sats transfer failed";
    }
    leaf-list sats-activate-failed {
      type uint16;
      description
        "Sats activate failed";
    }
    leaf-list sats-update-failed {
      type uint16;
      description
        "Sats update failed";
    }
    leaf-list sats-replace-failed {
      type uint16;
      description
        "Sats replace failed";
    }
    leaf-list sats-deactivate-failed {
      type uint16;
      description
        "Sats deactivate failed";
    }
    leaf-list sats-remove-failed {
      type uint16;
      description
        "Sats remove failed";
    }
    leaf-list sats-transfer-aborted {
      type uint16;
      description
        "Sats transfer aborted";
    }
    leaf-list sats-activate-aborted {
      type uint16;
      description
        "Sats activate aborted";
    }
    leaf-list sats-update-aborted {
      type uint16;
      description
        "Sats update aborted";
    }
    leaf-list sats-replace-aborted {
      type uint16;
      description
        "Sats replace aborted";
    }
    leaf-list sats-deactivate-aborted {
      type uint16;
      description
        "Sats deactivate aborted";
    }
    leaf-list sats-remove-aborted {
      type uint16;
      description
        "Sats remove aborted";
    }
    leaf-list sats-no-operation {
      type uint16;
      description
        "Sats no operation";
    }
    leaf-list sats-completed {
      type uint16;
      description
        "Sats completed";
    }
    leaf-list name-string {
      type ncs_rpc_notif_Xr-yang-string;
      description
        "Name strings";
    }
    list satellite {
      description
        "Breakdown per satellite table";
      uses ncs_rpc_notif_ICPE-INSTALL-SHOW-DETAIL-SATELLITE-TYPE;
    }
  }

  grouping live_ncs_ICPE-INSTALL-SHOW-DETAIL-SATELLITE-TYPE {
    description
      "ICPE INSTALL SHOW DETAIL SATELLITE TYPE";
    leaf satellite-id {
      type uint16;
      description
        "Satellite ID";
    }
    leaf state {
      type live_ncs_Icpe-install-sat-state;
      description
        "State";
    }
    leaf percentage {
      type uint16;
      units "percentage";
      description
        "Percentage";
    }
    leaf retries {
      type uint16;
      description
        "Retries";
    }
    leaf start-time {
      type uint32;
      description
        "Start time";
    }
    leaf end-time {
      type uint32;
      description
        "End time";
    }
    leaf info {
      type live_ncs_Xr-yang-string;
      description
        "Info";
    }
  }

  grouping live_ncs_ICPE-INSTALL-SHOW-DETAIL-TYPE {
    description
      "Detailed breakdown of install status";
    leaf operation-id-xr {
      type uint32;
      description
        "Operation ID";
    }
    leaf satellite-range {
      type live_ncs_Xr-yang-string;
      description
        "Satellite range";
    }
    leaf operation-type {
      type uint16;
      description
        "Operation type";
    }
    leaf progress-percentage {
      type uint16;
      units "percentage";
      description
        "Progress percentage";
    }
    leaf start-time {
      type uint32;
      description
        "Start time";
    }
    leaf end-time {
      type uint32;
      description
        "End time";
    }
    leaf reference-op {
      type boolean;
      description
        "Reference op";
    }
    leaf ref-type {
      type live_ncs_Icpe-oper-ref-type;
      description
        "Ref type";
    }
    leaf ref-name {
      type live_ncs_Xr-yang-string;
      description
        "Ref name";
    }
    leaf ref-state {
      type live_ncs_Icpe-install-sat-state;
      description
        "Ref state";
    }
    leaf-list sats-not-initiated {
      type uint16;
      description
        "Sats not initiated";
    }
    leaf-list sats-transferring {
      type uint16;
      description
        "Sats transferring";
    }
    leaf-list sats-activating {
      type uint16;
      description
        "Sats activating";
    }
    leaf-list sats-updating {
      type uint16;
      description
        "Sats updating";
    }
    leaf-list sats-replacing {
      type uint16;
      description
        "Sats replacing";
    }
    leaf-list sats-deactivating {
      type uint16;
      description
        "Sats deactivating";
    }
    leaf-list sats-removing {
      type uint16;
      description
        "Sats removing";
    }
    leaf-list sats-transfer-failed {
      type uint16;
      description
        "Sats transfer failed";
    }
    leaf-list sats-activate-failed {
      type uint16;
      description
        "Sats activate failed";
    }
    leaf-list sats-update-failed {
      type uint16;
      description
        "Sats update failed";
    }
    leaf-list sats-replace-failed {
      type uint16;
      description
        "Sats replace failed";
    }
    leaf-list sats-deactivate-failed {
      type uint16;
      description
        "Sats deactivate failed";
    }
    leaf-list sats-remove-failed {
      type uint16;
      description
        "Sats remove failed";
    }
    leaf-list sats-transfer-aborted {
      type uint16;
      description
        "Sats transfer aborted";
    }
    leaf-list sats-activate-aborted {
      type uint16;
      description
        "Sats activate aborted";
    }
    leaf-list sats-update-aborted {
      type uint16;
      description
        "Sats update aborted";
    }
    leaf-list sats-replace-aborted {
      type uint16;
      description
        "Sats replace aborted";
    }
    leaf-list sats-deactivate-aborted {
      type uint16;
      description
        "Sats deactivate aborted";
    }
    leaf-list sats-remove-aborted {
      type uint16;
      description
        "Sats remove aborted";
    }
    leaf-list sats-no-operation {
      type uint16;
      description
        "Sats no operation";
    }
    leaf-list sats-completed {
      type uint16;
      description
        "Sats completed";
    }
    leaf-list name-string {
      type live_ncs_Xr-yang-string;
      description
        "Name strings";
    }
    list satellite {
      description
        "Breakdown per satellite table";
      uses live_ncs_ICPE-INSTALL-SHOW-DETAIL-SATELLITE-TYPE;
    }
  }

  grouping ICPE-INSTALL-SHOW-DETAIL-SATELLITE-TYPE {
    description
      "ICPE INSTALL SHOW DETAIL SATELLITE TYPE";
    leaf satellite-id {
      type uint16;
      description
        "Satellite ID";
    }
    leaf state {
      type Icpe-install-sat-state;
      description
        "State";
    }
    leaf percentage {
      type uint16;
      units "percentage";
      description
        "Percentage";
    }
    leaf retries {
      type uint16;
      description
        "Retries";
    }
    leaf start-time {
      type uint32;
      description
        "Start time";
    }
    leaf end-time {
      type uint32;
      description
        "End time";
    }
    leaf info {
      type Xr-yang-string;
      description
        "Info";
    }
  }

  grouping ICPE-INSTALL-SHOW-DETAIL-TYPE {
    description
      "Detailed breakdown of install status";
    leaf operation-id-xr {
      type uint32;
      description
        "Operation ID";
    }
    leaf satellite-range {
      type Xr-yang-string;
      description
        "Satellite range";
    }
    leaf operation-type {
      type uint16;
      description
        "Operation type";
    }
    leaf progress-percentage {
      type uint16;
      units "percentage";
      description
        "Progress percentage";
    }
    leaf start-time {
      type uint32;
      description
        "Start time";
    }
    leaf end-time {
      type uint32;
      description
        "End time";
    }
    leaf reference-op {
      type boolean;
      description
        "Reference op";
    }
    leaf ref-type {
      type Icpe-oper-ref-type;
      description
        "Ref type";
    }
    leaf ref-name {
      type Xr-yang-string;
      description
        "Ref name";
    }
    leaf ref-state {
      type Icpe-install-sat-state;
      description
        "Ref state";
    }
    leaf-list sats-not-initiated {
      type uint16;
      description
        "Sats not initiated";
    }
    leaf-list sats-transferring {
      type uint16;
      description
        "Sats transferring";
    }
    leaf-list sats-activating {
      type uint16;
      description
        "Sats activating";
    }
    leaf-list sats-updating {
      type uint16;
      description
        "Sats updating";
    }
    leaf-list sats-replacing {
      type uint16;
      description
        "Sats replacing";
    }
    leaf-list sats-deactivating {
      type uint16;
      description
        "Sats deactivating";
    }
    leaf-list sats-removing {
      type uint16;
      description
        "Sats removing";
    }
    leaf-list sats-transfer-failed {
      type uint16;
      description
        "Sats transfer failed";
    }
    leaf-list sats-activate-failed {
      type uint16;
      description
        "Sats activate failed";
    }
    leaf-list sats-update-failed {
      type uint16;
      description
        "Sats update failed";
    }
    leaf-list sats-replace-failed {
      type uint16;
      description
        "Sats replace failed";
    }
    leaf-list sats-deactivate-failed {
      type uint16;
      description
        "Sats deactivate failed";
    }
    leaf-list sats-remove-failed {
      type uint16;
      description
        "Sats remove failed";
    }
    leaf-list sats-transfer-aborted {
      type uint16;
      description
        "Sats transfer aborted";
    }
    leaf-list sats-activate-aborted {
      type uint16;
      description
        "Sats activate aborted";
    }
    leaf-list sats-update-aborted {
      type uint16;
      description
        "Sats update aborted";
    }
    leaf-list sats-replace-aborted {
      type uint16;
      description
        "Sats replace aborted";
    }
    leaf-list sats-deactivate-aborted {
      type uint16;
      description
        "Sats deactivate aborted";
    }
    leaf-list sats-remove-aborted {
      type uint16;
      description
        "Sats remove aborted";
    }
    leaf-list sats-no-operation {
      type uint16;
      description
        "Sats no operation";
    }
    leaf-list sats-completed {
      type uint16;
      description
        "Sats completed";
    }
    leaf-list name-string {
      type Xr-yang-string;
      description
        "Name strings";
    }
    list satellite {
      description
        "Breakdown per satellite table";
      uses ICPE-INSTALL-SHOW-DETAIL-SATELLITE-TYPE;
    }
  }
}

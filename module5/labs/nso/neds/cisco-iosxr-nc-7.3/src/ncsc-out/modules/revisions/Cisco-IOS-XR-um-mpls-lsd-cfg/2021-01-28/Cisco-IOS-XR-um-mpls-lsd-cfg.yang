module Cisco-IOS-XR-um-mpls-lsd-cfg {
  // Generated by yanger -t ncs
  tailf:mount-id "cisco-iosxr-nc-7.3:cisco-iosxr-nc-7.3";
  tailf:ncs-device-type "netconf";

  namespace "http://cisco.com/ns/yang/Cisco-IOS-XR-um-mpls-lsd-cfg";
  prefix um-mpls-lsd-cfg;

  import cisco-semver {
    prefix semver;
  }
  import Cisco-IOS-XR-types {
    prefix xr;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-lsd package configuration.

     This YANG module augments the
     modules with configuration data.

     Copyright (c) 2019-2021 by Cisco Systems, Inc.
     All rights reserved.";

  revision 2021-01-28 {
    description
      "Added cisco-support task yang nodes";
    semver:module-version "3.1.0";
  }
  revision 2020-12-04 {
    description
      "Removed unsupported nodes
       2020-11-10
       Changed some constraints under table-0
       2020-11-09
       Changed table from a list to a container called table-0";
    semver:module-version "3.0.0";
  }
  revision 2020-05-20 {
    description
      "Added blocks node to the model";
    semver:module-version "2.1.0";
  }
  revision 2019-10-10 {
    description
      "Removed unnecessary augments from the model";
    semver:module-version "2.0.0";
  }
  revision 2019-06-10 {
    description
      "Establish semantic version baseline.";
    semver:module-version "1.0.0";
  }
  revision 2019-03-30 {
    description
      "Initial version";
  }

  augment "/ncs:devices/ncs:device/ncs:config" {
    container mpls {
      tailf:ncs-device-type "netconf";
      tailf:display-when "not(../../ncs:module) or ../../ncs:module[ncs:name='Cisco-IOS-XR-um-mpls-lsd-cfg']";
      description
        "Global MPLS configuration subcommands";
      container ip-ttl-propagate {
        description
          "Propagate IP TTL into the label stack";
        container disable {
          must 'not(local and forwarded)' {
            tailf:xpath-root 3;
          }
          presence "Indicates a disable node is configured.";
          description
            "Disable IP TTL propagation";
          container local {
            presence "Indicates a local node is configured.";
            description
              "Disable IP TTL propagation for only locally generated MPLS packets";
          }
          container forwarded {
            presence "Indicates a forwarded node is configured.";
            description
              "Disable IP TTL propagation for only forwarded MPLS packets";
          }
        }
      }
      container ipv6 {
        description
          "Configure IPv6 parameters";
        leaf ttl-expiration-pop {
          type uint32 {
            range "1..10" {
              description
                "Number of labels to pop on TTL expiry";
            }
          }
          description
            "Number of labels to pop when MPLS TTL expires";
        }
      }
      container ipv4 {
        description
          "Configure IPv4 parameters";
        leaf ttl-expiration-pop {
          type uint32 {
            range "1..10" {
              description
                "Number of labels to pop on TTL expiry";
            }
          }
          description
            "Number of labels to pop when MPLS TTL expires";
        }
      }
      container label {
        description
          "Label properties";
        container range {
          description
            "Label range";
          container table-0 {
            description
              "Specify label table";
            leaf minimum-label {
              type uint32 {
                range "16000..1048575";
              }
              must '../maximum-label' {
                tailf:xpath-root 3;
              }
              description
                "Manimum label value";
            }
            leaf maximum-label {
              type uint32 {
                range "16000..1048575";
              }
              must '../minimum-label' {
                tailf:xpath-root 3;
              }
              description
                "Maximum label value";
            }
            container static {
              must '../minimum-label' {
                tailf:xpath-root 3;
              }
              presence "Indicates a static node is configured.";
              description
                "Specify block of labels for static bindings";
              leaf minimum-label {
                type uint32 {
                  range "16..1048575" {
                    description
                      "Minimum static label value";
                  }
                }
                mandatory true;
                description
                  "Specify block of labels for static bindings";
              }
              leaf maximum-label {
                type uint32 {
                  range "16..1048575" {
                    description
                      "Maximum static label value";
                  }
                }
                mandatory true;
                description
                  "Maximum static label value";
              }
            }
          }
        }
        container blocks {
          description
            "Label blocks";
          list block {
            must 'end or size' {
              tailf:xpath-root 3;
            }
            key "name";
            description
              "Block of labels";
            leaf name {
              type xr:Cisco-ios-xr-string {
                length "1..1024" {
                  description
                    "Name of block to configure";
                }
              }
              description
                "Block name (unique identifier)";
            }
            leaf type {
              type enumeration {
                enum "cbf" {
                  value 3;
                  description
                    "CBF block";
                }
                enum "pfp" {
                  value 4;
                  description
                    "PFP block";
                }
              }
              mandatory true;
              description
                "Type of block to configure";
            }
            leaf start {
              type uint32 {
                range "16000..1048575" {
                  description
                    "Block lower bound";
                }
              }
              mandatory true;
              description
                "Start of block range";
            }
            leaf end {
              type uint32 {
                range "120..1048575" {
                  description
                    "Block upper bound";
                }
              }
              must 'not(../size)' {
                tailf:xpath-root 3;
              }
              description
                "End of block range";
            }
            leaf size {
              type uint32 {
                range "1..1032576" {
                  description
                    "Block size";
                }
              }
              must 'not(../end)' {
                tailf:xpath-root 3;
              }
              description
                "Size of the block";
            }
            leaf client {
              type xr:Cisco-ios-xr-string {
                length "1..48" {
                  description
                    "Name of the client instance";
                }
              }
              mandatory true;
              description
                "Block client";
            }
          }
        }
      }
      container lsd {
        description
          "MPLS LSD process command";
        container ltrace-buffer {
          description
            "MPLS LSD LTrace buffer files";
          leaf multiplier {
            type uint32 {
              range "2..5" {
                description
                  "Multiplier factor";
              }
            }
            description
              "Ltrace buffer file size multiplier";
          }
        }
        container app-reg-delay {
          description
            "Application registration delay";
          container disable {
            presence "Indicates a disable node is configured.";
            description
              "Disable delay for regular applications' registration";
          }
        }
      }
      container entropy-label {
        presence "Indicates a entropy-label node is configured.";
        description
          "Enable MPLS entropy label";
      }
    }
  }
  augment "/ncs:devices/ncs:device/ncs:live-status" {
    container mpls {
      tailf:ncs-device-type "netconf";
      tailf:display-when "not(../../ncs:module) or ../../ncs:module[ncs:name='Cisco-IOS-XR-um-mpls-lsd-cfg'] or (../../ncs:live-status-protocol[not(ncs:capability)]) or (../../ncs:live-status-protocol/ncs:capability/ncs:module[.='Cisco-IOS-XR-um-mpls-lsd-cfg'])";
      description
        "Global MPLS configuration subcommands";
      container ip-ttl-propagate {
        description
          "Propagate IP TTL into the label stack";
        container disable {
          // NCS drop must statement
          presence "Indicates a disable node is configured.";
          description
            "Disable IP TTL propagation";
          container local {
            presence "Indicates a local node is configured.";
            description
              "Disable IP TTL propagation for only locally generated MPLS packets";
          }
          container forwarded {
            presence "Indicates a forwarded node is configured.";
            description
              "Disable IP TTL propagation for only forwarded MPLS packets";
          }
        }
      }
      container ipv6 {
        description
          "Configure IPv6 parameters";
        leaf ttl-expiration-pop {
          type uint32 {
            range "1..10" {
              description
                "Number of labels to pop on TTL expiry";
            }
          }
          description
            "Number of labels to pop when MPLS TTL expires";
        }
      }
      container ipv4 {
        description
          "Configure IPv4 parameters";
        leaf ttl-expiration-pop {
          type uint32 {
            range "1..10" {
              description
                "Number of labels to pop on TTL expiry";
            }
          }
          description
            "Number of labels to pop when MPLS TTL expires";
        }
      }
      container label {
        description
          "Label properties";
        container range {
          description
            "Label range";
          container table-0 {
            description
              "Specify label table";
            leaf minimum-label {
              type uint32 {
                range "16000..1048575";
              }
              // NCS drop must statement
              description
                "Manimum label value";
            }
            leaf maximum-label {
              type uint32 {
                range "16000..1048575";
              }
              // NCS drop must statement
              description
                "Maximum label value";
            }
            container static {
              // NCS drop must statement
              presence "Indicates a static node is configured.";
              description
                "Specify block of labels for static bindings";
              leaf minimum-label {
                type uint32 {
                  range "16..1048575" {
                    description
                      "Minimum static label value";
                  }
                }
                // NCS drop mandatory statement
                description
                  "Specify block of labels for static bindings";
              }
              leaf maximum-label {
                type uint32 {
                  range "16..1048575" {
                    description
                      "Maximum static label value";
                  }
                }
                // NCS drop mandatory statement
                description
                  "Maximum static label value";
              }
            }
          }
        }
        container blocks {
          description
            "Label blocks";
          list block {
            // NCS drop must statement
            key "name";
            description
              "Block of labels";
            leaf name {
              type xr:live_ncs_Cisco-ios-xr-string;
              description
                "Block name (unique identifier)";
            }
            leaf type {
              type enumeration {
                enum "cbf" {
                  value 3;
                  description
                    "CBF block";
                }
                enum "pfp" {
                  value 4;
                  description
                    "PFP block";
                }
              }
              // NCS drop mandatory statement
              description
                "Type of block to configure";
            }
            leaf start {
              type uint32 {
                range "16000..1048575" {
                  description
                    "Block lower bound";
                }
              }
              // NCS drop mandatory statement
              description
                "Start of block range";
            }
            leaf end {
              type uint32 {
                range "120..1048575" {
                  description
                    "Block upper bound";
                }
              }
              // NCS drop must statement
              description
                "End of block range";
            }
            leaf size {
              type uint32 {
                range "1..1032576" {
                  description
                    "Block size";
                }
              }
              // NCS drop must statement
              description
                "Size of the block";
            }
            leaf client {
              type xr:live_ncs_Cisco-ios-xr-string;
              // NCS drop mandatory statement
              description
                "Block client";
            }
          }
        }
      }
      container lsd {
        description
          "MPLS LSD process command";
        container ltrace-buffer {
          description
            "MPLS LSD LTrace buffer files";
          leaf multiplier {
            type uint32 {
              range "2..5" {
                description
                  "Multiplier factor";
              }
            }
            description
              "Ltrace buffer file size multiplier";
          }
        }
        container app-reg-delay {
          description
            "Application registration delay";
          container disable {
            presence "Indicates a disable node is configured.";
            description
              "Disable delay for regular applications' registration";
          }
        }
      }
      container entropy-label {
        presence "Indicates a entropy-label node is configured.";
        description
          "Enable MPLS entropy label";
      }
    }
  }
  augment "/ncs:devices/ncs:template/ncs:ned-id/ncs:config" {
    container mpls {
      description
        "Global MPLS configuration subcommands";
      container ip-ttl-propagate {
        description
          "Propagate IP TTL into the label stack";
        container disable {
          // NCS drop must statement
          presence "Indicates a disable node is configured.";
          description
            "Disable IP TTL propagation";
          container local {
            presence "Indicates a local node is configured.";
            description
              "Disable IP TTL propagation for only locally generated MPLS packets";
          }
          container forwarded {
            presence "Indicates a forwarded node is configured.";
            description
              "Disable IP TTL propagation for only forwarded MPLS packets";
          }
        }
      }
      container ipv6 {
        description
          "Configure IPv6 parameters";
        leaf ttl-expiration-pop {
          type string;
          description
            "Number of labels to pop when MPLS TTL expires";
        }
      }
      container ipv4 {
        description
          "Configure IPv4 parameters";
        leaf ttl-expiration-pop {
          type string;
          description
            "Number of labels to pop when MPLS TTL expires";
        }
      }
      container label {
        description
          "Label properties";
        container range {
          description
            "Label range";
          container table-0 {
            description
              "Specify label table";
            leaf minimum-label {
              type string;
              // NCS drop must statement
              description
                "Manimum label value";
            }
            leaf maximum-label {
              type string;
              // NCS drop must statement
              description
                "Maximum label value";
            }
            container static {
              // NCS drop must statement
              presence "Indicates a static node is configured.";
              description
                "Specify block of labels for static bindings";
              leaf minimum-label {
                type string;
                // NCS drop mandatory statement
                description
                  "Specify block of labels for static bindings";
              }
              leaf maximum-label {
                type string;
                // NCS drop mandatory statement
                description
                  "Maximum static label value";
              }
            }
          }
        }
        container blocks {
          description
            "Label blocks";
          list block {
            // NCS patched for predictable order
            ordered-by user;
            // NCS drop must statement
            key "name";
            description
              "Block of labels";
            leaf name {
              type xr:ncs_template_Cisco-ios-xr-string;
              description
                "Block name (unique identifier)";
            }
            leaf type {
              type string;
              // NCS drop mandatory statement
              description
                "Type of block to configure";
            }
            leaf start {
              type string;
              // NCS drop mandatory statement
              description
                "Start of block range";
            }
            leaf end {
              type string;
              // NCS drop must statement
              description
                "End of block range";
            }
            leaf size {
              type string;
              // NCS drop must statement
              description
                "Size of the block";
            }
            leaf client {
              type xr:ncs_template_Cisco-ios-xr-string;
              // NCS drop mandatory statement
              description
                "Block client";
            }
          }
        }
      }
      container lsd {
        description
          "MPLS LSD process command";
        container ltrace-buffer {
          description
            "MPLS LSD LTrace buffer files";
          leaf multiplier {
            type string;
            description
              "Ltrace buffer file size multiplier";
          }
        }
        container app-reg-delay {
          description
            "Application registration delay";
          container disable {
            presence "Indicates a disable node is configured.";
            description
              "Disable delay for regular applications' registration";
          }
        }
      }
      container entropy-label {
        presence "Indicates a entropy-label node is configured.";
        description
          "Enable MPLS entropy label";
      }
    }
  }
}

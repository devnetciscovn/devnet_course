submodule Cisco-IOS-XR-cnbng-nal-oper-sub1 {
  // Generated by yanger -t ncs
  tailf:mount-id "cisco-iosxr-nc-7.3:cisco-iosxr-nc-7.3";

  belongs-to Cisco-IOS-XR-cnbng-nal-oper {
    prefix Cisco-IOS-XR-cnbng-nal-oper;
  }

  import ietf-inet-types {
    prefix inet;
  }
  import ietf-yang-types {
    prefix yang;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR cnbng-nal package operational data.

     Copyright (c) 2013-2021 by Cisco Systems, Inc.
     All rights reserved.";

  revision 2021-06-20 {
    description
      "Added new path for getting subscriber summary based on VRF name.";
    semver:module-version "1.1.0";
  }
  revision 2020-12-13 {
    description
      "NAL SVM service final timestamp.";
    semver:module-version "1.0.0";
  }
  revision 2020-12-10 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-19 {
    description
      "Added schema support for cnbng-nal filter oper commands.";
  }
  revision 2020-10-08 {
    description
      "Moved counter and AIPC stats to new bag files.";
  }
  revision 2020-10-05 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  typedef ncs_template_Nal-main-edm-oc-state {
    type string;
    description
      "Nal main edm oc state";
  }

  typedef ncs_template_Nal-cp-assoc-status {
    type string;
    description
      "Nal cp assoc status";
  }

  typedef ncs_template_Nal-cp-connection-status {
    type string;
    description
      "Nal cp connection status";
  }

  typedef ncs_template_Nal-main-edm-spa-rt-hist {
    type string;
    description
      "Type of SPA oc history data";
  }

  typedef ncs_template_Svm-service-state {
    type string;
    description
      "NAL SVM Service profile state";
  }

  typedef ncs_template_Nal-trans-client-data {
    type string;
    description
      "nal transaction client type";
  }

  typedef ncs_template_Nal-trans-state {
    type string;
    description
      "Nal transaction subscriber state";
  }

  typedef ncs_template_Nal-intf-oper {
    type string;
    description
      "Ipsub operation types";
  }

  typedef ncs_template_Svm-reconcile-state {
    type string;
    description
      "SVM reconcile state";
  }

  typedef ncs_template_Nal-spa-oper {
    type string;
    description
      "SPA oper type";
  }

  typedef ncs_template_Svn-sub-state {
    type string;
    description
      "SVM state of a subscriber";
  }

  typedef ncs_template_Svm-sub-oper {
    type string;
    description
      "Operation types from FSM to SVM";
  }

  typedef ncs_template_Oper-nal-db-subscriber {
    type string;
    description
      "Nal Subscriber type";
  }

  typedef ncs_template_Oper-nal-db-subscriber-state {
    type string;
    description
      "Nal Subscriber State";
  }

  typedef ncs_rpc_notif_Nal-main-edm-oc-state {
    type enumeration {
      enum "nal-main-edm-oc-state-init" {
        description
          "Initial state";
      }
      enum "nal-main-edm-oc-state-sent" {
        description
          "OC request sent to IM";
      }
      enum "nal-main-edm-oc-state-complete" {
        description
          "OC response received";
      }
      enum "nal-main-edm-oc-state-rib-req-queued" {
        description
          "RIB route request queued";
      }
      enum "nal-main-edm-oc-state-rib-req-sent" {
        description
          "RIB route request sent";
      }
      enum "nal-main-edm-oc-state-rib-req-complete" {
        description
          "RIB response received";
      }
    }
    description
      "Nal main edm oc state";
  }

  typedef ncs_rpc_notif_Nal-cp-assoc-status {
    type enumeration {
      enum "nal-spa-assoc-init" {
        value 1;
        description
          "Association status init";
      }
      enum "nal-spa-assoc-done" {
        value 2;
        description
          "Association status done";
      }
      enum "nal-spa-assoc-not-done" {
        value 3;
        description
          "Association status not-done";
      }
    }
    description
      "Nal cp assoc status";
  }

  typedef ncs_rpc_notif_Nal-cp-connection-status {
    type enumeration {
      enum "nal-spa-transport-init" {
        value 1;
        description
          "Transport status Init";
      }
      enum "nal-spa-transport-up" {
        value 2;
        description
          "Transport status Up";
      }
      enum "nal-spa-transport-down" {
        value 3;
        description
          "Transport status Down";
      }
    }
    description
      "Nal cp connection status";
  }

  typedef ncs_rpc_notif_Nal-main-edm-spa-rt-hist {
    type enumeration {
      enum "nal-main-edm-spa-rt-hist-type-request" {
        description
          "nal main edm spa rt hist type request";
      }
      enum "nal-main-edm-spa-rt-hist-type-response" {
        description
          "nal main edm spa rt hist type response";
      }
    }
    description
      "Type of SPA oc history data";
  }

  typedef ncs_rpc_notif_Svm-service-state {
    type enumeration {
      enum "nal-oper-svm-service-state-unknown" {
        value 0;
        description
          "nal oper svm service state unknown";
      }
      enum "nal-oper-svm-service-state-created" {
        value 1;
        description
          "nal oper svm service state created";
      }
      enum "nal-oper-svm-service-state-install-request-ed" {
        value 2;
        description
          "nal oper svm service state install request ed";
      }
      enum "nal-oper-svm-service-state-install-req-failed" {
        value 3;
        description
          "nal oper svm service state install req failed";
      }
      enum "nal-oper-svm-service-state-install-failed" {
        value 4;
        description
          "nal oper svm service state install failed";
      }
      enum "nal-oper-svm-service-state-installed" {
        value 5;
        description
          "nal oper svm service state installed";
      }
      enum "nal-oper-svm-service-state-un-install-request-ed" {
        value 6;
        description
          "nal oper svm service state un install request
           ed";
      }
      enum "nal-oper-svm-service-state-un-install-req-failed" {
        value 7;
        description
          "nal oper svm service state un install req
           failed";
      }
      enum "nal-oper-svm-service-state-un-install-failed" {
        value 8;
        description
          "nal oper svm service state un install failed";
      }
      enum "nal-oper-svm-service-state-un-installed" {
        value 9;
        description
          "nal oper svm service state un installed";
      }
      enum "nal-oper-svm-service-state-check-point-ed" {
        value 10;
        description
          "nal oper svm service state check point ed";
      }
      enum "nal-oper-svm-service-state-restored" {
        value 11;
        description
          "nal oper svm service state restored";
      }
      enum "nal-oper-svm-service-state-re-conc-iled" {
        value 12;
        description
          "nal oper svm service state re conc iled";
      }
      enum "nal-oper-svm-service-state-max" {
        value 13;
        description
          "nal oper svm service state max";
      }
    }
    description
      "NAL SVM Service profile state";
  }

  typedef ncs_rpc_notif_Nal-trans-client-data {
    type enumeration {
      enum "oper-nal-trans-client-server" {
        value 0;
        description
          "oper nal trans client server";
      }
      enum "oper-nal-trans-client-edm-hand-ler" {
        value 1;
        description
          "oper nal trans client edm hand ler";
      }
      enum "oper-nal-trans-client-nal-internal" {
        value 2;
        description
          "oper nal trans client nal internal";
      }
      enum "oper-nal-trans-client-nal-db-restore" {
        value 3;
        description
          "oper nal trans client nal db restore";
      }
      enum "oper-nal-trans-client-nal-sbydb-restore" {
        value 4;
        description
          "oper nal trans client nal sbydb restore";
      }
      enum "oper-nal-trans-client-dhcpv4" {
        value 5;
        description
          "oper nal trans client dhcpv4";
      }
      enum "oper-nal-trans-client-dhcpv6" {
        value 6;
        description
          "oper nal trans client dhcpv6";
      }
      enum "oper-nal-trans-client-spio" {
        value 7;
        description
          "oper nal trans client spio";
      }
      enum "oper-nal-trans-client-bdx" {
        value 8;
        description
          "oper nal trans client bdx";
      }
      enum "oper-nal-trans-cleint-im-notify" {
        value 9;
        description
          "oper nal trans cleint im notify";
      }
      enum "oper-nal-trans-client-statd" {
        value 10;
        description
          "oper nal trans client statd";
      }
      enum "oper-nal-trans-cleint-rib-notify" {
        value 11;
        description
          "oper nal trans cleint rib notify";
      }
      enum "oper-nal-trans-cleint-vrf-notify" {
        value 12;
        description
          "oper nal trans cleint vrf notify";
      }
      enum "oper-nal-trans-cleint-statsd-notify" {
        value 13;
        description
          "oper nal trans cleint statsd notify";
      }
      enum "oper-nal-trans-client-sub-db-recon" {
        value 14;
        description
          "oper nal trans client sub db recon";
      }
      enum "oper-nal-trans-client-rib-recon" {
        value 15;
        description
          "oper nal trans client rib recon";
      }
      enum "oper-nal-trans-client-im-recon" {
        value 16;
        description
          "oper nal trans client im recon";
      }
      enum "oper-nal-trans-client-ut-test" {
        value 17;
        description
          "oper nal trans client ut test";
      }
      enum "oper-nal-trans-client-max" {
        value 18;
        description
          "oper nal trans client max";
      }
    }
    description
      "nal transaction client type";
  }

  typedef ncs_rpc_notif_Nal-trans-state {
    type enumeration {
      enum "oper-nal-trans-state-init" {
        value 0;
        description
          "oper nal trans state init";
      }
      enum "oper-nal-trans-state-subscriber" {
        value 1;
        description
          "oper nal trans state subscriber";
      }
      enum "oper-nal-trans-state-subscriber-wait" {
        value 2;
        description
          "oper nal trans state subscriber wait";
      }
      enum "oper-nal-trans-state-invalid" {
        value 3;
        description
          "oper nal trans state invalid";
      }
      enum "oper-nal-trans-state-queued" {
        value 4;
        description
          "oper nal trans state queued";
      }
      enum "oper-nal-trans-state-subscriber-response" {
        value 5;
        description
          "oper nal trans state subscriber response";
      }
      enum "oper-nal-trans-state-check-point-wait" {
        value 6;
        description
          "oper nal trans state check point wait";
      }
      enum "oper-nal-trans-state-end" {
        value 7;
        description
          "oper nal trans state end";
      }
    }
    description
      "Nal transaction subscriber state";
  }

  typedef ncs_rpc_notif_Nal-intf-oper {
    type enumeration {
      enum "oper-nal-ip-sub-o-per-unknown" {
        value 0;
        description
          "oper nal ip sub o per unknown";
      }
      enum "oper-nal-ip-sub-o-per-create" {
        value 1;
        description
          "oper nal ip sub o per create";
      }
      enum "oper-nal-ip-sub-o-per-update" {
        value 2;
        description
          "oper nal ip sub o per update";
      }
      enum "oper-nal-ip-sub-o-per-rollback" {
        value 3;
        description
          "oper nal ip sub o per rollback";
      }
      enum "oper-nal-ip-sub-o-per-delete" {
        value 4;
        description
          "oper nal ip sub o per delete";
      }
    }
    description
      "Ipsub operation types";
  }

  typedef ncs_rpc_notif_Svm-reconcile-state {
    type enumeration {
      enum "oper-svm-recon-state-idle" {
        value 0;
        description
          "oper svm recon state idle";
      }
      enum "oper-svm-recon-state-created" {
        value 1;
        description
          "oper svm recon state created";
      }
      enum "oper-svm-recon-state-dt-associated" {
        value 2;
        description
          "oper svm recon state dt associated";
      }
      enum "oper-svm-recon-state-up-installed" {
        value 3;
        description
          "oper svm recon state up installed";
      }
      enum "oper-svm-recon-state-up-associated" {
        value 4;
        description
          "oper svm recon state up associated";
      }
      enum "oper-svm-recon-state-pd-request-ed" {
        value 5;
        description
          "oper svm recon state pd request ed";
      }
      enum "oper-svm-recon-state-max" {
        value 6;
        description
          "oper svm recon state max";
      }
    }
    description
      "SVM reconcile state";
  }

  typedef ncs_rpc_notif_Nal-spa-oper {
    type enumeration {
      enum "oper-spa-o-per-type-create" {
        value 1;
        description
          "oper spa o per type create";
      }
      enum "oper-spa-o-per-type-modify" {
        value 2;
        description
          "oper spa o per type modify";
      }
      enum "oper-spa-o-per-type-delete" {
        value 3;
        description
          "oper spa o per type delete";
      }
      enum "oper-spa-o-per-type-max" {
        value 4;
        description
          "oper spa o per type max";
      }
    }
    description
      "SPA oper type";
  }

  typedef ncs_rpc_notif_Svn-sub-state {
    type enumeration {
      enum "oper-nal-svm-state-unknown" {
        value 0;
        description
          "oper nal svm state unknown";
      }
      enum "oper-nal-svm-state-created" {
        value 1;
        description
          "oper nal svm state created";
      }
      enum "oper-nal-svm-state-install-request-ed" {
        value 2;
        description
          "oper nal svm state install request ed";
      }
      enum "oper-nal-svm-state-install-req-failed" {
        value 3;
        description
          "oper nal svm state install req failed";
      }
      enum "oper-nal-svm-state-install-failed" {
        value 4;
        description
          "oper nal svm state install failed";
      }
      enum "oper-nal-svm-state-installed" {
        value 5;
        description
          "oper nal svm state installed";
      }
      enum "oper-nal-svm-state-un-install-request-ed" {
        value 6;
        description
          "oper nal svm state un install request ed";
      }
      enum "oper-nal-svm-state-un-install-req-failed" {
        value 7;
        description
          "oper nal svm state un install req failed";
      }
      enum "oper-nal-svm-state-un-install-failed" {
        value 8;
        description
          "oper nal svm state un install failed";
      }
      enum "oper-nal-svm-state-un-installed" {
        value 9;
        description
          "oper nal svm state un installed";
      }
      enum "oper-nal-svm-state-up-assoc-request-ed" {
        value 10;
        description
          "oper nal svm state up assoc request ed";
      }
      enum "oper-nal-svm-state-up-assoc-req-failed" {
        value 11;
        description
          "oper nal svm state up assoc req failed";
      }
      enum "oper-nal-svm-state-up-assoc-failed" {
        value 12;
        description
          "oper nal svm state up assoc failed";
      }
      enum "oper-nal-svm-state-up-unassoc-request-ed" {
        value 13;
        description
          "oper nal svm state up unassoc request ed";
      }
      enum "oper-nal-svm-state-up-unassoc-req-failed" {
        value 14;
        description
          "oper nal svm state up unassoc req failed";
      }
      enum "oper-nal-svm-state-up-unassoc-failed" {
        value 15;
        description
          "oper nal svm state up unassoc failed";
      }
      enum "oper-nal-svm-state-srv-assoc-request-ed" {
        value 16;
        description
          "oper nal svm state srv assoc request ed";
      }
      enum "oper-nal-svm-state-srv-assoc-req-failed" {
        value 17;
        description
          "oper nal svm state srv assoc req failed";
      }
      enum "oper-nal-svm-state-srv-assoc-failed" {
        value 18;
        description
          "oper nal svm state srv assoc failed";
      }
      enum "oper-nal-svm-state-srv-unassoc-request-ed" {
        value 19;
        description
          "oper nal svm state srv unassoc request ed";
      }
      enum "oper-nal-svm-state-srv-unassoc-req-failed" {
        value 20;
        description
          "oper nal svm state srv unassoc req failed";
      }
      enum "oper-nal-svm-state-srv-unassoc-failed" {
        value 21;
        description
          "oper nal svm state srv unassoc failed";
      }
      enum "oper-nal-svm-state-pd-request-ed" {
        value 22;
        description
          "oper nal svm state pd request ed";
      }
      enum "oper-nal-svm-state-pd-req-failed" {
        value 23;
        description
          "oper nal svm state pd req failed";
      }
      enum "oper-nal-svm-state-rb-pd-request-ed" {
        value 24;
        description
          "oper nal svm state rb pd request ed";
      }
      enum "oper-nal-svm-state-rb-pd-req-failed" {
        value 25;
        description
          "oper nal svm state rb pd req failed";
      }
      enum "oper-nal-svm-state-pd-cfg-generated" {
        value 26;
        description
          "oper nal svm state pd cfg generated";
      }
      enum "oper-nal-svm-state-pd-cfg-gen-failed" {
        value 27;
        description
          "oper nal svm state pd cfg gen failed";
      }
      enum "oper-nal-svm-state-activate-request-ed" {
        value 28;
        description
          "oper nal svm state activate request ed";
      }
      enum "oper-nal-svm-state-activate-req-fail" {
        value 29;
        description
          "oper nal svm state activate req fail";
      }
      enum "oper-nal-svm-state-activate-fail" {
        value 30;
        description
          "oper nal svm state activate fail";
      }
      enum "oper-nal-svm-state-activated" {
        value 31;
        description
          "oper nal svm state activated";
      }
      enum "oper-nal-svm-state-pd-failed" {
        value 32;
        description
          "oper nal svm state pd failed";
      }
      enum "oper-nal-svm-state-pd-complete" {
        value 33;
        description
          "oper nal svm state pd complete";
      }
      enum "oper-nal-svm-state-destroy-request-ed" {
        value 34;
        description
          "oper nal svm state destroy request ed";
      }
      enum "oper-nal-svm-state-destroy-req-failed" {
        value 35;
        description
          "oper nal svm state destroy req failed";
      }
      enum "oper-nal-svm-state-destroy-failed" {
        value 36;
        description
          "oper nal svm state destroy failed";
      }
      enum "oper-nal-svm-state-destroyed" {
        value 37;
        description
          "oper nal svm state destroyed";
      }
      enum "oper-nal-svm-state-rollback" {
        value 38;
        description
          "oper nal svm state rollback";
      }
      enum "oper-nal-svm-state-replace-req-failed" {
        value 39;
        description
          "oper nal svm state replace req failed";
      }
      enum "oper-nal-svm-state-replace-request-ed" {
        value 40;
        description
          "oper nal svm state replace request ed";
      }
      enum "oper-nal-svm-state-max" {
        value 41;
        description
          "oper nal svm state max";
      }
    }
    description
      "SVM state of a subscriber";
  }

  typedef ncs_rpc_notif_Svm-sub-oper {
    type enumeration {
      enum "oper-nal-svm-sub-o-per-unknown" {
        value 0;
        description
          "oper nal svm sub o per unknown";
      }
      enum "oper-nal-svm-sub-o-per-create" {
        value 1;
        description
          "oper nal svm sub o per create";
      }
      enum "oper-nal-svm-sub-o-per-update" {
        value 2;
        description
          "oper nal svm sub o per update";
      }
      enum "oper-nal-svm-sub-o-per-delete" {
        value 3;
        description
          "oper nal svm sub o per delete";
      }
      enum "oper-nal-svm-sub-o-per-rollback" {
        value 4;
        description
          "oper nal svm sub o per rollback";
      }
      enum "oper-nal-svm-sub-o-per-cleanup" {
        value 5;
        description
          "oper nal svm sub o per cleanup";
      }
      enum "oper-nal-svm-sub-o-per-save" {
        value 6;
        description
          "oper nal svm sub o per save";
      }
      enum "oper-nal-svm-sub-o-per-max" {
        value 7;
        description
          "oper nal svm sub o per max";
      }
    }
    description
      "Operation types from FSM to SVM";
  }

  typedef ncs_rpc_notif_Oper-nal-db-subscriber {
    type enumeration {
      enum "invalid" {
        value 0;
        description
          "Invalid";
      }
      enum "ipoe" {
        value 1;
        description
          "IPoE";
      }
      enum "pppoe" {
        value 2;
        description
          "PPPoE";
      }
      enum "l2tp" {
        value 3;
        description
          "L2TP";
      }
    }
    description
      "Nal Subscriber type";
  }

  typedef ncs_rpc_notif_Oper-nal-db-subscriber-state {
    type enumeration {
      enum "init" {
        value 0;
        description
          "Invalid";
      }
      enum "connecting" {
        value 1;
        description
          "connecting";
      }
      enum "connected" {
        value 2;
        description
          "connected";
      }
      enum "activated" {
        value 3;
        description
          "activated";
      }
      enum "idle" {
        value 4;
        description
          "idle";
      }
      enum "disconnecting" {
        value 5;
        description
          "disconnecting";
      }
      enum "end" {
        value 6;
        description
          "end";
      }
    }
    description
      "Nal Subscriber State";
  }

  typedef live_ncs_Nal-main-edm-oc-state {
    type enumeration {
      enum "nal-main-edm-oc-state-init" {
        description
          "Initial state";
      }
      enum "nal-main-edm-oc-state-sent" {
        description
          "OC request sent to IM";
      }
      enum "nal-main-edm-oc-state-complete" {
        description
          "OC response received";
      }
      enum "nal-main-edm-oc-state-rib-req-queued" {
        description
          "RIB route request queued";
      }
      enum "nal-main-edm-oc-state-rib-req-sent" {
        description
          "RIB route request sent";
      }
      enum "nal-main-edm-oc-state-rib-req-complete" {
        description
          "RIB response received";
      }
    }
    description
      "Nal main edm oc state";
  }

  typedef live_ncs_Nal-cp-assoc-status {
    type enumeration {
      enum "nal-spa-assoc-init" {
        value 1;
        description
          "Association status init";
      }
      enum "nal-spa-assoc-done" {
        value 2;
        description
          "Association status done";
      }
      enum "nal-spa-assoc-not-done" {
        value 3;
        description
          "Association status not-done";
      }
    }
    description
      "Nal cp assoc status";
  }

  typedef live_ncs_Nal-cp-connection-status {
    type enumeration {
      enum "nal-spa-transport-init" {
        value 1;
        description
          "Transport status Init";
      }
      enum "nal-spa-transport-up" {
        value 2;
        description
          "Transport status Up";
      }
      enum "nal-spa-transport-down" {
        value 3;
        description
          "Transport status Down";
      }
    }
    description
      "Nal cp connection status";
  }

  typedef live_ncs_Nal-main-edm-spa-rt-hist {
    type enumeration {
      enum "nal-main-edm-spa-rt-hist-type-request" {
        description
          "nal main edm spa rt hist type request";
      }
      enum "nal-main-edm-spa-rt-hist-type-response" {
        description
          "nal main edm spa rt hist type response";
      }
    }
    description
      "Type of SPA oc history data";
  }

  typedef live_ncs_Svm-service-state {
    type enumeration {
      enum "nal-oper-svm-service-state-unknown" {
        value 0;
        description
          "nal oper svm service state unknown";
      }
      enum "nal-oper-svm-service-state-created" {
        value 1;
        description
          "nal oper svm service state created";
      }
      enum "nal-oper-svm-service-state-install-request-ed" {
        value 2;
        description
          "nal oper svm service state install request ed";
      }
      enum "nal-oper-svm-service-state-install-req-failed" {
        value 3;
        description
          "nal oper svm service state install req failed";
      }
      enum "nal-oper-svm-service-state-install-failed" {
        value 4;
        description
          "nal oper svm service state install failed";
      }
      enum "nal-oper-svm-service-state-installed" {
        value 5;
        description
          "nal oper svm service state installed";
      }
      enum "nal-oper-svm-service-state-un-install-request-ed" {
        value 6;
        description
          "nal oper svm service state un install request
           ed";
      }
      enum "nal-oper-svm-service-state-un-install-req-failed" {
        value 7;
        description
          "nal oper svm service state un install req
           failed";
      }
      enum "nal-oper-svm-service-state-un-install-failed" {
        value 8;
        description
          "nal oper svm service state un install failed";
      }
      enum "nal-oper-svm-service-state-un-installed" {
        value 9;
        description
          "nal oper svm service state un installed";
      }
      enum "nal-oper-svm-service-state-check-point-ed" {
        value 10;
        description
          "nal oper svm service state check point ed";
      }
      enum "nal-oper-svm-service-state-restored" {
        value 11;
        description
          "nal oper svm service state restored";
      }
      enum "nal-oper-svm-service-state-re-conc-iled" {
        value 12;
        description
          "nal oper svm service state re conc iled";
      }
      enum "nal-oper-svm-service-state-max" {
        value 13;
        description
          "nal oper svm service state max";
      }
    }
    description
      "NAL SVM Service profile state";
  }

  typedef live_ncs_Nal-trans-client-data {
    type enumeration {
      enum "oper-nal-trans-client-server" {
        value 0;
        description
          "oper nal trans client server";
      }
      enum "oper-nal-trans-client-edm-hand-ler" {
        value 1;
        description
          "oper nal trans client edm hand ler";
      }
      enum "oper-nal-trans-client-nal-internal" {
        value 2;
        description
          "oper nal trans client nal internal";
      }
      enum "oper-nal-trans-client-nal-db-restore" {
        value 3;
        description
          "oper nal trans client nal db restore";
      }
      enum "oper-nal-trans-client-nal-sbydb-restore" {
        value 4;
        description
          "oper nal trans client nal sbydb restore";
      }
      enum "oper-nal-trans-client-dhcpv4" {
        value 5;
        description
          "oper nal trans client dhcpv4";
      }
      enum "oper-nal-trans-client-dhcpv6" {
        value 6;
        description
          "oper nal trans client dhcpv6";
      }
      enum "oper-nal-trans-client-spio" {
        value 7;
        description
          "oper nal trans client spio";
      }
      enum "oper-nal-trans-client-bdx" {
        value 8;
        description
          "oper nal trans client bdx";
      }
      enum "oper-nal-trans-cleint-im-notify" {
        value 9;
        description
          "oper nal trans cleint im notify";
      }
      enum "oper-nal-trans-client-statd" {
        value 10;
        description
          "oper nal trans client statd";
      }
      enum "oper-nal-trans-cleint-rib-notify" {
        value 11;
        description
          "oper nal trans cleint rib notify";
      }
      enum "oper-nal-trans-cleint-vrf-notify" {
        value 12;
        description
          "oper nal trans cleint vrf notify";
      }
      enum "oper-nal-trans-cleint-statsd-notify" {
        value 13;
        description
          "oper nal trans cleint statsd notify";
      }
      enum "oper-nal-trans-client-sub-db-recon" {
        value 14;
        description
          "oper nal trans client sub db recon";
      }
      enum "oper-nal-trans-client-rib-recon" {
        value 15;
        description
          "oper nal trans client rib recon";
      }
      enum "oper-nal-trans-client-im-recon" {
        value 16;
        description
          "oper nal trans client im recon";
      }
      enum "oper-nal-trans-client-ut-test" {
        value 17;
        description
          "oper nal trans client ut test";
      }
      enum "oper-nal-trans-client-max" {
        value 18;
        description
          "oper nal trans client max";
      }
    }
    description
      "nal transaction client type";
  }

  typedef live_ncs_Nal-trans-state {
    type enumeration {
      enum "oper-nal-trans-state-init" {
        value 0;
        description
          "oper nal trans state init";
      }
      enum "oper-nal-trans-state-subscriber" {
        value 1;
        description
          "oper nal trans state subscriber";
      }
      enum "oper-nal-trans-state-subscriber-wait" {
        value 2;
        description
          "oper nal trans state subscriber wait";
      }
      enum "oper-nal-trans-state-invalid" {
        value 3;
        description
          "oper nal trans state invalid";
      }
      enum "oper-nal-trans-state-queued" {
        value 4;
        description
          "oper nal trans state queued";
      }
      enum "oper-nal-trans-state-subscriber-response" {
        value 5;
        description
          "oper nal trans state subscriber response";
      }
      enum "oper-nal-trans-state-check-point-wait" {
        value 6;
        description
          "oper nal trans state check point wait";
      }
      enum "oper-nal-trans-state-end" {
        value 7;
        description
          "oper nal trans state end";
      }
    }
    description
      "Nal transaction subscriber state";
  }

  typedef live_ncs_Nal-intf-oper {
    type enumeration {
      enum "oper-nal-ip-sub-o-per-unknown" {
        value 0;
        description
          "oper nal ip sub o per unknown";
      }
      enum "oper-nal-ip-sub-o-per-create" {
        value 1;
        description
          "oper nal ip sub o per create";
      }
      enum "oper-nal-ip-sub-o-per-update" {
        value 2;
        description
          "oper nal ip sub o per update";
      }
      enum "oper-nal-ip-sub-o-per-rollback" {
        value 3;
        description
          "oper nal ip sub o per rollback";
      }
      enum "oper-nal-ip-sub-o-per-delete" {
        value 4;
        description
          "oper nal ip sub o per delete";
      }
    }
    description
      "Ipsub operation types";
  }

  typedef live_ncs_Svm-reconcile-state {
    type enumeration {
      enum "oper-svm-recon-state-idle" {
        value 0;
        description
          "oper svm recon state idle";
      }
      enum "oper-svm-recon-state-created" {
        value 1;
        description
          "oper svm recon state created";
      }
      enum "oper-svm-recon-state-dt-associated" {
        value 2;
        description
          "oper svm recon state dt associated";
      }
      enum "oper-svm-recon-state-up-installed" {
        value 3;
        description
          "oper svm recon state up installed";
      }
      enum "oper-svm-recon-state-up-associated" {
        value 4;
        description
          "oper svm recon state up associated";
      }
      enum "oper-svm-recon-state-pd-request-ed" {
        value 5;
        description
          "oper svm recon state pd request ed";
      }
      enum "oper-svm-recon-state-max" {
        value 6;
        description
          "oper svm recon state max";
      }
    }
    description
      "SVM reconcile state";
  }

  typedef live_ncs_Nal-spa-oper {
    type enumeration {
      enum "oper-spa-o-per-type-create" {
        value 1;
        description
          "oper spa o per type create";
      }
      enum "oper-spa-o-per-type-modify" {
        value 2;
        description
          "oper spa o per type modify";
      }
      enum "oper-spa-o-per-type-delete" {
        value 3;
        description
          "oper spa o per type delete";
      }
      enum "oper-spa-o-per-type-max" {
        value 4;
        description
          "oper spa o per type max";
      }
    }
    description
      "SPA oper type";
  }

  typedef live_ncs_Svn-sub-state {
    type enumeration {
      enum "oper-nal-svm-state-unknown" {
        value 0;
        description
          "oper nal svm state unknown";
      }
      enum "oper-nal-svm-state-created" {
        value 1;
        description
          "oper nal svm state created";
      }
      enum "oper-nal-svm-state-install-request-ed" {
        value 2;
        description
          "oper nal svm state install request ed";
      }
      enum "oper-nal-svm-state-install-req-failed" {
        value 3;
        description
          "oper nal svm state install req failed";
      }
      enum "oper-nal-svm-state-install-failed" {
        value 4;
        description
          "oper nal svm state install failed";
      }
      enum "oper-nal-svm-state-installed" {
        value 5;
        description
          "oper nal svm state installed";
      }
      enum "oper-nal-svm-state-un-install-request-ed" {
        value 6;
        description
          "oper nal svm state un install request ed";
      }
      enum "oper-nal-svm-state-un-install-req-failed" {
        value 7;
        description
          "oper nal svm state un install req failed";
      }
      enum "oper-nal-svm-state-un-install-failed" {
        value 8;
        description
          "oper nal svm state un install failed";
      }
      enum "oper-nal-svm-state-un-installed" {
        value 9;
        description
          "oper nal svm state un installed";
      }
      enum "oper-nal-svm-state-up-assoc-request-ed" {
        value 10;
        description
          "oper nal svm state up assoc request ed";
      }
      enum "oper-nal-svm-state-up-assoc-req-failed" {
        value 11;
        description
          "oper nal svm state up assoc req failed";
      }
      enum "oper-nal-svm-state-up-assoc-failed" {
        value 12;
        description
          "oper nal svm state up assoc failed";
      }
      enum "oper-nal-svm-state-up-unassoc-request-ed" {
        value 13;
        description
          "oper nal svm state up unassoc request ed";
      }
      enum "oper-nal-svm-state-up-unassoc-req-failed" {
        value 14;
        description
          "oper nal svm state up unassoc req failed";
      }
      enum "oper-nal-svm-state-up-unassoc-failed" {
        value 15;
        description
          "oper nal svm state up unassoc failed";
      }
      enum "oper-nal-svm-state-srv-assoc-request-ed" {
        value 16;
        description
          "oper nal svm state srv assoc request ed";
      }
      enum "oper-nal-svm-state-srv-assoc-req-failed" {
        value 17;
        description
          "oper nal svm state srv assoc req failed";
      }
      enum "oper-nal-svm-state-srv-assoc-failed" {
        value 18;
        description
          "oper nal svm state srv assoc failed";
      }
      enum "oper-nal-svm-state-srv-unassoc-request-ed" {
        value 19;
        description
          "oper nal svm state srv unassoc request ed";
      }
      enum "oper-nal-svm-state-srv-unassoc-req-failed" {
        value 20;
        description
          "oper nal svm state srv unassoc req failed";
      }
      enum "oper-nal-svm-state-srv-unassoc-failed" {
        value 21;
        description
          "oper nal svm state srv unassoc failed";
      }
      enum "oper-nal-svm-state-pd-request-ed" {
        value 22;
        description
          "oper nal svm state pd request ed";
      }
      enum "oper-nal-svm-state-pd-req-failed" {
        value 23;
        description
          "oper nal svm state pd req failed";
      }
      enum "oper-nal-svm-state-rb-pd-request-ed" {
        value 24;
        description
          "oper nal svm state rb pd request ed";
      }
      enum "oper-nal-svm-state-rb-pd-req-failed" {
        value 25;
        description
          "oper nal svm state rb pd req failed";
      }
      enum "oper-nal-svm-state-pd-cfg-generated" {
        value 26;
        description
          "oper nal svm state pd cfg generated";
      }
      enum "oper-nal-svm-state-pd-cfg-gen-failed" {
        value 27;
        description
          "oper nal svm state pd cfg gen failed";
      }
      enum "oper-nal-svm-state-activate-request-ed" {
        value 28;
        description
          "oper nal svm state activate request ed";
      }
      enum "oper-nal-svm-state-activate-req-fail" {
        value 29;
        description
          "oper nal svm state activate req fail";
      }
      enum "oper-nal-svm-state-activate-fail" {
        value 30;
        description
          "oper nal svm state activate fail";
      }
      enum "oper-nal-svm-state-activated" {
        value 31;
        description
          "oper nal svm state activated";
      }
      enum "oper-nal-svm-state-pd-failed" {
        value 32;
        description
          "oper nal svm state pd failed";
      }
      enum "oper-nal-svm-state-pd-complete" {
        value 33;
        description
          "oper nal svm state pd complete";
      }
      enum "oper-nal-svm-state-destroy-request-ed" {
        value 34;
        description
          "oper nal svm state destroy request ed";
      }
      enum "oper-nal-svm-state-destroy-req-failed" {
        value 35;
        description
          "oper nal svm state destroy req failed";
      }
      enum "oper-nal-svm-state-destroy-failed" {
        value 36;
        description
          "oper nal svm state destroy failed";
      }
      enum "oper-nal-svm-state-destroyed" {
        value 37;
        description
          "oper nal svm state destroyed";
      }
      enum "oper-nal-svm-state-rollback" {
        value 38;
        description
          "oper nal svm state rollback";
      }
      enum "oper-nal-svm-state-replace-req-failed" {
        value 39;
        description
          "oper nal svm state replace req failed";
      }
      enum "oper-nal-svm-state-replace-request-ed" {
        value 40;
        description
          "oper nal svm state replace request ed";
      }
      enum "oper-nal-svm-state-max" {
        value 41;
        description
          "oper nal svm state max";
      }
    }
    description
      "SVM state of a subscriber";
  }

  typedef live_ncs_Svm-sub-oper {
    type enumeration {
      enum "oper-nal-svm-sub-o-per-unknown" {
        value 0;
        description
          "oper nal svm sub o per unknown";
      }
      enum "oper-nal-svm-sub-o-per-create" {
        value 1;
        description
          "oper nal svm sub o per create";
      }
      enum "oper-nal-svm-sub-o-per-update" {
        value 2;
        description
          "oper nal svm sub o per update";
      }
      enum "oper-nal-svm-sub-o-per-delete" {
        value 3;
        description
          "oper nal svm sub o per delete";
      }
      enum "oper-nal-svm-sub-o-per-rollback" {
        value 4;
        description
          "oper nal svm sub o per rollback";
      }
      enum "oper-nal-svm-sub-o-per-cleanup" {
        value 5;
        description
          "oper nal svm sub o per cleanup";
      }
      enum "oper-nal-svm-sub-o-per-save" {
        value 6;
        description
          "oper nal svm sub o per save";
      }
      enum "oper-nal-svm-sub-o-per-max" {
        value 7;
        description
          "oper nal svm sub o per max";
      }
    }
    description
      "Operation types from FSM to SVM";
  }

  typedef live_ncs_Oper-nal-db-subscriber {
    type enumeration {
      enum "invalid" {
        value 0;
        description
          "Invalid";
      }
      enum "ipoe" {
        value 1;
        description
          "IPoE";
      }
      enum "pppoe" {
        value 2;
        description
          "PPPoE";
      }
      enum "l2tp" {
        value 3;
        description
          "L2TP";
      }
    }
    description
      "Nal Subscriber type";
  }

  typedef live_ncs_Oper-nal-db-subscriber-state {
    type enumeration {
      enum "init" {
        value 0;
        description
          "Invalid";
      }
      enum "connecting" {
        value 1;
        description
          "connecting";
      }
      enum "connected" {
        value 2;
        description
          "connected";
      }
      enum "activated" {
        value 3;
        description
          "activated";
      }
      enum "idle" {
        value 4;
        description
          "idle";
      }
      enum "disconnecting" {
        value 5;
        description
          "disconnecting";
      }
      enum "end" {
        value 6;
        description
          "end";
      }
    }
    description
      "Nal Subscriber State";
  }

  typedef Nal-main-edm-oc-state {
    type enumeration {
      enum "nal-main-edm-oc-state-init" {
        description
          "Initial state";
      }
      enum "nal-main-edm-oc-state-sent" {
        description
          "OC request sent to IM";
      }
      enum "nal-main-edm-oc-state-complete" {
        description
          "OC response received";
      }
      enum "nal-main-edm-oc-state-rib-req-queued" {
        description
          "RIB route request queued";
      }
      enum "nal-main-edm-oc-state-rib-req-sent" {
        description
          "RIB route request sent";
      }
      enum "nal-main-edm-oc-state-rib-req-complete" {
        description
          "RIB response received";
      }
    }
    description
      "Nal main edm oc state";
  }

  typedef Nal-cp-assoc-status {
    type enumeration {
      enum "nal-spa-assoc-init" {
        value 1;
        description
          "Association status init";
      }
      enum "nal-spa-assoc-done" {
        value 2;
        description
          "Association status done";
      }
      enum "nal-spa-assoc-not-done" {
        value 3;
        description
          "Association status not-done";
      }
    }
    description
      "Nal cp assoc status";
  }

  typedef Nal-cp-connection-status {
    type enumeration {
      enum "nal-spa-transport-init" {
        value 1;
        description
          "Transport status Init";
      }
      enum "nal-spa-transport-up" {
        value 2;
        description
          "Transport status Up";
      }
      enum "nal-spa-transport-down" {
        value 3;
        description
          "Transport status Down";
      }
    }
    description
      "Nal cp connection status";
  }

  typedef Nal-main-edm-spa-rt-hist {
    type enumeration {
      enum "nal-main-edm-spa-rt-hist-type-request" {
        description
          "nal main edm spa rt hist type request";
      }
      enum "nal-main-edm-spa-rt-hist-type-response" {
        description
          "nal main edm spa rt hist type response";
      }
    }
    description
      "Type of SPA oc history data";
  }

  typedef Svm-service-state {
    type enumeration {
      enum "nal-oper-svm-service-state-unknown" {
        value 0;
        description
          "nal oper svm service state unknown";
      }
      enum "nal-oper-svm-service-state-created" {
        value 1;
        description
          "nal oper svm service state created";
      }
      enum "nal-oper-svm-service-state-install-request-ed" {
        value 2;
        description
          "nal oper svm service state install request ed";
      }
      enum "nal-oper-svm-service-state-install-req-failed" {
        value 3;
        description
          "nal oper svm service state install req failed";
      }
      enum "nal-oper-svm-service-state-install-failed" {
        value 4;
        description
          "nal oper svm service state install failed";
      }
      enum "nal-oper-svm-service-state-installed" {
        value 5;
        description
          "nal oper svm service state installed";
      }
      enum "nal-oper-svm-service-state-un-install-request-ed" {
        value 6;
        description
          "nal oper svm service state un install request
           ed";
      }
      enum "nal-oper-svm-service-state-un-install-req-failed" {
        value 7;
        description
          "nal oper svm service state un install req
           failed";
      }
      enum "nal-oper-svm-service-state-un-install-failed" {
        value 8;
        description
          "nal oper svm service state un install failed";
      }
      enum "nal-oper-svm-service-state-un-installed" {
        value 9;
        description
          "nal oper svm service state un installed";
      }
      enum "nal-oper-svm-service-state-check-point-ed" {
        value 10;
        description
          "nal oper svm service state check point ed";
      }
      enum "nal-oper-svm-service-state-restored" {
        value 11;
        description
          "nal oper svm service state restored";
      }
      enum "nal-oper-svm-service-state-re-conc-iled" {
        value 12;
        description
          "nal oper svm service state re conc iled";
      }
      enum "nal-oper-svm-service-state-max" {
        value 13;
        description
          "nal oper svm service state max";
      }
    }
    description
      "NAL SVM Service profile state";
  }

  typedef Nal-trans-client-data {
    type enumeration {
      enum "oper-nal-trans-client-server" {
        value 0;
        description
          "oper nal trans client server";
      }
      enum "oper-nal-trans-client-edm-hand-ler" {
        value 1;
        description
          "oper nal trans client edm hand ler";
      }
      enum "oper-nal-trans-client-nal-internal" {
        value 2;
        description
          "oper nal trans client nal internal";
      }
      enum "oper-nal-trans-client-nal-db-restore" {
        value 3;
        description
          "oper nal trans client nal db restore";
      }
      enum "oper-nal-trans-client-nal-sbydb-restore" {
        value 4;
        description
          "oper nal trans client nal sbydb restore";
      }
      enum "oper-nal-trans-client-dhcpv4" {
        value 5;
        description
          "oper nal trans client dhcpv4";
      }
      enum "oper-nal-trans-client-dhcpv6" {
        value 6;
        description
          "oper nal trans client dhcpv6";
      }
      enum "oper-nal-trans-client-spio" {
        value 7;
        description
          "oper nal trans client spio";
      }
      enum "oper-nal-trans-client-bdx" {
        value 8;
        description
          "oper nal trans client bdx";
      }
      enum "oper-nal-trans-cleint-im-notify" {
        value 9;
        description
          "oper nal trans cleint im notify";
      }
      enum "oper-nal-trans-client-statd" {
        value 10;
        description
          "oper nal trans client statd";
      }
      enum "oper-nal-trans-cleint-rib-notify" {
        value 11;
        description
          "oper nal trans cleint rib notify";
      }
      enum "oper-nal-trans-cleint-vrf-notify" {
        value 12;
        description
          "oper nal trans cleint vrf notify";
      }
      enum "oper-nal-trans-cleint-statsd-notify" {
        value 13;
        description
          "oper nal trans cleint statsd notify";
      }
      enum "oper-nal-trans-client-sub-db-recon" {
        value 14;
        description
          "oper nal trans client sub db recon";
      }
      enum "oper-nal-trans-client-rib-recon" {
        value 15;
        description
          "oper nal trans client rib recon";
      }
      enum "oper-nal-trans-client-im-recon" {
        value 16;
        description
          "oper nal trans client im recon";
      }
      enum "oper-nal-trans-client-ut-test" {
        value 17;
        description
          "oper nal trans client ut test";
      }
      enum "oper-nal-trans-client-max" {
        value 18;
        description
          "oper nal trans client max";
      }
    }
    description
      "nal transaction client type";
  }

  typedef Nal-trans-state {
    type enumeration {
      enum "oper-nal-trans-state-init" {
        value 0;
        description
          "oper nal trans state init";
      }
      enum "oper-nal-trans-state-subscriber" {
        value 1;
        description
          "oper nal trans state subscriber";
      }
      enum "oper-nal-trans-state-subscriber-wait" {
        value 2;
        description
          "oper nal trans state subscriber wait";
      }
      enum "oper-nal-trans-state-invalid" {
        value 3;
        description
          "oper nal trans state invalid";
      }
      enum "oper-nal-trans-state-queued" {
        value 4;
        description
          "oper nal trans state queued";
      }
      enum "oper-nal-trans-state-subscriber-response" {
        value 5;
        description
          "oper nal trans state subscriber response";
      }
      enum "oper-nal-trans-state-check-point-wait" {
        value 6;
        description
          "oper nal trans state check point wait";
      }
      enum "oper-nal-trans-state-end" {
        value 7;
        description
          "oper nal trans state end";
      }
    }
    description
      "Nal transaction subscriber state";
  }

  typedef Nal-intf-oper {
    type enumeration {
      enum "oper-nal-ip-sub-o-per-unknown" {
        value 0;
        description
          "oper nal ip sub o per unknown";
      }
      enum "oper-nal-ip-sub-o-per-create" {
        value 1;
        description
          "oper nal ip sub o per create";
      }
      enum "oper-nal-ip-sub-o-per-update" {
        value 2;
        description
          "oper nal ip sub o per update";
      }
      enum "oper-nal-ip-sub-o-per-rollback" {
        value 3;
        description
          "oper nal ip sub o per rollback";
      }
      enum "oper-nal-ip-sub-o-per-delete" {
        value 4;
        description
          "oper nal ip sub o per delete";
      }
    }
    description
      "Ipsub operation types";
  }

  typedef Svm-reconcile-state {
    type enumeration {
      enum "oper-svm-recon-state-idle" {
        value 0;
        description
          "oper svm recon state idle";
      }
      enum "oper-svm-recon-state-created" {
        value 1;
        description
          "oper svm recon state created";
      }
      enum "oper-svm-recon-state-dt-associated" {
        value 2;
        description
          "oper svm recon state dt associated";
      }
      enum "oper-svm-recon-state-up-installed" {
        value 3;
        description
          "oper svm recon state up installed";
      }
      enum "oper-svm-recon-state-up-associated" {
        value 4;
        description
          "oper svm recon state up associated";
      }
      enum "oper-svm-recon-state-pd-request-ed" {
        value 5;
        description
          "oper svm recon state pd request ed";
      }
      enum "oper-svm-recon-state-max" {
        value 6;
        description
          "oper svm recon state max";
      }
    }
    description
      "SVM reconcile state";
  }

  typedef Nal-spa-oper {
    type enumeration {
      enum "oper-spa-o-per-type-create" {
        value 1;
        description
          "oper spa o per type create";
      }
      enum "oper-spa-o-per-type-modify" {
        value 2;
        description
          "oper spa o per type modify";
      }
      enum "oper-spa-o-per-type-delete" {
        value 3;
        description
          "oper spa o per type delete";
      }
      enum "oper-spa-o-per-type-max" {
        value 4;
        description
          "oper spa o per type max";
      }
    }
    description
      "SPA oper type";
  }

  typedef Svn-sub-state {
    type enumeration {
      enum "oper-nal-svm-state-unknown" {
        value 0;
        description
          "oper nal svm state unknown";
      }
      enum "oper-nal-svm-state-created" {
        value 1;
        description
          "oper nal svm state created";
      }
      enum "oper-nal-svm-state-install-request-ed" {
        value 2;
        description
          "oper nal svm state install request ed";
      }
      enum "oper-nal-svm-state-install-req-failed" {
        value 3;
        description
          "oper nal svm state install req failed";
      }
      enum "oper-nal-svm-state-install-failed" {
        value 4;
        description
          "oper nal svm state install failed";
      }
      enum "oper-nal-svm-state-installed" {
        value 5;
        description
          "oper nal svm state installed";
      }
      enum "oper-nal-svm-state-un-install-request-ed" {
        value 6;
        description
          "oper nal svm state un install request ed";
      }
      enum "oper-nal-svm-state-un-install-req-failed" {
        value 7;
        description
          "oper nal svm state un install req failed";
      }
      enum "oper-nal-svm-state-un-install-failed" {
        value 8;
        description
          "oper nal svm state un install failed";
      }
      enum "oper-nal-svm-state-un-installed" {
        value 9;
        description
          "oper nal svm state un installed";
      }
      enum "oper-nal-svm-state-up-assoc-request-ed" {
        value 10;
        description
          "oper nal svm state up assoc request ed";
      }
      enum "oper-nal-svm-state-up-assoc-req-failed" {
        value 11;
        description
          "oper nal svm state up assoc req failed";
      }
      enum "oper-nal-svm-state-up-assoc-failed" {
        value 12;
        description
          "oper nal svm state up assoc failed";
      }
      enum "oper-nal-svm-state-up-unassoc-request-ed" {
        value 13;
        description
          "oper nal svm state up unassoc request ed";
      }
      enum "oper-nal-svm-state-up-unassoc-req-failed" {
        value 14;
        description
          "oper nal svm state up unassoc req failed";
      }
      enum "oper-nal-svm-state-up-unassoc-failed" {
        value 15;
        description
          "oper nal svm state up unassoc failed";
      }
      enum "oper-nal-svm-state-srv-assoc-request-ed" {
        value 16;
        description
          "oper nal svm state srv assoc request ed";
      }
      enum "oper-nal-svm-state-srv-assoc-req-failed" {
        value 17;
        description
          "oper nal svm state srv assoc req failed";
      }
      enum "oper-nal-svm-state-srv-assoc-failed" {
        value 18;
        description
          "oper nal svm state srv assoc failed";
      }
      enum "oper-nal-svm-state-srv-unassoc-request-ed" {
        value 19;
        description
          "oper nal svm state srv unassoc request ed";
      }
      enum "oper-nal-svm-state-srv-unassoc-req-failed" {
        value 20;
        description
          "oper nal svm state srv unassoc req failed";
      }
      enum "oper-nal-svm-state-srv-unassoc-failed" {
        value 21;
        description
          "oper nal svm state srv unassoc failed";
      }
      enum "oper-nal-svm-state-pd-request-ed" {
        value 22;
        description
          "oper nal svm state pd request ed";
      }
      enum "oper-nal-svm-state-pd-req-failed" {
        value 23;
        description
          "oper nal svm state pd req failed";
      }
      enum "oper-nal-svm-state-rb-pd-request-ed" {
        value 24;
        description
          "oper nal svm state rb pd request ed";
      }
      enum "oper-nal-svm-state-rb-pd-req-failed" {
        value 25;
        description
          "oper nal svm state rb pd req failed";
      }
      enum "oper-nal-svm-state-pd-cfg-generated" {
        value 26;
        description
          "oper nal svm state pd cfg generated";
      }
      enum "oper-nal-svm-state-pd-cfg-gen-failed" {
        value 27;
        description
          "oper nal svm state pd cfg gen failed";
      }
      enum "oper-nal-svm-state-activate-request-ed" {
        value 28;
        description
          "oper nal svm state activate request ed";
      }
      enum "oper-nal-svm-state-activate-req-fail" {
        value 29;
        description
          "oper nal svm state activate req fail";
      }
      enum "oper-nal-svm-state-activate-fail" {
        value 30;
        description
          "oper nal svm state activate fail";
      }
      enum "oper-nal-svm-state-activated" {
        value 31;
        description
          "oper nal svm state activated";
      }
      enum "oper-nal-svm-state-pd-failed" {
        value 32;
        description
          "oper nal svm state pd failed";
      }
      enum "oper-nal-svm-state-pd-complete" {
        value 33;
        description
          "oper nal svm state pd complete";
      }
      enum "oper-nal-svm-state-destroy-request-ed" {
        value 34;
        description
          "oper nal svm state destroy request ed";
      }
      enum "oper-nal-svm-state-destroy-req-failed" {
        value 35;
        description
          "oper nal svm state destroy req failed";
      }
      enum "oper-nal-svm-state-destroy-failed" {
        value 36;
        description
          "oper nal svm state destroy failed";
      }
      enum "oper-nal-svm-state-destroyed" {
        value 37;
        description
          "oper nal svm state destroyed";
      }
      enum "oper-nal-svm-state-rollback" {
        value 38;
        description
          "oper nal svm state rollback";
      }
      enum "oper-nal-svm-state-replace-req-failed" {
        value 39;
        description
          "oper nal svm state replace req failed";
      }
      enum "oper-nal-svm-state-replace-request-ed" {
        value 40;
        description
          "oper nal svm state replace request ed";
      }
      enum "oper-nal-svm-state-max" {
        value 41;
        description
          "oper nal svm state max";
      }
    }
    description
      "SVM state of a subscriber";
  }

  typedef Svm-sub-oper {
    type enumeration {
      enum "oper-nal-svm-sub-o-per-unknown" {
        value 0;
        description
          "oper nal svm sub o per unknown";
      }
      enum "oper-nal-svm-sub-o-per-create" {
        value 1;
        description
          "oper nal svm sub o per create";
      }
      enum "oper-nal-svm-sub-o-per-update" {
        value 2;
        description
          "oper nal svm sub o per update";
      }
      enum "oper-nal-svm-sub-o-per-delete" {
        value 3;
        description
          "oper nal svm sub o per delete";
      }
      enum "oper-nal-svm-sub-o-per-rollback" {
        value 4;
        description
          "oper nal svm sub o per rollback";
      }
      enum "oper-nal-svm-sub-o-per-cleanup" {
        value 5;
        description
          "oper nal svm sub o per cleanup";
      }
      enum "oper-nal-svm-sub-o-per-save" {
        value 6;
        description
          "oper nal svm sub o per save";
      }
      enum "oper-nal-svm-sub-o-per-max" {
        value 7;
        description
          "oper nal svm sub o per max";
      }
    }
    description
      "Operation types from FSM to SVM";
  }

  typedef Oper-nal-db-subscriber {
    type enumeration {
      enum "invalid" {
        value 0;
        description
          "Invalid";
      }
      enum "ipoe" {
        value 1;
        description
          "IPoE";
      }
      enum "pppoe" {
        value 2;
        description
          "PPPoE";
      }
      enum "l2tp" {
        value 3;
        description
          "L2TP";
      }
    }
    description
      "Nal Subscriber type";
  }

  typedef Oper-nal-db-subscriber-state {
    type enumeration {
      enum "init" {
        value 0;
        description
          "Invalid";
      }
      enum "connecting" {
        value 1;
        description
          "connecting";
      }
      enum "connected" {
        value 2;
        description
          "connected";
      }
      enum "activated" {
        value 3;
        description
          "activated";
      }
      enum "idle" {
        value 4;
        description
          "idle";
      }
      enum "disconnecting" {
        value 5;
        description
          "disconnecting";
      }
      enum "end" {
        value 6;
        description
          "end";
      }
    }
    description
      "Nal Subscriber State";
  }

  grouping ncs_template_NAL-MAIN-EDM-PROCESS-INFO {
    description
      "Process readiness data";
    leaf nal-process-restart-flag {
      type string;
      description
        "NAL Process's restart flag";
    }
    leaf nalot-connection-sts-flag {
      type string;
      description
        "NAL Object-tracking connection up status flag";
    }
    leaf nal-clear-session-timer-flag {
      type string;
      description
        "NAL Clear-Session Timer Flag";
    }
    leaf nal-clear-feature-timer-flag {
      type string;
      description
        "NAL Clear-Feature Timer Flag";
    }
    leaf disconnect-history-file-logg-enable-flag {
      type string;
      description
        "Subscriber Disconnect-history file-logging
         disable feature flag";
    }
    leaf test-client-cfg-enabled-flag {
      type string;
      description
        "NAL Test Client config enabled flag";
    }
    leaf nal-pre-init-role {
      type string;
      description
        "NAL Process's HA PreInit Role";
    }
    leaf nal-role {
      type string;
      description
        "NAL Process's HA Role";
    }
    leaf node-id {
      type string;
      description
        "NAL Process's running-instance location node-id";
    }
    leaf nalrsi-ctx-file-descriptor {
      type string;
      description
        "NAL RSI contex file-desc value";
    }
    leaf nal-pid-misc-flags {
      type string;
      description
        "NAL Main context Miscellaneous flags";
    }
    leaf nalsvm-subdb-conn-sts-flag {
      type string;
      description
        "NAL Process's SVM context SUBDB
         connection-status flag";
    }
    leaf nalsvmp-done-req-id {
      type string;
      description
        "NAL Process's SVM Produce-Done req-id";
    }
    leaf nalsvm-recon-last-upid {
      type string;
      description
        "NAL SVM Reconciliation Last UPID";
    }
    leaf nalsvm-reconn-pending-req {
      type string;
      description
        "NAL SVM Reconciliation Pending Requests";
    }
    leaf nalsvm-reconn-max-req {
      type string;
      description
        "NAL SVM Reconciliation Max Requests";
    }
    leaf nal-sub-ctx-replay-in-progress {
      type string;
      description
        "NAL Subscriber context stale cache-size";
    }
    leaf nal-subs-ctx-cache-queue-size {
      type string;
      description
        "NAL Subscriber context stale cache-size";
    }
    leaf nal-subs-ctx-stale-queue-size {
      type string;
      description
        "NAL Subscriber context stale queue-size";
    }
    leaf disconnect-queue-size {
      type string;
      description
        "NAL Subscriber disconnect queue size";
    }
    leaf nal-msg-local-seq-no {
      type string;
      description
        "NAL Message locally generated seq_no";
    }
    leaf nal-msg-seq-no {
      type string;
      description
        "NAL message seq_no towards SPA";
    }
    leaf nal-bulk-disc-invoke-time {
      type string;
      description
        "NAL Bulk Disconnect-session start time";
    }
    leaf nal-statistics-hold-timeout-val {
      type string;
      description
        "NAL Stats Hold-Timeout value";
    }
    leaf nal-statistics-hold-req-count {
      type string;
      description
        "NAL Stats Hold-Request Count";
    }
    leaf nal-statistics-hold-req-max {
      type string;
      description
        "NAL Stats Hold-Request Max-threshold";
    }
    leaf nal-statistics-stop-req-count {
      type string;
      description
        "NAL Stats Stop-Request counter";
    }
    leaf nal-statistics-interim-req-count {
      type string;
      description
        "NAL Stats Interim-Request counter";
    }
    leaf nal-clear-session-stats-req-count {
      type string;
      description
        "NAL Clear-Session Stats Request counter";
    }
    leaf nal-clear-feature-stats-req-count {
      type string;
      description
        "NAL Clear-Feature Stats Request counter";
    }
    leaf nal-stats-processing-flags {
      type string;
      description
        "NAL Statistics miscelleaneous flags";
    }
    leaf create-in-progress {
      type string;
      description
        "Number of subscriber create in progress";
    }
    leaf delete-in-progress {
      type string;
      description
        "Number of subscriber delete in progress";
    }
    leaf update-in-progress {
      type string;
      description
        "Number of subscriber update in progress";
    }
    leaf cp-recon-duration {
      type string;
      description
        "CP recon duration";
    }
    leaf cp-recon-flags {
      type string;
      description
        "CP recon flags";
    }
    leaf cp-replay-reqs-in-progress {
      type string;
      description
        "CP replay reqs in progress";
    }
    leaf cp-replay-subs-in-progress {
      type string;
      description
        "CP replay subs in progress";
    }
  }

  grouping ncs_template_NAL-MAIN-EDM-VRF-AFI-INSTANCE {
    description
      "NAL MAIN EDM VRF AFI INSTANCE";
    leaf vrf-address-family {
      type string;
      description
        "VRF Table Address-Family";
    }
    leaf vrf-info-table-flag {
      type string;
      description
        "VRF Table Flags";
    }
    leaf vrf-table-sync-flag {
      type string;
      description
        "buffer complete sent to RIB";
    }
    leaf protocol-id {
      type string;
      description
        "Protocol Id";
    }
    leaf vrf-table-id {
      type string;
      description
        "VRF Table-Id";
    }
    leaf vrf-pending-routes {
      type string;
      description
        "VRF Table Pending-routes";
    }
    leaf ref-count {
      type string;
      description
        "No.of interfaces referencing this table";
    }
    leaf max-ref-count {
      type string;
      description
        "Max No. of interfaces allowed";
    }
  }

  grouping ncs_template_NAL-MAIN-EDM-VRFTBL-INFO {
    description
      "NAL VRF Table Info bag";
    leaf vrf-name-xr {
      type string;
      description
        "Vrf Name";
    }
    list nal-vrf-afi-instance-info {
      // NCS patched for predictable order
      ordered-by user;
      description
        "NAL VRF AFI Instance table info";
      uses ncs_template_NAL-MAIN-EDM-VRF-AFI-INSTANCE;
    }
  }

  grouping ncs_template_NAL-MAIN-EDM-OC-ENTRY {
    description
      "NAL owner-channel entries";
    leaf afi {
      type string;
      description
        "Address family for this route";
    }
    leaf ipv6-prefix {
      type string;
      description
        "ipv6 prefix address";
    }
    leaf ipv4-prefix {
      type string;
      description
        "ipv4 prefix address";
    }
    leaf prefix-length {
      type string;
      description
        "Prefix length";
    }
    leaf primary-address {
      type string;
      description
        "Secondary address";
    }
    leaf state {
      type ncs_template_Nal-main-edm-oc-state;
      description
        "Status";
    }
    leaf vrf-xr {
      type string;
      description
        "VRF name";
    }
    leaf if-handle {
      type xr:ncs_template_Interface-name;
      description
        "Interface Handle";
    }
    leaf tag {
      type string;
      description
        "Route tag";
    }
    leaf flags {
      type string;
      description
        "Checkpoint flags";
    }
  }

  grouping ncs_template_NAL-AIPC-SERVER-STATS-DATA {
    description
      "aipc server stats";
    leaf conn-present {
      type string;
      description
        "connection status";
    }
    leaf service-name {
      type string;
      description
        "process Name";
    }
    leaf tx-attempt-count {
      type string;
      description
        "Tx attempt count";
    }
    leaf tx-count {
      type string;
      description
        "tx count";
    }
    leaf rx-count {
      type string;
      description
        "Rx count";
    }
    leaf notify-connect-count {
      type string;
      description
        "Notify connect count";
    }
    leaf notify-queue-high-count {
      type string;
      description
        "Notify Queue High count";
    }
    leaf notify-queue-low-count {
      type string;
      description
        "Notify Queue low count";
    }
    leaf notify-queue-full-count {
      type string;
      description
        "Notify Queue full count";
    }
    leaf notify-data-waiting-count {
      type string;
      description
        "Notify data waiting count";
    }
    leaf notify-error-count {
      type string;
      description
        "Notify error count";
    }
    leaf notify-close-count {
      type string;
      description
        "Notify close count";
    }
    leaf notify-sendstatus-count {
      type string;
      description
        "Notify send status count";
    }
    leaf notify-open-count {
      type string;
      description
        "Notify open count";
    }
    leaf pulse-data-waiting-count {
      type string;
      description
        "Pulse Data waiting count";
    }
    leaf queue-full {
      type string;
      description
        "Queue full";
    }
    leaf queue-full-drop {
      type string;
      description
        "Queue full drop";
    }
    leaf queue-ewouldblock-count {
      type string;
      description
        "queue would block count";
    }
    leaf outstanding-buffers {
      type string;
      description
        "Outstanding Buffers";
    }
    leaf cumulative-overflow-msgs {
      type string;
      description
        "cumulative overflow message";
    }
    leaf hwm-overflow-msgs {
      type string;
      description
        "Hwm overflow msg";
    }
    leaf get-mtu-failure {
      type string;
      description
        "Get Mtu Failure";
    }
    leaf get-buffer-failure {
      type string;
      description
        "get Buffer Failure";
    }
    leaf get-buffer-datap-failure {
      type string;
      description
        "get Buffer datap Failure";
    }
    leaf conn-failure {
      type string;
      description
        "Conn Failure";
    }
    leaf send-failure {
      type string;
      description
        "Send Failure";
    }
    leaf receive-failure {
      type string;
      description
        "receive Failure";
    }
    leaf release-buffer-failure {
      type string;
      description
        "Release Buffer failure";
    }
    leaf overflow-q-flush-count {
      type string;
      description
        "Overflow flush count";
    }
    leaf notify-queue-low-count-after-high {
      type string;
      description
        "notify queue low count after high";
    }
    leaf last-high-watermark-count-timestamp {
      type string;
      description
        "High WaterMark timestamp";
    }
    leaf last-low-watermark-count-timestamp {
      type string;
      description
        "Low WaterMark timestamp";
    }
  }

  grouping ncs_template_NAL-MAIN-EDM-OC-SUMMARY {
    description
      "Dynamic routes and OC entries summary";
    leaf v4-oc-entries {
      type string;
      description
        "Total V4 OC entries primary/secondary";
    }
    leaf v6-oc-entries {
      type string;
      description
        "Total V6 OC entries";
    }
    leaf v4-primary-entries {
      type string;
      description
        "Total primary addresses";
    }
    leaf v4-sec-entries {
      type string;
      description
        "Total secondary addresses";
    }
    leaf v4-rib-entries {
      type string;
      description
        "Total V4 RIB entries";
    }
    leaf v6-rib-entries {
      type string;
      description
        "Total V6 RIB entries";
    }
    leaf replayed-oc-entries {
      type string;
      description
        "Total entries replayed during last reconcile";
    }
  }

  grouping ncs_template_NAL-MAIN-EDM-CP-CONN-STS-INFO {
    description
      "NAL User & Control-plane connection status
       information";
    leaf nal-transport-user-plane-src-conn-flag {
      type string;
      description
        "True if NAL Transport user-plane source
         connection address is configured";
    }
    leaf nalcp-svr-connect-sts {
      type ncs_template_Nal-cp-connection-status;
      description
        "NAL control-plane connection-status value";
    }
    leaf nalcp-svr-connect-sts-time {
      type string;
      description
        "NAL control-plane connection-status time stamp";
    }
    leaf nalcp-svr-connect-sts-prev {
      type ncs_template_Nal-cp-connection-status;
      description
        "NAL control-plane prev connection-status value";
    }
    leaf nalcp-svr-connect-sts-time-prev {
      type string;
      description
        "NAL control-plane prev connection-status time
         stamp";
    }
    leaf cp-assoc-status {
      type ncs_template_Nal-cp-assoc-status;
      description
        "Control plane association status";
    }
    leaf cp-assoc-status-time {
      type string;
      description
        "Control plane association status time stamp";
    }
    leaf nal-transport-user-plane-source-conn-addr-family {
      type string;
      description
        "NAL Transport user-plane source server
         connection address-family";
    }
    leaf nal-transport-up-source-ipv4-address {
      type string;
      description
        "NAL Transport user-plane server connection IPv4
         address";
    }
    leaf nal-transport-up-source-ipv6-address {
      type string;
      description
        "NAL Transport user-plane server connection IPv6
         address";
    }
    leaf nal-transport-up-src-loop-back-if-name {
      type string;
      description
        "NAL Transport user-plane server loopback
         interface-name";
    }
    leaf nal-transport-up-source-gtpu-port {
      type string;
      description
        "NAL Transport user-plane server connection GTPU
         port-number";
    }
    leaf nal-transport-up-source-pfcp-port {
      type string;
      description
        "NAL Transport user-plane server connection PFCP
         port-number";
    }
    leaf nal-transport-up-source-vrf-name {
      type string;
      description
        "NAL Transport user-plane server connection
         VRF-Name";
    }
    leaf nal-transport-control-plane-primary-srv-addr-family {
      type string;
      description
        "NAL transport control-plane primary-server
         connection address-family";
    }
    leaf nal-transport-cp-primary-ipv4-address {
      type string;
      description
        "NAL Transport C-plane primary-server connection
         IPv4 address";
    }
    leaf nal-transport-cp-primary-ipv6-address {
      type string;
      description
        "NAL Transport C-plane primary-server connection
         IPv6 address";
    }
    leaf nal-transport-cp-server-gtpu-port {
      type string;
      description
        "NAL Transport C-plane server's GTPU port-number";
    }
    leaf nal-transport-cp-server-pfcp-port {
      type string;
      description
        "NAL Transport C-plane server's PFCP port-number";
    }
    leaf retry-count {
      type string;
      description
        "CP association request retry count";
    }
  }

  grouping ncs_template_NAL-MAIN-EDM-PROCESS-READINESS {
    description
      "Process readiness data";
    leaf resync-pending-flags {
      type string;
      description
        "Resync operations pending for NAL process";
    }
    leaf sir-ready {
      type string;
      description
        "Status of SIR readiness";
    }
  }

  grouping ncs_template_NAL-MAIN-EDM-PARENT-INTF-INITIATOR-DATA {
    description
      "NAL MAIN EDM PARENT INTF INITIATOR DATA";
    leaf is-configured {
      type string;
      description
        "Ture if the initiator is configred";
    }
  }

  grouping ncs_template_NAL-MAIN-EDM-PARENT-INTF-INITIATORS {
    description
      "Initiator protocol details";
    container intiator-type {
      description
        "DHCP information";
      uses ncs_template_NAL-MAIN-EDM-PARENT-INTF-INITIATOR-DATA;
    }
  }

  grouping ncs_template_NAL-MAIN-EDM-PARENT-INTF-DATA {
    description
      "Parent interface data";
    container initiators {
      description
        "Configurational state-statistics for each
         initiating protocol enabled on this parent
         interface";
      uses ncs_template_NAL-MAIN-EDM-PARENT-INTF-INITIATORS;
    }
    leaf parent-interface {
      type xr:ncs_template_Interface-name;
      description
        "Ifhandle of parent interface";
    }
    leaf interface-creation-time {
      type string;
      description
        "Interface creation time in Month Date HH:MM:SS
         format";
    }
    leaf age {
      type string;
      description
        "Age in HH:MM:SS format";
    }
    leaf parent-intf-flags {
      type string;
      description
        "Access Interface flags";
    }
    leaf nal-ether-encap {
      type string;
      description
        "Ether Encap Attribute";
    }
    leaf effective-bandwidth {
      type string;
      description
        "Effective Bandwidth";
    }
    leaf max-bandwidth {
      type string;
      description
        "Maximum Bandwidth";
    }
    leaf link-local {
      type string;
      description
        "link local address";
    }
  }

  grouping ncs_template_NAL-MAIN-EDM-SPA-RT-PROV-HIST-DATA {
    description
      "Route provision request response history";
    container request-response-timestamp {
      description
        "Timestamp of request or response";
      uses ncs_template_NAL-TIMESPEC;
    }
    leaf type {
      type ncs_template_Nal-main-edm-spa-rt-hist;
      description
        "Type of route history data";
    }
    list data {
      // NCS patched for predictable order
      ordered-by user;
      description
        "Request or Response";
      leaf entry {
        type string;
        description
          "Request or Response";
      }
    }
  }

  grouping ncs_template_NAL-MAIN-EDM-CHUNK-DATA {
    description
      "NAL MAIN EDM CHUNK DATA";
    leaf chunk-name {
      type string;
      description
        "Chunk Name";
    }
    leaf chunk-id {
      type string;
      description
        "Chunk Id";
    }
    leaf chunk-total-alloc {
      type string;
      description
        "Total number of chunk malloc done";
    }
    leaf chunk-total-free {
      type string;
      description
        "Total number of chunk free done";
    }
    leaf chunk-in-use {
      type string;
      description
        "total number of chunk blocks in use";
    }
  }

  grouping ncs_template_NAL-MAIN-EDM-CHUNK-STATS {
    description
      "NAL MAIN EDM CHUNK STATS";
    list chunk-stat {
      // NCS patched for predictable order
      ordered-by user;
      description
        "Chunk Memory statistics";
      uses ncs_template_NAL-MAIN-EDM-CHUNK-DATA;
    }
  }

  grouping ncs_template_NAL-SUBSCRIBER-DISCONNECT-HISTORY-DATA {
    description
      "Subscriber disconnect history bag";
    container fail-data {
      description
        "failed data";
      uses ncs_template_NAL-LAST-FAILED-DATA;
    }
    container session-data {
      description
        "subscriber session data info";
      uses ncs_template_NAL-SUBSCRIBER-SESSION-INFO;
    }
    leaf disc-cause {
      type string;
      description
        "Disconnect code";
    }
    list event-history {
      // NCS patched for predictable order
      ordered-by user;
      description
        "subscriber event history";
      uses ncs_template_NAL-SUB-DISC-HISTORY-EVT-DATA;
    }
  }

  grouping ncs_template_EVT-HIST-ENTRY {
    description
      "Event history Entry";
    leaf evt-timestamp {
      type string;
      description
        "The timestamp of the event";
    }
    leaf evt-name {
      type string;
      description
        "Event name";
    }
    leaf evt-type {
      type string;
      description
        "Event type";
    }
    leaf evt-many {
      type string;
      description
        "Multiple instance flag";
    }
    leaf evt-sticky {
      type string;
      description
        "Sticky flag";
    }
    list evt-data {
      // NCS patched for predictable order
      ordered-by user;
      description
        "Optional data";
      leaf entry {
        type string;
        description
          "Optional data";
      }
    }
  }

  grouping ncs_template_EVT-HIST-INFO {
    description
      "Per object event history";
    leaf evt-class-name {
      type string;
      description
        "Class name string";
    }
    list evt-entry {
      // NCS patched for predictable order
      ordered-by user;
      description
        "Array of event entries";
      uses ncs_template_EVT-HIST-ENTRY;
    }
  }

  grouping ncs_template_NAL-MAIN-EDM-EVENTS {
    description
      "NAL Main process init information";
    container event-history {
      description
        "Main process boot up events";
      uses ncs_template_EVT-HIST-INFO;
    }
    container im-event-history {
      description
        "IM module events";
      uses ncs_template_EVT-HIST-INFO;
    }
    container svm-event-history {
      description
        "SVM module events";
      uses ncs_template_EVT-HIST-INFO;
    }
    container rib-event-history {
      description
        "RIB module events";
      uses ncs_template_EVT-HIST-INFO;
    }
    container cp-event-history {
      description
        "CP module events";
      uses ncs_template_EVT-HIST-INFO;
    }
    container config-event-history {
      description
        "Config module events";
      uses ncs_template_EVT-HIST-INFO;
    }
  }

  grouping ncs_template_NAL-SUBSCRIBER-AFI-SUMMARY {
    description
      "Subscriber afi summary data";
    leaf none {
      type string;
      description
        "No afi";
    }
    leaf ipv4 {
      type string;
      description
        "IPv4 count";
    }
    leaf ipv6 {
      type string;
      description
        "IPv6 count";
    }
    leaf dual {
      type string;
      description
        "Dual count";
    }
    leaf total {
      type string;
      description
        "Total";
    }
  }

  grouping ncs_template_NAL-SUBSCRIBER-STATE-SUMMARY {
    description
      "Subscriber state summary data";
    leaf initializing {
      type string;
      description
        "Initializing";
    }
    leaf connecting {
      type string;
      description
        "Connecting";
    }
    leaf connected {
      type string;
      description
        "Connected";
    }
    leaf activated {
      type string;
      description
        "Activated";
    }
    leaf idle {
      type string;
      description
        "Idle";
    }
    leaf disconnecting {
      type string;
      description
        "Disconnecting";
    }
    leaf total {
      type string;
      description
        "Total";
    }
  }

  grouping ncs_template_NAL-SUBSCRIBER-SUMMARY {
    description
      "Subscriber summary data";
    container ipoe-state-summary {
      description
        "IPoE State Summary";
      uses ncs_template_NAL-SUBSCRIBER-STATE-SUMMARY;
    }
    container pppoe-state-summary {
      description
        "PPPoE State Summary";
      uses ncs_template_NAL-SUBSCRIBER-STATE-SUMMARY;
    }
    container ipoe-afi-summary {
      description
        "IPoE AFI Summary";
      uses ncs_template_NAL-SUBSCRIBER-AFI-SUMMARY;
    }
    container pppoe-afi-summary {
      description
        "PPPoE AFI Summary";
      uses ncs_template_NAL-SUBSCRIBER-AFI-SUMMARY;
    }
  }

  grouping ncs_template_NAL-SUBSCRIBER-DISCONNECT-HISTORY-UNIQUE-DATA {
    description
      "Subscriber unique disconnect history Bag";
    leaf disconnect-unique-session-count {
      type string;
      description
        "Number of sessions disconnected with this error
         code";
    }
    leaf disconnect-errorcode {
      type string;
      description
        "error code";
    }
    leaf sub-if-name {
      type string;
      description
        "Interface Name";
    }
    leaf sub-disc-time {
      type string;
      description
        "Subscriber Disconnect Time ";
    }
    leaf disc-reason {
      type string;
      description
        "Disconnect reason";
    }
  }

  grouping ncs_template_NAL-SERVICE-PROFILE-DATA {
    description
      "NAL service profile information";
    leaf service-name {
      type string;
      description
        "Name of the service";
    }
    leaf service-id {
      type string;
      description
        "Service id assigned by SUBDB";
    }
    leaf use-count {
      type string;
      description
        "Number of subscribers using this profile";
    }
    leaf state {
      type ncs_template_Svm-service-state;
      description
        "State of the service";
    }
    leaf fail-err {
      type string;
      description
        "Installation failure rc";
    }
    leaf stale-timer-remaining {
      type string;
      description
        "stale timer remaining";
    }
    leaf assoc-in-progress {
      type string;
      description
        "No of subscribers need to use this profile";
    }
    list wait-upi-dqueue {
      // NCS patched for predictable order
      ordered-by user;
      description
        "List of UPIDs waiting for this service";
      leaf entry {
        type string;
        description
          "List of UPIDs waiting for this service";
      }
    }
  }

  grouping ncs_template_IPSUB-BASE-INIT {
    description
      "ipsub base init data";
    leaf type {
      type string;
      description
        "Init data type";
    }
    leaf version {
      type string;
      description
        "Init data version";
    }
    leaf length {
      type string;
      description
        "Init data length";
    }
  }

  grouping ncs_template_IPSUB-INTF-INIT-TYPE {
    description
      "Subscriber intf init data";
    container base {
      description
        "base";
      uses ncs_template_IPSUB-BASE-INIT;
    }
    leaf subscriber-mac {
      type string;
      description
        "MAC address";
    }
    leaf vlan-tag-count {
      type string;
      description
        "Vlan tag count";
    }
    leaf vrf-table-id {
      type string;
      description
        "Vrf table id ";
    }
    leaf v6-vrf-table-id {
      type string;
      description
        "Ipv6 Vrf table id ";
    }
    leaf up-link-gre-key {
      type string;
      description
        "Up link gre key";
    }
    leaf down-link-gre-key {
      type string;
      description
        "Down link gre key";
    }
    leaf subscriber-gw-mac {
      type string;
      description
        "Gateway MAC address";
    }
    leaf sub-attr-bits {
      type string;
      description
        "Subscriber attr bits";
    }
    leaf sub-info-bits {
      type string;
      description
        "Subscriber info bits";
    }
    leaf subscriber-ipv4 {
      type string;
      description
        "Subscriber IPv4";
    }
    leaf nexthop-ipv4 {
      type string;
      description
        "next hop  IPv4 address";
    }
    leaf subscriber-ipv6 {
      type string;
      description
        "Subscriber Ipv6 address";
    }
    leaf subscriber-ipv6-prefix {
      type string;
      description
        "Subscriber Ipv6 address";
    }
    leaf nexthop-ipv6 {
      type string;
      description
        "Nexthop Ipv6 address";
    }
    leaf v6-len {
      type string;
      description
        "V6 len";
    }
    leaf v6-prefix-len {
      type string;
      description
        "V6 prefix len";
    }
    leaf template-ifh {
      type string;
      description
        "Template interface handle";
    }
    leaf ipv4-mtu {
      type string;
      description
        "Ipv4 MTU";
    }
    leaf ipv6-mtu {
      type string;
      description
        "Ipv6 MTU";
    }
    leaf odns-deviceid-higher {
      type string;
      description
        "ODNS device id highter";
    }
    leaf odns-deviceid-lower {
      type string;
      description
        "ODNS device id Lower";
    }
    list vlan-stack {
      // NCS patched for predictable order
      ordered-by user;
      // NCS drop max-elements statement
      description
        "vlan stack type";
      uses ncs_template_DOT1Q-TAG-DATA-TYPE;
    }
  }

  grouping ncs_template_NAL-TRANS-CONTEXT-DATA {
    description
      "Nal transaction context";
    leaf state {
      type ncs_template_Nal-trans-state;
      description
        "Subscriber transactio state";
    }
    leaf client-type {
      type ncs_template_Nal-trans-client-data;
      description
        "Client type indicate who is triggert this
         transction";
    }
    leaf trans-id {
      type string;
      description
        "Transaction ID";
    }
    leaf disconnect-ack {
      type string;
      description
        "Disconnect Ack";
    }
    leaf module-err {
      type string;
      description
        "Error generated by sub module";
    }
    leaf module-interaction-mask {
      type string;
      description
        "Flag to indicate which sub-module interactions
         are in progress";
    }
    leaf rollback-module-mask {
      type string;
      description
        "Flag to indicate which sub-module rollback needs
         to be invoked";
    }
    leaf pending-cb-bitmask {
      type string;
      description
        "Flag indicating pending callbacks for this
         transaction";
    }
  }

  grouping ncs_template_NAL-TRANS-SUB-CONTEXT-DATA {
    description
      "Subscriber transaction context";
    container trans-context {
      description
        "trans context";
      uses ncs_template_NAL-TRANS-CONTEXT-DATA;
    }
  }

  grouping ncs_template_NAL-IPSUB-INFLIGHT-DATA {
    description
      "Nal ipsub inflight data";
    leaf opearation {
      type ncs_template_Nal-intf-oper;
      description
        "Operation in progress";
    }
    leaf flags {
      type string;
      description
        "Flags to represent pending activities";
    }
    leaf fail-rc {
      type string;
      description
        "Backup of update error, internal rollback in
         progresss";
    }
  }

  grouping ncs_template_SVM-INFLIGHT-DATA {
    description
      "SVM inflight data";
    leaf service-name {
      type string;
      description
        "Name of the service";
    }
    leaf service-id {
      type string;
      description
        "Service id assigned by SUBDB";
    }
    leaf operation {
      type ncs_template_Nal-spa-oper;
      description
        "Operation to be performed";
    }
    leaf service-flags {
      type string;
      description
        "Service flags";
    }
    leaf params-list {
      type string;
      description
        "Attribute list of service params";
    }
    leaf feature-id {
      type string;
      description
        "Feature ID";
    }
  }

  grouping ncs_template_NAL-SVM-INFLIGHT-DATA {
    description
      "Nal SVM inflight data";
    leaf opearation {
      type ncs_template_Svm-sub-oper;
      description
        "Operation in progress";
    }
    leaf state {
      type ncs_template_Svn-sub-state;
      description
        "State of the subscriber SVM data";
    }
    leaf fail-rc {
      type string;
      description
        "Fail rc";
    }
    leaf up-list {
      type string;
      description
        "User profile attribute list";
    }
    leaf remove-list {
      type string;
      description
        "User profile attribute remove list";
    }
    leaf service-index {
      type string;
      description
        "Service that is currently under process";
    }
    leaf subdb-pd-req-id {
      type string;
      description
        "SUBDB produce done req id";
    }
    leaf reconcile-state {
      type ncs_template_Svm-reconcile-state;
      description
        "Reconcilitation state";
    }
    list service {
      // NCS patched for predictable order
      ordered-by user;
      description
        "Service list array";
      uses ncs_template_SVM-INFLIGHT-DATA;
    }
  }

  grouping ncs_template_DOT1Q-TAG-DATA-TYPE {
    description
      "dot1q tag type";
    leaf etype {
      type string;
      description
        "etype";
    }
    leaf ucv {
      type string;
      description
        "ucv";
    }
  }

  grouping ncs_template_NAL-SUB-INTF-DATA {
    description
      "subscriber interface info";
    leaf vlan-tag-count {
      type string;
      description
        "Vlan tag count";
    }
    leaf sub-attr-bits {
      type string;
      description
        "Subscriber attr bits";
    }
    leaf flags {
      type string;
      description
        "flags bits";
    }
    leaf vrf-id {
      type string;
      description
        "vrf ID";
    }
    leaf v4-table-id {
      type string;
      description
        "V4 table id";
    }
    leaf v6-table-id {
      type string;
      description
        "V6 table id";
    }
    list vlan-stack {
      // NCS patched for predictable order
      ordered-by user;
      // NCS drop max-elements statement
      description
        "vlan stack type";
      uses ncs_template_DOT1Q-TAG-DATA-TYPE;
    }
  }

  grouping ncs_template_NAL-LAST-FAILED-DATA {
    description
      "NAL subscriber last failed transaction data";
    leaf data {
      type string;
      description
        "Failed data";
    }
    leaf msg-txn-id {
      type string;
      description
        "Message Txn ID";
    }
    leaf sess-txn-id {
      type string;
      description
        "Session Txn ID";
    }
    leaf feature-mask {
      type string;
      description
        "Feature Mask";
    }
    leaf svm-state {
      type string;
      description
        "SVM state";
    }
    leaf ip-sub-flags {
      type string;
      description
        "IPSUB flags";
    }
    leaf pending-callback {
      type string;
      description
        "Pending Callback";
    }
    leaf failure-reason {
      type string;
      description
        "Failure Reason";
    }
    leaf failure-timestamp {
      type string;
      description
        "Failure Timestamp";
    }
  }

  grouping ncs_template_NAL-SUBSCRIBER-DEACTIVATED-SERVICE {
    description
      "NAL subscriber deactivated service information";
    leaf service-name {
      type string;
      description
        "Name of the service";
    }
    leaf deactivation-time {
      type string;
      description
        "service deactivation Time";
    }
    leaf bytes-in {
      type string;
      units "byte";
      description
        "Bytes in";
    }
    leaf bytes-out {
      type string;
      units "byte";
      description
        "Bytes out";
    }
    leaf bytes-ingiga {
      type string;
      units "byte";
      description
        "In Bytes in Giga";
    }
    leaf bytes-out-giga {
      type string;
      units "byte";
      description
        "Bytes out in Giga";
    }
  }

  grouping ncs_template_NAL-SUBSCRIBER-SESSION-DATA-INTERNAL {
    description
      "Subscriber context data";
    container session-data {
      description
        "subscriber session data info";
      uses ncs_template_NAL-SUBSCRIBER-SESSION-INFO;
    }
    container sub-intf {
      description
        "sub intf";
      uses ncs_template_NAL-SUB-INTF-DATA;
    }
    container svm-inflight {
      description
        "svm inflight";
      uses ncs_template_NAL-SVM-INFLIGHT-DATA;
    }
    container ipsub-inflight {
      description
        "ipsub inflight";
      uses ncs_template_NAL-IPSUB-INFLIGHT-DATA;
    }
    container trans-sub-context {
      description
        "trans sub context";
      uses ncs_template_NAL-TRANS-SUB-CONTEXT-DATA;
    }
    container last-init-data {
      description
        "last init data";
      uses ncs_template_IPSUB-INTF-INIT-TYPE;
    }
    leaf subscriber-flags {
      type string;
      description
        "Subscriber flags";
    }
    leaf ha-flags {
      type string;
      description
        "Subscriber flags";
    }
    leaf last-transaction-result {
      type string;
      description
        "Last Transaction Result";
    }
    leaf hold-stats-error {
      type string;
      description
        "hold stats status";
    }
    leaf clear-stats-error {
      type string;
      description
        "clear stats status";
    }
    leaf packets-in {
      type string;
      description
        "No of packets In";
    }
    leaf packets-out {
      type string;
      description
        "No of packets Out";
    }
    leaf ipv4-packets-in {
      type string;
      description
        "No of IPv4 packets In";
    }
    leaf ipv4-packets-out {
      type string;
      description
        "No of IPv4 packets Out";
    }
    leaf ipv4-bytes-in {
      type string;
      description
        "IPv4 Bytes in";
    }
    leaf ipv4-bytes-out {
      type string;
      description
        "IPv4 Bytes out";
    }
    leaf ipv4-bytes-in-giga {
      type string;
      description
        "IPv4 Bytes in Giga";
    }
    leaf ipv4-bytes-out-giga {
      type string;
      description
        "IPv4 Bytes out in Giga";
    }
    leaf ipv6-packets-in {
      type string;
      description
        "No of IPv6 packets In";
    }
    leaf ipv6-packets-out {
      type string;
      description
        "No of IPv6 packets Out";
    }
    leaf ipv6-bytes-in {
      type string;
      description
        "IPv6 Bytes in";
    }
    leaf ipv6-bytes-out {
      type string;
      description
        "IPv6 Bytes out";
    }
    leaf ipv6-bytes-in-giga {
      type string;
      description
        "IPv6 Bytes in Giga";
    }
    leaf ipv6-bytes-out-giga {
      type string;
      description
        "IPv6 Bytes out in Giga";
    }
    leaf transaction-id {
      type string;
      description
        "Subscriber transaction id";
    }
    leaf loopback-name {
      type string;
      description
        "Loopback Name";
    }
    leaf stale-feature-id-info {
      type string;
      description
        "subscriber stale feature id info";
    }
    leaf sus-dconnect-time {
      type string;
      description
        "Subscriber disconnect Time";
    }
    leaf obj-hdl {
      type string;
      description
        "objext handle";
    }
    leaf spi-oattched {
      type string;
      description
        "Has SPIO attached";
    }
    list deactivated-service {
      // NCS patched for predictable order
      ordered-by user;
      description
        "last deactivated services";
      uses ncs_template_NAL-SUBSCRIBER-DEACTIVATED-SERVICE;
    }
    list last-fail {
      // NCS patched for predictable order
      ordered-by user;
      description
        "last failed transaction data";
      uses ncs_template_NAL-LAST-FAILED-DATA;
    }
  }

  grouping ncs_template_NAL-OPER-FADB-RECORD-DATA {
    description
      "NAL OPER FADB RECORD DATA";
    leaf feature-id {
      type string;
      description
        "Subscriber Feature-Id";
    }
    leaf upid {
      type string;
      description
        "User-plane ID";
    }
    leaf service-id {
      type string;
      description
        "Subscriber Service-Id";
    }
    leaf interim-fail-count {
      type string;
      description
        "Interim Fail Count";
    }
    leaf stale-timestamp {
      type string;
      description
        "Stale timestamp";
    }
    leaf hold-rc {
      type string;
      description
        "Hold RC";
    }
    leaf interim-error {
      type string;
      description
        "Interim Error";
    }
  }

  grouping ncs_template_NAL-SUBSCRIBER-SESSION-DATA {
    description
      "NAL subscriber detail data information";
    container sub-info {
      description
        "subscriber session data info";
      uses ncs_template_NAL-SUBSCRIBER-SESSION-INFO;
    }
  }

  grouping ncs_template_NAL-TIMESPEC {
    description
      "Structure to replicate timespec";
    leaf tv-sec {
      type string;
      description
        "Time in sec";
    }
    leaf tv-nsec {
      type string;
      description
        "Time in nsec";
    }
  }

  grouping ncs_template_NAL-SUB-DISC-HISTORY-EVT-DATA {
    description
      "Sub disc history event history bag";
    container evt-time {
      description
        "Event time";
      uses ncs_template_NAL-TIMESPEC;
    }
    leaf evt-type {
      type string;
      description
        "Event type";
    }
    leaf event-history-index {
      type string;
      description
        "Event History Index";
    }
  }

  grouping ncs_template_NAL-SUB-ACTIVATED-SERVICE {
    description
      "NAL subscriber activated service information";
    leaf service-name {
      type string;
      description
        "Name of the service";
    }
    leaf activation-time {
      type string;
      description
        "service deactivation Time";
    }
    leaf flags {
      type string;
      description
        "flags";
    }
    leaf feature-id {
      type string;
      description
        "Feature ID";
    }
    leaf bytes-in {
      type string;
      units "byte";
      description
        "Bytes in";
    }
    leaf bytes-out {
      type string;
      units "byte";
      description
        "Bytes out";
    }
    leaf bytes-ingiga {
      type string;
      units "byte";
      description
        "In Bytes in Giga";
    }
    leaf bytes-out-giga {
      type string;
      units "byte";
      description
        "Bytes out in Giga";
    }
    leaf final-time {
      type string;
      description
        "service final stats Time";
    }
  }

  grouping ncs_template_NAL-SUBSCRIBER-SESSION-INFO-BRIEF {
    description
      "NAL subscriber  information brief";
    leaf cp-id {
      type string;
      description
        "Control-plane ID";
    }
    leaf ifhandle {
      type xr:ncs_template_Interface-name;
      description
        "Subscriber Interface name";
    }
    leaf subscriber-fsm-state {
      type ncs_template_Oper-nal-db-subscriber-state;
      description
        "Nal Subscriber state";
    }
    leaf mac-address {
      type string;
      description
        "MAC address";
    }
    leaf vrf-name {
      type string;
      description
        "Vrf Name";
    }
    leaf subscriber-ipv4-address {
      type string;
      description
        "IPv4 Address of the subscriber";
    }
    leaf framed-ipv4-addr {
      type string;
      description
        "framed ipv4 addr";
    }
    leaf framed-ipv4-prefix-len {
      type string;
      description
        "framed ipv4 prefix len";
    }
    leaf ipv6-iana-address {
      type string;
      description
        "ipv6 iana address";
    }
    leaf ipv6-iapd-address {
      type string;
      description
        "ipv6  iapd address";
    }
    leaf ipv6-iapd-prefix {
      type string;
      description
        "ipv6  iapd prefix";
    }
    leaf framed-ipv6-addr {
      type string;
      description
        "framed ipv6 addr";
    }
    leaf framed-ipv6-prefix-len {
      type string;
      description
        "framed ipv6 prefix len";
    }
  }

  grouping ncs_template_NAL-SUBSCRIBER-SESSION-INFO {
    description
      "NAL subscriber  information";
    container session-brief {
      description
        "session brief";
      uses ncs_template_NAL-SUBSCRIBER-SESSION-INFO-BRIEF;
    }
    leaf up-id {
      type string;
      description
        "User-plane ID";
    }
    leaf pppoe-session-id {
      type string;
      description
        "PPPoE sesison ID";
    }
    leaf retry-count {
      type string;
      description
        "Retry count";
    }
    leaf local-magic-number {
      type string;
      description
        "Local magic number";
    }
    leaf peer-magic-number {
      type string;
      description
        "Peer magic number";
    }
    leaf keep-alive-interval {
      type string;
      description
        "Keep alive interval";
    }
    leaf total-ka-req-sent {
      type string;
      description
        "Total KA Req Sent";
    }
    leaf total-ka-resp-recv {
      type string;
      description
        "Total KA Resp Recv";
    }
    leaf total-ka-req-recv {
      type string;
      description
        "Total KA Req Recv";
    }
    leaf total-ka-resp-sent {
      type string;
      description
        "Total KA Resp Sent";
    }
    leaf mtu {
      type string;
      description
        "Max transfer unit";
    }
    leaf is-encap-string-ready {
      type string;
      description
        "Flag whether encap String is ready or not";
    }
    leaf ka-echo-request-counter {
      type string;
      description
        "Keepalive  req sent but resp not received";
    }
    leaf lcp-identity {
      type string;
      description
        "Identification for KA echo req";
    }
    leaf pppflags {
      type string;
      description
        "PPP flags";
    }
    leaf subscriber-type {
      type ncs_template_Oper-nal-db-subscriber;
      description
        "Nal Subacriber type";
    }
    leaf parent-ifhandle {
      type xr:ncs_template_Interface-name;
      description
        "Parent interface";
    }
    leaf parent-interface {
      type string;
      description
        "Parent interface";
    }
    leaf subscriber-interface {
      type string;
      description
        "Subscriber interface";
    }
    leaf inner-vlan {
      type string;
      description
        "Inner Vlan";
    }
    leaf outer-vlan {
      type string;
      description
        "Outer Vlan";
    }
    leaf cpe-link-local-address {
      type string;
      description
        "CPE link local address";
    }
    leaf framed-ipv6-next-hop {
      type string;
      description
        "framed ipv6 next hop";
    }
    leaf framed-ipv6-tag {
      type string;
      description
        "framed ipv6 tag";
    }
    leaf framed-ipv4-next-hop {
      type string;
      description
        "framed ipv4 next hop";
    }
    leaf framed-ipv4-tag {
      type string;
      description
        "framed ipv4 tag";
    }
    leaf feature-id-info {
      type string;
      description
        "Subscriber feature id info";
    }
    leaf subscriber-flags {
      type string;
      description
        "Subscriber flags";
    }
    leaf interim-interval {
      type string;
      description
        "Interim Interval";
    }
    leaf last-interim-time-stamp {
      type string;
      description
        "Last Interim Time Stamp";
    }
    leaf interim-fail-count {
      type string;
      description
        "Interim Fail Count";
    }
    leaf interim-error {
      type string;
      description
        "Interim Error";
    }
    leaf bytes-in {
      type string;
      units "byte";
      description
        "Bytes in";
    }
    leaf bytes-out {
      type string;
      units "byte";
      description
        "Bytes out";
    }
    leaf bytes-ingiga {
      type string;
      units "byte";
      description
        "In Bytes in Giga";
    }
    leaf bytes-out-giga {
      type string;
      units "byte";
      description
        "Bytes out in Giga";
    }
    leaf subscriber-create-time {
      type string;
      description
        "Subscriber Create Time";
    }
    leaf subscriber-ipv4-up-time {
      type string;
      description
        "Subscriber IPv4 Up Time";
    }
    leaf subscriber-ipv6-up-time {
      type string;
      description
        "Subscriber IPv6 Up Time";
    }
    leaf subscriber-ipv4-down-time {
      type string;
      description
        "Subscriber IPv4 Down Time";
    }
    leaf subscriber-ipv6-down-time {
      type string;
      description
        "Subscriber IPv6 Down Time";
    }
    leaf subscriber-af-down-reason {
      type string;
      description
        "Subscriber AF Down Reason";
    }
    leaf afup-flags {
      type string;
      description
        "AF ipv4/ipv6 up falgs";
    }
    leaf ip-sub-flags {
      type string;
      description
        "IPSUB  flags";
    }
    leaf sub-disc-time {
      type string;
      description
        "Subscriber Disconnect Time ";
    }
    list active-service {
      // NCS patched for predictable order
      ordered-by user;
      description
        "activated services";
      uses ncs_template_NAL-SUB-ACTIVATED-SERVICE;
    }
  }

  grouping ncs_template_NAL-SUBSCRIBER-DISCONNECT-HISTORY-UNIQUE-INTERNAL-DATA {
    description
      "Subscriber unique disconnect history Bag";
    container session-data {
      description
        "subscriber session data info";
      uses ncs_template_NAL-SUBSCRIBER-SESSION-INFO;
    }
    list event-history {
      // NCS patched for predictable order
      ordered-by user;
      description
        "subscriber event history";
      uses ncs_template_NAL-SUB-DISC-HISTORY-EVT-DATA;
    }
  }

  grouping ncs_template_NAL-SUBSCRIBER-DISCONNECT-HISTORY-UNIQUE-DETAIL-DATA {
    description
      "Subscriber unique disconnect history detail Bag";
    leaf disconnect-unique-session-count {
      type string;
      description
        "Number of sessions disconnected with this error
         code";
    }
    leaf disc-reason {
      type string;
      description
        "Disconnect reason";
    }
    leaf disconnect-errorcode {
      type string;
      description
        "error code";
    }
    list unique-detail {
      // NCS patched for predictable order
      ordered-by user;
      // NCS drop max-elements statement
      description
        "unique detail session info for last three
         disconnected sessions";
      uses ncs_template_NAL-SUBSCRIBER-DISCONNECT-HISTORY-UNIQUE-INTERNAL-DATA;
    }
  }

  grouping ncs_rpc_notif_NAL-MAIN-EDM-PROCESS-INFO {
    description
      "Process readiness data";
    leaf nal-process-restart-flag {
      type boolean;
      description
        "NAL Process's restart flag";
    }
    leaf nalot-connection-sts-flag {
      type boolean;
      description
        "NAL Object-tracking connection up status flag";
    }
    leaf nal-clear-session-timer-flag {
      type boolean;
      description
        "NAL Clear-Session Timer Flag";
    }
    leaf nal-clear-feature-timer-flag {
      type boolean;
      description
        "NAL Clear-Feature Timer Flag";
    }
    leaf disconnect-history-file-logg-enable-flag {
      type boolean;
      description
        "Subscriber Disconnect-history file-logging
         disable feature flag";
    }
    leaf test-client-cfg-enabled-flag {
      type boolean;
      description
        "NAL Test Client config enabled flag";
    }
    leaf nal-pre-init-role {
      type uint8;
      description
        "NAL Process's HA PreInit Role";
    }
    leaf nal-role {
      type uint8;
      description
        "NAL Process's HA Role";
    }
    leaf node-id {
      type uint32;
      description
        "NAL Process's running-instance location node-id";
    }
    leaf nalrsi-ctx-file-descriptor {
      type int32;
      description
        "NAL RSI contex file-desc value";
    }
    leaf nal-pid-misc-flags {
      type uint32;
      description
        "NAL Main context Miscellaneous flags";
    }
    leaf nalsvm-subdb-conn-sts-flag {
      type uint8;
      description
        "NAL Process's SVM context SUBDB
         connection-status flag";
    }
    leaf nalsvmp-done-req-id {
      type uint32;
      description
        "NAL Process's SVM Produce-Done req-id";
    }
    leaf nalsvm-recon-last-upid {
      type uint32;
      description
        "NAL SVM Reconciliation Last UPID";
    }
    leaf nalsvm-reconn-pending-req {
      type uint32;
      description
        "NAL SVM Reconciliation Pending Requests";
    }
    leaf nalsvm-reconn-max-req {
      type uint32;
      description
        "NAL SVM Reconciliation Max Requests";
    }
    leaf nal-sub-ctx-replay-in-progress {
      type uint32;
      description
        "NAL Subscriber context stale cache-size";
    }
    leaf nal-subs-ctx-cache-queue-size {
      type uint32;
      description
        "NAL Subscriber context stale cache-size";
    }
    leaf nal-subs-ctx-stale-queue-size {
      type uint32;
      description
        "NAL Subscriber context stale queue-size";
    }
    leaf disconnect-queue-size {
      type uint32;
      description
        "NAL Subscriber disconnect queue size";
    }
    leaf nal-msg-local-seq-no {
      type uint32;
      description
        "NAL Message locally generated seq_no";
    }
    leaf nal-msg-seq-no {
      type uint32;
      description
        "NAL message seq_no towards SPA";
    }
    leaf nal-bulk-disc-invoke-time {
      type uint64;
      description
        "NAL Bulk Disconnect-session start time";
    }
    leaf nal-statistics-hold-timeout-val {
      type uint32;
      description
        "NAL Stats Hold-Timeout value";
    }
    leaf nal-statistics-hold-req-count {
      type uint32;
      description
        "NAL Stats Hold-Request Count";
    }
    leaf nal-statistics-hold-req-max {
      type uint32;
      description
        "NAL Stats Hold-Request Max-threshold";
    }
    leaf nal-statistics-stop-req-count {
      type uint32;
      description
        "NAL Stats Stop-Request counter";
    }
    leaf nal-statistics-interim-req-count {
      type uint32;
      description
        "NAL Stats Interim-Request counter";
    }
    leaf nal-clear-session-stats-req-count {
      type uint32;
      description
        "NAL Clear-Session Stats Request counter";
    }
    leaf nal-clear-feature-stats-req-count {
      type uint32;
      description
        "NAL Clear-Feature Stats Request counter";
    }
    leaf nal-stats-processing-flags {
      type uint32;
      description
        "NAL Statistics miscelleaneous flags";
    }
    leaf create-in-progress {
      type uint32;
      description
        "Number of subscriber create in progress";
    }
    leaf delete-in-progress {
      type uint32;
      description
        "Number of subscriber delete in progress";
    }
    leaf update-in-progress {
      type uint32;
      description
        "Number of subscriber update in progress";
    }
    leaf cp-recon-duration {
      type uint32;
      description
        "CP recon duration";
    }
    leaf cp-recon-flags {
      type uint32;
      description
        "CP recon flags";
    }
    leaf cp-replay-reqs-in-progress {
      type uint32;
      description
        "CP replay reqs in progress";
    }
    leaf cp-replay-subs-in-progress {
      type uint32;
      description
        "CP replay subs in progress";
    }
  }

  grouping ncs_rpc_notif_NAL-MAIN-EDM-VRF-AFI-INSTANCE {
    description
      "NAL MAIN EDM VRF AFI INSTANCE";
    leaf vrf-address-family {
      type uint8;
      description
        "VRF Table Address-Family";
    }
    leaf vrf-info-table-flag {
      type uint8;
      description
        "VRF Table Flags";
    }
    leaf vrf-table-sync-flag {
      type uint8;
      description
        "buffer complete sent to RIB";
    }
    leaf protocol-id {
      type uint16;
      description
        "Protocol Id";
    }
    leaf vrf-table-id {
      type uint32;
      description
        "VRF Table-Id";
    }
    leaf vrf-pending-routes {
      type uint32;
      description
        "VRF Table Pending-routes";
    }
    leaf ref-count {
      type uint64;
      description
        "No.of interfaces referencing this table";
    }
    leaf max-ref-count {
      type uint64;
      description
        "Max No. of interfaces allowed";
    }
  }

  grouping ncs_rpc_notif_NAL-MAIN-EDM-VRFTBL-INFO {
    description
      "NAL VRF Table Info bag";
    leaf vrf-name-xr {
      type string {
        length "0..33";
      }
      description
        "Vrf Name";
    }
    list nal-vrf-afi-instance-info {
      description
        "NAL VRF AFI Instance table info";
      uses ncs_rpc_notif_NAL-MAIN-EDM-VRF-AFI-INSTANCE;
    }
  }

  grouping ncs_rpc_notif_NAL-MAIN-EDM-OC-ENTRY {
    description
      "NAL owner-channel entries";
    leaf afi {
      type uint8;
      description
        "Address family for this route";
    }
    leaf ipv6-prefix {
      type inet:ipv6-address;
      description
        "ipv6 prefix address";
    }
    leaf ipv4-prefix {
      type inet:ipv4-address;
      description
        "ipv4 prefix address";
    }
    leaf prefix-length {
      type uint32;
      description
        "Prefix length";
    }
    leaf primary-address {
      type inet:ipv4-address;
      description
        "Secondary address";
    }
    leaf state {
      type ncs_rpc_notif_Nal-main-edm-oc-state;
      description
        "Status";
    }
    leaf vrf-xr {
      type string {
        length "0..33";
      }
      description
        "VRF name";
    }
    leaf if-handle {
      type xr:ncs_rpc_notif_Interface-name;
      description
        "Interface Handle";
    }
    leaf tag {
      type uint32;
      description
        "Route tag";
    }
    leaf flags {
      type uint32;
      description
        "Checkpoint flags";
    }
  }

  grouping ncs_rpc_notif_NAL-AIPC-SERVER-STATS-DATA {
    description
      "aipc server stats";
    leaf conn-present {
      type boolean;
      description
        "connection status";
    }
    leaf service-name {
      type string {
        length "0..256";
      }
      description
        "process Name";
    }
    leaf tx-attempt-count {
      type uint32;
      description
        "Tx attempt count";
    }
    leaf tx-count {
      type uint32;
      description
        "tx count";
    }
    leaf rx-count {
      type uint32;
      description
        "Rx count";
    }
    leaf notify-connect-count {
      type uint32;
      description
        "Notify connect count";
    }
    leaf notify-queue-high-count {
      type uint32;
      description
        "Notify Queue High count";
    }
    leaf notify-queue-low-count {
      type uint32;
      description
        "Notify Queue low count";
    }
    leaf notify-queue-full-count {
      type uint32;
      description
        "Notify Queue full count";
    }
    leaf notify-data-waiting-count {
      type uint32;
      description
        "Notify data waiting count";
    }
    leaf notify-error-count {
      type uint32;
      description
        "Notify error count";
    }
    leaf notify-close-count {
      type uint32;
      description
        "Notify close count";
    }
    leaf notify-sendstatus-count {
      type uint32;
      description
        "Notify send status count";
    }
    leaf notify-open-count {
      type uint32;
      description
        "Notify open count";
    }
    leaf pulse-data-waiting-count {
      type uint32;
      description
        "Pulse Data waiting count";
    }
    leaf queue-full {
      type boolean;
      description
        "Queue full";
    }
    leaf queue-full-drop {
      type uint32;
      description
        "Queue full drop";
    }
    leaf queue-ewouldblock-count {
      type uint32;
      description
        "queue would block count";
    }
    leaf outstanding-buffers {
      type uint32;
      description
        "Outstanding Buffers";
    }
    leaf cumulative-overflow-msgs {
      type uint32;
      description
        "cumulative overflow message";
    }
    leaf hwm-overflow-msgs {
      type uint32;
      description
        "Hwm overflow msg";
    }
    leaf get-mtu-failure {
      type uint32;
      description
        "Get Mtu Failure";
    }
    leaf get-buffer-failure {
      type uint32;
      description
        "get Buffer Failure";
    }
    leaf get-buffer-datap-failure {
      type uint32;
      description
        "get Buffer datap Failure";
    }
    leaf conn-failure {
      type uint32;
      description
        "Conn Failure";
    }
    leaf send-failure {
      type uint32;
      description
        "Send Failure";
    }
    leaf receive-failure {
      type uint32;
      description
        "receive Failure";
    }
    leaf release-buffer-failure {
      type uint32;
      description
        "Release Buffer failure";
    }
    leaf overflow-q-flush-count {
      type uint32;
      description
        "Overflow flush count";
    }
    leaf notify-queue-low-count-after-high {
      type uint32;
      description
        "notify queue low count after high";
    }
    leaf last-high-watermark-count-timestamp {
      type uint32;
      description
        "High WaterMark timestamp";
    }
    leaf last-low-watermark-count-timestamp {
      type uint32;
      description
        "Low WaterMark timestamp";
    }
  }

  grouping ncs_rpc_notif_NAL-MAIN-EDM-OC-SUMMARY {
    description
      "Dynamic routes and OC entries summary";
    leaf v4-oc-entries {
      type uint32;
      description
        "Total V4 OC entries primary/secondary";
    }
    leaf v6-oc-entries {
      type uint32;
      description
        "Total V6 OC entries";
    }
    leaf v4-primary-entries {
      type uint32;
      description
        "Total primary addresses";
    }
    leaf v4-sec-entries {
      type uint32;
      description
        "Total secondary addresses";
    }
    leaf v4-rib-entries {
      type uint32;
      description
        "Total V4 RIB entries";
    }
    leaf v6-rib-entries {
      type uint32;
      description
        "Total V6 RIB entries";
    }
    leaf replayed-oc-entries {
      type uint32;
      description
        "Total entries replayed during last reconcile";
    }
  }

  grouping ncs_rpc_notif_NAL-MAIN-EDM-CP-CONN-STS-INFO {
    description
      "NAL User & Control-plane connection status
       information";
    leaf nal-transport-user-plane-src-conn-flag {
      type boolean;
      description
        "True if NAL Transport user-plane source
         connection address is configured";
    }
    leaf nalcp-svr-connect-sts {
      type ncs_rpc_notif_Nal-cp-connection-status;
      description
        "NAL control-plane connection-status value";
    }
    leaf nalcp-svr-connect-sts-time {
      type uint32;
      description
        "NAL control-plane connection-status time stamp";
    }
    leaf nalcp-svr-connect-sts-prev {
      type ncs_rpc_notif_Nal-cp-connection-status;
      description
        "NAL control-plane prev connection-status value";
    }
    leaf nalcp-svr-connect-sts-time-prev {
      type uint32;
      description
        "NAL control-plane prev connection-status time
         stamp";
    }
    leaf cp-assoc-status {
      type ncs_rpc_notif_Nal-cp-assoc-status;
      description
        "Control plane association status";
    }
    leaf cp-assoc-status-time {
      type uint32;
      description
        "Control plane association status time stamp";
    }
    leaf nal-transport-user-plane-source-conn-addr-family {
      type uint8;
      description
        "NAL Transport user-plane source server
         connection address-family";
    }
    leaf nal-transport-up-source-ipv4-address {
      type inet:ipv4-address;
      description
        "NAL Transport user-plane server connection IPv4
         address";
    }
    leaf nal-transport-up-source-ipv6-address {
      type inet:ipv6-address;
      description
        "NAL Transport user-plane server connection IPv6
         address";
    }
    leaf nal-transport-up-src-loop-back-if-name {
      type string {
        length "0..64";
      }
      description
        "NAL Transport user-plane server loopback
         interface-name";
    }
    leaf nal-transport-up-source-gtpu-port {
      type uint32;
      description
        "NAL Transport user-plane server connection GTPU
         port-number";
    }
    leaf nal-transport-up-source-pfcp-port {
      type uint32;
      description
        "NAL Transport user-plane server connection PFCP
         port-number";
    }
    leaf nal-transport-up-source-vrf-name {
      type string {
        length "0..33";
      }
      description
        "NAL Transport user-plane server connection
         VRF-Name";
    }
    leaf nal-transport-control-plane-primary-srv-addr-family {
      type uint8;
      description
        "NAL transport control-plane primary-server
         connection address-family";
    }
    leaf nal-transport-cp-primary-ipv4-address {
      type inet:ipv4-address;
      description
        "NAL Transport C-plane primary-server connection
         IPv4 address";
    }
    leaf nal-transport-cp-primary-ipv6-address {
      type inet:ipv6-address;
      description
        "NAL Transport C-plane primary-server connection
         IPv6 address";
    }
    leaf nal-transport-cp-server-gtpu-port {
      type uint32;
      description
        "NAL Transport C-plane server's GTPU port-number";
    }
    leaf nal-transport-cp-server-pfcp-port {
      type uint32;
      description
        "NAL Transport C-plane server's PFCP port-number";
    }
    leaf retry-count {
      type uint16;
      description
        "CP association request retry count";
    }
  }

  grouping ncs_rpc_notif_NAL-MAIN-EDM-PROCESS-READINESS {
    description
      "Process readiness data";
    leaf resync-pending-flags {
      type uint32;
      description
        "Resync operations pending for NAL process";
    }
    leaf sir-ready {
      type boolean;
      description
        "Status of SIR readiness";
    }
  }

  grouping ncs_rpc_notif_NAL-MAIN-EDM-PARENT-INTF-INITIATOR-DATA {
    description
      "NAL MAIN EDM PARENT INTF INITIATOR DATA";
    leaf is-configured {
      type boolean;
      description
        "Ture if the initiator is configred";
    }
  }

  grouping ncs_rpc_notif_NAL-MAIN-EDM-PARENT-INTF-INITIATORS {
    description
      "Initiator protocol details";
    container intiator-type {
      description
        "DHCP information";
      uses ncs_rpc_notif_NAL-MAIN-EDM-PARENT-INTF-INITIATOR-DATA;
    }
  }

  grouping ncs_rpc_notif_NAL-MAIN-EDM-PARENT-INTF-DATA {
    description
      "Parent interface data";
    container initiators {
      description
        "Configurational state-statistics for each
         initiating protocol enabled on this parent
         interface";
      uses ncs_rpc_notif_NAL-MAIN-EDM-PARENT-INTF-INITIATORS;
    }
    leaf parent-interface {
      type xr:ncs_rpc_notif_Interface-name;
      description
        "Ifhandle of parent interface";
    }
    leaf interface-creation-time {
      type string;
      description
        "Interface creation time in Month Date HH:MM:SS
         format";
    }
    leaf age {
      type string;
      description
        "Age in HH:MM:SS format";
    }
    leaf parent-intf-flags {
      type uint32;
      description
        "Access Interface flags";
    }
    leaf nal-ether-encap {
      type yang:hex-string;
      description
        "Ether Encap Attribute";
    }
    leaf effective-bandwidth {
      type uint32;
      description
        "Effective Bandwidth";
    }
    leaf max-bandwidth {
      type uint32;
      description
        "Maximum Bandwidth";
    }
    leaf link-local {
      type inet:ipv6-address;
      description
        "link local address";
    }
  }

  grouping ncs_rpc_notif_NAL-MAIN-EDM-SPA-RT-PROV-HIST-DATA {
    description
      "Route provision request response history";
    container request-response-timestamp {
      description
        "Timestamp of request or response";
      uses ncs_rpc_notif_NAL-TIMESPEC;
    }
    leaf type {
      type ncs_rpc_notif_Nal-main-edm-spa-rt-hist;
      description
        "Type of route history data";
    }
    list data {
      description
        "Request or Response";
      leaf entry {
        type uint8;
        description
          "Request or Response";
      }
    }
  }

  grouping ncs_rpc_notif_NAL-MAIN-EDM-CHUNK-DATA {
    description
      "NAL MAIN EDM CHUNK DATA";
    leaf chunk-name {
      type string;
      description
        "Chunk Name";
    }
    leaf chunk-id {
      type uint32;
      description
        "Chunk Id";
    }
    leaf chunk-total-alloc {
      type uint32;
      description
        "Total number of chunk malloc done";
    }
    leaf chunk-total-free {
      type uint32;
      description
        "Total number of chunk free done";
    }
    leaf chunk-in-use {
      type uint32;
      description
        "total number of chunk blocks in use";
    }
  }

  grouping ncs_rpc_notif_NAL-MAIN-EDM-CHUNK-STATS {
    description
      "NAL MAIN EDM CHUNK STATS";
    list chunk-stat {
      description
        "Chunk Memory statistics";
      uses ncs_rpc_notif_NAL-MAIN-EDM-CHUNK-DATA;
    }
  }

  grouping ncs_rpc_notif_NAL-SUBSCRIBER-DISCONNECT-HISTORY-DATA {
    description
      "Subscriber disconnect history bag";
    container fail-data {
      description
        "failed data";
      uses ncs_rpc_notif_NAL-LAST-FAILED-DATA;
    }
    container session-data {
      description
        "subscriber session data info";
      uses ncs_rpc_notif_NAL-SUBSCRIBER-SESSION-INFO;
    }
    leaf disc-cause {
      type uint32;
      description
        "Disconnect code";
    }
    list event-history {
      description
        "subscriber event history";
      uses ncs_rpc_notif_NAL-SUB-DISC-HISTORY-EVT-DATA;
    }
  }

  grouping ncs_rpc_notif_EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    list evt-data {
      description
        "Optional data";
      leaf entry {
        type uint32;
        description
          "Optional data";
      }
    }
  }

  grouping ncs_rpc_notif_EVT-HIST-INFO {
    description
      "Per object event history";
    leaf evt-class-name {
      type string;
      description
        "Class name string";
    }
    list evt-entry {
      description
        "Array of event entries";
      uses ncs_rpc_notif_EVT-HIST-ENTRY;
    }
  }

  grouping ncs_rpc_notif_NAL-MAIN-EDM-EVENTS {
    description
      "NAL Main process init information";
    container event-history {
      description
        "Main process boot up events";
      uses ncs_rpc_notif_EVT-HIST-INFO;
    }
    container im-event-history {
      description
        "IM module events";
      uses ncs_rpc_notif_EVT-HIST-INFO;
    }
    container svm-event-history {
      description
        "SVM module events";
      uses ncs_rpc_notif_EVT-HIST-INFO;
    }
    container rib-event-history {
      description
        "RIB module events";
      uses ncs_rpc_notif_EVT-HIST-INFO;
    }
    container cp-event-history {
      description
        "CP module events";
      uses ncs_rpc_notif_EVT-HIST-INFO;
    }
    container config-event-history {
      description
        "Config module events";
      uses ncs_rpc_notif_EVT-HIST-INFO;
    }
  }

  grouping ncs_rpc_notif_NAL-SUBSCRIBER-AFI-SUMMARY {
    description
      "Subscriber afi summary data";
    leaf none {
      type uint32;
      description
        "No afi";
    }
    leaf ipv4 {
      type uint32;
      description
        "IPv4 count";
    }
    leaf ipv6 {
      type uint32;
      description
        "IPv6 count";
    }
    leaf dual {
      type uint32;
      description
        "Dual count";
    }
    leaf total {
      type uint32;
      description
        "Total";
    }
  }

  grouping ncs_rpc_notif_NAL-SUBSCRIBER-STATE-SUMMARY {
    description
      "Subscriber state summary data";
    leaf initializing {
      type uint32;
      description
        "Initializing";
    }
    leaf connecting {
      type uint32;
      description
        "Connecting";
    }
    leaf connected {
      type uint32;
      description
        "Connected";
    }
    leaf activated {
      type uint32;
      description
        "Activated";
    }
    leaf idle {
      type uint32;
      description
        "Idle";
    }
    leaf disconnecting {
      type uint32;
      description
        "Disconnecting";
    }
    leaf total {
      type uint32;
      description
        "Total";
    }
  }

  grouping ncs_rpc_notif_NAL-SUBSCRIBER-SUMMARY {
    description
      "Subscriber summary data";
    container ipoe-state-summary {
      description
        "IPoE State Summary";
      uses ncs_rpc_notif_NAL-SUBSCRIBER-STATE-SUMMARY;
    }
    container pppoe-state-summary {
      description
        "PPPoE State Summary";
      uses ncs_rpc_notif_NAL-SUBSCRIBER-STATE-SUMMARY;
    }
    container ipoe-afi-summary {
      description
        "IPoE AFI Summary";
      uses ncs_rpc_notif_NAL-SUBSCRIBER-AFI-SUMMARY;
    }
    container pppoe-afi-summary {
      description
        "PPPoE AFI Summary";
      uses ncs_rpc_notif_NAL-SUBSCRIBER-AFI-SUMMARY;
    }
  }

  grouping ncs_rpc_notif_NAL-SUBSCRIBER-DISCONNECT-HISTORY-UNIQUE-DATA {
    description
      "Subscriber unique disconnect history Bag";
    leaf disconnect-unique-session-count {
      type uint32;
      description
        "Number of sessions disconnected with this error
         code";
    }
    leaf disconnect-errorcode {
      type uint32;
      description
        "error code";
    }
    leaf sub-if-name {
      type string {
        length "0..64";
      }
      description
        "Interface Name";
    }
    leaf sub-disc-time {
      type uint32;
      description
        "Subscriber Disconnect Time ";
    }
    leaf disc-reason {
      type string {
        length "0..64";
      }
      description
        "Disconnect reason";
    }
  }

  grouping ncs_rpc_notif_NAL-SERVICE-PROFILE-DATA {
    description
      "NAL service profile information";
    leaf service-name {
      type string {
        length "0..65";
      }
      description
        "Name of the service";
    }
    leaf service-id {
      type uint32;
      description
        "Service id assigned by SUBDB";
    }
    leaf use-count {
      type uint32;
      description
        "Number of subscribers using this profile";
    }
    leaf state {
      type ncs_rpc_notif_Svm-service-state;
      description
        "State of the service";
    }
    leaf fail-err {
      type uint32;
      description
        "Installation failure rc";
    }
    leaf stale-timer-remaining {
      type uint32;
      description
        "stale timer remaining";
    }
    leaf assoc-in-progress {
      type uint32;
      description
        "No of subscribers need to use this profile";
    }
    list wait-upi-dqueue {
      description
        "List of UPIDs waiting for this service";
      leaf entry {
        type uint32;
        description
          "List of UPIDs waiting for this service";
      }
    }
  }

  grouping ncs_rpc_notif_IPSUB-BASE-INIT {
    description
      "ipsub base init data";
    leaf type {
      type uint8;
      description
        "Init data type";
    }
    leaf version {
      type uint8;
      description
        "Init data version";
    }
    leaf length {
      type uint16;
      description
        "Init data length";
    }
  }

  grouping ncs_rpc_notif_IPSUB-INTF-INIT-TYPE {
    description
      "Subscriber intf init data";
    container base {
      description
        "base";
      uses ncs_rpc_notif_IPSUB-BASE-INIT;
    }
    leaf subscriber-mac {
      type yang:mac-address;
      description
        "MAC address";
    }
    leaf vlan-tag-count {
      type uint16;
      description
        "Vlan tag count";
    }
    leaf vrf-table-id {
      type uint32;
      description
        "Vrf table id ";
    }
    leaf v6-vrf-table-id {
      type uint32;
      description
        "Ipv6 Vrf table id ";
    }
    leaf up-link-gre-key {
      type uint32;
      description
        "Up link gre key";
    }
    leaf down-link-gre-key {
      type uint32;
      description
        "Down link gre key";
    }
    leaf subscriber-gw-mac {
      type yang:mac-address;
      description
        "Gateway MAC address";
    }
    leaf sub-attr-bits {
      type uint8;
      description
        "Subscriber attr bits";
    }
    leaf sub-info-bits {
      type uint8;
      description
        "Subscriber info bits";
    }
    leaf subscriber-ipv4 {
      type uint32;
      description
        "Subscriber IPv4";
    }
    leaf nexthop-ipv4 {
      type uint32;
      description
        "next hop  IPv4 address";
    }
    leaf subscriber-ipv6 {
      type inet:ipv6-address;
      description
        "Subscriber Ipv6 address";
    }
    leaf subscriber-ipv6-prefix {
      type inet:ipv6-address;
      description
        "Subscriber Ipv6 address";
    }
    leaf nexthop-ipv6 {
      type inet:ipv6-address;
      description
        "Nexthop Ipv6 address";
    }
    leaf v6-len {
      type uint8;
      description
        "V6 len";
    }
    leaf v6-prefix-len {
      type uint8;
      description
        "V6 prefix len";
    }
    leaf template-ifh {
      type uint32;
      description
        "Template interface handle";
    }
    leaf ipv4-mtu {
      type uint16;
      description
        "Ipv4 MTU";
    }
    leaf ipv6-mtu {
      type uint16;
      description
        "Ipv6 MTU";
    }
    leaf odns-deviceid-higher {
      type uint32;
      description
        "ODNS device id highter";
    }
    leaf odns-deviceid-lower {
      type uint32;
      description
        "ODNS device id Lower";
    }
    list vlan-stack {
      max-elements 2;
      description
        "vlan stack type";
      uses ncs_rpc_notif_DOT1Q-TAG-DATA-TYPE;
    }
  }

  grouping ncs_rpc_notif_NAL-TRANS-CONTEXT-DATA {
    description
      "Nal transaction context";
    leaf state {
      type ncs_rpc_notif_Nal-trans-state;
      description
        "Subscriber transactio state";
    }
    leaf client-type {
      type ncs_rpc_notif_Nal-trans-client-data;
      description
        "Client type indicate who is triggert this
         transction";
    }
    leaf trans-id {
      type uint32;
      description
        "Transaction ID";
    }
    leaf disconnect-ack {
      type uint32;
      description
        "Disconnect Ack";
    }
    leaf module-err {
      type uint32;
      description
        "Error generated by sub module";
    }
    leaf module-interaction-mask {
      type uint64;
      description
        "Flag to indicate which sub-module interactions
         are in progress";
    }
    leaf rollback-module-mask {
      type uint64;
      description
        "Flag to indicate which sub-module rollback needs
         to be invoked";
    }
    leaf pending-cb-bitmask {
      type uint64;
      description
        "Flag indicating pending callbacks for this
         transaction";
    }
  }

  grouping ncs_rpc_notif_NAL-TRANS-SUB-CONTEXT-DATA {
    description
      "Subscriber transaction context";
    container trans-context {
      description
        "trans context";
      uses ncs_rpc_notif_NAL-TRANS-CONTEXT-DATA;
    }
  }

  grouping ncs_rpc_notif_NAL-IPSUB-INFLIGHT-DATA {
    description
      "Nal ipsub inflight data";
    leaf opearation {
      type ncs_rpc_notif_Nal-intf-oper;
      description
        "Operation in progress";
    }
    leaf flags {
      type uint64;
      description
        "Flags to represent pending activities";
    }
    leaf fail-rc {
      type uint32;
      description
        "Backup of update error, internal rollback in
         progresss";
    }
  }

  grouping ncs_rpc_notif_SVM-INFLIGHT-DATA {
    description
      "SVM inflight data";
    leaf service-name {
      type string {
        length "0..65";
      }
      description
        "Name of the service";
    }
    leaf service-id {
      type uint32;
      description
        "Service id assigned by SUBDB";
    }
    leaf operation {
      type ncs_rpc_notif_Nal-spa-oper;
      description
        "Operation to be performed";
    }
    leaf service-flags {
      type uint32;
      description
        "Service flags";
    }
    leaf params-list {
      type yang:hex-string;
      description
        "Attribute list of service params";
    }
    leaf feature-id {
      type uint32;
      description
        "Feature ID";
    }
  }

  grouping ncs_rpc_notif_NAL-SVM-INFLIGHT-DATA {
    description
      "Nal SVM inflight data";
    leaf opearation {
      type ncs_rpc_notif_Svm-sub-oper;
      description
        "Operation in progress";
    }
    leaf state {
      type ncs_rpc_notif_Svn-sub-state;
      description
        "State of the subscriber SVM data";
    }
    leaf fail-rc {
      type uint32;
      description
        "Fail rc";
    }
    leaf up-list {
      type yang:hex-string;
      description
        "User profile attribute list";
    }
    leaf remove-list {
      type yang:hex-string;
      description
        "User profile attribute remove list";
    }
    leaf service-index {
      type uint32;
      description
        "Service that is currently under process";
    }
    leaf subdb-pd-req-id {
      type uint32;
      description
        "SUBDB produce done req id";
    }
    leaf reconcile-state {
      type ncs_rpc_notif_Svm-reconcile-state;
      description
        "Reconcilitation state";
    }
    list service {
      description
        "Service list array";
      uses ncs_rpc_notif_SVM-INFLIGHT-DATA;
    }
  }

  grouping ncs_rpc_notif_DOT1Q-TAG-DATA-TYPE {
    description
      "dot1q tag type";
    leaf etype {
      type uint16;
      description
        "etype";
    }
    leaf ucv {
      type uint16;
      description
        "ucv";
    }
  }

  grouping ncs_rpc_notif_NAL-SUB-INTF-DATA {
    description
      "subscriber interface info";
    leaf vlan-tag-count {
      type uint16;
      description
        "Vlan tag count";
    }
    leaf sub-attr-bits {
      type uint8;
      description
        "Subscriber attr bits";
    }
    leaf flags {
      type uint64;
      description
        "flags bits";
    }
    leaf vrf-id {
      type uint32;
      description
        "vrf ID";
    }
    leaf v4-table-id {
      type uint32;
      description
        "V4 table id";
    }
    leaf v6-table-id {
      type uint32;
      description
        "V6 table id";
    }
    list vlan-stack {
      max-elements 2;
      description
        "vlan stack type";
      uses ncs_rpc_notif_DOT1Q-TAG-DATA-TYPE;
    }
  }

  grouping ncs_rpc_notif_NAL-LAST-FAILED-DATA {
    description
      "NAL subscriber last failed transaction data";
    leaf data {
      type string {
        length "0..256";
      }
      description
        "Failed data";
    }
    leaf msg-txn-id {
      type uint32;
      description
        "Message Txn ID";
    }
    leaf sess-txn-id {
      type uint32;
      description
        "Session Txn ID";
    }
    leaf feature-mask {
      type uint32;
      description
        "Feature Mask";
    }
    leaf svm-state {
      type uint32;
      description
        "SVM state";
    }
    leaf ip-sub-flags {
      type uint64;
      description
        "IPSUB flags";
    }
    leaf pending-callback {
      type uint64;
      description
        "Pending Callback";
    }
    leaf failure-reason {
      type uint32;
      description
        "Failure Reason";
    }
    leaf failure-timestamp {
      type uint32;
      description
        "Failure Timestamp";
    }
  }

  grouping ncs_rpc_notif_NAL-SUBSCRIBER-DEACTIVATED-SERVICE {
    description
      "NAL subscriber deactivated service information";
    leaf service-name {
      type string {
        length "0..65";
      }
      description
        "Name of the service";
    }
    leaf deactivation-time {
      type uint32;
      description
        "service deactivation Time";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
  }

  grouping ncs_rpc_notif_NAL-SUBSCRIBER-SESSION-DATA-INTERNAL {
    description
      "Subscriber context data";
    container session-data {
      description
        "subscriber session data info";
      uses ncs_rpc_notif_NAL-SUBSCRIBER-SESSION-INFO;
    }
    container sub-intf {
      description
        "sub intf";
      uses ncs_rpc_notif_NAL-SUB-INTF-DATA;
    }
    container svm-inflight {
      description
        "svm inflight";
      uses ncs_rpc_notif_NAL-SVM-INFLIGHT-DATA;
    }
    container ipsub-inflight {
      description
        "ipsub inflight";
      uses ncs_rpc_notif_NAL-IPSUB-INFLIGHT-DATA;
    }
    container trans-sub-context {
      description
        "trans sub context";
      uses ncs_rpc_notif_NAL-TRANS-SUB-CONTEXT-DATA;
    }
    container last-init-data {
      description
        "last init data";
      uses ncs_rpc_notif_IPSUB-INTF-INIT-TYPE;
    }
    leaf subscriber-flags {
      type uint32;
      description
        "Subscriber flags";
    }
    leaf ha-flags {
      type uint32;
      description
        "Subscriber flags";
    }
    leaf last-transaction-result {
      type uint32;
      description
        "Last Transaction Result";
    }
    leaf hold-stats-error {
      type uint32;
      description
        "hold stats status";
    }
    leaf clear-stats-error {
      type uint32;
      description
        "clear stats status";
    }
    leaf packets-in {
      type uint32;
      description
        "No of packets In";
    }
    leaf packets-out {
      type uint32;
      description
        "No of packets Out";
    }
    leaf ipv4-packets-in {
      type uint32;
      description
        "No of IPv4 packets In";
    }
    leaf ipv4-packets-out {
      type uint32;
      description
        "No of IPv4 packets Out";
    }
    leaf ipv4-bytes-in {
      type uint32;
      description
        "IPv4 Bytes in";
    }
    leaf ipv4-bytes-out {
      type uint32;
      description
        "IPv4 Bytes out";
    }
    leaf ipv4-bytes-in-giga {
      type uint32;
      description
        "IPv4 Bytes in Giga";
    }
    leaf ipv4-bytes-out-giga {
      type uint32;
      description
        "IPv4 Bytes out in Giga";
    }
    leaf ipv6-packets-in {
      type uint32;
      description
        "No of IPv6 packets In";
    }
    leaf ipv6-packets-out {
      type uint32;
      description
        "No of IPv6 packets Out";
    }
    leaf ipv6-bytes-in {
      type uint32;
      description
        "IPv6 Bytes in";
    }
    leaf ipv6-bytes-out {
      type uint32;
      description
        "IPv6 Bytes out";
    }
    leaf ipv6-bytes-in-giga {
      type uint32;
      description
        "IPv6 Bytes in Giga";
    }
    leaf ipv6-bytes-out-giga {
      type uint32;
      description
        "IPv6 Bytes out in Giga";
    }
    leaf transaction-id {
      type uint32;
      description
        "Subscriber transaction id";
    }
    leaf loopback-name {
      type string {
        length "0..65";
      }
      description
        "Loopback Name";
    }
    leaf stale-feature-id-info {
      type uint32;
      description
        "subscriber stale feature id info";
    }
    leaf sus-dconnect-time {
      type uint32;
      description
        "Subscriber disconnect Time";
    }
    leaf obj-hdl {
      type uint64;
      description
        "objext handle";
    }
    leaf spi-oattched {
      type boolean;
      description
        "Has SPIO attached";
    }
    list deactivated-service {
      description
        "last deactivated services";
      uses ncs_rpc_notif_NAL-SUBSCRIBER-DEACTIVATED-SERVICE;
    }
    list last-fail {
      description
        "last failed transaction data";
      uses ncs_rpc_notif_NAL-LAST-FAILED-DATA;
    }
  }

  grouping ncs_rpc_notif_NAL-OPER-FADB-RECORD-DATA {
    description
      "NAL OPER FADB RECORD DATA";
    leaf feature-id {
      type uint32;
      description
        "Subscriber Feature-Id";
    }
    leaf upid {
      type uint32;
      description
        "User-plane ID";
    }
    leaf service-id {
      type uint32;
      description
        "Subscriber Service-Id";
    }
    leaf interim-fail-count {
      type uint32;
      description
        "Interim Fail Count";
    }
    leaf stale-timestamp {
      type uint32;
      description
        "Stale timestamp";
    }
    leaf hold-rc {
      type uint32;
      description
        "Hold RC";
    }
    leaf interim-error {
      type uint32;
      description
        "Interim Error";
    }
  }

  grouping ncs_rpc_notif_NAL-SUBSCRIBER-SESSION-DATA {
    description
      "NAL subscriber detail data information";
    container sub-info {
      description
        "subscriber session data info";
      uses ncs_rpc_notif_NAL-SUBSCRIBER-SESSION-INFO;
    }
  }

  grouping ncs_rpc_notif_NAL-TIMESPEC {
    description
      "Structure to replicate timespec";
    leaf tv-sec {
      type uint32;
      description
        "Time in sec";
    }
    leaf tv-nsec {
      type uint32;
      description
        "Time in nsec";
    }
  }

  grouping ncs_rpc_notif_NAL-SUB-DISC-HISTORY-EVT-DATA {
    description
      "Sub disc history event history bag";
    container evt-time {
      description
        "Event time";
      uses ncs_rpc_notif_NAL-TIMESPEC;
    }
    leaf evt-type {
      type uint8;
      description
        "Event type";
    }
    leaf event-history-index {
      type uint32;
      description
        "Event History Index";
    }
  }

  grouping ncs_rpc_notif_NAL-SUB-ACTIVATED-SERVICE {
    description
      "NAL subscriber activated service information";
    leaf service-name {
      type string {
        length "0..65";
      }
      description
        "Name of the service";
    }
    leaf activation-time {
      type uint32;
      description
        "service deactivation Time";
    }
    leaf flags {
      type uint32;
      description
        "flags";
    }
    leaf feature-id {
      type uint32;
      description
        "Feature ID";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf final-time {
      type uint32;
      description
        "service final stats Time";
    }
  }

  grouping ncs_rpc_notif_NAL-SUBSCRIBER-SESSION-INFO-BRIEF {
    description
      "NAL subscriber  information brief";
    leaf cp-id {
      type uint32;
      description
        "Control-plane ID";
    }
    leaf ifhandle {
      type xr:ncs_rpc_notif_Interface-name;
      description
        "Subscriber Interface name";
    }
    leaf subscriber-fsm-state {
      type ncs_rpc_notif_Oper-nal-db-subscriber-state;
      description
        "Nal Subscriber state";
    }
    leaf mac-address {
      type yang:mac-address;
      description
        "MAC address";
    }
    leaf vrf-name {
      type string {
        length "0..33";
      }
      description
        "Vrf Name";
    }
    leaf subscriber-ipv4-address {
      type inet:ipv4-address;
      description
        "IPv4 Address of the subscriber";
    }
    leaf framed-ipv4-addr {
      type inet:ipv4-address;
      description
        "framed ipv4 addr";
    }
    leaf framed-ipv4-prefix-len {
      type uint8;
      description
        "framed ipv4 prefix len";
    }
    leaf ipv6-iana-address {
      type inet:ipv6-address;
      description
        "ipv6 iana address";
    }
    leaf ipv6-iapd-address {
      type inet:ipv6-address;
      description
        "ipv6  iapd address";
    }
    leaf ipv6-iapd-prefix {
      type uint8;
      description
        "ipv6  iapd prefix";
    }
    leaf framed-ipv6-addr {
      type inet:ipv6-address;
      description
        "framed ipv6 addr";
    }
    leaf framed-ipv6-prefix-len {
      type uint8;
      description
        "framed ipv6 prefix len";
    }
  }

  grouping ncs_rpc_notif_NAL-SUBSCRIBER-SESSION-INFO {
    description
      "NAL subscriber  information";
    container session-brief {
      description
        "session brief";
      uses ncs_rpc_notif_NAL-SUBSCRIBER-SESSION-INFO-BRIEF;
    }
    leaf up-id {
      type uint32;
      description
        "User-plane ID";
    }
    leaf pppoe-session-id {
      type uint16;
      description
        "PPPoE sesison ID";
    }
    leaf retry-count {
      type uint32;
      description
        "Retry count";
    }
    leaf local-magic-number {
      type uint32;
      description
        "Local magic number";
    }
    leaf peer-magic-number {
      type uint32;
      description
        "Peer magic number";
    }
    leaf keep-alive-interval {
      type uint32;
      description
        "Keep alive interval";
    }
    leaf total-ka-req-sent {
      type uint32;
      description
        "Total KA Req Sent";
    }
    leaf total-ka-resp-recv {
      type uint32;
      description
        "Total KA Resp Recv";
    }
    leaf total-ka-req-recv {
      type uint32;
      description
        "Total KA Req Recv";
    }
    leaf total-ka-resp-sent {
      type uint32;
      description
        "Total KA Resp Sent";
    }
    leaf mtu {
      type uint32;
      description
        "Max transfer unit";
    }
    leaf is-encap-string-ready {
      type boolean;
      description
        "Flag whether encap String is ready or not";
    }
    leaf ka-echo-request-counter {
      type uint32;
      description
        "Keepalive  req sent but resp not received";
    }
    leaf lcp-identity {
      type uint8;
      description
        "Identification for KA echo req";
    }
    leaf pppflags {
      type uint32;
      description
        "PPP flags";
    }
    leaf subscriber-type {
      type ncs_rpc_notif_Oper-nal-db-subscriber;
      description
        "Nal Subacriber type";
    }
    leaf parent-ifhandle {
      type xr:ncs_rpc_notif_Interface-name;
      description
        "Parent interface";
    }
    leaf parent-interface {
      type string {
        length "0..64";
      }
      description
        "Parent interface";
    }
    leaf subscriber-interface {
      type string {
        length "0..64";
      }
      description
        "Subscriber interface";
    }
    leaf inner-vlan {
      type uint32;
      description
        "Inner Vlan";
    }
    leaf outer-vlan {
      type uint32;
      description
        "Outer Vlan";
    }
    leaf cpe-link-local-address {
      type inet:ipv6-address;
      description
        "CPE link local address";
    }
    leaf framed-ipv6-next-hop {
      type inet:ipv6-address;
      description
        "framed ipv6 next hop";
    }
    leaf framed-ipv6-tag {
      type uint32;
      description
        "framed ipv6 tag";
    }
    leaf framed-ipv4-next-hop {
      type inet:ipv4-address;
      description
        "framed ipv4 next hop";
    }
    leaf framed-ipv4-tag {
      type uint32;
      description
        "framed ipv4 tag";
    }
    leaf feature-id-info {
      type uint32;
      description
        "Subscriber feature id info";
    }
    leaf subscriber-flags {
      type uint32;
      description
        "Subscriber flags";
    }
    leaf interim-interval {
      type uint32;
      description
        "Interim Interval";
    }
    leaf last-interim-time-stamp {
      type uint32;
      description
        "Last Interim Time Stamp";
    }
    leaf interim-fail-count {
      type uint32;
      description
        "Interim Fail Count";
    }
    leaf interim-error {
      type uint32;
      description
        "Interim Error";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf subscriber-create-time {
      type uint32;
      description
        "Subscriber Create Time";
    }
    leaf subscriber-ipv4-up-time {
      type uint32;
      description
        "Subscriber IPv4 Up Time";
    }
    leaf subscriber-ipv6-up-time {
      type uint32;
      description
        "Subscriber IPv6 Up Time";
    }
    leaf subscriber-ipv4-down-time {
      type uint32;
      description
        "Subscriber IPv4 Down Time";
    }
    leaf subscriber-ipv6-down-time {
      type uint32;
      description
        "Subscriber IPv6 Down Time";
    }
    leaf subscriber-af-down-reason {
      type uint32;
      description
        "Subscriber AF Down Reason";
    }
    leaf afup-flags {
      type uint32;
      description
        "AF ipv4/ipv6 up falgs";
    }
    leaf ip-sub-flags {
      type uint64;
      description
        "IPSUB  flags";
    }
    leaf sub-disc-time {
      type uint32;
      description
        "Subscriber Disconnect Time ";
    }
    list active-service {
      description
        "activated services";
      uses ncs_rpc_notif_NAL-SUB-ACTIVATED-SERVICE;
    }
  }

  grouping ncs_rpc_notif_NAL-SUBSCRIBER-DISCONNECT-HISTORY-UNIQUE-INTERNAL-DATA {
    description
      "Subscriber unique disconnect history Bag";
    container session-data {
      description
        "subscriber session data info";
      uses ncs_rpc_notif_NAL-SUBSCRIBER-SESSION-INFO;
    }
    list event-history {
      description
        "subscriber event history";
      uses ncs_rpc_notif_NAL-SUB-DISC-HISTORY-EVT-DATA;
    }
  }

  grouping ncs_rpc_notif_NAL-SUBSCRIBER-DISCONNECT-HISTORY-UNIQUE-DETAIL-DATA {
    description
      "Subscriber unique disconnect history detail Bag";
    leaf disconnect-unique-session-count {
      type uint32;
      description
        "Number of sessions disconnected with this error
         code";
    }
    leaf disc-reason {
      type string {
        length "0..64";
      }
      description
        "Disconnect reason";
    }
    leaf disconnect-errorcode {
      type uint32;
      description
        "error code";
    }
    list unique-detail {
      max-elements 3;
      description
        "unique detail session info for last three
         disconnected sessions";
      uses ncs_rpc_notif_NAL-SUBSCRIBER-DISCONNECT-HISTORY-UNIQUE-INTERNAL-DATA;
    }
  }

  grouping live_ncs_NAL-MAIN-EDM-PROCESS-INFO {
    description
      "Process readiness data";
    leaf nal-process-restart-flag {
      type boolean;
      description
        "NAL Process's restart flag";
    }
    leaf nalot-connection-sts-flag {
      type boolean;
      description
        "NAL Object-tracking connection up status flag";
    }
    leaf nal-clear-session-timer-flag {
      type boolean;
      description
        "NAL Clear-Session Timer Flag";
    }
    leaf nal-clear-feature-timer-flag {
      type boolean;
      description
        "NAL Clear-Feature Timer Flag";
    }
    leaf disconnect-history-file-logg-enable-flag {
      type boolean;
      description
        "Subscriber Disconnect-history file-logging
         disable feature flag";
    }
    leaf test-client-cfg-enabled-flag {
      type boolean;
      description
        "NAL Test Client config enabled flag";
    }
    leaf nal-pre-init-role {
      type uint8;
      description
        "NAL Process's HA PreInit Role";
    }
    leaf nal-role {
      type uint8;
      description
        "NAL Process's HA Role";
    }
    leaf node-id {
      type uint32;
      description
        "NAL Process's running-instance location node-id";
    }
    leaf nalrsi-ctx-file-descriptor {
      type int32;
      description
        "NAL RSI contex file-desc value";
    }
    leaf nal-pid-misc-flags {
      type uint32;
      description
        "NAL Main context Miscellaneous flags";
    }
    leaf nalsvm-subdb-conn-sts-flag {
      type uint8;
      description
        "NAL Process's SVM context SUBDB
         connection-status flag";
    }
    leaf nalsvmp-done-req-id {
      type uint32;
      description
        "NAL Process's SVM Produce-Done req-id";
    }
    leaf nalsvm-recon-last-upid {
      type uint32;
      description
        "NAL SVM Reconciliation Last UPID";
    }
    leaf nalsvm-reconn-pending-req {
      type uint32;
      description
        "NAL SVM Reconciliation Pending Requests";
    }
    leaf nalsvm-reconn-max-req {
      type uint32;
      description
        "NAL SVM Reconciliation Max Requests";
    }
    leaf nal-sub-ctx-replay-in-progress {
      type uint32;
      description
        "NAL Subscriber context stale cache-size";
    }
    leaf nal-subs-ctx-cache-queue-size {
      type uint32;
      description
        "NAL Subscriber context stale cache-size";
    }
    leaf nal-subs-ctx-stale-queue-size {
      type uint32;
      description
        "NAL Subscriber context stale queue-size";
    }
    leaf disconnect-queue-size {
      type uint32;
      description
        "NAL Subscriber disconnect queue size";
    }
    leaf nal-msg-local-seq-no {
      type uint32;
      description
        "NAL Message locally generated seq_no";
    }
    leaf nal-msg-seq-no {
      type uint32;
      description
        "NAL message seq_no towards SPA";
    }
    leaf nal-bulk-disc-invoke-time {
      type uint64;
      description
        "NAL Bulk Disconnect-session start time";
    }
    leaf nal-statistics-hold-timeout-val {
      type uint32;
      description
        "NAL Stats Hold-Timeout value";
    }
    leaf nal-statistics-hold-req-count {
      type uint32;
      description
        "NAL Stats Hold-Request Count";
    }
    leaf nal-statistics-hold-req-max {
      type uint32;
      description
        "NAL Stats Hold-Request Max-threshold";
    }
    leaf nal-statistics-stop-req-count {
      type uint32;
      description
        "NAL Stats Stop-Request counter";
    }
    leaf nal-statistics-interim-req-count {
      type uint32;
      description
        "NAL Stats Interim-Request counter";
    }
    leaf nal-clear-session-stats-req-count {
      type uint32;
      description
        "NAL Clear-Session Stats Request counter";
    }
    leaf nal-clear-feature-stats-req-count {
      type uint32;
      description
        "NAL Clear-Feature Stats Request counter";
    }
    leaf nal-stats-processing-flags {
      type uint32;
      description
        "NAL Statistics miscelleaneous flags";
    }
    leaf create-in-progress {
      type uint32;
      description
        "Number of subscriber create in progress";
    }
    leaf delete-in-progress {
      type uint32;
      description
        "Number of subscriber delete in progress";
    }
    leaf update-in-progress {
      type uint32;
      description
        "Number of subscriber update in progress";
    }
    leaf cp-recon-duration {
      type uint32;
      description
        "CP recon duration";
    }
    leaf cp-recon-flags {
      type uint32;
      description
        "CP recon flags";
    }
    leaf cp-replay-reqs-in-progress {
      type uint32;
      description
        "CP replay reqs in progress";
    }
    leaf cp-replay-subs-in-progress {
      type uint32;
      description
        "CP replay subs in progress";
    }
  }

  grouping live_ncs_NAL-MAIN-EDM-VRF-AFI-INSTANCE {
    description
      "NAL MAIN EDM VRF AFI INSTANCE";
    leaf vrf-address-family {
      type uint8;
      description
        "VRF Table Address-Family";
    }
    leaf vrf-info-table-flag {
      type uint8;
      description
        "VRF Table Flags";
    }
    leaf vrf-table-sync-flag {
      type uint8;
      description
        "buffer complete sent to RIB";
    }
    leaf protocol-id {
      type uint16;
      description
        "Protocol Id";
    }
    leaf vrf-table-id {
      type uint32;
      description
        "VRF Table-Id";
    }
    leaf vrf-pending-routes {
      type uint32;
      description
        "VRF Table Pending-routes";
    }
    leaf ref-count {
      type uint64;
      description
        "No.of interfaces referencing this table";
    }
    leaf max-ref-count {
      type uint64;
      description
        "Max No. of interfaces allowed";
    }
  }

  grouping live_ncs_NAL-MAIN-EDM-VRFTBL-INFO {
    description
      "NAL VRF Table Info bag";
    leaf vrf-name-xr {
      type string {
        length "0..33";
      }
      description
        "Vrf Name";
    }
    list nal-vrf-afi-instance-info {
      description
        "NAL VRF AFI Instance table info";
      uses live_ncs_NAL-MAIN-EDM-VRF-AFI-INSTANCE;
    }
  }

  grouping live_ncs_NAL-MAIN-EDM-OC-ENTRY {
    description
      "NAL owner-channel entries";
    leaf afi {
      type uint8;
      description
        "Address family for this route";
    }
    leaf ipv6-prefix {
      type inet:ipv6-address;
      description
        "ipv6 prefix address";
    }
    leaf ipv4-prefix {
      type inet:ipv4-address;
      description
        "ipv4 prefix address";
    }
    leaf prefix-length {
      type uint32;
      description
        "Prefix length";
    }
    leaf primary-address {
      type inet:ipv4-address;
      description
        "Secondary address";
    }
    leaf state {
      type live_ncs_Nal-main-edm-oc-state;
      description
        "Status";
    }
    leaf vrf-xr {
      type string {
        length "0..33";
      }
      description
        "VRF name";
    }
    leaf if-handle {
      type xr:live_ncs_Interface-name;
      description
        "Interface Handle";
    }
    leaf tag {
      type uint32;
      description
        "Route tag";
    }
    leaf flags {
      type uint32;
      description
        "Checkpoint flags";
    }
  }

  grouping live_ncs_NAL-AIPC-SERVER-STATS-DATA {
    description
      "aipc server stats";
    leaf conn-present {
      type boolean;
      description
        "connection status";
    }
    leaf service-name {
      type string {
        length "0..256";
      }
      description
        "process Name";
    }
    leaf tx-attempt-count {
      type uint32;
      description
        "Tx attempt count";
    }
    leaf tx-count {
      type uint32;
      description
        "tx count";
    }
    leaf rx-count {
      type uint32;
      description
        "Rx count";
    }
    leaf notify-connect-count {
      type uint32;
      description
        "Notify connect count";
    }
    leaf notify-queue-high-count {
      type uint32;
      description
        "Notify Queue High count";
    }
    leaf notify-queue-low-count {
      type uint32;
      description
        "Notify Queue low count";
    }
    leaf notify-queue-full-count {
      type uint32;
      description
        "Notify Queue full count";
    }
    leaf notify-data-waiting-count {
      type uint32;
      description
        "Notify data waiting count";
    }
    leaf notify-error-count {
      type uint32;
      description
        "Notify error count";
    }
    leaf notify-close-count {
      type uint32;
      description
        "Notify close count";
    }
    leaf notify-sendstatus-count {
      type uint32;
      description
        "Notify send status count";
    }
    leaf notify-open-count {
      type uint32;
      description
        "Notify open count";
    }
    leaf pulse-data-waiting-count {
      type uint32;
      description
        "Pulse Data waiting count";
    }
    leaf queue-full {
      type boolean;
      description
        "Queue full";
    }
    leaf queue-full-drop {
      type uint32;
      description
        "Queue full drop";
    }
    leaf queue-ewouldblock-count {
      type uint32;
      description
        "queue would block count";
    }
    leaf outstanding-buffers {
      type uint32;
      description
        "Outstanding Buffers";
    }
    leaf cumulative-overflow-msgs {
      type uint32;
      description
        "cumulative overflow message";
    }
    leaf hwm-overflow-msgs {
      type uint32;
      description
        "Hwm overflow msg";
    }
    leaf get-mtu-failure {
      type uint32;
      description
        "Get Mtu Failure";
    }
    leaf get-buffer-failure {
      type uint32;
      description
        "get Buffer Failure";
    }
    leaf get-buffer-datap-failure {
      type uint32;
      description
        "get Buffer datap Failure";
    }
    leaf conn-failure {
      type uint32;
      description
        "Conn Failure";
    }
    leaf send-failure {
      type uint32;
      description
        "Send Failure";
    }
    leaf receive-failure {
      type uint32;
      description
        "receive Failure";
    }
    leaf release-buffer-failure {
      type uint32;
      description
        "Release Buffer failure";
    }
    leaf overflow-q-flush-count {
      type uint32;
      description
        "Overflow flush count";
    }
    leaf notify-queue-low-count-after-high {
      type uint32;
      description
        "notify queue low count after high";
    }
    leaf last-high-watermark-count-timestamp {
      type uint32;
      description
        "High WaterMark timestamp";
    }
    leaf last-low-watermark-count-timestamp {
      type uint32;
      description
        "Low WaterMark timestamp";
    }
  }

  grouping live_ncs_NAL-MAIN-EDM-OC-SUMMARY {
    description
      "Dynamic routes and OC entries summary";
    leaf v4-oc-entries {
      type uint32;
      description
        "Total V4 OC entries primary/secondary";
    }
    leaf v6-oc-entries {
      type uint32;
      description
        "Total V6 OC entries";
    }
    leaf v4-primary-entries {
      type uint32;
      description
        "Total primary addresses";
    }
    leaf v4-sec-entries {
      type uint32;
      description
        "Total secondary addresses";
    }
    leaf v4-rib-entries {
      type uint32;
      description
        "Total V4 RIB entries";
    }
    leaf v6-rib-entries {
      type uint32;
      description
        "Total V6 RIB entries";
    }
    leaf replayed-oc-entries {
      type uint32;
      description
        "Total entries replayed during last reconcile";
    }
  }

  grouping live_ncs_NAL-MAIN-EDM-CP-CONN-STS-INFO {
    description
      "NAL User & Control-plane connection status
       information";
    leaf nal-transport-user-plane-src-conn-flag {
      type boolean;
      description
        "True if NAL Transport user-plane source
         connection address is configured";
    }
    leaf nalcp-svr-connect-sts {
      type live_ncs_Nal-cp-connection-status;
      description
        "NAL control-plane connection-status value";
    }
    leaf nalcp-svr-connect-sts-time {
      type uint32;
      description
        "NAL control-plane connection-status time stamp";
    }
    leaf nalcp-svr-connect-sts-prev {
      type live_ncs_Nal-cp-connection-status;
      description
        "NAL control-plane prev connection-status value";
    }
    leaf nalcp-svr-connect-sts-time-prev {
      type uint32;
      description
        "NAL control-plane prev connection-status time
         stamp";
    }
    leaf cp-assoc-status {
      type live_ncs_Nal-cp-assoc-status;
      description
        "Control plane association status";
    }
    leaf cp-assoc-status-time {
      type uint32;
      description
        "Control plane association status time stamp";
    }
    leaf nal-transport-user-plane-source-conn-addr-family {
      type uint8;
      description
        "NAL Transport user-plane source server
         connection address-family";
    }
    leaf nal-transport-up-source-ipv4-address {
      type inet:ipv4-address;
      description
        "NAL Transport user-plane server connection IPv4
         address";
    }
    leaf nal-transport-up-source-ipv6-address {
      type inet:ipv6-address;
      description
        "NAL Transport user-plane server connection IPv6
         address";
    }
    leaf nal-transport-up-src-loop-back-if-name {
      type string {
        length "0..64";
      }
      description
        "NAL Transport user-plane server loopback
         interface-name";
    }
    leaf nal-transport-up-source-gtpu-port {
      type uint32;
      description
        "NAL Transport user-plane server connection GTPU
         port-number";
    }
    leaf nal-transport-up-source-pfcp-port {
      type uint32;
      description
        "NAL Transport user-plane server connection PFCP
         port-number";
    }
    leaf nal-transport-up-source-vrf-name {
      type string {
        length "0..33";
      }
      description
        "NAL Transport user-plane server connection
         VRF-Name";
    }
    leaf nal-transport-control-plane-primary-srv-addr-family {
      type uint8;
      description
        "NAL transport control-plane primary-server
         connection address-family";
    }
    leaf nal-transport-cp-primary-ipv4-address {
      type inet:ipv4-address;
      description
        "NAL Transport C-plane primary-server connection
         IPv4 address";
    }
    leaf nal-transport-cp-primary-ipv6-address {
      type inet:ipv6-address;
      description
        "NAL Transport C-plane primary-server connection
         IPv6 address";
    }
    leaf nal-transport-cp-server-gtpu-port {
      type uint32;
      description
        "NAL Transport C-plane server's GTPU port-number";
    }
    leaf nal-transport-cp-server-pfcp-port {
      type uint32;
      description
        "NAL Transport C-plane server's PFCP port-number";
    }
    leaf retry-count {
      type uint16;
      description
        "CP association request retry count";
    }
  }

  grouping live_ncs_NAL-MAIN-EDM-PROCESS-READINESS {
    description
      "Process readiness data";
    leaf resync-pending-flags {
      type uint32;
      description
        "Resync operations pending for NAL process";
    }
    leaf sir-ready {
      type boolean;
      description
        "Status of SIR readiness";
    }
  }

  grouping live_ncs_NAL-MAIN-EDM-PARENT-INTF-INITIATOR-DATA {
    description
      "NAL MAIN EDM PARENT INTF INITIATOR DATA";
    leaf is-configured {
      type boolean;
      description
        "Ture if the initiator is configred";
    }
  }

  grouping live_ncs_NAL-MAIN-EDM-PARENT-INTF-INITIATORS {
    description
      "Initiator protocol details";
    container intiator-type {
      description
        "DHCP information";
      uses live_ncs_NAL-MAIN-EDM-PARENT-INTF-INITIATOR-DATA;
    }
  }

  grouping live_ncs_NAL-MAIN-EDM-PARENT-INTF-DATA {
    description
      "Parent interface data";
    container initiators {
      description
        "Configurational state-statistics for each
         initiating protocol enabled on this parent
         interface";
      uses live_ncs_NAL-MAIN-EDM-PARENT-INTF-INITIATORS;
    }
    leaf parent-interface {
      type xr:live_ncs_Interface-name;
      description
        "Ifhandle of parent interface";
    }
    leaf interface-creation-time {
      type string;
      description
        "Interface creation time in Month Date HH:MM:SS
         format";
    }
    leaf age {
      type string;
      description
        "Age in HH:MM:SS format";
    }
    leaf parent-intf-flags {
      type uint32;
      description
        "Access Interface flags";
    }
    leaf nal-ether-encap {
      type yang:hex-string;
      description
        "Ether Encap Attribute";
    }
    leaf effective-bandwidth {
      type uint32;
      description
        "Effective Bandwidth";
    }
    leaf max-bandwidth {
      type uint32;
      description
        "Maximum Bandwidth";
    }
    leaf link-local {
      type inet:ipv6-address;
      description
        "link local address";
    }
  }

  grouping live_ncs_NAL-MAIN-EDM-SPA-RT-PROV-HIST-DATA {
    description
      "Route provision request response history";
    container request-response-timestamp {
      description
        "Timestamp of request or response";
      uses live_ncs_NAL-TIMESPEC;
    }
    leaf type {
      type live_ncs_Nal-main-edm-spa-rt-hist;
      description
        "Type of route history data";
    }
    list data {
      description
        "Request or Response";
      leaf entry {
        type uint8;
        description
          "Request or Response";
      }
    }
  }

  grouping live_ncs_NAL-MAIN-EDM-CHUNK-DATA {
    description
      "NAL MAIN EDM CHUNK DATA";
    leaf chunk-name {
      type string;
      description
        "Chunk Name";
    }
    leaf chunk-id {
      type uint32;
      description
        "Chunk Id";
    }
    leaf chunk-total-alloc {
      type uint32;
      description
        "Total number of chunk malloc done";
    }
    leaf chunk-total-free {
      type uint32;
      description
        "Total number of chunk free done";
    }
    leaf chunk-in-use {
      type uint32;
      description
        "total number of chunk blocks in use";
    }
  }

  grouping live_ncs_NAL-MAIN-EDM-CHUNK-STATS {
    description
      "NAL MAIN EDM CHUNK STATS";
    list chunk-stat {
      description
        "Chunk Memory statistics";
      uses live_ncs_NAL-MAIN-EDM-CHUNK-DATA;
    }
  }

  grouping live_ncs_NAL-SUBSCRIBER-DISCONNECT-HISTORY-DATA {
    description
      "Subscriber disconnect history bag";
    container fail-data {
      description
        "failed data";
      uses live_ncs_NAL-LAST-FAILED-DATA;
    }
    container session-data {
      description
        "subscriber session data info";
      uses live_ncs_NAL-SUBSCRIBER-SESSION-INFO;
    }
    leaf disc-cause {
      type uint32;
      description
        "Disconnect code";
    }
    list event-history {
      description
        "subscriber event history";
      uses live_ncs_NAL-SUB-DISC-HISTORY-EVT-DATA;
    }
  }

  grouping live_ncs_EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    list evt-data {
      description
        "Optional data";
      leaf entry {
        type uint32;
        description
          "Optional data";
      }
    }
  }

  grouping live_ncs_EVT-HIST-INFO {
    description
      "Per object event history";
    leaf evt-class-name {
      type string;
      description
        "Class name string";
    }
    list evt-entry {
      description
        "Array of event entries";
      uses live_ncs_EVT-HIST-ENTRY;
    }
  }

  grouping live_ncs_NAL-MAIN-EDM-EVENTS {
    description
      "NAL Main process init information";
    container event-history {
      description
        "Main process boot up events";
      uses live_ncs_EVT-HIST-INFO;
    }
    container im-event-history {
      description
        "IM module events";
      uses live_ncs_EVT-HIST-INFO;
    }
    container svm-event-history {
      description
        "SVM module events";
      uses live_ncs_EVT-HIST-INFO;
    }
    container rib-event-history {
      description
        "RIB module events";
      uses live_ncs_EVT-HIST-INFO;
    }
    container cp-event-history {
      description
        "CP module events";
      uses live_ncs_EVT-HIST-INFO;
    }
    container config-event-history {
      description
        "Config module events";
      uses live_ncs_EVT-HIST-INFO;
    }
  }

  grouping live_ncs_NAL-SUBSCRIBER-AFI-SUMMARY {
    description
      "Subscriber afi summary data";
    leaf none {
      type uint32;
      description
        "No afi";
    }
    leaf ipv4 {
      type uint32;
      description
        "IPv4 count";
    }
    leaf ipv6 {
      type uint32;
      description
        "IPv6 count";
    }
    leaf dual {
      type uint32;
      description
        "Dual count";
    }
    leaf total {
      type uint32;
      description
        "Total";
    }
  }

  grouping live_ncs_NAL-SUBSCRIBER-STATE-SUMMARY {
    description
      "Subscriber state summary data";
    leaf initializing {
      type uint32;
      description
        "Initializing";
    }
    leaf connecting {
      type uint32;
      description
        "Connecting";
    }
    leaf connected {
      type uint32;
      description
        "Connected";
    }
    leaf activated {
      type uint32;
      description
        "Activated";
    }
    leaf idle {
      type uint32;
      description
        "Idle";
    }
    leaf disconnecting {
      type uint32;
      description
        "Disconnecting";
    }
    leaf total {
      type uint32;
      description
        "Total";
    }
  }

  grouping live_ncs_NAL-SUBSCRIBER-SUMMARY {
    description
      "Subscriber summary data";
    container ipoe-state-summary {
      description
        "IPoE State Summary";
      uses live_ncs_NAL-SUBSCRIBER-STATE-SUMMARY;
    }
    container pppoe-state-summary {
      description
        "PPPoE State Summary";
      uses live_ncs_NAL-SUBSCRIBER-STATE-SUMMARY;
    }
    container ipoe-afi-summary {
      description
        "IPoE AFI Summary";
      uses live_ncs_NAL-SUBSCRIBER-AFI-SUMMARY;
    }
    container pppoe-afi-summary {
      description
        "PPPoE AFI Summary";
      uses live_ncs_NAL-SUBSCRIBER-AFI-SUMMARY;
    }
  }

  grouping live_ncs_NAL-SUBSCRIBER-DISCONNECT-HISTORY-UNIQUE-DATA {
    description
      "Subscriber unique disconnect history Bag";
    leaf disconnect-unique-session-count {
      type uint32;
      description
        "Number of sessions disconnected with this error
         code";
    }
    leaf disconnect-errorcode {
      type uint32;
      description
        "error code";
    }
    leaf sub-if-name {
      type string {
        length "0..64";
      }
      description
        "Interface Name";
    }
    leaf sub-disc-time {
      type uint32;
      description
        "Subscriber Disconnect Time ";
    }
    leaf disc-reason {
      type string {
        length "0..64";
      }
      description
        "Disconnect reason";
    }
  }

  grouping live_ncs_NAL-SERVICE-PROFILE-DATA {
    description
      "NAL service profile information";
    leaf service-name {
      type string {
        length "0..65";
      }
      description
        "Name of the service";
    }
    leaf service-id {
      type uint32;
      description
        "Service id assigned by SUBDB";
    }
    leaf use-count {
      type uint32;
      description
        "Number of subscribers using this profile";
    }
    leaf state {
      type live_ncs_Svm-service-state;
      description
        "State of the service";
    }
    leaf fail-err {
      type uint32;
      description
        "Installation failure rc";
    }
    leaf stale-timer-remaining {
      type uint32;
      description
        "stale timer remaining";
    }
    leaf assoc-in-progress {
      type uint32;
      description
        "No of subscribers need to use this profile";
    }
    list wait-upi-dqueue {
      description
        "List of UPIDs waiting for this service";
      leaf entry {
        type uint32;
        description
          "List of UPIDs waiting for this service";
      }
    }
  }

  grouping live_ncs_IPSUB-BASE-INIT {
    description
      "ipsub base init data";
    leaf type {
      type uint8;
      description
        "Init data type";
    }
    leaf version {
      type uint8;
      description
        "Init data version";
    }
    leaf length {
      type uint16;
      description
        "Init data length";
    }
  }

  grouping live_ncs_IPSUB-INTF-INIT-TYPE {
    description
      "Subscriber intf init data";
    container base {
      description
        "base";
      uses live_ncs_IPSUB-BASE-INIT;
    }
    leaf subscriber-mac {
      type yang:mac-address;
      description
        "MAC address";
    }
    leaf vlan-tag-count {
      type uint16;
      description
        "Vlan tag count";
    }
    leaf vrf-table-id {
      type uint32;
      description
        "Vrf table id ";
    }
    leaf v6-vrf-table-id {
      type uint32;
      description
        "Ipv6 Vrf table id ";
    }
    leaf up-link-gre-key {
      type uint32;
      description
        "Up link gre key";
    }
    leaf down-link-gre-key {
      type uint32;
      description
        "Down link gre key";
    }
    leaf subscriber-gw-mac {
      type yang:mac-address;
      description
        "Gateway MAC address";
    }
    leaf sub-attr-bits {
      type uint8;
      description
        "Subscriber attr bits";
    }
    leaf sub-info-bits {
      type uint8;
      description
        "Subscriber info bits";
    }
    leaf subscriber-ipv4 {
      type uint32;
      description
        "Subscriber IPv4";
    }
    leaf nexthop-ipv4 {
      type uint32;
      description
        "next hop  IPv4 address";
    }
    leaf subscriber-ipv6 {
      type inet:ipv6-address;
      description
        "Subscriber Ipv6 address";
    }
    leaf subscriber-ipv6-prefix {
      type inet:ipv6-address;
      description
        "Subscriber Ipv6 address";
    }
    leaf nexthop-ipv6 {
      type inet:ipv6-address;
      description
        "Nexthop Ipv6 address";
    }
    leaf v6-len {
      type uint8;
      description
        "V6 len";
    }
    leaf v6-prefix-len {
      type uint8;
      description
        "V6 prefix len";
    }
    leaf template-ifh {
      type uint32;
      description
        "Template interface handle";
    }
    leaf ipv4-mtu {
      type uint16;
      description
        "Ipv4 MTU";
    }
    leaf ipv6-mtu {
      type uint16;
      description
        "Ipv6 MTU";
    }
    leaf odns-deviceid-higher {
      type uint32;
      description
        "ODNS device id highter";
    }
    leaf odns-deviceid-lower {
      type uint32;
      description
        "ODNS device id Lower";
    }
    list vlan-stack {
      // NCS drop max-elements statement
      description
        "vlan stack type";
      uses live_ncs_DOT1Q-TAG-DATA-TYPE;
    }
  }

  grouping live_ncs_NAL-TRANS-CONTEXT-DATA {
    description
      "Nal transaction context";
    leaf state {
      type live_ncs_Nal-trans-state;
      description
        "Subscriber transactio state";
    }
    leaf client-type {
      type live_ncs_Nal-trans-client-data;
      description
        "Client type indicate who is triggert this
         transction";
    }
    leaf trans-id {
      type uint32;
      description
        "Transaction ID";
    }
    leaf disconnect-ack {
      type uint32;
      description
        "Disconnect Ack";
    }
    leaf module-err {
      type uint32;
      description
        "Error generated by sub module";
    }
    leaf module-interaction-mask {
      type uint64;
      description
        "Flag to indicate which sub-module interactions
         are in progress";
    }
    leaf rollback-module-mask {
      type uint64;
      description
        "Flag to indicate which sub-module rollback needs
         to be invoked";
    }
    leaf pending-cb-bitmask {
      type uint64;
      description
        "Flag indicating pending callbacks for this
         transaction";
    }
  }

  grouping live_ncs_NAL-TRANS-SUB-CONTEXT-DATA {
    description
      "Subscriber transaction context";
    container trans-context {
      description
        "trans context";
      uses live_ncs_NAL-TRANS-CONTEXT-DATA;
    }
  }

  grouping live_ncs_NAL-IPSUB-INFLIGHT-DATA {
    description
      "Nal ipsub inflight data";
    leaf opearation {
      type live_ncs_Nal-intf-oper;
      description
        "Operation in progress";
    }
    leaf flags {
      type uint64;
      description
        "Flags to represent pending activities";
    }
    leaf fail-rc {
      type uint32;
      description
        "Backup of update error, internal rollback in
         progresss";
    }
  }

  grouping live_ncs_SVM-INFLIGHT-DATA {
    description
      "SVM inflight data";
    leaf service-name {
      type string {
        length "0..65";
      }
      description
        "Name of the service";
    }
    leaf service-id {
      type uint32;
      description
        "Service id assigned by SUBDB";
    }
    leaf operation {
      type live_ncs_Nal-spa-oper;
      description
        "Operation to be performed";
    }
    leaf service-flags {
      type uint32;
      description
        "Service flags";
    }
    leaf params-list {
      type yang:hex-string;
      description
        "Attribute list of service params";
    }
    leaf feature-id {
      type uint32;
      description
        "Feature ID";
    }
  }

  grouping live_ncs_NAL-SVM-INFLIGHT-DATA {
    description
      "Nal SVM inflight data";
    leaf opearation {
      type live_ncs_Svm-sub-oper;
      description
        "Operation in progress";
    }
    leaf state {
      type live_ncs_Svn-sub-state;
      description
        "State of the subscriber SVM data";
    }
    leaf fail-rc {
      type uint32;
      description
        "Fail rc";
    }
    leaf up-list {
      type yang:hex-string;
      description
        "User profile attribute list";
    }
    leaf remove-list {
      type yang:hex-string;
      description
        "User profile attribute remove list";
    }
    leaf service-index {
      type uint32;
      description
        "Service that is currently under process";
    }
    leaf subdb-pd-req-id {
      type uint32;
      description
        "SUBDB produce done req id";
    }
    leaf reconcile-state {
      type live_ncs_Svm-reconcile-state;
      description
        "Reconcilitation state";
    }
    list service {
      description
        "Service list array";
      uses live_ncs_SVM-INFLIGHT-DATA;
    }
  }

  grouping live_ncs_DOT1Q-TAG-DATA-TYPE {
    description
      "dot1q tag type";
    leaf etype {
      type uint16;
      description
        "etype";
    }
    leaf ucv {
      type uint16;
      description
        "ucv";
    }
  }

  grouping live_ncs_NAL-SUB-INTF-DATA {
    description
      "subscriber interface info";
    leaf vlan-tag-count {
      type uint16;
      description
        "Vlan tag count";
    }
    leaf sub-attr-bits {
      type uint8;
      description
        "Subscriber attr bits";
    }
    leaf flags {
      type uint64;
      description
        "flags bits";
    }
    leaf vrf-id {
      type uint32;
      description
        "vrf ID";
    }
    leaf v4-table-id {
      type uint32;
      description
        "V4 table id";
    }
    leaf v6-table-id {
      type uint32;
      description
        "V6 table id";
    }
    list vlan-stack {
      // NCS drop max-elements statement
      description
        "vlan stack type";
      uses live_ncs_DOT1Q-TAG-DATA-TYPE;
    }
  }

  grouping live_ncs_NAL-LAST-FAILED-DATA {
    description
      "NAL subscriber last failed transaction data";
    leaf data {
      type string {
        length "0..256";
      }
      description
        "Failed data";
    }
    leaf msg-txn-id {
      type uint32;
      description
        "Message Txn ID";
    }
    leaf sess-txn-id {
      type uint32;
      description
        "Session Txn ID";
    }
    leaf feature-mask {
      type uint32;
      description
        "Feature Mask";
    }
    leaf svm-state {
      type uint32;
      description
        "SVM state";
    }
    leaf ip-sub-flags {
      type uint64;
      description
        "IPSUB flags";
    }
    leaf pending-callback {
      type uint64;
      description
        "Pending Callback";
    }
    leaf failure-reason {
      type uint32;
      description
        "Failure Reason";
    }
    leaf failure-timestamp {
      type uint32;
      description
        "Failure Timestamp";
    }
  }

  grouping live_ncs_NAL-SUBSCRIBER-DEACTIVATED-SERVICE {
    description
      "NAL subscriber deactivated service information";
    leaf service-name {
      type string {
        length "0..65";
      }
      description
        "Name of the service";
    }
    leaf deactivation-time {
      type uint32;
      description
        "service deactivation Time";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
  }

  grouping live_ncs_NAL-SUBSCRIBER-SESSION-DATA-INTERNAL {
    description
      "Subscriber context data";
    container session-data {
      description
        "subscriber session data info";
      uses live_ncs_NAL-SUBSCRIBER-SESSION-INFO;
    }
    container sub-intf {
      description
        "sub intf";
      uses live_ncs_NAL-SUB-INTF-DATA;
    }
    container svm-inflight {
      description
        "svm inflight";
      uses live_ncs_NAL-SVM-INFLIGHT-DATA;
    }
    container ipsub-inflight {
      description
        "ipsub inflight";
      uses live_ncs_NAL-IPSUB-INFLIGHT-DATA;
    }
    container trans-sub-context {
      description
        "trans sub context";
      uses live_ncs_NAL-TRANS-SUB-CONTEXT-DATA;
    }
    container last-init-data {
      description
        "last init data";
      uses live_ncs_IPSUB-INTF-INIT-TYPE;
    }
    leaf subscriber-flags {
      type uint32;
      description
        "Subscriber flags";
    }
    leaf ha-flags {
      type uint32;
      description
        "Subscriber flags";
    }
    leaf last-transaction-result {
      type uint32;
      description
        "Last Transaction Result";
    }
    leaf hold-stats-error {
      type uint32;
      description
        "hold stats status";
    }
    leaf clear-stats-error {
      type uint32;
      description
        "clear stats status";
    }
    leaf packets-in {
      type uint32;
      description
        "No of packets In";
    }
    leaf packets-out {
      type uint32;
      description
        "No of packets Out";
    }
    leaf ipv4-packets-in {
      type uint32;
      description
        "No of IPv4 packets In";
    }
    leaf ipv4-packets-out {
      type uint32;
      description
        "No of IPv4 packets Out";
    }
    leaf ipv4-bytes-in {
      type uint32;
      description
        "IPv4 Bytes in";
    }
    leaf ipv4-bytes-out {
      type uint32;
      description
        "IPv4 Bytes out";
    }
    leaf ipv4-bytes-in-giga {
      type uint32;
      description
        "IPv4 Bytes in Giga";
    }
    leaf ipv4-bytes-out-giga {
      type uint32;
      description
        "IPv4 Bytes out in Giga";
    }
    leaf ipv6-packets-in {
      type uint32;
      description
        "No of IPv6 packets In";
    }
    leaf ipv6-packets-out {
      type uint32;
      description
        "No of IPv6 packets Out";
    }
    leaf ipv6-bytes-in {
      type uint32;
      description
        "IPv6 Bytes in";
    }
    leaf ipv6-bytes-out {
      type uint32;
      description
        "IPv6 Bytes out";
    }
    leaf ipv6-bytes-in-giga {
      type uint32;
      description
        "IPv6 Bytes in Giga";
    }
    leaf ipv6-bytes-out-giga {
      type uint32;
      description
        "IPv6 Bytes out in Giga";
    }
    leaf transaction-id {
      type uint32;
      description
        "Subscriber transaction id";
    }
    leaf loopback-name {
      type string {
        length "0..65";
      }
      description
        "Loopback Name";
    }
    leaf stale-feature-id-info {
      type uint32;
      description
        "subscriber stale feature id info";
    }
    leaf sus-dconnect-time {
      type uint32;
      description
        "Subscriber disconnect Time";
    }
    leaf obj-hdl {
      type uint64;
      description
        "objext handle";
    }
    leaf spi-oattched {
      type boolean;
      description
        "Has SPIO attached";
    }
    list deactivated-service {
      description
        "last deactivated services";
      uses live_ncs_NAL-SUBSCRIBER-DEACTIVATED-SERVICE;
    }
    list last-fail {
      description
        "last failed transaction data";
      uses live_ncs_NAL-LAST-FAILED-DATA;
    }
  }

  grouping live_ncs_NAL-OPER-FADB-RECORD-DATA {
    description
      "NAL OPER FADB RECORD DATA";
    leaf feature-id {
      type uint32;
      description
        "Subscriber Feature-Id";
    }
    leaf upid {
      type uint32;
      description
        "User-plane ID";
    }
    leaf service-id {
      type uint32;
      description
        "Subscriber Service-Id";
    }
    leaf interim-fail-count {
      type uint32;
      description
        "Interim Fail Count";
    }
    leaf stale-timestamp {
      type uint32;
      description
        "Stale timestamp";
    }
    leaf hold-rc {
      type uint32;
      description
        "Hold RC";
    }
    leaf interim-error {
      type uint32;
      description
        "Interim Error";
    }
  }

  grouping live_ncs_NAL-SUBSCRIBER-SESSION-DATA {
    description
      "NAL subscriber detail data information";
    container sub-info {
      description
        "subscriber session data info";
      uses live_ncs_NAL-SUBSCRIBER-SESSION-INFO;
    }
  }

  grouping live_ncs_NAL-TIMESPEC {
    description
      "Structure to replicate timespec";
    leaf tv-sec {
      type uint32;
      description
        "Time in sec";
    }
    leaf tv-nsec {
      type uint32;
      description
        "Time in nsec";
    }
  }

  grouping live_ncs_NAL-SUB-DISC-HISTORY-EVT-DATA {
    description
      "Sub disc history event history bag";
    container evt-time {
      description
        "Event time";
      uses live_ncs_NAL-TIMESPEC;
    }
    leaf evt-type {
      type uint8;
      description
        "Event type";
    }
    leaf event-history-index {
      type uint32;
      description
        "Event History Index";
    }
  }

  grouping live_ncs_NAL-SUB-ACTIVATED-SERVICE {
    description
      "NAL subscriber activated service information";
    leaf service-name {
      type string {
        length "0..65";
      }
      description
        "Name of the service";
    }
    leaf activation-time {
      type uint32;
      description
        "service deactivation Time";
    }
    leaf flags {
      type uint32;
      description
        "flags";
    }
    leaf feature-id {
      type uint32;
      description
        "Feature ID";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf final-time {
      type uint32;
      description
        "service final stats Time";
    }
  }

  grouping live_ncs_NAL-SUBSCRIBER-SESSION-INFO-BRIEF {
    description
      "NAL subscriber  information brief";
    leaf cp-id {
      type uint32;
      description
        "Control-plane ID";
    }
    leaf ifhandle {
      type xr:live_ncs_Interface-name;
      description
        "Subscriber Interface name";
    }
    leaf subscriber-fsm-state {
      type live_ncs_Oper-nal-db-subscriber-state;
      description
        "Nal Subscriber state";
    }
    leaf mac-address {
      type yang:mac-address;
      description
        "MAC address";
    }
    leaf vrf-name {
      type string {
        length "0..33";
      }
      description
        "Vrf Name";
    }
    leaf subscriber-ipv4-address {
      type inet:ipv4-address;
      description
        "IPv4 Address of the subscriber";
    }
    leaf framed-ipv4-addr {
      type inet:ipv4-address;
      description
        "framed ipv4 addr";
    }
    leaf framed-ipv4-prefix-len {
      type uint8;
      description
        "framed ipv4 prefix len";
    }
    leaf ipv6-iana-address {
      type inet:ipv6-address;
      description
        "ipv6 iana address";
    }
    leaf ipv6-iapd-address {
      type inet:ipv6-address;
      description
        "ipv6  iapd address";
    }
    leaf ipv6-iapd-prefix {
      type uint8;
      description
        "ipv6  iapd prefix";
    }
    leaf framed-ipv6-addr {
      type inet:ipv6-address;
      description
        "framed ipv6 addr";
    }
    leaf framed-ipv6-prefix-len {
      type uint8;
      description
        "framed ipv6 prefix len";
    }
  }

  grouping live_ncs_NAL-SUBSCRIBER-SESSION-INFO {
    description
      "NAL subscriber  information";
    container session-brief {
      description
        "session brief";
      uses live_ncs_NAL-SUBSCRIBER-SESSION-INFO-BRIEF;
    }
    leaf up-id {
      type uint32;
      description
        "User-plane ID";
    }
    leaf pppoe-session-id {
      type uint16;
      description
        "PPPoE sesison ID";
    }
    leaf retry-count {
      type uint32;
      description
        "Retry count";
    }
    leaf local-magic-number {
      type uint32;
      description
        "Local magic number";
    }
    leaf peer-magic-number {
      type uint32;
      description
        "Peer magic number";
    }
    leaf keep-alive-interval {
      type uint32;
      description
        "Keep alive interval";
    }
    leaf total-ka-req-sent {
      type uint32;
      description
        "Total KA Req Sent";
    }
    leaf total-ka-resp-recv {
      type uint32;
      description
        "Total KA Resp Recv";
    }
    leaf total-ka-req-recv {
      type uint32;
      description
        "Total KA Req Recv";
    }
    leaf total-ka-resp-sent {
      type uint32;
      description
        "Total KA Resp Sent";
    }
    leaf mtu {
      type uint32;
      description
        "Max transfer unit";
    }
    leaf is-encap-string-ready {
      type boolean;
      description
        "Flag whether encap String is ready or not";
    }
    leaf ka-echo-request-counter {
      type uint32;
      description
        "Keepalive  req sent but resp not received";
    }
    leaf lcp-identity {
      type uint8;
      description
        "Identification for KA echo req";
    }
    leaf pppflags {
      type uint32;
      description
        "PPP flags";
    }
    leaf subscriber-type {
      type live_ncs_Oper-nal-db-subscriber;
      description
        "Nal Subacriber type";
    }
    leaf parent-ifhandle {
      type xr:live_ncs_Interface-name;
      description
        "Parent interface";
    }
    leaf parent-interface {
      type string {
        length "0..64";
      }
      description
        "Parent interface";
    }
    leaf subscriber-interface {
      type string {
        length "0..64";
      }
      description
        "Subscriber interface";
    }
    leaf inner-vlan {
      type uint32;
      description
        "Inner Vlan";
    }
    leaf outer-vlan {
      type uint32;
      description
        "Outer Vlan";
    }
    leaf cpe-link-local-address {
      type inet:ipv6-address;
      description
        "CPE link local address";
    }
    leaf framed-ipv6-next-hop {
      type inet:ipv6-address;
      description
        "framed ipv6 next hop";
    }
    leaf framed-ipv6-tag {
      type uint32;
      description
        "framed ipv6 tag";
    }
    leaf framed-ipv4-next-hop {
      type inet:ipv4-address;
      description
        "framed ipv4 next hop";
    }
    leaf framed-ipv4-tag {
      type uint32;
      description
        "framed ipv4 tag";
    }
    leaf feature-id-info {
      type uint32;
      description
        "Subscriber feature id info";
    }
    leaf subscriber-flags {
      type uint32;
      description
        "Subscriber flags";
    }
    leaf interim-interval {
      type uint32;
      description
        "Interim Interval";
    }
    leaf last-interim-time-stamp {
      type uint32;
      description
        "Last Interim Time Stamp";
    }
    leaf interim-fail-count {
      type uint32;
      description
        "Interim Fail Count";
    }
    leaf interim-error {
      type uint32;
      description
        "Interim Error";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf subscriber-create-time {
      type uint32;
      description
        "Subscriber Create Time";
    }
    leaf subscriber-ipv4-up-time {
      type uint32;
      description
        "Subscriber IPv4 Up Time";
    }
    leaf subscriber-ipv6-up-time {
      type uint32;
      description
        "Subscriber IPv6 Up Time";
    }
    leaf subscriber-ipv4-down-time {
      type uint32;
      description
        "Subscriber IPv4 Down Time";
    }
    leaf subscriber-ipv6-down-time {
      type uint32;
      description
        "Subscriber IPv6 Down Time";
    }
    leaf subscriber-af-down-reason {
      type uint32;
      description
        "Subscriber AF Down Reason";
    }
    leaf afup-flags {
      type uint32;
      description
        "AF ipv4/ipv6 up falgs";
    }
    leaf ip-sub-flags {
      type uint64;
      description
        "IPSUB  flags";
    }
    leaf sub-disc-time {
      type uint32;
      description
        "Subscriber Disconnect Time ";
    }
    list active-service {
      description
        "activated services";
      uses live_ncs_NAL-SUB-ACTIVATED-SERVICE;
    }
  }

  grouping live_ncs_NAL-SUBSCRIBER-DISCONNECT-HISTORY-UNIQUE-INTERNAL-DATA {
    description
      "Subscriber unique disconnect history Bag";
    container session-data {
      description
        "subscriber session data info";
      uses live_ncs_NAL-SUBSCRIBER-SESSION-INFO;
    }
    list event-history {
      description
        "subscriber event history";
      uses live_ncs_NAL-SUB-DISC-HISTORY-EVT-DATA;
    }
  }

  grouping live_ncs_NAL-SUBSCRIBER-DISCONNECT-HISTORY-UNIQUE-DETAIL-DATA {
    description
      "Subscriber unique disconnect history detail Bag";
    leaf disconnect-unique-session-count {
      type uint32;
      description
        "Number of sessions disconnected with this error
         code";
    }
    leaf disc-reason {
      type string {
        length "0..64";
      }
      description
        "Disconnect reason";
    }
    leaf disconnect-errorcode {
      type uint32;
      description
        "error code";
    }
    list unique-detail {
      // NCS drop max-elements statement
      description
        "unique detail session info for last three
         disconnected sessions";
      uses live_ncs_NAL-SUBSCRIBER-DISCONNECT-HISTORY-UNIQUE-INTERNAL-DATA;
    }
  }

  grouping NAL-MAIN-EDM-PROCESS-INFO {
    description
      "Process readiness data";
    leaf nal-process-restart-flag {
      type boolean;
      description
        "NAL Process's restart flag";
    }
    leaf nalot-connection-sts-flag {
      type boolean;
      description
        "NAL Object-tracking connection up status flag";
    }
    leaf nal-clear-session-timer-flag {
      type boolean;
      description
        "NAL Clear-Session Timer Flag";
    }
    leaf nal-clear-feature-timer-flag {
      type boolean;
      description
        "NAL Clear-Feature Timer Flag";
    }
    leaf disconnect-history-file-logg-enable-flag {
      type boolean;
      description
        "Subscriber Disconnect-history file-logging
         disable feature flag";
    }
    leaf test-client-cfg-enabled-flag {
      type boolean;
      description
        "NAL Test Client config enabled flag";
    }
    leaf nal-pre-init-role {
      type uint8;
      description
        "NAL Process's HA PreInit Role";
    }
    leaf nal-role {
      type uint8;
      description
        "NAL Process's HA Role";
    }
    leaf node-id {
      type uint32;
      description
        "NAL Process's running-instance location node-id";
    }
    leaf nalrsi-ctx-file-descriptor {
      type int32;
      description
        "NAL RSI contex file-desc value";
    }
    leaf nal-pid-misc-flags {
      type uint32;
      description
        "NAL Main context Miscellaneous flags";
    }
    leaf nalsvm-subdb-conn-sts-flag {
      type uint8;
      description
        "NAL Process's SVM context SUBDB
         connection-status flag";
    }
    leaf nalsvmp-done-req-id {
      type uint32;
      description
        "NAL Process's SVM Produce-Done req-id";
    }
    leaf nalsvm-recon-last-upid {
      type uint32;
      description
        "NAL SVM Reconciliation Last UPID";
    }
    leaf nalsvm-reconn-pending-req {
      type uint32;
      description
        "NAL SVM Reconciliation Pending Requests";
    }
    leaf nalsvm-reconn-max-req {
      type uint32;
      description
        "NAL SVM Reconciliation Max Requests";
    }
    leaf nal-sub-ctx-replay-in-progress {
      type uint32;
      description
        "NAL Subscriber context stale cache-size";
    }
    leaf nal-subs-ctx-cache-queue-size {
      type uint32;
      description
        "NAL Subscriber context stale cache-size";
    }
    leaf nal-subs-ctx-stale-queue-size {
      type uint32;
      description
        "NAL Subscriber context stale queue-size";
    }
    leaf disconnect-queue-size {
      type uint32;
      description
        "NAL Subscriber disconnect queue size";
    }
    leaf nal-msg-local-seq-no {
      type uint32;
      description
        "NAL Message locally generated seq_no";
    }
    leaf nal-msg-seq-no {
      type uint32;
      description
        "NAL message seq_no towards SPA";
    }
    leaf nal-bulk-disc-invoke-time {
      type uint64;
      description
        "NAL Bulk Disconnect-session start time";
    }
    leaf nal-statistics-hold-timeout-val {
      type uint32;
      description
        "NAL Stats Hold-Timeout value";
    }
    leaf nal-statistics-hold-req-count {
      type uint32;
      description
        "NAL Stats Hold-Request Count";
    }
    leaf nal-statistics-hold-req-max {
      type uint32;
      description
        "NAL Stats Hold-Request Max-threshold";
    }
    leaf nal-statistics-stop-req-count {
      type uint32;
      description
        "NAL Stats Stop-Request counter";
    }
    leaf nal-statistics-interim-req-count {
      type uint32;
      description
        "NAL Stats Interim-Request counter";
    }
    leaf nal-clear-session-stats-req-count {
      type uint32;
      description
        "NAL Clear-Session Stats Request counter";
    }
    leaf nal-clear-feature-stats-req-count {
      type uint32;
      description
        "NAL Clear-Feature Stats Request counter";
    }
    leaf nal-stats-processing-flags {
      type uint32;
      description
        "NAL Statistics miscelleaneous flags";
    }
    leaf create-in-progress {
      type uint32;
      description
        "Number of subscriber create in progress";
    }
    leaf delete-in-progress {
      type uint32;
      description
        "Number of subscriber delete in progress";
    }
    leaf update-in-progress {
      type uint32;
      description
        "Number of subscriber update in progress";
    }
    leaf cp-recon-duration {
      type uint32;
      description
        "CP recon duration";
    }
    leaf cp-recon-flags {
      type uint32;
      description
        "CP recon flags";
    }
    leaf cp-replay-reqs-in-progress {
      type uint32;
      description
        "CP replay reqs in progress";
    }
    leaf cp-replay-subs-in-progress {
      type uint32;
      description
        "CP replay subs in progress";
    }
  }

  grouping NAL-MAIN-EDM-VRF-AFI-INSTANCE {
    description
      "NAL MAIN EDM VRF AFI INSTANCE";
    leaf vrf-address-family {
      type uint8;
      description
        "VRF Table Address-Family";
    }
    leaf vrf-info-table-flag {
      type uint8;
      description
        "VRF Table Flags";
    }
    leaf vrf-table-sync-flag {
      type uint8;
      description
        "buffer complete sent to RIB";
    }
    leaf protocol-id {
      type uint16;
      description
        "Protocol Id";
    }
    leaf vrf-table-id {
      type uint32;
      description
        "VRF Table-Id";
    }
    leaf vrf-pending-routes {
      type uint32;
      description
        "VRF Table Pending-routes";
    }
    leaf ref-count {
      type uint64;
      description
        "No.of interfaces referencing this table";
    }
    leaf max-ref-count {
      type uint64;
      description
        "Max No. of interfaces allowed";
    }
  }

  grouping NAL-MAIN-EDM-VRFTBL-INFO {
    description
      "NAL VRF Table Info bag";
    leaf vrf-name-xr {
      type string {
        length "0..33";
      }
      description
        "Vrf Name";
    }
    list nal-vrf-afi-instance-info {
      description
        "NAL VRF AFI Instance table info";
      uses NAL-MAIN-EDM-VRF-AFI-INSTANCE;
    }
  }

  grouping NAL-MAIN-EDM-OC-ENTRY {
    description
      "NAL owner-channel entries";
    leaf afi {
      type uint8;
      description
        "Address family for this route";
    }
    leaf ipv6-prefix {
      type inet:ipv6-address;
      description
        "ipv6 prefix address";
    }
    leaf ipv4-prefix {
      type inet:ipv4-address;
      description
        "ipv4 prefix address";
    }
    leaf prefix-length {
      type uint32;
      description
        "Prefix length";
    }
    leaf primary-address {
      type inet:ipv4-address;
      description
        "Secondary address";
    }
    leaf state {
      type Nal-main-edm-oc-state;
      description
        "Status";
    }
    leaf vrf-xr {
      type string {
        length "0..33";
      }
      description
        "VRF name";
    }
    leaf if-handle {
      type xr:Interface-name;
      description
        "Interface Handle";
    }
    leaf tag {
      type uint32;
      description
        "Route tag";
    }
    leaf flags {
      type uint32;
      description
        "Checkpoint flags";
    }
  }

  grouping NAL-AIPC-SERVER-STATS-DATA {
    description
      "aipc server stats";
    leaf conn-present {
      type boolean;
      description
        "connection status";
    }
    leaf service-name {
      type string {
        length "0..256";
      }
      description
        "process Name";
    }
    leaf tx-attempt-count {
      type uint32;
      description
        "Tx attempt count";
    }
    leaf tx-count {
      type uint32;
      description
        "tx count";
    }
    leaf rx-count {
      type uint32;
      description
        "Rx count";
    }
    leaf notify-connect-count {
      type uint32;
      description
        "Notify connect count";
    }
    leaf notify-queue-high-count {
      type uint32;
      description
        "Notify Queue High count";
    }
    leaf notify-queue-low-count {
      type uint32;
      description
        "Notify Queue low count";
    }
    leaf notify-queue-full-count {
      type uint32;
      description
        "Notify Queue full count";
    }
    leaf notify-data-waiting-count {
      type uint32;
      description
        "Notify data waiting count";
    }
    leaf notify-error-count {
      type uint32;
      description
        "Notify error count";
    }
    leaf notify-close-count {
      type uint32;
      description
        "Notify close count";
    }
    leaf notify-sendstatus-count {
      type uint32;
      description
        "Notify send status count";
    }
    leaf notify-open-count {
      type uint32;
      description
        "Notify open count";
    }
    leaf pulse-data-waiting-count {
      type uint32;
      description
        "Pulse Data waiting count";
    }
    leaf queue-full {
      type boolean;
      description
        "Queue full";
    }
    leaf queue-full-drop {
      type uint32;
      description
        "Queue full drop";
    }
    leaf queue-ewouldblock-count {
      type uint32;
      description
        "queue would block count";
    }
    leaf outstanding-buffers {
      type uint32;
      description
        "Outstanding Buffers";
    }
    leaf cumulative-overflow-msgs {
      type uint32;
      description
        "cumulative overflow message";
    }
    leaf hwm-overflow-msgs {
      type uint32;
      description
        "Hwm overflow msg";
    }
    leaf get-mtu-failure {
      type uint32;
      description
        "Get Mtu Failure";
    }
    leaf get-buffer-failure {
      type uint32;
      description
        "get Buffer Failure";
    }
    leaf get-buffer-datap-failure {
      type uint32;
      description
        "get Buffer datap Failure";
    }
    leaf conn-failure {
      type uint32;
      description
        "Conn Failure";
    }
    leaf send-failure {
      type uint32;
      description
        "Send Failure";
    }
    leaf receive-failure {
      type uint32;
      description
        "receive Failure";
    }
    leaf release-buffer-failure {
      type uint32;
      description
        "Release Buffer failure";
    }
    leaf overflow-q-flush-count {
      type uint32;
      description
        "Overflow flush count";
    }
    leaf notify-queue-low-count-after-high {
      type uint32;
      description
        "notify queue low count after high";
    }
    leaf last-high-watermark-count-timestamp {
      type uint32;
      description
        "High WaterMark timestamp";
    }
    leaf last-low-watermark-count-timestamp {
      type uint32;
      description
        "Low WaterMark timestamp";
    }
  }

  grouping NAL-MAIN-EDM-OC-SUMMARY {
    description
      "Dynamic routes and OC entries summary";
    leaf v4-oc-entries {
      type uint32;
      description
        "Total V4 OC entries primary/secondary";
    }
    leaf v6-oc-entries {
      type uint32;
      description
        "Total V6 OC entries";
    }
    leaf v4-primary-entries {
      type uint32;
      description
        "Total primary addresses";
    }
    leaf v4-sec-entries {
      type uint32;
      description
        "Total secondary addresses";
    }
    leaf v4-rib-entries {
      type uint32;
      description
        "Total V4 RIB entries";
    }
    leaf v6-rib-entries {
      type uint32;
      description
        "Total V6 RIB entries";
    }
    leaf replayed-oc-entries {
      type uint32;
      description
        "Total entries replayed during last reconcile";
    }
  }

  grouping NAL-MAIN-EDM-CP-CONN-STS-INFO {
    description
      "NAL User & Control-plane connection status
       information";
    leaf nal-transport-user-plane-src-conn-flag {
      type boolean;
      description
        "True if NAL Transport user-plane source
         connection address is configured";
    }
    leaf nalcp-svr-connect-sts {
      type Nal-cp-connection-status;
      description
        "NAL control-plane connection-status value";
    }
    leaf nalcp-svr-connect-sts-time {
      type uint32;
      description
        "NAL control-plane connection-status time stamp";
    }
    leaf nalcp-svr-connect-sts-prev {
      type Nal-cp-connection-status;
      description
        "NAL control-plane prev connection-status value";
    }
    leaf nalcp-svr-connect-sts-time-prev {
      type uint32;
      description
        "NAL control-plane prev connection-status time
         stamp";
    }
    leaf cp-assoc-status {
      type Nal-cp-assoc-status;
      description
        "Control plane association status";
    }
    leaf cp-assoc-status-time {
      type uint32;
      description
        "Control plane association status time stamp";
    }
    leaf nal-transport-user-plane-source-conn-addr-family {
      type uint8;
      description
        "NAL Transport user-plane source server
         connection address-family";
    }
    leaf nal-transport-up-source-ipv4-address {
      type inet:ipv4-address;
      description
        "NAL Transport user-plane server connection IPv4
         address";
    }
    leaf nal-transport-up-source-ipv6-address {
      type inet:ipv6-address;
      description
        "NAL Transport user-plane server connection IPv6
         address";
    }
    leaf nal-transport-up-src-loop-back-if-name {
      type string {
        length "0..64";
      }
      description
        "NAL Transport user-plane server loopback
         interface-name";
    }
    leaf nal-transport-up-source-gtpu-port {
      type uint32;
      description
        "NAL Transport user-plane server connection GTPU
         port-number";
    }
    leaf nal-transport-up-source-pfcp-port {
      type uint32;
      description
        "NAL Transport user-plane server connection PFCP
         port-number";
    }
    leaf nal-transport-up-source-vrf-name {
      type string {
        length "0..33";
      }
      description
        "NAL Transport user-plane server connection
         VRF-Name";
    }
    leaf nal-transport-control-plane-primary-srv-addr-family {
      type uint8;
      description
        "NAL transport control-plane primary-server
         connection address-family";
    }
    leaf nal-transport-cp-primary-ipv4-address {
      type inet:ipv4-address;
      description
        "NAL Transport C-plane primary-server connection
         IPv4 address";
    }
    leaf nal-transport-cp-primary-ipv6-address {
      type inet:ipv6-address;
      description
        "NAL Transport C-plane primary-server connection
         IPv6 address";
    }
    leaf nal-transport-cp-server-gtpu-port {
      type uint32;
      description
        "NAL Transport C-plane server's GTPU port-number";
    }
    leaf nal-transport-cp-server-pfcp-port {
      type uint32;
      description
        "NAL Transport C-plane server's PFCP port-number";
    }
    leaf retry-count {
      type uint16;
      description
        "CP association request retry count";
    }
  }

  grouping NAL-MAIN-EDM-PROCESS-READINESS {
    description
      "Process readiness data";
    leaf resync-pending-flags {
      type uint32;
      description
        "Resync operations pending for NAL process";
    }
    leaf sir-ready {
      type boolean;
      description
        "Status of SIR readiness";
    }
  }

  grouping NAL-MAIN-EDM-PARENT-INTF-INITIATOR-DATA {
    description
      "NAL MAIN EDM PARENT INTF INITIATOR DATA";
    leaf is-configured {
      type boolean;
      description
        "Ture if the initiator is configred";
    }
  }

  grouping NAL-MAIN-EDM-PARENT-INTF-INITIATORS {
    description
      "Initiator protocol details";
    container intiator-type {
      description
        "DHCP information";
      uses NAL-MAIN-EDM-PARENT-INTF-INITIATOR-DATA;
    }
  }

  grouping NAL-MAIN-EDM-PARENT-INTF-DATA {
    description
      "Parent interface data";
    container initiators {
      description
        "Configurational state-statistics for each
         initiating protocol enabled on this parent
         interface";
      uses NAL-MAIN-EDM-PARENT-INTF-INITIATORS;
    }
    leaf parent-interface {
      type xr:Interface-name;
      description
        "Ifhandle of parent interface";
    }
    leaf interface-creation-time {
      type string;
      description
        "Interface creation time in Month Date HH:MM:SS
         format";
    }
    leaf age {
      type string;
      description
        "Age in HH:MM:SS format";
    }
    leaf parent-intf-flags {
      type uint32;
      description
        "Access Interface flags";
    }
    leaf nal-ether-encap {
      type yang:hex-string;
      description
        "Ether Encap Attribute";
    }
    leaf effective-bandwidth {
      type uint32;
      description
        "Effective Bandwidth";
    }
    leaf max-bandwidth {
      type uint32;
      description
        "Maximum Bandwidth";
    }
    leaf link-local {
      type inet:ipv6-address;
      description
        "link local address";
    }
  }

  grouping NAL-MAIN-EDM-SPA-RT-PROV-HIST-DATA {
    description
      "Route provision request response history";
    container request-response-timestamp {
      description
        "Timestamp of request or response";
      uses NAL-TIMESPEC;
    }
    leaf type {
      type Nal-main-edm-spa-rt-hist;
      description
        "Type of route history data";
    }
    list data {
      description
        "Request or Response";
      leaf entry {
        type uint8;
        description
          "Request or Response";
      }
    }
  }

  grouping NAL-MAIN-EDM-CHUNK-DATA {
    description
      "NAL MAIN EDM CHUNK DATA";
    leaf chunk-name {
      type string;
      description
        "Chunk Name";
    }
    leaf chunk-id {
      type uint32;
      description
        "Chunk Id";
    }
    leaf chunk-total-alloc {
      type uint32;
      description
        "Total number of chunk malloc done";
    }
    leaf chunk-total-free {
      type uint32;
      description
        "Total number of chunk free done";
    }
    leaf chunk-in-use {
      type uint32;
      description
        "total number of chunk blocks in use";
    }
  }

  grouping NAL-MAIN-EDM-CHUNK-STATS {
    description
      "NAL MAIN EDM CHUNK STATS";
    list chunk-stat {
      description
        "Chunk Memory statistics";
      uses NAL-MAIN-EDM-CHUNK-DATA;
    }
  }

  grouping NAL-SUBSCRIBER-DISCONNECT-HISTORY-DATA {
    description
      "Subscriber disconnect history bag";
    container fail-data {
      description
        "failed data";
      uses NAL-LAST-FAILED-DATA;
    }
    container session-data {
      description
        "subscriber session data info";
      uses NAL-SUBSCRIBER-SESSION-INFO;
    }
    leaf disc-cause {
      type uint32;
      description
        "Disconnect code";
    }
    list event-history {
      description
        "subscriber event history";
      uses NAL-SUB-DISC-HISTORY-EVT-DATA;
    }
  }

  grouping EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    list evt-data {
      description
        "Optional data";
      leaf entry {
        type uint32;
        description
          "Optional data";
      }
    }
  }

  grouping EVT-HIST-INFO {
    description
      "Per object event history";
    leaf evt-class-name {
      type string;
      description
        "Class name string";
    }
    list evt-entry {
      description
        "Array of event entries";
      uses EVT-HIST-ENTRY;
    }
  }

  grouping NAL-MAIN-EDM-EVENTS {
    description
      "NAL Main process init information";
    container event-history {
      description
        "Main process boot up events";
      uses EVT-HIST-INFO;
    }
    container im-event-history {
      description
        "IM module events";
      uses EVT-HIST-INFO;
    }
    container svm-event-history {
      description
        "SVM module events";
      uses EVT-HIST-INFO;
    }
    container rib-event-history {
      description
        "RIB module events";
      uses EVT-HIST-INFO;
    }
    container cp-event-history {
      description
        "CP module events";
      uses EVT-HIST-INFO;
    }
    container config-event-history {
      description
        "Config module events";
      uses EVT-HIST-INFO;
    }
  }

  grouping NAL-SUBSCRIBER-AFI-SUMMARY {
    description
      "Subscriber afi summary data";
    leaf none {
      type uint32;
      description
        "No afi";
    }
    leaf ipv4 {
      type uint32;
      description
        "IPv4 count";
    }
    leaf ipv6 {
      type uint32;
      description
        "IPv6 count";
    }
    leaf dual {
      type uint32;
      description
        "Dual count";
    }
    leaf total {
      type uint32;
      description
        "Total";
    }
  }

  grouping NAL-SUBSCRIBER-STATE-SUMMARY {
    description
      "Subscriber state summary data";
    leaf initializing {
      type uint32;
      description
        "Initializing";
    }
    leaf connecting {
      type uint32;
      description
        "Connecting";
    }
    leaf connected {
      type uint32;
      description
        "Connected";
    }
    leaf activated {
      type uint32;
      description
        "Activated";
    }
    leaf idle {
      type uint32;
      description
        "Idle";
    }
    leaf disconnecting {
      type uint32;
      description
        "Disconnecting";
    }
    leaf total {
      type uint32;
      description
        "Total";
    }
  }

  grouping NAL-SUBSCRIBER-SUMMARY {
    description
      "Subscriber summary data";
    container ipoe-state-summary {
      description
        "IPoE State Summary";
      uses NAL-SUBSCRIBER-STATE-SUMMARY;
    }
    container pppoe-state-summary {
      description
        "PPPoE State Summary";
      uses NAL-SUBSCRIBER-STATE-SUMMARY;
    }
    container ipoe-afi-summary {
      description
        "IPoE AFI Summary";
      uses NAL-SUBSCRIBER-AFI-SUMMARY;
    }
    container pppoe-afi-summary {
      description
        "PPPoE AFI Summary";
      uses NAL-SUBSCRIBER-AFI-SUMMARY;
    }
  }

  grouping NAL-SUBSCRIBER-DISCONNECT-HISTORY-UNIQUE-DATA {
    description
      "Subscriber unique disconnect history Bag";
    leaf disconnect-unique-session-count {
      type uint32;
      description
        "Number of sessions disconnected with this error
         code";
    }
    leaf disconnect-errorcode {
      type uint32;
      description
        "error code";
    }
    leaf sub-if-name {
      type string {
        length "0..64";
      }
      description
        "Interface Name";
    }
    leaf sub-disc-time {
      type uint32;
      description
        "Subscriber Disconnect Time ";
    }
    leaf disc-reason {
      type string {
        length "0..64";
      }
      description
        "Disconnect reason";
    }
  }

  grouping NAL-SERVICE-PROFILE-DATA {
    description
      "NAL service profile information";
    leaf service-name {
      type string {
        length "0..65";
      }
      description
        "Name of the service";
    }
    leaf service-id {
      type uint32;
      description
        "Service id assigned by SUBDB";
    }
    leaf use-count {
      type uint32;
      description
        "Number of subscribers using this profile";
    }
    leaf state {
      type Svm-service-state;
      description
        "State of the service";
    }
    leaf fail-err {
      type uint32;
      description
        "Installation failure rc";
    }
    leaf stale-timer-remaining {
      type uint32;
      description
        "stale timer remaining";
    }
    leaf assoc-in-progress {
      type uint32;
      description
        "No of subscribers need to use this profile";
    }
    list wait-upi-dqueue {
      description
        "List of UPIDs waiting for this service";
      leaf entry {
        type uint32;
        description
          "List of UPIDs waiting for this service";
      }
    }
  }

  grouping IPSUB-BASE-INIT {
    description
      "ipsub base init data";
    leaf type {
      type uint8;
      description
        "Init data type";
    }
    leaf version {
      type uint8;
      description
        "Init data version";
    }
    leaf length {
      type uint16;
      description
        "Init data length";
    }
  }

  grouping IPSUB-INTF-INIT-TYPE {
    description
      "Subscriber intf init data";
    container base {
      description
        "base";
      uses IPSUB-BASE-INIT;
    }
    leaf subscriber-mac {
      type yang:mac-address;
      description
        "MAC address";
    }
    leaf vlan-tag-count {
      type uint16;
      description
        "Vlan tag count";
    }
    leaf vrf-table-id {
      type uint32;
      description
        "Vrf table id ";
    }
    leaf v6-vrf-table-id {
      type uint32;
      description
        "Ipv6 Vrf table id ";
    }
    leaf up-link-gre-key {
      type uint32;
      description
        "Up link gre key";
    }
    leaf down-link-gre-key {
      type uint32;
      description
        "Down link gre key";
    }
    leaf subscriber-gw-mac {
      type yang:mac-address;
      description
        "Gateway MAC address";
    }
    leaf sub-attr-bits {
      type uint8;
      description
        "Subscriber attr bits";
    }
    leaf sub-info-bits {
      type uint8;
      description
        "Subscriber info bits";
    }
    leaf subscriber-ipv4 {
      type uint32;
      description
        "Subscriber IPv4";
    }
    leaf nexthop-ipv4 {
      type uint32;
      description
        "next hop  IPv4 address";
    }
    leaf subscriber-ipv6 {
      type inet:ipv6-address;
      description
        "Subscriber Ipv6 address";
    }
    leaf subscriber-ipv6-prefix {
      type inet:ipv6-address;
      description
        "Subscriber Ipv6 address";
    }
    leaf nexthop-ipv6 {
      type inet:ipv6-address;
      description
        "Nexthop Ipv6 address";
    }
    leaf v6-len {
      type uint8;
      description
        "V6 len";
    }
    leaf v6-prefix-len {
      type uint8;
      description
        "V6 prefix len";
    }
    leaf template-ifh {
      type uint32;
      description
        "Template interface handle";
    }
    leaf ipv4-mtu {
      type uint16;
      description
        "Ipv4 MTU";
    }
    leaf ipv6-mtu {
      type uint16;
      description
        "Ipv6 MTU";
    }
    leaf odns-deviceid-higher {
      type uint32;
      description
        "ODNS device id highter";
    }
    leaf odns-deviceid-lower {
      type uint32;
      description
        "ODNS device id Lower";
    }
    list vlan-stack {
      max-elements 2;
      description
        "vlan stack type";
      uses DOT1Q-TAG-DATA-TYPE;
    }
  }

  grouping NAL-TRANS-CONTEXT-DATA {
    description
      "Nal transaction context";
    leaf state {
      type Nal-trans-state;
      description
        "Subscriber transactio state";
    }
    leaf client-type {
      type Nal-trans-client-data;
      description
        "Client type indicate who is triggert this
         transction";
    }
    leaf trans-id {
      type uint32;
      description
        "Transaction ID";
    }
    leaf disconnect-ack {
      type uint32;
      description
        "Disconnect Ack";
    }
    leaf module-err {
      type uint32;
      description
        "Error generated by sub module";
    }
    leaf module-interaction-mask {
      type uint64;
      description
        "Flag to indicate which sub-module interactions
         are in progress";
    }
    leaf rollback-module-mask {
      type uint64;
      description
        "Flag to indicate which sub-module rollback needs
         to be invoked";
    }
    leaf pending-cb-bitmask {
      type uint64;
      description
        "Flag indicating pending callbacks for this
         transaction";
    }
  }

  grouping NAL-TRANS-SUB-CONTEXT-DATA {
    description
      "Subscriber transaction context";
    container trans-context {
      description
        "trans context";
      uses NAL-TRANS-CONTEXT-DATA;
    }
  }

  grouping NAL-IPSUB-INFLIGHT-DATA {
    description
      "Nal ipsub inflight data";
    leaf opearation {
      type Nal-intf-oper;
      description
        "Operation in progress";
    }
    leaf flags {
      type uint64;
      description
        "Flags to represent pending activities";
    }
    leaf fail-rc {
      type uint32;
      description
        "Backup of update error, internal rollback in
         progresss";
    }
  }

  grouping SVM-INFLIGHT-DATA {
    description
      "SVM inflight data";
    leaf service-name {
      type string {
        length "0..65";
      }
      description
        "Name of the service";
    }
    leaf service-id {
      type uint32;
      description
        "Service id assigned by SUBDB";
    }
    leaf operation {
      type Nal-spa-oper;
      description
        "Operation to be performed";
    }
    leaf service-flags {
      type uint32;
      description
        "Service flags";
    }
    leaf params-list {
      type yang:hex-string;
      description
        "Attribute list of service params";
    }
    leaf feature-id {
      type uint32;
      description
        "Feature ID";
    }
  }

  grouping NAL-SVM-INFLIGHT-DATA {
    description
      "Nal SVM inflight data";
    leaf opearation {
      type Svm-sub-oper;
      description
        "Operation in progress";
    }
    leaf state {
      type Svn-sub-state;
      description
        "State of the subscriber SVM data";
    }
    leaf fail-rc {
      type uint32;
      description
        "Fail rc";
    }
    leaf up-list {
      type yang:hex-string;
      description
        "User profile attribute list";
    }
    leaf remove-list {
      type yang:hex-string;
      description
        "User profile attribute remove list";
    }
    leaf service-index {
      type uint32;
      description
        "Service that is currently under process";
    }
    leaf subdb-pd-req-id {
      type uint32;
      description
        "SUBDB produce done req id";
    }
    leaf reconcile-state {
      type Svm-reconcile-state;
      description
        "Reconcilitation state";
    }
    list service {
      description
        "Service list array";
      uses SVM-INFLIGHT-DATA;
    }
  }

  grouping DOT1Q-TAG-DATA-TYPE {
    description
      "dot1q tag type";
    leaf etype {
      type uint16;
      description
        "etype";
    }
    leaf ucv {
      type uint16;
      description
        "ucv";
    }
  }

  grouping NAL-SUB-INTF-DATA {
    description
      "subscriber interface info";
    leaf vlan-tag-count {
      type uint16;
      description
        "Vlan tag count";
    }
    leaf sub-attr-bits {
      type uint8;
      description
        "Subscriber attr bits";
    }
    leaf flags {
      type uint64;
      description
        "flags bits";
    }
    leaf vrf-id {
      type uint32;
      description
        "vrf ID";
    }
    leaf v4-table-id {
      type uint32;
      description
        "V4 table id";
    }
    leaf v6-table-id {
      type uint32;
      description
        "V6 table id";
    }
    list vlan-stack {
      max-elements 2;
      description
        "vlan stack type";
      uses DOT1Q-TAG-DATA-TYPE;
    }
  }

  grouping NAL-LAST-FAILED-DATA {
    description
      "NAL subscriber last failed transaction data";
    leaf data {
      type string {
        length "0..256";
      }
      description
        "Failed data";
    }
    leaf msg-txn-id {
      type uint32;
      description
        "Message Txn ID";
    }
    leaf sess-txn-id {
      type uint32;
      description
        "Session Txn ID";
    }
    leaf feature-mask {
      type uint32;
      description
        "Feature Mask";
    }
    leaf svm-state {
      type uint32;
      description
        "SVM state";
    }
    leaf ip-sub-flags {
      type uint64;
      description
        "IPSUB flags";
    }
    leaf pending-callback {
      type uint64;
      description
        "Pending Callback";
    }
    leaf failure-reason {
      type uint32;
      description
        "Failure Reason";
    }
    leaf failure-timestamp {
      type uint32;
      description
        "Failure Timestamp";
    }
  }

  grouping NAL-SUBSCRIBER-DEACTIVATED-SERVICE {
    description
      "NAL subscriber deactivated service information";
    leaf service-name {
      type string {
        length "0..65";
      }
      description
        "Name of the service";
    }
    leaf deactivation-time {
      type uint32;
      description
        "service deactivation Time";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
  }

  grouping NAL-SUBSCRIBER-SESSION-DATA-INTERNAL {
    description
      "Subscriber context data";
    container session-data {
      description
        "subscriber session data info";
      uses NAL-SUBSCRIBER-SESSION-INFO;
    }
    container sub-intf {
      description
        "sub intf";
      uses NAL-SUB-INTF-DATA;
    }
    container svm-inflight {
      description
        "svm inflight";
      uses NAL-SVM-INFLIGHT-DATA;
    }
    container ipsub-inflight {
      description
        "ipsub inflight";
      uses NAL-IPSUB-INFLIGHT-DATA;
    }
    container trans-sub-context {
      description
        "trans sub context";
      uses NAL-TRANS-SUB-CONTEXT-DATA;
    }
    container last-init-data {
      description
        "last init data";
      uses IPSUB-INTF-INIT-TYPE;
    }
    leaf subscriber-flags {
      type uint32;
      description
        "Subscriber flags";
    }
    leaf ha-flags {
      type uint32;
      description
        "Subscriber flags";
    }
    leaf last-transaction-result {
      type uint32;
      description
        "Last Transaction Result";
    }
    leaf hold-stats-error {
      type uint32;
      description
        "hold stats status";
    }
    leaf clear-stats-error {
      type uint32;
      description
        "clear stats status";
    }
    leaf packets-in {
      type uint32;
      description
        "No of packets In";
    }
    leaf packets-out {
      type uint32;
      description
        "No of packets Out";
    }
    leaf ipv4-packets-in {
      type uint32;
      description
        "No of IPv4 packets In";
    }
    leaf ipv4-packets-out {
      type uint32;
      description
        "No of IPv4 packets Out";
    }
    leaf ipv4-bytes-in {
      type uint32;
      description
        "IPv4 Bytes in";
    }
    leaf ipv4-bytes-out {
      type uint32;
      description
        "IPv4 Bytes out";
    }
    leaf ipv4-bytes-in-giga {
      type uint32;
      description
        "IPv4 Bytes in Giga";
    }
    leaf ipv4-bytes-out-giga {
      type uint32;
      description
        "IPv4 Bytes out in Giga";
    }
    leaf ipv6-packets-in {
      type uint32;
      description
        "No of IPv6 packets In";
    }
    leaf ipv6-packets-out {
      type uint32;
      description
        "No of IPv6 packets Out";
    }
    leaf ipv6-bytes-in {
      type uint32;
      description
        "IPv6 Bytes in";
    }
    leaf ipv6-bytes-out {
      type uint32;
      description
        "IPv6 Bytes out";
    }
    leaf ipv6-bytes-in-giga {
      type uint32;
      description
        "IPv6 Bytes in Giga";
    }
    leaf ipv6-bytes-out-giga {
      type uint32;
      description
        "IPv6 Bytes out in Giga";
    }
    leaf transaction-id {
      type uint32;
      description
        "Subscriber transaction id";
    }
    leaf loopback-name {
      type string {
        length "0..65";
      }
      description
        "Loopback Name";
    }
    leaf stale-feature-id-info {
      type uint32;
      description
        "subscriber stale feature id info";
    }
    leaf sus-dconnect-time {
      type uint32;
      description
        "Subscriber disconnect Time";
    }
    leaf obj-hdl {
      type uint64;
      description
        "objext handle";
    }
    leaf spi-oattched {
      type boolean;
      description
        "Has SPIO attached";
    }
    list deactivated-service {
      description
        "last deactivated services";
      uses NAL-SUBSCRIBER-DEACTIVATED-SERVICE;
    }
    list last-fail {
      description
        "last failed transaction data";
      uses NAL-LAST-FAILED-DATA;
    }
  }

  grouping NAL-OPER-FADB-RECORD-DATA {
    description
      "NAL OPER FADB RECORD DATA";
    leaf feature-id {
      type uint32;
      description
        "Subscriber Feature-Id";
    }
    leaf upid {
      type uint32;
      description
        "User-plane ID";
    }
    leaf service-id {
      type uint32;
      description
        "Subscriber Service-Id";
    }
    leaf interim-fail-count {
      type uint32;
      description
        "Interim Fail Count";
    }
    leaf stale-timestamp {
      type uint32;
      description
        "Stale timestamp";
    }
    leaf hold-rc {
      type uint32;
      description
        "Hold RC";
    }
    leaf interim-error {
      type uint32;
      description
        "Interim Error";
    }
  }

  grouping NAL-SUBSCRIBER-SESSION-DATA {
    description
      "NAL subscriber detail data information";
    container sub-info {
      description
        "subscriber session data info";
      uses NAL-SUBSCRIBER-SESSION-INFO;
    }
  }

  grouping NAL-TIMESPEC {
    description
      "Structure to replicate timespec";
    leaf tv-sec {
      type uint32;
      description
        "Time in sec";
    }
    leaf tv-nsec {
      type uint32;
      description
        "Time in nsec";
    }
  }

  grouping NAL-SUB-DISC-HISTORY-EVT-DATA {
    description
      "Sub disc history event history bag";
    container evt-time {
      description
        "Event time";
      uses NAL-TIMESPEC;
    }
    leaf evt-type {
      type uint8;
      description
        "Event type";
    }
    leaf event-history-index {
      type uint32;
      description
        "Event History Index";
    }
  }

  grouping NAL-SUB-ACTIVATED-SERVICE {
    description
      "NAL subscriber activated service information";
    leaf service-name {
      type string {
        length "0..65";
      }
      description
        "Name of the service";
    }
    leaf activation-time {
      type uint32;
      description
        "service deactivation Time";
    }
    leaf flags {
      type uint32;
      description
        "flags";
    }
    leaf feature-id {
      type uint32;
      description
        "Feature ID";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf final-time {
      type uint32;
      description
        "service final stats Time";
    }
  }

  grouping NAL-SUBSCRIBER-SESSION-INFO-BRIEF {
    description
      "NAL subscriber  information brief";
    leaf cp-id {
      type uint32;
      description
        "Control-plane ID";
    }
    leaf ifhandle {
      type xr:Interface-name;
      description
        "Subscriber Interface name";
    }
    leaf subscriber-fsm-state {
      type Oper-nal-db-subscriber-state;
      description
        "Nal Subscriber state";
    }
    leaf mac-address {
      type yang:mac-address;
      description
        "MAC address";
    }
    leaf vrf-name {
      type string {
        length "0..33";
      }
      description
        "Vrf Name";
    }
    leaf subscriber-ipv4-address {
      type inet:ipv4-address;
      description
        "IPv4 Address of the subscriber";
    }
    leaf framed-ipv4-addr {
      type inet:ipv4-address;
      description
        "framed ipv4 addr";
    }
    leaf framed-ipv4-prefix-len {
      type uint8;
      description
        "framed ipv4 prefix len";
    }
    leaf ipv6-iana-address {
      type inet:ipv6-address;
      description
        "ipv6 iana address";
    }
    leaf ipv6-iapd-address {
      type inet:ipv6-address;
      description
        "ipv6  iapd address";
    }
    leaf ipv6-iapd-prefix {
      type uint8;
      description
        "ipv6  iapd prefix";
    }
    leaf framed-ipv6-addr {
      type inet:ipv6-address;
      description
        "framed ipv6 addr";
    }
    leaf framed-ipv6-prefix-len {
      type uint8;
      description
        "framed ipv6 prefix len";
    }
  }

  grouping NAL-SUBSCRIBER-SESSION-INFO {
    description
      "NAL subscriber  information";
    container session-brief {
      description
        "session brief";
      uses NAL-SUBSCRIBER-SESSION-INFO-BRIEF;
    }
    leaf up-id {
      type uint32;
      description
        "User-plane ID";
    }
    leaf pppoe-session-id {
      type uint16;
      description
        "PPPoE sesison ID";
    }
    leaf retry-count {
      type uint32;
      description
        "Retry count";
    }
    leaf local-magic-number {
      type uint32;
      description
        "Local magic number";
    }
    leaf peer-magic-number {
      type uint32;
      description
        "Peer magic number";
    }
    leaf keep-alive-interval {
      type uint32;
      description
        "Keep alive interval";
    }
    leaf total-ka-req-sent {
      type uint32;
      description
        "Total KA Req Sent";
    }
    leaf total-ka-resp-recv {
      type uint32;
      description
        "Total KA Resp Recv";
    }
    leaf total-ka-req-recv {
      type uint32;
      description
        "Total KA Req Recv";
    }
    leaf total-ka-resp-sent {
      type uint32;
      description
        "Total KA Resp Sent";
    }
    leaf mtu {
      type uint32;
      description
        "Max transfer unit";
    }
    leaf is-encap-string-ready {
      type boolean;
      description
        "Flag whether encap String is ready or not";
    }
    leaf ka-echo-request-counter {
      type uint32;
      description
        "Keepalive  req sent but resp not received";
    }
    leaf lcp-identity {
      type uint8;
      description
        "Identification for KA echo req";
    }
    leaf pppflags {
      type uint32;
      description
        "PPP flags";
    }
    leaf subscriber-type {
      type Oper-nal-db-subscriber;
      description
        "Nal Subacriber type";
    }
    leaf parent-ifhandle {
      type xr:Interface-name;
      description
        "Parent interface";
    }
    leaf parent-interface {
      type string {
        length "0..64";
      }
      description
        "Parent interface";
    }
    leaf subscriber-interface {
      type string {
        length "0..64";
      }
      description
        "Subscriber interface";
    }
    leaf inner-vlan {
      type uint32;
      description
        "Inner Vlan";
    }
    leaf outer-vlan {
      type uint32;
      description
        "Outer Vlan";
    }
    leaf cpe-link-local-address {
      type inet:ipv6-address;
      description
        "CPE link local address";
    }
    leaf framed-ipv6-next-hop {
      type inet:ipv6-address;
      description
        "framed ipv6 next hop";
    }
    leaf framed-ipv6-tag {
      type uint32;
      description
        "framed ipv6 tag";
    }
    leaf framed-ipv4-next-hop {
      type inet:ipv4-address;
      description
        "framed ipv4 next hop";
    }
    leaf framed-ipv4-tag {
      type uint32;
      description
        "framed ipv4 tag";
    }
    leaf feature-id-info {
      type uint32;
      description
        "Subscriber feature id info";
    }
    leaf subscriber-flags {
      type uint32;
      description
        "Subscriber flags";
    }
    leaf interim-interval {
      type uint32;
      description
        "Interim Interval";
    }
    leaf last-interim-time-stamp {
      type uint32;
      description
        "Last Interim Time Stamp";
    }
    leaf interim-fail-count {
      type uint32;
      description
        "Interim Fail Count";
    }
    leaf interim-error {
      type uint32;
      description
        "Interim Error";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf subscriber-create-time {
      type uint32;
      description
        "Subscriber Create Time";
    }
    leaf subscriber-ipv4-up-time {
      type uint32;
      description
        "Subscriber IPv4 Up Time";
    }
    leaf subscriber-ipv6-up-time {
      type uint32;
      description
        "Subscriber IPv6 Up Time";
    }
    leaf subscriber-ipv4-down-time {
      type uint32;
      description
        "Subscriber IPv4 Down Time";
    }
    leaf subscriber-ipv6-down-time {
      type uint32;
      description
        "Subscriber IPv6 Down Time";
    }
    leaf subscriber-af-down-reason {
      type uint32;
      description
        "Subscriber AF Down Reason";
    }
    leaf afup-flags {
      type uint32;
      description
        "AF ipv4/ipv6 up falgs";
    }
    leaf ip-sub-flags {
      type uint64;
      description
        "IPSUB  flags";
    }
    leaf sub-disc-time {
      type uint32;
      description
        "Subscriber Disconnect Time ";
    }
    list active-service {
      description
        "activated services";
      uses NAL-SUB-ACTIVATED-SERVICE;
    }
  }

  grouping NAL-SUBSCRIBER-DISCONNECT-HISTORY-UNIQUE-INTERNAL-DATA {
    description
      "Subscriber unique disconnect history Bag";
    container session-data {
      description
        "subscriber session data info";
      uses NAL-SUBSCRIBER-SESSION-INFO;
    }
    list event-history {
      description
        "subscriber event history";
      uses NAL-SUB-DISC-HISTORY-EVT-DATA;
    }
  }

  grouping NAL-SUBSCRIBER-DISCONNECT-HISTORY-UNIQUE-DETAIL-DATA {
    description
      "Subscriber unique disconnect history detail Bag";
    leaf disconnect-unique-session-count {
      type uint32;
      description
        "Number of sessions disconnected with this error
         code";
    }
    leaf disc-reason {
      type string {
        length "0..64";
      }
      description
        "Disconnect reason";
    }
    leaf disconnect-errorcode {
      type uint32;
      description
        "error code";
    }
    list unique-detail {
      max-elements 3;
      description
        "unique detail session info for last three
         disconnected sessions";
      uses NAL-SUBSCRIBER-DISCONNECT-HISTORY-UNIQUE-INTERNAL-DATA;
    }
  }
}

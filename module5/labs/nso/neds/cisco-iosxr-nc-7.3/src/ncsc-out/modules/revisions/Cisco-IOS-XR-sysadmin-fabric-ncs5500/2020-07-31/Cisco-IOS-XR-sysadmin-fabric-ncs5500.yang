module Cisco-IOS-XR-sysadmin-fabric-ncs5500 {
  // Generated by yanger -t ncs
  tailf:mount-id "cisco-iosxr-nc-7.3:cisco-iosxr-nc-7.3";
  tailf:ncs-device-type "netconf";

  namespace "http://www.cisco.com/ns/yang/Cisco-IOS-XR-sysadmin-fabric-ncs5500";
  prefix fabric;

  import Cisco-IOS-XR-sysadmin-fabric-mgr-fgid-ncs5500 {
    prefix fabric-fgid;
  }
  import Cisco-IOS-XR-sysadmin-fabric-mgr-fsdb-server-ncs5500 {
    prefix fabric-fsdb;
  }
  import Cisco-IOS-XR-sysadmin-fabric-mgr-fsdb-aggregator-ncs5500 {
    prefix fabric-fsdb-aggr;
  }
  import Cisco-IOS-XR-sysadmin-fabric-driver-sfe-ncs5500 {
    prefix fabric-sfe;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2020-07-31 {
    description
      "Importing platform specific yang as required";
    semver:module-version "1.2.0";
  }
  revision 2019-07-01 {
    description
      "Modified to import NCS5500 platform specific yang file";
    semver:module-version "1.1.0";
  }
  revision 2019-04-15 {
    description
      "Establish semantic version baseline.";
    semver:module-version "1.0.0";
  }
  revision 2017-05-01 {
    description
      "Namespace change to comply with Cisco guidelines on namespace";
  }

  grouping ncs_template_fabric_action_cmds {
    container fabric_action {
      container fabric {
        description
          "Fabric resource commands";
        uses fabric-fsdb-aggr:ncs_template_fsdb_aggr_ppu;
      }
    }
  }

  grouping ncs_template_fabric_clear {
    container fabric {
      description
        "Fabric resource commands";
      uses fabric-fsdb-aggr:ncs_template_fsdb_aggr_clear;
    }
  }

  grouping ncs_template_fabric {
    container fabric {
      description
        "Fabric resource commands";
      container fabric {
        description
          "Fabric configuration";
        container fsdbagg {
          uses fabric-fsdb-aggr:ncs_template_fsdb_agg_conf_plane;
        }
        uses fabric-fgid:ncs_template_fgid_conf_resource;
      }
      // NCS drop config false container oper
    }
    // NCS drop config false container sfe_oper
  }

  grouping ncs_rpc_notif_fabric_action_cmds {
    container fabric_action {
      container fabric {
        description
          "Fabric resource commands";
        uses fabric-fsdb-aggr:ncs_rpc_notif_fsdb_aggr_ppu;
      }
    }
  }

  grouping ncs_rpc_notif_fabric_clear {
    container fabric {
      description
        "Fabric resource commands";
      uses fabric-fsdb-aggr:ncs_rpc_notif_fsdb_aggr_clear;
    }
  }

  grouping ncs_rpc_notif_fabric {
    container fabric {
      description
        "Fabric resource commands";
      container fabric {
        description
          "Fabric configuration";
        container fsdbagg {
          uses fabric-fsdb-aggr:ncs_rpc_notif_fsdb_agg_conf_plane;
        }
        uses fabric-fgid:ncs_rpc_notif_fgid_conf_resource;
      }
      container oper {
        config false;
        uses fabric-fgid:ncs_rpc_notif_fgid;
        uses fabric-fsdb-aggr:ncs_rpc_notif_fsdb_aggr;
        uses fabric-fsdb:ncs_rpc_notif_fsdb_svr;
      }
    }
    container sfe_oper {
      config false;
      uses fabric-sfe:ncs_rpc_notif_sfe;
    }
  }

  grouping live_ncs_fabric_action_cmds {
    container fabric_action {
      container fabric {
        description
          "Fabric resource commands";
        uses fabric-fsdb-aggr:live_ncs_fsdb_aggr_ppu;
      }
    }
  }

  grouping live_ncs_fabric_clear {
    container fabric {
      description
        "Fabric resource commands";
      uses fabric-fsdb-aggr:live_ncs_fsdb_aggr_clear;
    }
  }

  grouping live_ncs_fabric {
    container fabric {
      description
        "Fabric resource commands";
      container fabric {
        description
          "Fabric configuration";
        container fsdbagg {
          uses fabric-fsdb-aggr:live_ncs_fsdb_agg_conf_plane;
        }
        uses fabric-fgid:live_ncs_fgid_conf_resource;
      }
      container oper {
        uses fabric-fgid:live_ncs_fgid;
        uses fabric-fsdb-aggr:live_ncs_fsdb_aggr;
        uses fabric-fsdb:live_ncs_fsdb_svr;
      }
    }
    container sfe_oper {
      uses fabric-sfe:live_ncs_sfe;
    }
  }

  grouping fabric_action_cmds {
    container fabric_action {
      container fabric {
        description
          "Fabric resource commands";
        uses fabric-fsdb-aggr:fsdb_aggr_ppu;
      }
    }
  }

  grouping fabric_clear {
    container fabric {
      description
        "Fabric resource commands";
      uses fabric-fsdb-aggr:fsdb_aggr_clear;
    }
  }

  grouping fabric {
    container fabric {
      description
        "Fabric resource commands";
      container fabric {
        description
          "Fabric configuration";
        container fsdbagg {
          uses fabric-fsdb-aggr:fsdb_agg_conf_plane;
        }
        uses fabric-fgid:fgid_conf_resource;
      }
      // NCS drop config false container oper
    }
    // NCS drop config false container sfe_oper
  }
}

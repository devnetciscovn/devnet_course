module Cisco-IOS-XR-healthcheck-oper {
  // Generated by yanger -t ncs
  tailf:mount-id "cisco-iosxr-nc-7.3:cisco-iosxr-nc-7.3";
  tailf:ncs-device-type "netconf";

  namespace "http://cisco.com/ns/yang/Cisco-IOS-XR-healthcheck-oper";
  prefix healthcheck-oper;

  import Cisco-IOS-XR-types {
    prefix xr;
  }
  import cisco-semver {
    prefix semver;
  }
  include Cisco-IOS-XR-healthcheck-oper-sub2 {
    revision-date 2020-09-18;
  }
  include Cisco-IOS-XR-healthcheck-oper-sub1 {
    revision-date 2020-09-18;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR healthcheck package operational data.

     This module contains definitions
     for the following management objects:
       health-check: Healthcheck Operational data space

     Copyright (c) 2013-2020 by Cisco Systems, Inc.
     All rights reserved.";

  revision 2020-09-18 {
    description
      "Fabric health metric updated.";
    semver:module-version "1.0.0";
  }
  revision 2019-04-05 {
    description
      "Establish semantic version baseline.";
  }
  revision 2015-11-09 {
    description
      "IOS XR 6.0 revision.";
  }

  augment "/ncs:devices/ncs:device/ncs:config" {
    // NCS drop config false container 'health-check'
  }
  augment "/ncs:devices/ncs:device/ncs:live-status" {
    container health-check {
      tailf:ncs-device-type "netconf";
      tailf:display-when "not(../../ncs:module) or ../../ncs:module[ncs:name='Cisco-IOS-XR-healthcheck-oper'] or (../../ncs:live-status-protocol[not(ncs:capability)]) or (../../ncs:live-status-protocol/ncs:capability/ncs:module[.='Cisco-IOS-XR-healthcheck-oper'])";
      description
        "Healthcheck Operational data space";
      container metric-info {
        description
          "Metric Info";
        container fpd {
          description
            "FPD Metric";
          uses live_ncs_HCMGR-FPD-METRIC-DATA;
        }
        container redundancy {
          description
            "REDUNDANCY Metric";
          uses live_ncs_HCMGR-REDUNDANCY-METRIC-DATA;
        }
        container fabric-health {
          description
            "FABRIC-HEALTH Metric";
          uses live_ncs_HCMGR-FABRIC-HEALTH-METRIC-DATA;
        }
        container platform {
          description
            "PLATFORM Metric";
          uses live_ncs_HCMGR-PLATFORM-METRIC-DATA;
        }
        container interface-counters {
          description
            "Interface Counters Metric";
          container interface-counters-details {
            description
              "Interface Name";
            list interface-counters-detail {
              key "intf-name";
              description
                "Interface Name";
              container interface-counters-detail-data {
                description
                  "Interface Counters Metric Detail";
                uses live_ncs_HCMGR-INTF-COUNTERS-METRIC-DETAIL-DATA;
              }
              leaf intf-name {
                type xr:live_ncs_Interface-name;
                description
                  "Interface Name";
              }
            }
          }
          container interface-counters-info {
            description
              "Interface Counters Metric Info";
            uses live_ncs_HCMGR-INTF-COUNTERS-METRIC-DATA;
          }
        }
        container asic-errors {
          description
            "Asic Errors Metric";
          container asic-errors-details {
            description
              "Node Name";
            list asic-errors-detail {
              key "node-name";
              description
                "Node Name";
              container asic-errors-detail-data {
                description
                  "Asic-Errors Metric Detail";
                uses live_ncs_HCMGR-ASIC-ERRORS-METRIC-DETAIL-DATA;
              }
              leaf node-name {
                type xr:live_ncs_Cisco-ios-xr-string;
                description
                  "Node Name";
              }
            }
          }
          container asic-errors-info {
            description
              "Asic-Errors Metric Info";
            uses live_ncs_HCMGR-ASIC-ERRORS-METRIC-DATA;
          }
        }
        container free-memory {
          description
            "Free Memory Metric";
          uses live_ncs_HCMGR-FREE-MEM-METRIC-DATA;
        }
        container custom-metric {
          description
            "Custom Metric Oper Data";
          container custom-metric-infos {
            description
              "name";
            list custom-metric-info {
              key "metric-name";
              description
                "Metric Name";
              container custom-metric-info-data {
                description
                  "Custom-Metric Oper Data";
                uses live_ncs_HCMGR-CUSTOM-METRIC-DATA;
              }
              leaf metric-name {
                type xr:live_ncs_Cisco-ios-xr-string;
                description
                  "Metric Name";
              }
            }
          }
        }
        container fabric-stats {
          description
            "Asic Errors Metric";
          container fabric-stats-info {
            description
              "Fabric-Stats Metric Info";
            uses live_ncs_HCMGR-FABRIC-STATS-METRIC-DATA;
          }
          container fabric-stats-details {
            description
              "Plane Id";
            list fabric-stats-detail {
              key "plane-id";
              description
                "Plane Id";
              container fabric-stats-detail-data {
                description
                  "Fabric-Stats Metric Detail";
                uses live_ncs_HCMGR-FABRIC-STATS-METRIC-DETAIL-DATA;
              }
              leaf plane-id {
                type uint32;
                description
                  "Plane Id";
              }
            }
          }
        }
        container filesystem {
          description
            "Filesystem Metric";
          uses live_ncs_HCMGR-FILESYSTEM-METRIC-DATA;
        }
        container shared-memory {
          description
            "Shared Memory Metric";
          uses live_ncs_HCMGR-SHARED-MEM-METRIC-DATA;
        }
        container cpu {
          description
            "CPU Metric";
          uses live_ncs_HCMGR-CPU-METRIC-DATA;
        }
      }
      container report-info {
        description
          "Report data bag";
        uses live_ncs_HCMGR-REPORT-DATA;
      }
      container status-info {
        description
          "Status data bag";
        uses live_ncs_HCMGR-STATUS-DATA;
      }
    }
  }
  augment "/ncs:devices/ncs:template/ncs:ned-id/ncs:config" {
    // NCS drop config false container 'health-check'
  }
}

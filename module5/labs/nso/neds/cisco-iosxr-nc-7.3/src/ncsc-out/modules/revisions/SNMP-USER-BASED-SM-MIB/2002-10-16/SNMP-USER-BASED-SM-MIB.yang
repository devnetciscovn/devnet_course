module SNMP-USER-BASED-SM-MIB {
  // Generated by yanger -t ncs
  tailf:mount-id "cisco-iosxr-nc-7.3:cisco-iosxr-nc-7.3";
  tailf:ncs-device-type "netconf";

  namespace "http://tail-f.com/ns/mibs/SNMP-USER-BASED-SM-MIB/200210160000Z";
  prefix SNMP_USER_BASED_SM_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }
  import tailf-ncs {
    prefix ncs;
  }

  revision 2002-10-16 {
    description
      "";
  }

  typedef ncs_template_KeyChange {
    type string;
  }

  typedef ncs_template_usmUserNameType {
    type string;
  }

  typedef ncs_template_usmUserPublicType {
    type string;
  }

  typedef ncs_rpc_notif_KeyChange {
    type tailf:hex-list {
      pattern '(((([0-9A-Fa-f]{2}):)*([0-9A-Fa-f]{2}))){0,1}';
    }
  }

  typedef ncs_rpc_notif_usmUserNameType {
    type string {
      length "1 .. 32";
    }
  }

  typedef ncs_rpc_notif_usmUserPublicType {
    type tailf:hex-list {
      pattern '(((([0-9A-Fa-f]{2}):){0,31}([0-9A-Fa-f]{2}))){0,1}';
      tailf:value-length "min .. 32";
    }
  }

  typedef live_ncs_KeyChange {
    type tailf:hex-list {
      pattern '(((([0-9A-Fa-f]{2}):)*([0-9A-Fa-f]{2}))){0,1}';
    }
  }

  typedef live_ncs_usmUserNameType {
    type string {
      length "1 .. 32";
    }
  }

  typedef live_ncs_usmUserPublicType {
    type tailf:hex-list {
      pattern '(((([0-9A-Fa-f]{2}):){0,31}([0-9A-Fa-f]{2}))){0,1}';
      tailf:value-length "min .. 32";
    }
  }

  typedef KeyChange {
    type tailf:hex-list {
      pattern '(((([0-9A-Fa-f]{2}):)*([0-9A-Fa-f]{2}))){0,1}';
    }
  }

  typedef usmUserNameType {
    type string {
      length "1 .. 32";
    }
  }

  typedef usmUserPublicType {
    type tailf:hex-list {
      pattern '(((([0-9A-Fa-f]{2}):){0,31}([0-9A-Fa-f]{2}))){0,1}';
      tailf:value-length "min .. 32";
    }
  }

  augment "/ncs:devices/ncs:device/ncs:config" {
    container SNMP-USER-BASED-SM-MIB {
      tailf:ncs-device-type "netconf";
      tailf:display-when "not(../../ncs:module) or ../../ncs:module[ncs:name='SNMP-USER-BASED-SM-MIB']";
      // NCS drop config false container usmStats
      container usmUserTable {
        list usmUserEntry {
          key "usmUserEngineID usmUserName";
          unique "usmUserEngineID usmUserSecurityName";
          leaf usmUserEngineID {
            type SNMP_FRAMEWORK_MIB:SnmpEngineID;
          }
          leaf usmUserName {
            type usmUserNameType;
          }
          leaf usmUserSecurityName {
            type SNMP_FRAMEWORK_MIB:SnmpAdminString;
            mandatory true;
          }
          leaf usmUserCloneFrom {
            type SNMPv2_TC:RowPointer;
          }
          leaf usmUserAuthProtocol {
            type SNMPv2_TC:AutonomousType;
            default "1.3.6.1.6.3.10.1.1.1";
          }
          leaf usmUserAuthKeyChange {
            type KeyChange;
          }
          leaf usmUserOwnAuthKeyChange {
            type KeyChange;
          }
          leaf usmUserPrivProtocol {
            type SNMPv2_TC:AutonomousType;
            default "1.3.6.1.6.3.10.1.2.1";
          }
          leaf usmUserPrivKeyChange {
            type KeyChange;
          }
          leaf usmUserOwnPrivKeyChange {
            type KeyChange;
          }
          leaf usmUserPublic {
            type usmUserPublicType;
          }
          leaf usmUserStorageType {
            type SNMPv2_TC:StorageType;
            default "nonVolatile";
          }
          leaf usmUserAuthKey {
            type KeyChange;
          }
          leaf usmUserPrivKey {
            type KeyChange;
          }
        }
      }
    }
  }
  augment "/ncs:devices/ncs:device/ncs:live-status" {
    container SNMP-USER-BASED-SM-MIB {
      tailf:ncs-device-type "netconf";
      tailf:display-when "not(../../ncs:module) or ../../ncs:module[ncs:name='SNMP-USER-BASED-SM-MIB'] or (../../ncs:live-status-protocol[not(ncs:capability)]) or (../../ncs:live-status-protocol/ncs:capability/ncs:module[.='SNMP-USER-BASED-SM-MIB'])";
      container usmStats {
        leaf usmStatsUnsupportedSecLevels {
          type yang:counter32;
        }
        leaf usmStatsNotInTimeWindows {
          type yang:counter32;
        }
        leaf usmStatsUnknownUserNames {
          type yang:counter32;
        }
        leaf usmStatsUnknownEngineIDs {
          type yang:counter32;
        }
        leaf usmStatsWrongDigests {
          type yang:counter32;
        }
        leaf usmStatsDecryptionErrors {
          type yang:counter32;
        }
      }
      container usmUserTable {
        list usmUserEntry {
          key "usmUserEngineID usmUserName";
          unique "usmUserEngineID usmUserSecurityName";
          leaf usmUserEngineID {
            type SNMP_FRAMEWORK_MIB:live_ncs_SnmpEngineID;
          }
          leaf usmUserName {
            type live_ncs_usmUserNameType;
          }
          leaf usmUserSecurityName {
            type SNMP_FRAMEWORK_MIB:live_ncs_SnmpAdminString;
            // NCS drop mandatory statement
          }
          leaf usmUserCloneFrom {
            type SNMPv2_TC:live_ncs_RowPointer;
          }
          leaf usmUserAuthProtocol {
            type SNMPv2_TC:live_ncs_AutonomousType;
            // NCS drop default statement
          }
          leaf usmUserAuthKeyChange {
            type live_ncs_KeyChange;
          }
          leaf usmUserOwnAuthKeyChange {
            type live_ncs_KeyChange;
          }
          leaf usmUserPrivProtocol {
            type SNMPv2_TC:live_ncs_AutonomousType;
            // NCS drop default statement
          }
          leaf usmUserPrivKeyChange {
            type live_ncs_KeyChange;
          }
          leaf usmUserOwnPrivKeyChange {
            type live_ncs_KeyChange;
          }
          leaf usmUserPublic {
            type live_ncs_usmUserPublicType;
          }
          leaf usmUserStorageType {
            type SNMPv2_TC:live_ncs_StorageType;
            // NCS drop default statement
          }
          leaf usmUserAuthKey {
            type live_ncs_KeyChange;
          }
          leaf usmUserPrivKey {
            type live_ncs_KeyChange;
          }
        }
      }
    }
  }
  augment "/ncs:devices/ncs:template/ncs:ned-id/ncs:config" {
    container SNMP-USER-BASED-SM-MIB {
      // NCS drop config false container usmStats
      container usmUserTable {
        list usmUserEntry {
          // NCS patched for predictable order
          ordered-by user;
          key "usmUserEngineID usmUserName";
          unique "usmUserEngineID usmUserSecurityName";
          leaf usmUserEngineID {
            type SNMP_FRAMEWORK_MIB:ncs_template_SnmpEngineID;
          }
          leaf usmUserName {
            type ncs_template_usmUserNameType;
          }
          leaf usmUserSecurityName {
            type SNMP_FRAMEWORK_MIB:ncs_template_SnmpAdminString;
            // NCS drop mandatory statement
          }
          leaf usmUserCloneFrom {
            type SNMPv2_TC:ncs_template_RowPointer;
          }
          leaf usmUserAuthProtocol {
            type SNMPv2_TC:ncs_template_AutonomousType;
            // NCS drop default statement
          }
          leaf usmUserAuthKeyChange {
            type ncs_template_KeyChange;
          }
          leaf usmUserOwnAuthKeyChange {
            type ncs_template_KeyChange;
          }
          leaf usmUserPrivProtocol {
            type SNMPv2_TC:ncs_template_AutonomousType;
            // NCS drop default statement
          }
          leaf usmUserPrivKeyChange {
            type ncs_template_KeyChange;
          }
          leaf usmUserOwnPrivKeyChange {
            type ncs_template_KeyChange;
          }
          leaf usmUserPublic {
            type ncs_template_usmUserPublicType;
          }
          leaf usmUserStorageType {
            type SNMPv2_TC:ncs_template_StorageType;
            // NCS drop default statement
          }
          leaf usmUserAuthKey {
            type ncs_template_KeyChange;
          }
          leaf usmUserPrivKey {
            type ncs_template_KeyChange;
          }
        }
      }
    }
  }
}

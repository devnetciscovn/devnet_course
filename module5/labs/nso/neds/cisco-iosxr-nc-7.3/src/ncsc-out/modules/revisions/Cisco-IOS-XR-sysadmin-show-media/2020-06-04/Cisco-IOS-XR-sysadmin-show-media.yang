module Cisco-IOS-XR-sysadmin-show-media {
  // Generated by yanger -t ncs
  tailf:mount-id "cisco-iosxr-nc-7.3:cisco-iosxr-nc-7.3";
  tailf:ncs-device-type "netconf";

  namespace "http://www.cisco.com/ns/yang/Cisco-IOS-XR-sysadmin-show-media";
  prefix mediasvrh;

  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin to
     report back memory utilization in sysadmin.

     Copyright (c) 2018-2020 by Cisco Systems, Inc.
     All rights reserved.";

  revision 2020-06-04 {
    description
      "Breaking output show_media_report into fields";
    semver:module-version "2.0.0";
  }
  revision 2020-04-08 {
    description
      "Suppressing raw output";
    semver:module-version "1.0.0";
  }
  revision 2019-04-15 {
    description
      "Establish semantic version baseline.";
    semver:module-version "1.0.0";
  }
  revision 2019-02-06 {
    description
      "Initial revision";
  }

  augment "/ncs:devices/ncs:device/ncs:config" {
    // NCS drop config false container 'ShowMedia'
  }
  augment "/ncs:devices/ncs:device/ncs:live-status" {
    container ShowMedia {
      tailf:ncs-device-type "netconf";
      tailf:display-when "not(../../ncs:module) or ../../ncs:module[ncs:name='Cisco-IOS-XR-sysadmin-show-media'] or (../../ncs:live-status-protocol[not(ncs:capability)]) or (../../ncs:live-status-protocol/ncs:capability/ncs:module[.='Cisco-IOS-XR-sysadmin-show-media'])";
      description
        "Show the memory usage in sysadmin";
      list all-locations {
        key "location";
        description
          "Media information for system";
        leaf location {
          type string;
          description
            "Media information for one node";
        }
        list partition {
          key "name";
          leaf name {
            type string;
            description
              "Media partition name";
          }
          leaf size {
            type string;
            description
              "Media partition size in T/G/M/K/B";
          }
          leaf used {
            type string;
            description
              "Media partition used space in T/G/M/K/B";
          }
          leaf percent {
            type string;
            description
              "Media partition used space percentage";
          }
          leaf avail {
            type string;
            description
              "Media partition available space in T/G/M/K/B";
          }
        }
      }
    }
  }
  augment "/ncs:devices/ncs:template/ncs:ned-id/ncs:config" {
    // NCS drop config false container 'ShowMedia'
  }
}

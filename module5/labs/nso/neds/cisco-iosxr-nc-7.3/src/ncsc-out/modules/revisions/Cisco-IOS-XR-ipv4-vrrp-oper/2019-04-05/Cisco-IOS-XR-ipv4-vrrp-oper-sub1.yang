submodule Cisco-IOS-XR-ipv4-vrrp-oper-sub1 {
  // Generated by yanger -t ncs
  tailf:mount-id "cisco-iosxr-nc-7.3:cisco-iosxr-nc-7.3";

  belongs-to Cisco-IOS-XR-ipv4-vrrp-oper {
    prefix Cisco-IOS-XR-ipv4-vrrp-oper;
  }

  import ietf-inet-types {
    prefix inet;
  }
  import ietf-yang-types {
    prefix yang;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv4-vrrp package operational data.

     Copyright (c) 2013-2019 by Cisco Systems, Inc.
     All rights reserved.";

  revision 2019-04-05 {
    description
      "Establish semantic version baseline.";
    semver:module-version "1.0.0";
  }
  revision 2018-12-12 {
    description
      "Moved router id to a range type.";
  }
  revision 2017-09-07 {
    description
      "Fixed type translation error.";
  }
  revision 2017-05-01 {
    description
      "Fixing backward compatibility error in module.";
  }
  revision 2016-12-16 {
    description
      "IOS XR 6.2.1 revision.";
  }
  revision 2015-11-09 {
    description
      "IOS XR 6.0 revision.";
  }

  typedef ncs_template_Vrrp-vmac-state {
    type string;
    description
      "Vrrp vmac state";
  }

  typedef ncs_template_Vrrp-state-change-reason {
    type string;
    description
      "Vrrp state change reason";
  }

  typedef ncs_template_Vrrp-bfd-session-state {
    type string;
    description
      "Vrrp bfd session state";
  }

  typedef ncs_template_Vrrp-prot-auth {
    type string;
    description
      "Vrrp prot auth";
  }

  typedef ncs_template_Vrrp-bag-protocol-state {
    type string;
    description
      "VRRP protocol state";
  }

  typedef ncs_template_Vrrp-vip-state {
    type string;
    description
      "Vrrp vip state";
  }

  typedef ncs_template_Vrrp-b-af {
    type string;
    description
      "Vrrp b af";
  }

  typedef ncs_template_Vrrp-version {
    type string;
    description
      "Vrrp version";
  }

  typedef ncs_rpc_notif_Vrrp-vmac-state {
    type enumeration {
      enum "stored" {
        value 0;
        description
          "VMAC stored locally";
      }
      enum "reserved" {
        value 1;
        description
          "VMAC reserved in mac table";
      }
      enum "active" {
        value 2;
        description
          "VMAC active in mac table";
      }
      enum "reserving" {
        value 3;
        description
          "VMAC not yet reserved in mac table";
      }
    }
    description
      "Vrrp vmac state";
  }

  typedef ncs_rpc_notif_Vrrp-state-change-reason {
    type enumeration {
      enum "state-change-bfd-down" {
        value 0;
        description
          "BFD session down";
      }
      enum "state-change-virtual-ip-configured" {
        value 1;
        description
          "Virtual IP configured";
      }
      enum "state-change-interface-ip" {
        value 2;
        description
          "Interface IP update";
      }
      enum "state-change-delay-timer" {
        value 3;
        description
          "Delay timer expired";
      }
      enum "state-change-startup" {
        value 4;
        description
          "Ready on startup";
      }
      enum "state-change-interface-up" {
        value 5;
        description
          "Interface Up update";
      }
      enum "state-change-interface-down" {
        value 6;
        description
          "Interface Down update";
      }
      enum "state-change-master-down-timer" {
        value 7;
        description
          "Master down timer expired";
      }
      enum "state-change-higher-priority-master" {
        value 8;
        description
          "Higher priority advert received";
      }
      enum "state-change-fhrp-admin" {
        value 9;
        description
          "FHRP Admin state change";
      }
      enum "state-change-mgo-parent" {
        value 10;
        description
          "Change of MGO parent session";
      }
      enum "state-change-chkpt-update" {
        value 11;
        description
          "Checkpoint update from Primary VRRP instance";
      }
      enum "state-change-issu-resync" {
        value 12;
        description
          "Resync following ISSU primary event";
      }
    }
    description
      "Vrrp state change reason";
  }

  typedef ncs_rpc_notif_Vrrp-bfd-session-state {
    type enumeration {
      enum "bfd-state-none" {
        value 0;
        description
          "None";
      }
      enum "bfd-state-inactive" {
        value 1;
        description
          "Inactive";
      }
      enum "bfd-state-up" {
        value 2;
        description
          "Up";
      }
      enum "bfd-state-down" {
        value 3;
        description
          "Down";
      }
    }
    description
      "Vrrp bfd session state";
  }

  typedef ncs_rpc_notif_Vrrp-prot-auth {
    type enumeration {
      enum "authentication-none" {
        value 0;
        description
          "Down";
      }
      enum "authentication-text" {
        value 1;
        description
          "Simple Text";
      }
      enum "authentication-ip" {
        value 2;
        description
          "IP header";
      }
    }
    description
      "Vrrp prot auth";
  }

  typedef ncs_rpc_notif_Vrrp-bag-protocol-state {
    type enumeration {
      enum "state-initial" {
        value 1;
        description
          "Initial";
      }
      enum "state-backup" {
        value 2;
        description
          "Backup";
      }
      enum "state-master" {
        value 3;
        description
          "Master";
      }
    }
    description
      "VRRP protocol state";
  }

  typedef ncs_rpc_notif_Vrrp-vip-state {
    type enumeration {
      enum "virtual-ip-state-down" {
        value 0;
        description
          "Down";
      }
      enum "virtual-ip-state-up" {
        value 1;
        description
          "Up";
      }
    }
    description
      "Vrrp vip state";
  }

  typedef ncs_rpc_notif_Vrrp-b-af {
    type enumeration {
      enum "address-family-ipv4" {
        description
          "IPv4 Address Family";
      }
      enum "address-family-ipv6" {
        description
          "IPv6 Address Family";
      }
      enum "vrrp-baf-count" {
        description
          "Number of Adddress Families";
      }
    }
    description
      "Vrrp b af";
  }

  typedef ncs_rpc_notif_Vrrp-version {
    type uint8;
    description
      "Vrrp version";
  }

  typedef live_ncs_Vrrp-vmac-state {
    type enumeration {
      enum "stored" {
        value 0;
        description
          "VMAC stored locally";
      }
      enum "reserved" {
        value 1;
        description
          "VMAC reserved in mac table";
      }
      enum "active" {
        value 2;
        description
          "VMAC active in mac table";
      }
      enum "reserving" {
        value 3;
        description
          "VMAC not yet reserved in mac table";
      }
    }
    description
      "Vrrp vmac state";
  }

  typedef live_ncs_Vrrp-state-change-reason {
    type enumeration {
      enum "state-change-bfd-down" {
        value 0;
        description
          "BFD session down";
      }
      enum "state-change-virtual-ip-configured" {
        value 1;
        description
          "Virtual IP configured";
      }
      enum "state-change-interface-ip" {
        value 2;
        description
          "Interface IP update";
      }
      enum "state-change-delay-timer" {
        value 3;
        description
          "Delay timer expired";
      }
      enum "state-change-startup" {
        value 4;
        description
          "Ready on startup";
      }
      enum "state-change-interface-up" {
        value 5;
        description
          "Interface Up update";
      }
      enum "state-change-interface-down" {
        value 6;
        description
          "Interface Down update";
      }
      enum "state-change-master-down-timer" {
        value 7;
        description
          "Master down timer expired";
      }
      enum "state-change-higher-priority-master" {
        value 8;
        description
          "Higher priority advert received";
      }
      enum "state-change-fhrp-admin" {
        value 9;
        description
          "FHRP Admin state change";
      }
      enum "state-change-mgo-parent" {
        value 10;
        description
          "Change of MGO parent session";
      }
      enum "state-change-chkpt-update" {
        value 11;
        description
          "Checkpoint update from Primary VRRP instance";
      }
      enum "state-change-issu-resync" {
        value 12;
        description
          "Resync following ISSU primary event";
      }
    }
    description
      "Vrrp state change reason";
  }

  typedef live_ncs_Vrrp-bfd-session-state {
    type enumeration {
      enum "bfd-state-none" {
        value 0;
        description
          "None";
      }
      enum "bfd-state-inactive" {
        value 1;
        description
          "Inactive";
      }
      enum "bfd-state-up" {
        value 2;
        description
          "Up";
      }
      enum "bfd-state-down" {
        value 3;
        description
          "Down";
      }
    }
    description
      "Vrrp bfd session state";
  }

  typedef live_ncs_Vrrp-prot-auth {
    type enumeration {
      enum "authentication-none" {
        value 0;
        description
          "Down";
      }
      enum "authentication-text" {
        value 1;
        description
          "Simple Text";
      }
      enum "authentication-ip" {
        value 2;
        description
          "IP header";
      }
    }
    description
      "Vrrp prot auth";
  }

  typedef live_ncs_Vrrp-bag-protocol-state {
    type enumeration {
      enum "state-initial" {
        value 1;
        description
          "Initial";
      }
      enum "state-backup" {
        value 2;
        description
          "Backup";
      }
      enum "state-master" {
        value 3;
        description
          "Master";
      }
    }
    description
      "VRRP protocol state";
  }

  typedef live_ncs_Vrrp-vip-state {
    type enumeration {
      enum "virtual-ip-state-down" {
        value 0;
        description
          "Down";
      }
      enum "virtual-ip-state-up" {
        value 1;
        description
          "Up";
      }
    }
    description
      "Vrrp vip state";
  }

  typedef live_ncs_Vrrp-b-af {
    type enumeration {
      enum "address-family-ipv4" {
        description
          "IPv4 Address Family";
      }
      enum "address-family-ipv6" {
        description
          "IPv6 Address Family";
      }
      enum "vrrp-baf-count" {
        description
          "Number of Adddress Families";
      }
    }
    description
      "Vrrp b af";
  }

  typedef live_ncs_Vrrp-version {
    type uint8;
    description
      "Vrrp version";
  }

  typedef Vrrp-vmac-state {
    type enumeration {
      enum "stored" {
        value 0;
        description
          "VMAC stored locally";
      }
      enum "reserved" {
        value 1;
        description
          "VMAC reserved in mac table";
      }
      enum "active" {
        value 2;
        description
          "VMAC active in mac table";
      }
      enum "reserving" {
        value 3;
        description
          "VMAC not yet reserved in mac table";
      }
    }
    description
      "Vrrp vmac state";
  }

  typedef Vrrp-state-change-reason {
    type enumeration {
      enum "state-change-bfd-down" {
        value 0;
        description
          "BFD session down";
      }
      enum "state-change-virtual-ip-configured" {
        value 1;
        description
          "Virtual IP configured";
      }
      enum "state-change-interface-ip" {
        value 2;
        description
          "Interface IP update";
      }
      enum "state-change-delay-timer" {
        value 3;
        description
          "Delay timer expired";
      }
      enum "state-change-startup" {
        value 4;
        description
          "Ready on startup";
      }
      enum "state-change-interface-up" {
        value 5;
        description
          "Interface Up update";
      }
      enum "state-change-interface-down" {
        value 6;
        description
          "Interface Down update";
      }
      enum "state-change-master-down-timer" {
        value 7;
        description
          "Master down timer expired";
      }
      enum "state-change-higher-priority-master" {
        value 8;
        description
          "Higher priority advert received";
      }
      enum "state-change-fhrp-admin" {
        value 9;
        description
          "FHRP Admin state change";
      }
      enum "state-change-mgo-parent" {
        value 10;
        description
          "Change of MGO parent session";
      }
      enum "state-change-chkpt-update" {
        value 11;
        description
          "Checkpoint update from Primary VRRP instance";
      }
      enum "state-change-issu-resync" {
        value 12;
        description
          "Resync following ISSU primary event";
      }
    }
    description
      "Vrrp state change reason";
  }

  typedef Vrrp-bfd-session-state {
    type enumeration {
      enum "bfd-state-none" {
        value 0;
        description
          "None";
      }
      enum "bfd-state-inactive" {
        value 1;
        description
          "Inactive";
      }
      enum "bfd-state-up" {
        value 2;
        description
          "Up";
      }
      enum "bfd-state-down" {
        value 3;
        description
          "Down";
      }
    }
    description
      "Vrrp bfd session state";
  }

  typedef Vrrp-prot-auth {
    type enumeration {
      enum "authentication-none" {
        value 0;
        description
          "Down";
      }
      enum "authentication-text" {
        value 1;
        description
          "Simple Text";
      }
      enum "authentication-ip" {
        value 2;
        description
          "IP header";
      }
    }
    description
      "Vrrp prot auth";
  }

  typedef Vrrp-bag-protocol-state {
    type enumeration {
      enum "state-initial" {
        value 1;
        description
          "Initial";
      }
      enum "state-backup" {
        value 2;
        description
          "Backup";
      }
      enum "state-master" {
        value 3;
        description
          "Master";
      }
    }
    description
      "VRRP protocol state";
  }

  typedef Vrrp-vip-state {
    type enumeration {
      enum "virtual-ip-state-down" {
        value 0;
        description
          "Down";
      }
      enum "virtual-ip-state-up" {
        value 1;
        description
          "Up";
      }
    }
    description
      "Vrrp vip state";
  }

  typedef Vrrp-b-af {
    type enumeration {
      enum "address-family-ipv4" {
        description
          "IPv4 Address Family";
      }
      enum "address-family-ipv6" {
        description
          "IPv6 Address Family";
      }
      enum "vrrp-baf-count" {
        description
          "Number of Adddress Families";
      }
    }
    description
      "Vrrp b af";
  }

  typedef Vrrp-version {
    type uint8;
    description
      "Vrrp version";
  }

  grouping ncs_template_VRRP-SLAVE-INFO-TYPE {
    description
      "Slave info";
    leaf slave-interface {
      type string;
      description
        "Interface of slave";
    }
    leaf slave-virtual-router-id {
      type string;
      description
        "VRID of slave";
    }
  }

  grouping ncs_template_VRRP-MGO-INFO {
    description
      "MGO group data";
    leaf primary-session-name {
      type string;
      description
        "Session Name";
    }
    leaf primary-session-interface {
      type xr:ncs_template_Interface-name;
      description
        "Interface of primary session";
    }
    leaf primary-af-name {
      type ncs_template_Vrrp-b-af;
      description
        "Address family of primary session";
    }
    leaf primary-session-number {
      type string;
      description
        "VRID of primary session";
    }
    leaf primary-session-state {
      type ncs_template_Vrrp-bag-protocol-state;
      description
        "State of primary session";
    }
    list slave {
      // NCS patched for predictable order
      ordered-by user;
      description
        "List of slaves following this primary session";
      uses ncs_template_VRRP-SLAVE-INFO-TYPE;
    }
  }

  grouping ncs_template_VRRP-INTERFACE-INFO {
    description
      "VRRP Interface statistics";
    leaf interface {
      type xr:ncs_template_Interface-name;
      description
        "IM Interface";
    }
    leaf invalid-checksum-count {
      type string;
      description
        "Invalid checksum";
    }
    leaf invalid-version-count {
      type string;
      description
        "Unknown/unsupported version";
    }
    leaf invalid-vrid-count {
      type string;
      description
        "Invalid vrID";
    }
    leaf invalid-packet-length-count {
      type string;
      description
        "Bad packet lengths";
    }
  }

  grouping ncs_template_VRRP-STATE-CHANGE-INFO-TYPE {
    description
      "State change info";
    container time {
      description
        "Time of state change";
      uses ncs_template_VRRP-BAG-TIMESTAMP;
    }
    leaf old-state {
      type ncs_template_Vrrp-bag-protocol-state;
      description
        "Old State";
    }
    leaf new-state {
      type ncs_template_Vrrp-bag-protocol-state;
      description
        "New State";
    }
    leaf reason {
      type ncs_template_Vrrp-state-change-reason;
      description
        "Reason for state change";
    }
  }

  grouping ncs_template_VRRP-BAG-TIMESTAMP {
    description
      "Timestamp";
    leaf seconds {
      type string;
      units "second";
      description
        "Seconds";
    }
    leaf nanoseconds {
      type string;
      units "nanosecond";
      description
        "Nanoseconds";
    }
  }

  grouping ncs_template_IPV6-BAG-ADDR {
    description
      "IPV6 BAG ADDR";
    leaf ipv6-address {
      type string;
      description
        "IPV6Address";
    }
  }

  grouping ncs_template_VRRP-VROUTER-INFO {
    description
      "Detailed vrID specific information";
    container resign-sent-time {
      description
        "Time last resign was sent";
      uses ncs_template_VRRP-BAG-TIMESTAMP;
    }
    container resign-received-time {
      description
        "Time last resign was received";
      uses ncs_template_VRRP-BAG-TIMESTAMP;
    }
    leaf interface-name-xr {
      type string;
      description
        "IM Interface Name";
    }
    leaf virtual-router-id-xr {
      type string;
      description
        "Virtual Router ID";
    }
    leaf version {
      type ncs_template_Vrrp-version;
      description
        "VRRP Protocol Version";
    }
    leaf address-family {
      type ncs_template_Vrrp-b-af;
      description
        "Address family";
    }
    leaf session-name {
      type string;
      description
        "Session Name";
    }
    leaf slaves {
      type string;
      description
        "Number of slaves following state";
    }
    leaf is-slave {
      type string;
      description
        "Group is a slave group";
    }
    leaf followed-session-name {
      type string;
      description
        "Followed Session Name";
    }
    leaf secondary-address-count {
      type string;
      description
        "Configured VRRP secondary address count";
    }
    leaf operational-address-count {
      type string;
      description
        "Operational VRRP address count";
    }
    leaf primary-virtual-ip {
      type string;
      description
        "Configured IPv4 Primary address";
    }
    leaf configured-down-address-count {
      type string;
      description
        " Configured but Down VRRP address count";
    }
    leaf virtual-linklocal-ipv6-address {
      type string;
      description
        "Virtual linklocal IPv6 address";
    }
    leaf primary-state {
      type ncs_template_Vrrp-vip-state;
      description
        "State of primary IP address";
    }
    leaf master-ip-address {
      type string;
      description
        "Master router real IP address";
    }
    leaf master-ipv6-address {
      type string;
      description
        "Master router real IPv6 address";
    }
    leaf master-priority {
      type string;
      description
        "Master router priority";
    }
    leaf vrrp-state {
      type ncs_template_Vrrp-bag-protocol-state;
      description
        "VRRP state";
    }
    leaf authentication-type {
      type ncs_template_Vrrp-prot-auth;
      description
        "Authentication type";
    }
    leaf authentication-string {
      type string;
      description
        "Authentication data";
    }
    leaf configured-advertize-time {
      type string;
      description
        "Configured advertize time";
    }
    leaf oper-advertize-time {
      type string;
      description
        "Operational advertize time";
    }
    leaf min-delay-time {
      type string;
      units "millisecond";
      description
        "Minimum delay time in msecs";
    }
    leaf reload-delay-time {
      type string;
      units "millisecond";
      description
        "Reload delay time in msecs";
    }
    leaf delay-timer-flag {
      type string;
      description
        "Delay timer running flag";
    }
    leaf delay-timer-secs {
      type string;
      units "second";
      description
        "Delay timer running time secs";
    }
    leaf delay-timer-msecs {
      type string;
      units "millisecond";
      description
        "Delay timer running time msecs";
    }
    leaf authentication-flag {
      type string;
      description
        "Text authentication configured flag";
    }
    leaf force-timer-flag {
      type string;
      description
        "Configured timers forced flag";
    }
    leaf preempt-flag {
      type string;
      description
        "Preempt configured flag";
    }
    leaf ip-address-owner-flag {
      type string;
      description
        "IP address owner flag";
    }
    leaf is-accept-mode {
      type string;
      description
        "Is accept mode";
    }
    leaf preempt-delay-time {
      type string;
      description
        "Preempt delay time";
    }
    leaf configured-priority {
      type string;
      description
        "Configured priority";
    }
    leaf operational-priority {
      type string;
      description
        "Operational priority";
    }
    leaf priority-decrement {
      type string;
      description
        "Priority decrement";
    }
    leaf tracked-interface-count {
      type string;
      description
        "Number of items tracked";
    }
    leaf tracked-interface-up-count {
      type string;
      description
        "Number of tracked items up";
    }
    leaf tracked-item-count {
      type string;
      description
        "Number of tracked items";
    }
    leaf tracked-item-up-count {
      type string;
      description
        "Number of tracked items in UP state";
    }
    leaf time-in-current-state {
      type string;
      units "second";
      description
        "Time in current state secs";
    }
    leaf state-change-count {
      type string;
      description
        "Number of state changes";
    }
    leaf time-vrouter-up {
      type string;
      units "centisecond";
      description
        "Time vrouter is up in centiseconds";
    }
    leaf master-count {
      type string;
      description
        "No. of times become Master";
    }
    leaf adverts-received-count {
      type string;
      description
        "No. of advertisements received";
    }
    leaf advert-interval-error-count {
      type string;
      description
        "Advertise interval errors";
    }
    leaf adverts-sent-count {
      type string;
      description
        "No. of advertisements sent";
    }
    leaf authentication-fail-count {
      type string;
      description
        "Authentication failures";
    }
    leaf ttl-error-count {
      type string;
      description
        "TTL errors";
    }
    leaf priority-zero-received-count {
      type string;
      description
        "No. priority 0 received";
    }
    leaf priority-zero-sent-count {
      type string;
      description
        "No. priority 0 sent";
    }
    leaf invalid-packet-count {
      type string;
      description
        "Invalid packets received";
    }
    leaf address-list-error-count {
      type string;
      description
        "Address list errors";
    }
    leaf invalid-auth-type-count {
      type string;
      description
        "Invalid authentication type";
    }
    leaf auth-type-mismatch-count {
      type string;
      description
        "Authentication type mismatches";
    }
    leaf pkt-length-errors-count {
      type string;
      description
        "Packet length errors";
    }
    leaf time-stats-discontinuity {
      type string;
      description
        "Time since a statistics discontinuity in ticks
         (10ns units)";
    }
    leaf bfd-session-state {
      type ncs_template_Vrrp-bfd-session-state;
      description
        "BFD session state";
    }
    leaf bfd-interval {
      type string;
      description
        "BFD packet send interval";
    }
    leaf bfd-multiplier {
      type string;
      description
        "BFD multiplier";
    }
    leaf bfd-cfg-remote-ip {
      type string;
      description
        "BFD configured remote IP";
    }
    leaf bfd-configured-remote-ipv6-address {
      type string;
      description
        "BFD configured remote IPv6";
    }
    leaf state-from-checkpoint {
      type string;
      description
        "Whether state recovered from checkpoint";
    }
    leaf interface-ipv4-address {
      type string;
      description
        "The Interface Primary IPv4 address";
    }
    leaf interface-ipv6-address {
      type string;
      description
        "The Interface linklocal IPv6 address";
    }
    leaf virtual-mac-address {
      type string;
      description
        "Virtual mac address";
    }
    leaf virtual-mac-address-state {
      type ncs_template_Vrrp-vmac-state;
      description
        "Virtual mac address state";
    }
    leaf-list operational-address {
      // NCS patched for predictable order
      ordered-by user;
      type string;
      description
        "Operational IPv4 VRRP addresses";
    }
    leaf-list ipv4-configured-down-address {
      // NCS patched for predictable order
      ordered-by user;
      type string;
      description
        "IPv4 Configured but Down VRRP addresses";
    }
    list ipv6-operational-address {
      // NCS patched for predictable order
      ordered-by user;
      description
        "IPv6 Operational VRRP addresses";
      uses ncs_template_IPV6-BAG-ADDR;
    }
    list ipv6-configured-down-address {
      // NCS patched for predictable order
      ordered-by user;
      description
        "IPv6 Configured but Down VRRP addresses";
      uses ncs_template_IPV6-BAG-ADDR;
    }
    list track-item-info {
      // NCS patched for predictable order
      ordered-by user;
      description
        "Track Item Info";
      uses ncs_template_VRRP-TRACKITEM-INFO;
    }
    list state-change-history {
      // NCS patched for predictable order
      ordered-by user;
      description
        "State change history";
      uses ncs_template_VRRP-STATE-CHANGE-INFO-TYPE;
    }
  }

  grouping ncs_template_VRRP-TRACKITEM-INFO {
    description
      "Tracked item information";
    leaf interface {
      type xr:ncs_template_Interface-name;
      description
        "IM Interface";
    }
    leaf virtual-router-id-xr {
      type string;
      description
        "Virtual Router ID";
    }
    leaf tracked-item-type {
      type string;
      description
        "Type of tracked item";
    }
    leaf tracked-item-index {
      type string;
      description
        "Tracked item index";
    }
    leaf state {
      type string;
      description
        "State of the tracked item";
    }
    leaf priority {
      type string;
      description
        "Priority weight of item";
    }
  }

  grouping ncs_template_VRRP-SUMMARY-INFO {
    description
      "VRRP summary statistics";
    leaf ipv4-sessions-master-owner {
      type string;
      description
        "Number of IPv4 sessions in MASTER (owner) state";
    }
    leaf ipv4-sessions-master {
      type string;
      description
        "Number of IPv4 sessions in MASTER state";
    }
    leaf ipv4-sessions-backup {
      type string;
      description
        "Number of IPv4 sessions in BACKUP state";
    }
    leaf ipv4-sessions-init {
      type string;
      description
        "Number of IPv4 sessions in INIT state";
    }
    leaf ipv4-slaves-master {
      type string;
      description
        "Number of IPv4 slaves in MASTER state";
    }
    leaf ipv4-slaves-backup {
      type string;
      description
        "Number of IPv4 slaves in BACKUP state";
    }
    leaf ipv4-slaves-init {
      type string;
      description
        "Number of IPv4 slaves in INIT state";
    }
    leaf ipv4-virtual-ip-addresses-master-owner-up {
      type string;
      description
        "Number of UP IPv4 Virtual IP Addresses on
         virtual routers in MASTER (owner) state";
    }
    leaf ipv4-virtual-ip-addresses-master-owner-down {
      type string;
      description
        "Number of DOWN IPv4 Virtual IP Addresses on
         virtual routers in MASTER (owner) state";
    }
    leaf ipv4-virtual-ip-addresses-master-up {
      type string;
      description
        "Number of UP IPv4 Virtual IP Addresses on
         virtual routers in MASTER state";
    }
    leaf ipv4-virtual-ip-addresses-master-down {
      type string;
      description
        "Number of DOWN IPv4 Virtual IP Addresses on
         virtual routers in MASTER state";
    }
    leaf ipv4-virtual-ip-addresses-backup-up {
      type string;
      description
        "Number of UP IPv4 Virtual IP Addresses on
         virtual routers in BACKUP state";
    }
    leaf ipv4-virtual-ip-addresses-backup-down {
      type string;
      description
        "Number of DOWN IPv4 Virtual IP Addresses on
         virtual routers in BACKUP state";
    }
    leaf ipv4-virtual-ip-addresses-init-up {
      type string;
      description
        "Number of UP IPv4 Virtual IP Addresses on
         virtual routers in INIT state";
    }
    leaf ipv4-virtual-ip-addresses-init-down {
      type string;
      description
        "Number of DOWN IPv4 Virtual IP Addresses on
         virtual routers in INIT state";
    }
    leaf ipv6-sessions-master-owner {
      type string;
      description
        "Number of IPv6 sessions in MASTER (owner) state";
    }
    leaf ipv6-sessions-master {
      type string;
      description
        "Number of IPv6 sessions in MASTER state";
    }
    leaf ipv6-sessions-backup {
      type string;
      description
        "Number of IPv6 sessions in BACKUP state";
    }
    leaf ipv6-sessions-init {
      type string;
      description
        "Number of IPv6 sessions in INIT state";
    }
    leaf ipv6-slaves-master {
      type string;
      description
        "Number of IPv6 slaves in MASTER state";
    }
    leaf ipv6-slaves-backup {
      type string;
      description
        "Number of IPv6 slaves in BACKUP state";
    }
    leaf ipv6-slaves-init {
      type string;
      description
        "Number of IPv6 slaves in INIT state";
    }
    leaf ipv6-virtual-ip-addresses-master-owner-up {
      type string;
      description
        "Number of UP IPv6 Virtual IP Addresses on
         virtual routers in MASTER (owner) state";
    }
    leaf ipv6-virtual-ip-addresses-master-owner-down {
      type string;
      description
        "Number of DOWN IPv6 Virtual IP Addresses on
         virtual routers in MASTER (owner) state";
    }
    leaf ipv6-virtual-ip-addresses-master-up {
      type string;
      description
        "Number of UP IPv6 Virtual IP Addresses on
         virtual routers in MASTER state";
    }
    leaf ipv6-virtual-ip-addresses-master-down {
      type string;
      description
        "Number of DOWN IPv6 Virtual IP Addresses on
         virtual routers in MASTER state";
    }
    leaf ipv6-virtual-ip-addresses-backup-up {
      type string;
      description
        "Number of UP IPv6 Virtual IP Addresses on
         virtual routers in BACKUP state";
    }
    leaf ipv6-virtual-ip-addresses-backup-down {
      type string;
      description
        "Number of DOWN IPv6 Virtual IP Addresses on
         virtual routers in BACKUP state";
    }
    leaf ipv6-virtual-ip-addresses-init-up {
      type string;
      description
        "Number of UP IPv6 Virtual IP Addresses on
         virtual routers in INIT state";
    }
    leaf ipv6-virtual-ip-addresses-init-down {
      type string;
      description
        "Number of DOWN IPv6 Virtual IP Addresses on
         virtual routers in INIT state";
    }
    leaf interfaces-ipv4-state-up {
      type string;
      description
        "Number of VRRP interfaces with IPv4 caps in UP
         state";
    }
    leaf interfaces-ipv4-state-down {
      type string;
      description
        "Number of VRRP interfaces with IPv4 caps in DOWN
         state";
    }
    leaf tracked-interfaces-ipv4-state-up {
      type string;
      description
        "Number of tracked interfaces with IPv4 caps in
         UP state";
    }
    leaf tracked-interfaces-ipv4-state-down {
      type string;
      description
        "Number of tracked interfaces with IPv4 caps in
         DOWN state";
    }
    leaf interfaces-ipv6-state-up {
      type string;
      description
        "Number of VRRP interfaces with IPv6 caps in UP
         state";
    }
    leaf interfaces-ipv6-state-down {
      type string;
      description
        "Number of VRRP interfaces with IPv6 caps in DOWN
         state";
    }
    leaf tracked-interfaces-ipv6-state-up {
      type string;
      description
        "Number of tracked interfaces with IPv6 caps in
         UP state";
    }
    leaf tracked-interfaces-ipv6-state-down {
      type string;
      description
        "Number of tracked interfaces with IPv6 caps in
         DOWN state";
    }
    leaf tracked-objects-state-up {
      type string;
      description
        "Number of tracked objects in UP state";
    }
    leaf tracked-objects-state-down {
      type string;
      description
        "Number of tracked objects in DOWN state";
    }
    leaf bfd-sessions-up {
      type string;
      description
        "Number of VRRP IPv4 BFD sessions in UP state";
    }
    leaf bfd-sessions-down {
      type string;
      description
        "Number of VRRP IPv4 BFD sessions in DOWN state";
    }
    leaf bfd-session-inactive {
      type string;
      description
        "Number of VRRP IPv4 BFD sessions in INACTIVE
         state";
    }
    leaf ipv6bfd-sessions-up {
      type string;
      description
        "Number of VRRP IPv6 BFD sessions in UP state";
    }
    leaf ipv6bfd-sessions-down {
      type string;
      description
        "Number of VRRP IPv6 BFD sessions in DOWN state";
    }
    leaf ipv6bfd-session-inactive {
      type string;
      description
        "Number of VRRP IPv6 BFD sessions in INACTIVE
         state";
    }
  }

  grouping ncs_rpc_notif_VRRP-SLAVE-INFO-TYPE {
    description
      "Slave info";
    leaf slave-interface {
      type string {
        length "0..64";
      }
      description
        "Interface of slave";
    }
    leaf slave-virtual-router-id {
      type uint32;
      description
        "VRID of slave";
    }
  }

  grouping ncs_rpc_notif_VRRP-MGO-INFO {
    description
      "MGO group data";
    leaf primary-session-name {
      type string {
        length "0..16";
      }
      description
        "Session Name";
    }
    leaf primary-session-interface {
      type xr:ncs_rpc_notif_Interface-name;
      description
        "Interface of primary session";
    }
    leaf primary-af-name {
      type ncs_rpc_notif_Vrrp-b-af;
      description
        "Address family of primary session";
    }
    leaf primary-session-number {
      type uint32;
      description
        "VRID of primary session";
    }
    leaf primary-session-state {
      type ncs_rpc_notif_Vrrp-bag-protocol-state;
      description
        "State of primary session";
    }
    list slave {
      description
        "List of slaves following this primary session";
      uses ncs_rpc_notif_VRRP-SLAVE-INFO-TYPE;
    }
  }

  grouping ncs_rpc_notif_VRRP-INTERFACE-INFO {
    description
      "VRRP Interface statistics";
    leaf interface {
      type xr:ncs_rpc_notif_Interface-name;
      description
        "IM Interface";
    }
    leaf invalid-checksum-count {
      type uint32;
      description
        "Invalid checksum";
    }
    leaf invalid-version-count {
      type uint32;
      description
        "Unknown/unsupported version";
    }
    leaf invalid-vrid-count {
      type uint32;
      description
        "Invalid vrID";
    }
    leaf invalid-packet-length-count {
      type uint32;
      description
        "Bad packet lengths";
    }
  }

  grouping ncs_rpc_notif_VRRP-STATE-CHANGE-INFO-TYPE {
    description
      "State change info";
    container time {
      description
        "Time of state change";
      uses ncs_rpc_notif_VRRP-BAG-TIMESTAMP;
    }
    leaf old-state {
      type ncs_rpc_notif_Vrrp-bag-protocol-state;
      description
        "Old State";
    }
    leaf new-state {
      type ncs_rpc_notif_Vrrp-bag-protocol-state;
      description
        "New State";
    }
    leaf reason {
      type ncs_rpc_notif_Vrrp-state-change-reason;
      description
        "Reason for state change";
    }
  }

  grouping ncs_rpc_notif_VRRP-BAG-TIMESTAMP {
    description
      "Timestamp";
    leaf seconds {
      type uint32;
      units "second";
      description
        "Seconds";
    }
    leaf nanoseconds {
      type uint32;
      units "nanosecond";
      description
        "Nanoseconds";
    }
  }

  grouping ncs_rpc_notif_IPV6-BAG-ADDR {
    description
      "IPV6 BAG ADDR";
    leaf ipv6-address {
      type inet:ipv6-address;
      description
        "IPV6Address";
    }
  }

  grouping ncs_rpc_notif_VRRP-VROUTER-INFO {
    description
      "Detailed vrID specific information";
    container resign-sent-time {
      description
        "Time last resign was sent";
      uses ncs_rpc_notif_VRRP-BAG-TIMESTAMP;
    }
    container resign-received-time {
      description
        "Time last resign was received";
      uses ncs_rpc_notif_VRRP-BAG-TIMESTAMP;
    }
    leaf interface-name-xr {
      type string {
        length "0..64";
      }
      description
        "IM Interface Name";
    }
    leaf virtual-router-id-xr {
      type uint32;
      description
        "Virtual Router ID";
    }
    leaf version {
      type ncs_rpc_notif_Vrrp-version;
      description
        "VRRP Protocol Version";
    }
    leaf address-family {
      type ncs_rpc_notif_Vrrp-b-af;
      description
        "Address family";
    }
    leaf session-name {
      type string {
        length "0..16";
      }
      description
        "Session Name";
    }
    leaf slaves {
      type uint32;
      description
        "Number of slaves following state";
    }
    leaf is-slave {
      type boolean;
      description
        "Group is a slave group";
    }
    leaf followed-session-name {
      type string {
        length "0..16";
      }
      description
        "Followed Session Name";
    }
    leaf secondary-address-count {
      type uint8;
      description
        "Configured VRRP secondary address count";
    }
    leaf operational-address-count {
      type uint8;
      description
        "Operational VRRP address count";
    }
    leaf primary-virtual-ip {
      type inet:ipv4-address;
      description
        "Configured IPv4 Primary address";
    }
    leaf configured-down-address-count {
      type uint8;
      description
        " Configured but Down VRRP address count";
    }
    leaf virtual-linklocal-ipv6-address {
      type inet:ipv6-address;
      description
        "Virtual linklocal IPv6 address";
    }
    leaf primary-state {
      type ncs_rpc_notif_Vrrp-vip-state;
      description
        "State of primary IP address";
    }
    leaf master-ip-address {
      type inet:ipv4-address;
      description
        "Master router real IP address";
    }
    leaf master-ipv6-address {
      type inet:ipv6-address;
      description
        "Master router real IPv6 address";
    }
    leaf master-priority {
      type uint8;
      description
        "Master router priority";
    }
    leaf vrrp-state {
      type ncs_rpc_notif_Vrrp-bag-protocol-state;
      description
        "VRRP state";
    }
    leaf authentication-type {
      type ncs_rpc_notif_Vrrp-prot-auth;
      description
        "Authentication type";
    }
    leaf authentication-string {
      type string;
      description
        "Authentication data";
    }
    leaf configured-advertize-time {
      type uint32;
      description
        "Configured advertize time";
    }
    leaf oper-advertize-time {
      type uint32;
      description
        "Operational advertize time";
    }
    leaf min-delay-time {
      type uint32;
      units "millisecond";
      description
        "Minimum delay time in msecs";
    }
    leaf reload-delay-time {
      type uint32;
      units "millisecond";
      description
        "Reload delay time in msecs";
    }
    leaf delay-timer-flag {
      type boolean;
      description
        "Delay timer running flag";
    }
    leaf delay-timer-secs {
      type uint32;
      units "second";
      description
        "Delay timer running time secs";
    }
    leaf delay-timer-msecs {
      type uint32;
      units "millisecond";
      description
        "Delay timer running time msecs";
    }
    leaf authentication-flag {
      type boolean;
      description
        "Text authentication configured flag";
    }
    leaf force-timer-flag {
      type boolean;
      description
        "Configured timers forced flag";
    }
    leaf preempt-flag {
      type boolean;
      description
        "Preempt configured flag";
    }
    leaf ip-address-owner-flag {
      type boolean;
      description
        "IP address owner flag";
    }
    leaf is-accept-mode {
      type boolean;
      description
        "Is accept mode";
    }
    leaf preempt-delay-time {
      type uint16;
      description
        "Preempt delay time";
    }
    leaf configured-priority {
      type uint8;
      description
        "Configured priority";
    }
    leaf operational-priority {
      type uint8;
      description
        "Operational priority";
    }
    leaf priority-decrement {
      type uint32;
      description
        "Priority decrement";
    }
    leaf tracked-interface-count {
      type uint32;
      description
        "Number of items tracked";
    }
    leaf tracked-interface-up-count {
      type uint32;
      description
        "Number of tracked items up";
    }
    leaf tracked-item-count {
      type uint32;
      description
        "Number of tracked items";
    }
    leaf tracked-item-up-count {
      type uint32;
      description
        "Number of tracked items in UP state";
    }
    leaf time-in-current-state {
      type uint32;
      units "second";
      description
        "Time in current state secs";
    }
    leaf state-change-count {
      type uint32;
      description
        "Number of state changes";
    }
    leaf time-vrouter-up {
      type uint32;
      units "centisecond";
      description
        "Time vrouter is up in centiseconds";
    }
    leaf master-count {
      type uint32;
      description
        "No. of times become Master";
    }
    leaf adverts-received-count {
      type uint32;
      description
        "No. of advertisements received";
    }
    leaf advert-interval-error-count {
      type uint32;
      description
        "Advertise interval errors";
    }
    leaf adverts-sent-count {
      type uint32;
      description
        "No. of advertisements sent";
    }
    leaf authentication-fail-count {
      type uint32;
      description
        "Authentication failures";
    }
    leaf ttl-error-count {
      type uint32;
      description
        "TTL errors";
    }
    leaf priority-zero-received-count {
      type uint32;
      description
        "No. priority 0 received";
    }
    leaf priority-zero-sent-count {
      type uint32;
      description
        "No. priority 0 sent";
    }
    leaf invalid-packet-count {
      type uint32;
      description
        "Invalid packets received";
    }
    leaf address-list-error-count {
      type uint32;
      description
        "Address list errors";
    }
    leaf invalid-auth-type-count {
      type uint32;
      description
        "Invalid authentication type";
    }
    leaf auth-type-mismatch-count {
      type uint32;
      description
        "Authentication type mismatches";
    }
    leaf pkt-length-errors-count {
      type uint32;
      description
        "Packet length errors";
    }
    leaf time-stats-discontinuity {
      type uint32;
      description
        "Time since a statistics discontinuity in ticks
         (10ns units)";
    }
    leaf bfd-session-state {
      type ncs_rpc_notif_Vrrp-bfd-session-state;
      description
        "BFD session state";
    }
    leaf bfd-interval {
      type uint32;
      description
        "BFD packet send interval";
    }
    leaf bfd-multiplier {
      type uint32;
      description
        "BFD multiplier";
    }
    leaf bfd-cfg-remote-ip {
      type inet:ipv4-address;
      description
        "BFD configured remote IP";
    }
    leaf bfd-configured-remote-ipv6-address {
      type inet:ipv6-address;
      description
        "BFD configured remote IPv6";
    }
    leaf state-from-checkpoint {
      type boolean;
      description
        "Whether state recovered from checkpoint";
    }
    leaf interface-ipv4-address {
      type inet:ipv4-address;
      description
        "The Interface Primary IPv4 address";
    }
    leaf interface-ipv6-address {
      type inet:ipv6-address;
      description
        "The Interface linklocal IPv6 address";
    }
    leaf virtual-mac-address {
      type yang:mac-address;
      description
        "Virtual mac address";
    }
    leaf virtual-mac-address-state {
      type ncs_rpc_notif_Vrrp-vmac-state;
      description
        "Virtual mac address state";
    }
    leaf-list operational-address {
      type inet:ipv4-address;
      description
        "Operational IPv4 VRRP addresses";
    }
    leaf-list ipv4-configured-down-address {
      type inet:ipv4-address;
      description
        "IPv4 Configured but Down VRRP addresses";
    }
    list ipv6-operational-address {
      description
        "IPv6 Operational VRRP addresses";
      uses ncs_rpc_notif_IPV6-BAG-ADDR;
    }
    list ipv6-configured-down-address {
      description
        "IPv6 Configured but Down VRRP addresses";
      uses ncs_rpc_notif_IPV6-BAG-ADDR;
    }
    list track-item-info {
      description
        "Track Item Info";
      uses ncs_rpc_notif_VRRP-TRACKITEM-INFO;
    }
    list state-change-history {
      description
        "State change history";
      uses ncs_rpc_notif_VRRP-STATE-CHANGE-INFO-TYPE;
    }
  }

  grouping ncs_rpc_notif_VRRP-TRACKITEM-INFO {
    description
      "Tracked item information";
    leaf interface {
      type xr:ncs_rpc_notif_Interface-name;
      description
        "IM Interface";
    }
    leaf virtual-router-id-xr {
      type uint32;
      description
        "Virtual Router ID";
    }
    leaf tracked-item-type {
      type uint16;
      description
        "Type of tracked item";
    }
    leaf tracked-item-index {
      type string {
        length "0..32";
      }
      description
        "Tracked item index";
    }
    leaf state {
      type uint8;
      description
        "State of the tracked item";
    }
    leaf priority {
      type uint8;
      description
        "Priority weight of item";
    }
  }

  grouping ncs_rpc_notif_VRRP-SUMMARY-INFO {
    description
      "VRRP summary statistics";
    leaf ipv4-sessions-master-owner {
      type uint32;
      description
        "Number of IPv4 sessions in MASTER (owner) state";
    }
    leaf ipv4-sessions-master {
      type uint32;
      description
        "Number of IPv4 sessions in MASTER state";
    }
    leaf ipv4-sessions-backup {
      type uint32;
      description
        "Number of IPv4 sessions in BACKUP state";
    }
    leaf ipv4-sessions-init {
      type uint32;
      description
        "Number of IPv4 sessions in INIT state";
    }
    leaf ipv4-slaves-master {
      type uint32;
      description
        "Number of IPv4 slaves in MASTER state";
    }
    leaf ipv4-slaves-backup {
      type uint32;
      description
        "Number of IPv4 slaves in BACKUP state";
    }
    leaf ipv4-slaves-init {
      type uint32;
      description
        "Number of IPv4 slaves in INIT state";
    }
    leaf ipv4-virtual-ip-addresses-master-owner-up {
      type uint32;
      description
        "Number of UP IPv4 Virtual IP Addresses on
         virtual routers in MASTER (owner) state";
    }
    leaf ipv4-virtual-ip-addresses-master-owner-down {
      type uint32;
      description
        "Number of DOWN IPv4 Virtual IP Addresses on
         virtual routers in MASTER (owner) state";
    }
    leaf ipv4-virtual-ip-addresses-master-up {
      type uint32;
      description
        "Number of UP IPv4 Virtual IP Addresses on
         virtual routers in MASTER state";
    }
    leaf ipv4-virtual-ip-addresses-master-down {
      type uint32;
      description
        "Number of DOWN IPv4 Virtual IP Addresses on
         virtual routers in MASTER state";
    }
    leaf ipv4-virtual-ip-addresses-backup-up {
      type uint32;
      description
        "Number of UP IPv4 Virtual IP Addresses on
         virtual routers in BACKUP state";
    }
    leaf ipv4-virtual-ip-addresses-backup-down {
      type uint32;
      description
        "Number of DOWN IPv4 Virtual IP Addresses on
         virtual routers in BACKUP state";
    }
    leaf ipv4-virtual-ip-addresses-init-up {
      type uint32;
      description
        "Number of UP IPv4 Virtual IP Addresses on
         virtual routers in INIT state";
    }
    leaf ipv4-virtual-ip-addresses-init-down {
      type uint32;
      description
        "Number of DOWN IPv4 Virtual IP Addresses on
         virtual routers in INIT state";
    }
    leaf ipv6-sessions-master-owner {
      type uint32;
      description
        "Number of IPv6 sessions in MASTER (owner) state";
    }
    leaf ipv6-sessions-master {
      type uint32;
      description
        "Number of IPv6 sessions in MASTER state";
    }
    leaf ipv6-sessions-backup {
      type uint32;
      description
        "Number of IPv6 sessions in BACKUP state";
    }
    leaf ipv6-sessions-init {
      type uint32;
      description
        "Number of IPv6 sessions in INIT state";
    }
    leaf ipv6-slaves-master {
      type uint32;
      description
        "Number of IPv6 slaves in MASTER state";
    }
    leaf ipv6-slaves-backup {
      type uint32;
      description
        "Number of IPv6 slaves in BACKUP state";
    }
    leaf ipv6-slaves-init {
      type uint32;
      description
        "Number of IPv6 slaves in INIT state";
    }
    leaf ipv6-virtual-ip-addresses-master-owner-up {
      type uint32;
      description
        "Number of UP IPv6 Virtual IP Addresses on
         virtual routers in MASTER (owner) state";
    }
    leaf ipv6-virtual-ip-addresses-master-owner-down {
      type uint32;
      description
        "Number of DOWN IPv6 Virtual IP Addresses on
         virtual routers in MASTER (owner) state";
    }
    leaf ipv6-virtual-ip-addresses-master-up {
      type uint32;
      description
        "Number of UP IPv6 Virtual IP Addresses on
         virtual routers in MASTER state";
    }
    leaf ipv6-virtual-ip-addresses-master-down {
      type uint32;
      description
        "Number of DOWN IPv6 Virtual IP Addresses on
         virtual routers in MASTER state";
    }
    leaf ipv6-virtual-ip-addresses-backup-up {
      type uint32;
      description
        "Number of UP IPv6 Virtual IP Addresses on
         virtual routers in BACKUP state";
    }
    leaf ipv6-virtual-ip-addresses-backup-down {
      type uint32;
      description
        "Number of DOWN IPv6 Virtual IP Addresses on
         virtual routers in BACKUP state";
    }
    leaf ipv6-virtual-ip-addresses-init-up {
      type uint32;
      description
        "Number of UP IPv6 Virtual IP Addresses on
         virtual routers in INIT state";
    }
    leaf ipv6-virtual-ip-addresses-init-down {
      type uint32;
      description
        "Number of DOWN IPv6 Virtual IP Addresses on
         virtual routers in INIT state";
    }
    leaf interfaces-ipv4-state-up {
      type uint32;
      description
        "Number of VRRP interfaces with IPv4 caps in UP
         state";
    }
    leaf interfaces-ipv4-state-down {
      type uint32;
      description
        "Number of VRRP interfaces with IPv4 caps in DOWN
         state";
    }
    leaf tracked-interfaces-ipv4-state-up {
      type uint32;
      description
        "Number of tracked interfaces with IPv4 caps in
         UP state";
    }
    leaf tracked-interfaces-ipv4-state-down {
      type uint32;
      description
        "Number of tracked interfaces with IPv4 caps in
         DOWN state";
    }
    leaf interfaces-ipv6-state-up {
      type uint32;
      description
        "Number of VRRP interfaces with IPv6 caps in UP
         state";
    }
    leaf interfaces-ipv6-state-down {
      type uint32;
      description
        "Number of VRRP interfaces with IPv6 caps in DOWN
         state";
    }
    leaf tracked-interfaces-ipv6-state-up {
      type uint32;
      description
        "Number of tracked interfaces with IPv6 caps in
         UP state";
    }
    leaf tracked-interfaces-ipv6-state-down {
      type uint32;
      description
        "Number of tracked interfaces with IPv6 caps in
         DOWN state";
    }
    leaf tracked-objects-state-up {
      type uint32;
      description
        "Number of tracked objects in UP state";
    }
    leaf tracked-objects-state-down {
      type uint32;
      description
        "Number of tracked objects in DOWN state";
    }
    leaf bfd-sessions-up {
      type uint32;
      description
        "Number of VRRP IPv4 BFD sessions in UP state";
    }
    leaf bfd-sessions-down {
      type uint32;
      description
        "Number of VRRP IPv4 BFD sessions in DOWN state";
    }
    leaf bfd-session-inactive {
      type uint32;
      description
        "Number of VRRP IPv4 BFD sessions in INACTIVE
         state";
    }
    leaf ipv6bfd-sessions-up {
      type uint32;
      description
        "Number of VRRP IPv6 BFD sessions in UP state";
    }
    leaf ipv6bfd-sessions-down {
      type uint32;
      description
        "Number of VRRP IPv6 BFD sessions in DOWN state";
    }
    leaf ipv6bfd-session-inactive {
      type uint32;
      description
        "Number of VRRP IPv6 BFD sessions in INACTIVE
         state";
    }
  }

  grouping live_ncs_VRRP-SLAVE-INFO-TYPE {
    description
      "Slave info";
    leaf slave-interface {
      type string {
        length "0..64";
      }
      description
        "Interface of slave";
    }
    leaf slave-virtual-router-id {
      type uint32;
      description
        "VRID of slave";
    }
  }

  grouping live_ncs_VRRP-MGO-INFO {
    description
      "MGO group data";
    leaf primary-session-name {
      type string {
        length "0..16";
      }
      description
        "Session Name";
    }
    leaf primary-session-interface {
      type xr:live_ncs_Interface-name;
      description
        "Interface of primary session";
    }
    leaf primary-af-name {
      type live_ncs_Vrrp-b-af;
      description
        "Address family of primary session";
    }
    leaf primary-session-number {
      type uint32;
      description
        "VRID of primary session";
    }
    leaf primary-session-state {
      type live_ncs_Vrrp-bag-protocol-state;
      description
        "State of primary session";
    }
    list slave {
      description
        "List of slaves following this primary session";
      uses live_ncs_VRRP-SLAVE-INFO-TYPE;
    }
  }

  grouping live_ncs_VRRP-INTERFACE-INFO {
    description
      "VRRP Interface statistics";
    leaf interface {
      type xr:live_ncs_Interface-name;
      description
        "IM Interface";
    }
    leaf invalid-checksum-count {
      type uint32;
      description
        "Invalid checksum";
    }
    leaf invalid-version-count {
      type uint32;
      description
        "Unknown/unsupported version";
    }
    leaf invalid-vrid-count {
      type uint32;
      description
        "Invalid vrID";
    }
    leaf invalid-packet-length-count {
      type uint32;
      description
        "Bad packet lengths";
    }
  }

  grouping live_ncs_VRRP-STATE-CHANGE-INFO-TYPE {
    description
      "State change info";
    container time {
      description
        "Time of state change";
      uses live_ncs_VRRP-BAG-TIMESTAMP;
    }
    leaf old-state {
      type live_ncs_Vrrp-bag-protocol-state;
      description
        "Old State";
    }
    leaf new-state {
      type live_ncs_Vrrp-bag-protocol-state;
      description
        "New State";
    }
    leaf reason {
      type live_ncs_Vrrp-state-change-reason;
      description
        "Reason for state change";
    }
  }

  grouping live_ncs_VRRP-BAG-TIMESTAMP {
    description
      "Timestamp";
    leaf seconds {
      type uint32;
      units "second";
      description
        "Seconds";
    }
    leaf nanoseconds {
      type uint32;
      units "nanosecond";
      description
        "Nanoseconds";
    }
  }

  grouping live_ncs_IPV6-BAG-ADDR {
    description
      "IPV6 BAG ADDR";
    leaf ipv6-address {
      type inet:ipv6-address;
      description
        "IPV6Address";
    }
  }

  grouping live_ncs_VRRP-VROUTER-INFO {
    description
      "Detailed vrID specific information";
    container resign-sent-time {
      description
        "Time last resign was sent";
      uses live_ncs_VRRP-BAG-TIMESTAMP;
    }
    container resign-received-time {
      description
        "Time last resign was received";
      uses live_ncs_VRRP-BAG-TIMESTAMP;
    }
    leaf interface-name-xr {
      type string {
        length "0..64";
      }
      description
        "IM Interface Name";
    }
    leaf virtual-router-id-xr {
      type uint32;
      description
        "Virtual Router ID";
    }
    leaf version {
      type live_ncs_Vrrp-version;
      description
        "VRRP Protocol Version";
    }
    leaf address-family {
      type live_ncs_Vrrp-b-af;
      description
        "Address family";
    }
    leaf session-name {
      type string {
        length "0..16";
      }
      description
        "Session Name";
    }
    leaf slaves {
      type uint32;
      description
        "Number of slaves following state";
    }
    leaf is-slave {
      type boolean;
      description
        "Group is a slave group";
    }
    leaf followed-session-name {
      type string {
        length "0..16";
      }
      description
        "Followed Session Name";
    }
    leaf secondary-address-count {
      type uint8;
      description
        "Configured VRRP secondary address count";
    }
    leaf operational-address-count {
      type uint8;
      description
        "Operational VRRP address count";
    }
    leaf primary-virtual-ip {
      type inet:ipv4-address;
      description
        "Configured IPv4 Primary address";
    }
    leaf configured-down-address-count {
      type uint8;
      description
        " Configured but Down VRRP address count";
    }
    leaf virtual-linklocal-ipv6-address {
      type inet:ipv6-address;
      description
        "Virtual linklocal IPv6 address";
    }
    leaf primary-state {
      type live_ncs_Vrrp-vip-state;
      description
        "State of primary IP address";
    }
    leaf master-ip-address {
      type inet:ipv4-address;
      description
        "Master router real IP address";
    }
    leaf master-ipv6-address {
      type inet:ipv6-address;
      description
        "Master router real IPv6 address";
    }
    leaf master-priority {
      type uint8;
      description
        "Master router priority";
    }
    leaf vrrp-state {
      type live_ncs_Vrrp-bag-protocol-state;
      description
        "VRRP state";
    }
    leaf authentication-type {
      type live_ncs_Vrrp-prot-auth;
      description
        "Authentication type";
    }
    leaf authentication-string {
      type string;
      description
        "Authentication data";
    }
    leaf configured-advertize-time {
      type uint32;
      description
        "Configured advertize time";
    }
    leaf oper-advertize-time {
      type uint32;
      description
        "Operational advertize time";
    }
    leaf min-delay-time {
      type uint32;
      units "millisecond";
      description
        "Minimum delay time in msecs";
    }
    leaf reload-delay-time {
      type uint32;
      units "millisecond";
      description
        "Reload delay time in msecs";
    }
    leaf delay-timer-flag {
      type boolean;
      description
        "Delay timer running flag";
    }
    leaf delay-timer-secs {
      type uint32;
      units "second";
      description
        "Delay timer running time secs";
    }
    leaf delay-timer-msecs {
      type uint32;
      units "millisecond";
      description
        "Delay timer running time msecs";
    }
    leaf authentication-flag {
      type boolean;
      description
        "Text authentication configured flag";
    }
    leaf force-timer-flag {
      type boolean;
      description
        "Configured timers forced flag";
    }
    leaf preempt-flag {
      type boolean;
      description
        "Preempt configured flag";
    }
    leaf ip-address-owner-flag {
      type boolean;
      description
        "IP address owner flag";
    }
    leaf is-accept-mode {
      type boolean;
      description
        "Is accept mode";
    }
    leaf preempt-delay-time {
      type uint16;
      description
        "Preempt delay time";
    }
    leaf configured-priority {
      type uint8;
      description
        "Configured priority";
    }
    leaf operational-priority {
      type uint8;
      description
        "Operational priority";
    }
    leaf priority-decrement {
      type uint32;
      description
        "Priority decrement";
    }
    leaf tracked-interface-count {
      type uint32;
      description
        "Number of items tracked";
    }
    leaf tracked-interface-up-count {
      type uint32;
      description
        "Number of tracked items up";
    }
    leaf tracked-item-count {
      type uint32;
      description
        "Number of tracked items";
    }
    leaf tracked-item-up-count {
      type uint32;
      description
        "Number of tracked items in UP state";
    }
    leaf time-in-current-state {
      type uint32;
      units "second";
      description
        "Time in current state secs";
    }
    leaf state-change-count {
      type uint32;
      description
        "Number of state changes";
    }
    leaf time-vrouter-up {
      type uint32;
      units "centisecond";
      description
        "Time vrouter is up in centiseconds";
    }
    leaf master-count {
      type uint32;
      description
        "No. of times become Master";
    }
    leaf adverts-received-count {
      type uint32;
      description
        "No. of advertisements received";
    }
    leaf advert-interval-error-count {
      type uint32;
      description
        "Advertise interval errors";
    }
    leaf adverts-sent-count {
      type uint32;
      description
        "No. of advertisements sent";
    }
    leaf authentication-fail-count {
      type uint32;
      description
        "Authentication failures";
    }
    leaf ttl-error-count {
      type uint32;
      description
        "TTL errors";
    }
    leaf priority-zero-received-count {
      type uint32;
      description
        "No. priority 0 received";
    }
    leaf priority-zero-sent-count {
      type uint32;
      description
        "No. priority 0 sent";
    }
    leaf invalid-packet-count {
      type uint32;
      description
        "Invalid packets received";
    }
    leaf address-list-error-count {
      type uint32;
      description
        "Address list errors";
    }
    leaf invalid-auth-type-count {
      type uint32;
      description
        "Invalid authentication type";
    }
    leaf auth-type-mismatch-count {
      type uint32;
      description
        "Authentication type mismatches";
    }
    leaf pkt-length-errors-count {
      type uint32;
      description
        "Packet length errors";
    }
    leaf time-stats-discontinuity {
      type uint32;
      description
        "Time since a statistics discontinuity in ticks
         (10ns units)";
    }
    leaf bfd-session-state {
      type live_ncs_Vrrp-bfd-session-state;
      description
        "BFD session state";
    }
    leaf bfd-interval {
      type uint32;
      description
        "BFD packet send interval";
    }
    leaf bfd-multiplier {
      type uint32;
      description
        "BFD multiplier";
    }
    leaf bfd-cfg-remote-ip {
      type inet:ipv4-address;
      description
        "BFD configured remote IP";
    }
    leaf bfd-configured-remote-ipv6-address {
      type inet:ipv6-address;
      description
        "BFD configured remote IPv6";
    }
    leaf state-from-checkpoint {
      type boolean;
      description
        "Whether state recovered from checkpoint";
    }
    leaf interface-ipv4-address {
      type inet:ipv4-address;
      description
        "The Interface Primary IPv4 address";
    }
    leaf interface-ipv6-address {
      type inet:ipv6-address;
      description
        "The Interface linklocal IPv6 address";
    }
    leaf virtual-mac-address {
      type yang:mac-address;
      description
        "Virtual mac address";
    }
    leaf virtual-mac-address-state {
      type live_ncs_Vrrp-vmac-state;
      description
        "Virtual mac address state";
    }
    leaf-list operational-address {
      type inet:ipv4-address;
      description
        "Operational IPv4 VRRP addresses";
    }
    leaf-list ipv4-configured-down-address {
      type inet:ipv4-address;
      description
        "IPv4 Configured but Down VRRP addresses";
    }
    list ipv6-operational-address {
      description
        "IPv6 Operational VRRP addresses";
      uses live_ncs_IPV6-BAG-ADDR;
    }
    list ipv6-configured-down-address {
      description
        "IPv6 Configured but Down VRRP addresses";
      uses live_ncs_IPV6-BAG-ADDR;
    }
    list track-item-info {
      description
        "Track Item Info";
      uses live_ncs_VRRP-TRACKITEM-INFO;
    }
    list state-change-history {
      description
        "State change history";
      uses live_ncs_VRRP-STATE-CHANGE-INFO-TYPE;
    }
  }

  grouping live_ncs_VRRP-TRACKITEM-INFO {
    description
      "Tracked item information";
    leaf interface {
      type xr:live_ncs_Interface-name;
      description
        "IM Interface";
    }
    leaf virtual-router-id-xr {
      type uint32;
      description
        "Virtual Router ID";
    }
    leaf tracked-item-type {
      type uint16;
      description
        "Type of tracked item";
    }
    leaf tracked-item-index {
      type string {
        length "0..32";
      }
      description
        "Tracked item index";
    }
    leaf state {
      type uint8;
      description
        "State of the tracked item";
    }
    leaf priority {
      type uint8;
      description
        "Priority weight of item";
    }
  }

  grouping live_ncs_VRRP-SUMMARY-INFO {
    description
      "VRRP summary statistics";
    leaf ipv4-sessions-master-owner {
      type uint32;
      description
        "Number of IPv4 sessions in MASTER (owner) state";
    }
    leaf ipv4-sessions-master {
      type uint32;
      description
        "Number of IPv4 sessions in MASTER state";
    }
    leaf ipv4-sessions-backup {
      type uint32;
      description
        "Number of IPv4 sessions in BACKUP state";
    }
    leaf ipv4-sessions-init {
      type uint32;
      description
        "Number of IPv4 sessions in INIT state";
    }
    leaf ipv4-slaves-master {
      type uint32;
      description
        "Number of IPv4 slaves in MASTER state";
    }
    leaf ipv4-slaves-backup {
      type uint32;
      description
        "Number of IPv4 slaves in BACKUP state";
    }
    leaf ipv4-slaves-init {
      type uint32;
      description
        "Number of IPv4 slaves in INIT state";
    }
    leaf ipv4-virtual-ip-addresses-master-owner-up {
      type uint32;
      description
        "Number of UP IPv4 Virtual IP Addresses on
         virtual routers in MASTER (owner) state";
    }
    leaf ipv4-virtual-ip-addresses-master-owner-down {
      type uint32;
      description
        "Number of DOWN IPv4 Virtual IP Addresses on
         virtual routers in MASTER (owner) state";
    }
    leaf ipv4-virtual-ip-addresses-master-up {
      type uint32;
      description
        "Number of UP IPv4 Virtual IP Addresses on
         virtual routers in MASTER state";
    }
    leaf ipv4-virtual-ip-addresses-master-down {
      type uint32;
      description
        "Number of DOWN IPv4 Virtual IP Addresses on
         virtual routers in MASTER state";
    }
    leaf ipv4-virtual-ip-addresses-backup-up {
      type uint32;
      description
        "Number of UP IPv4 Virtual IP Addresses on
         virtual routers in BACKUP state";
    }
    leaf ipv4-virtual-ip-addresses-backup-down {
      type uint32;
      description
        "Number of DOWN IPv4 Virtual IP Addresses on
         virtual routers in BACKUP state";
    }
    leaf ipv4-virtual-ip-addresses-init-up {
      type uint32;
      description
        "Number of UP IPv4 Virtual IP Addresses on
         virtual routers in INIT state";
    }
    leaf ipv4-virtual-ip-addresses-init-down {
      type uint32;
      description
        "Number of DOWN IPv4 Virtual IP Addresses on
         virtual routers in INIT state";
    }
    leaf ipv6-sessions-master-owner {
      type uint32;
      description
        "Number of IPv6 sessions in MASTER (owner) state";
    }
    leaf ipv6-sessions-master {
      type uint32;
      description
        "Number of IPv6 sessions in MASTER state";
    }
    leaf ipv6-sessions-backup {
      type uint32;
      description
        "Number of IPv6 sessions in BACKUP state";
    }
    leaf ipv6-sessions-init {
      type uint32;
      description
        "Number of IPv6 sessions in INIT state";
    }
    leaf ipv6-slaves-master {
      type uint32;
      description
        "Number of IPv6 slaves in MASTER state";
    }
    leaf ipv6-slaves-backup {
      type uint32;
      description
        "Number of IPv6 slaves in BACKUP state";
    }
    leaf ipv6-slaves-init {
      type uint32;
      description
        "Number of IPv6 slaves in INIT state";
    }
    leaf ipv6-virtual-ip-addresses-master-owner-up {
      type uint32;
      description
        "Number of UP IPv6 Virtual IP Addresses on
         virtual routers in MASTER (owner) state";
    }
    leaf ipv6-virtual-ip-addresses-master-owner-down {
      type uint32;
      description
        "Number of DOWN IPv6 Virtual IP Addresses on
         virtual routers in MASTER (owner) state";
    }
    leaf ipv6-virtual-ip-addresses-master-up {
      type uint32;
      description
        "Number of UP IPv6 Virtual IP Addresses on
         virtual routers in MASTER state";
    }
    leaf ipv6-virtual-ip-addresses-master-down {
      type uint32;
      description
        "Number of DOWN IPv6 Virtual IP Addresses on
         virtual routers in MASTER state";
    }
    leaf ipv6-virtual-ip-addresses-backup-up {
      type uint32;
      description
        "Number of UP IPv6 Virtual IP Addresses on
         virtual routers in BACKUP state";
    }
    leaf ipv6-virtual-ip-addresses-backup-down {
      type uint32;
      description
        "Number of DOWN IPv6 Virtual IP Addresses on
         virtual routers in BACKUP state";
    }
    leaf ipv6-virtual-ip-addresses-init-up {
      type uint32;
      description
        "Number of UP IPv6 Virtual IP Addresses on
         virtual routers in INIT state";
    }
    leaf ipv6-virtual-ip-addresses-init-down {
      type uint32;
      description
        "Number of DOWN IPv6 Virtual IP Addresses on
         virtual routers in INIT state";
    }
    leaf interfaces-ipv4-state-up {
      type uint32;
      description
        "Number of VRRP interfaces with IPv4 caps in UP
         state";
    }
    leaf interfaces-ipv4-state-down {
      type uint32;
      description
        "Number of VRRP interfaces with IPv4 caps in DOWN
         state";
    }
    leaf tracked-interfaces-ipv4-state-up {
      type uint32;
      description
        "Number of tracked interfaces with IPv4 caps in
         UP state";
    }
    leaf tracked-interfaces-ipv4-state-down {
      type uint32;
      description
        "Number of tracked interfaces with IPv4 caps in
         DOWN state";
    }
    leaf interfaces-ipv6-state-up {
      type uint32;
      description
        "Number of VRRP interfaces with IPv6 caps in UP
         state";
    }
    leaf interfaces-ipv6-state-down {
      type uint32;
      description
        "Number of VRRP interfaces with IPv6 caps in DOWN
         state";
    }
    leaf tracked-interfaces-ipv6-state-up {
      type uint32;
      description
        "Number of tracked interfaces with IPv6 caps in
         UP state";
    }
    leaf tracked-interfaces-ipv6-state-down {
      type uint32;
      description
        "Number of tracked interfaces with IPv6 caps in
         DOWN state";
    }
    leaf tracked-objects-state-up {
      type uint32;
      description
        "Number of tracked objects in UP state";
    }
    leaf tracked-objects-state-down {
      type uint32;
      description
        "Number of tracked objects in DOWN state";
    }
    leaf bfd-sessions-up {
      type uint32;
      description
        "Number of VRRP IPv4 BFD sessions in UP state";
    }
    leaf bfd-sessions-down {
      type uint32;
      description
        "Number of VRRP IPv4 BFD sessions in DOWN state";
    }
    leaf bfd-session-inactive {
      type uint32;
      description
        "Number of VRRP IPv4 BFD sessions in INACTIVE
         state";
    }
    leaf ipv6bfd-sessions-up {
      type uint32;
      description
        "Number of VRRP IPv6 BFD sessions in UP state";
    }
    leaf ipv6bfd-sessions-down {
      type uint32;
      description
        "Number of VRRP IPv6 BFD sessions in DOWN state";
    }
    leaf ipv6bfd-session-inactive {
      type uint32;
      description
        "Number of VRRP IPv6 BFD sessions in INACTIVE
         state";
    }
  }

  grouping VRRP-SLAVE-INFO-TYPE {
    description
      "Slave info";
    leaf slave-interface {
      type string {
        length "0..64";
      }
      description
        "Interface of slave";
    }
    leaf slave-virtual-router-id {
      type uint32;
      description
        "VRID of slave";
    }
  }

  grouping VRRP-MGO-INFO {
    description
      "MGO group data";
    leaf primary-session-name {
      type string {
        length "0..16";
      }
      description
        "Session Name";
    }
    leaf primary-session-interface {
      type xr:Interface-name;
      description
        "Interface of primary session";
    }
    leaf primary-af-name {
      type Vrrp-b-af;
      description
        "Address family of primary session";
    }
    leaf primary-session-number {
      type uint32;
      description
        "VRID of primary session";
    }
    leaf primary-session-state {
      type Vrrp-bag-protocol-state;
      description
        "State of primary session";
    }
    list slave {
      description
        "List of slaves following this primary session";
      uses VRRP-SLAVE-INFO-TYPE;
    }
  }

  grouping VRRP-INTERFACE-INFO {
    description
      "VRRP Interface statistics";
    leaf interface {
      type xr:Interface-name;
      description
        "IM Interface";
    }
    leaf invalid-checksum-count {
      type uint32;
      description
        "Invalid checksum";
    }
    leaf invalid-version-count {
      type uint32;
      description
        "Unknown/unsupported version";
    }
    leaf invalid-vrid-count {
      type uint32;
      description
        "Invalid vrID";
    }
    leaf invalid-packet-length-count {
      type uint32;
      description
        "Bad packet lengths";
    }
  }

  grouping VRRP-STATE-CHANGE-INFO-TYPE {
    description
      "State change info";
    container time {
      description
        "Time of state change";
      uses VRRP-BAG-TIMESTAMP;
    }
    leaf old-state {
      type Vrrp-bag-protocol-state;
      description
        "Old State";
    }
    leaf new-state {
      type Vrrp-bag-protocol-state;
      description
        "New State";
    }
    leaf reason {
      type Vrrp-state-change-reason;
      description
        "Reason for state change";
    }
  }

  grouping VRRP-BAG-TIMESTAMP {
    description
      "Timestamp";
    leaf seconds {
      type uint32;
      units "second";
      description
        "Seconds";
    }
    leaf nanoseconds {
      type uint32;
      units "nanosecond";
      description
        "Nanoseconds";
    }
  }

  grouping IPV6-BAG-ADDR {
    description
      "IPV6 BAG ADDR";
    leaf ipv6-address {
      type inet:ipv6-address;
      description
        "IPV6Address";
    }
  }

  grouping VRRP-VROUTER-INFO {
    description
      "Detailed vrID specific information";
    container resign-sent-time {
      description
        "Time last resign was sent";
      uses VRRP-BAG-TIMESTAMP;
    }
    container resign-received-time {
      description
        "Time last resign was received";
      uses VRRP-BAG-TIMESTAMP;
    }
    leaf interface-name-xr {
      type string {
        length "0..64";
      }
      description
        "IM Interface Name";
    }
    leaf virtual-router-id-xr {
      type uint32;
      description
        "Virtual Router ID";
    }
    leaf version {
      type Vrrp-version;
      description
        "VRRP Protocol Version";
    }
    leaf address-family {
      type Vrrp-b-af;
      description
        "Address family";
    }
    leaf session-name {
      type string {
        length "0..16";
      }
      description
        "Session Name";
    }
    leaf slaves {
      type uint32;
      description
        "Number of slaves following state";
    }
    leaf is-slave {
      type boolean;
      description
        "Group is a slave group";
    }
    leaf followed-session-name {
      type string {
        length "0..16";
      }
      description
        "Followed Session Name";
    }
    leaf secondary-address-count {
      type uint8;
      description
        "Configured VRRP secondary address count";
    }
    leaf operational-address-count {
      type uint8;
      description
        "Operational VRRP address count";
    }
    leaf primary-virtual-ip {
      type inet:ipv4-address;
      description
        "Configured IPv4 Primary address";
    }
    leaf configured-down-address-count {
      type uint8;
      description
        " Configured but Down VRRP address count";
    }
    leaf virtual-linklocal-ipv6-address {
      type inet:ipv6-address;
      description
        "Virtual linklocal IPv6 address";
    }
    leaf primary-state {
      type Vrrp-vip-state;
      description
        "State of primary IP address";
    }
    leaf master-ip-address {
      type inet:ipv4-address;
      description
        "Master router real IP address";
    }
    leaf master-ipv6-address {
      type inet:ipv6-address;
      description
        "Master router real IPv6 address";
    }
    leaf master-priority {
      type uint8;
      description
        "Master router priority";
    }
    leaf vrrp-state {
      type Vrrp-bag-protocol-state;
      description
        "VRRP state";
    }
    leaf authentication-type {
      type Vrrp-prot-auth;
      description
        "Authentication type";
    }
    leaf authentication-string {
      type string;
      description
        "Authentication data";
    }
    leaf configured-advertize-time {
      type uint32;
      description
        "Configured advertize time";
    }
    leaf oper-advertize-time {
      type uint32;
      description
        "Operational advertize time";
    }
    leaf min-delay-time {
      type uint32;
      units "millisecond";
      description
        "Minimum delay time in msecs";
    }
    leaf reload-delay-time {
      type uint32;
      units "millisecond";
      description
        "Reload delay time in msecs";
    }
    leaf delay-timer-flag {
      type boolean;
      description
        "Delay timer running flag";
    }
    leaf delay-timer-secs {
      type uint32;
      units "second";
      description
        "Delay timer running time secs";
    }
    leaf delay-timer-msecs {
      type uint32;
      units "millisecond";
      description
        "Delay timer running time msecs";
    }
    leaf authentication-flag {
      type boolean;
      description
        "Text authentication configured flag";
    }
    leaf force-timer-flag {
      type boolean;
      description
        "Configured timers forced flag";
    }
    leaf preempt-flag {
      type boolean;
      description
        "Preempt configured flag";
    }
    leaf ip-address-owner-flag {
      type boolean;
      description
        "IP address owner flag";
    }
    leaf is-accept-mode {
      type boolean;
      description
        "Is accept mode";
    }
    leaf preempt-delay-time {
      type uint16;
      description
        "Preempt delay time";
    }
    leaf configured-priority {
      type uint8;
      description
        "Configured priority";
    }
    leaf operational-priority {
      type uint8;
      description
        "Operational priority";
    }
    leaf priority-decrement {
      type uint32;
      description
        "Priority decrement";
    }
    leaf tracked-interface-count {
      type uint32;
      description
        "Number of items tracked";
    }
    leaf tracked-interface-up-count {
      type uint32;
      description
        "Number of tracked items up";
    }
    leaf tracked-item-count {
      type uint32;
      description
        "Number of tracked items";
    }
    leaf tracked-item-up-count {
      type uint32;
      description
        "Number of tracked items in UP state";
    }
    leaf time-in-current-state {
      type uint32;
      units "second";
      description
        "Time in current state secs";
    }
    leaf state-change-count {
      type uint32;
      description
        "Number of state changes";
    }
    leaf time-vrouter-up {
      type uint32;
      units "centisecond";
      description
        "Time vrouter is up in centiseconds";
    }
    leaf master-count {
      type uint32;
      description
        "No. of times become Master";
    }
    leaf adverts-received-count {
      type uint32;
      description
        "No. of advertisements received";
    }
    leaf advert-interval-error-count {
      type uint32;
      description
        "Advertise interval errors";
    }
    leaf adverts-sent-count {
      type uint32;
      description
        "No. of advertisements sent";
    }
    leaf authentication-fail-count {
      type uint32;
      description
        "Authentication failures";
    }
    leaf ttl-error-count {
      type uint32;
      description
        "TTL errors";
    }
    leaf priority-zero-received-count {
      type uint32;
      description
        "No. priority 0 received";
    }
    leaf priority-zero-sent-count {
      type uint32;
      description
        "No. priority 0 sent";
    }
    leaf invalid-packet-count {
      type uint32;
      description
        "Invalid packets received";
    }
    leaf address-list-error-count {
      type uint32;
      description
        "Address list errors";
    }
    leaf invalid-auth-type-count {
      type uint32;
      description
        "Invalid authentication type";
    }
    leaf auth-type-mismatch-count {
      type uint32;
      description
        "Authentication type mismatches";
    }
    leaf pkt-length-errors-count {
      type uint32;
      description
        "Packet length errors";
    }
    leaf time-stats-discontinuity {
      type uint32;
      description
        "Time since a statistics discontinuity in ticks
         (10ns units)";
    }
    leaf bfd-session-state {
      type Vrrp-bfd-session-state;
      description
        "BFD session state";
    }
    leaf bfd-interval {
      type uint32;
      description
        "BFD packet send interval";
    }
    leaf bfd-multiplier {
      type uint32;
      description
        "BFD multiplier";
    }
    leaf bfd-cfg-remote-ip {
      type inet:ipv4-address;
      description
        "BFD configured remote IP";
    }
    leaf bfd-configured-remote-ipv6-address {
      type inet:ipv6-address;
      description
        "BFD configured remote IPv6";
    }
    leaf state-from-checkpoint {
      type boolean;
      description
        "Whether state recovered from checkpoint";
    }
    leaf interface-ipv4-address {
      type inet:ipv4-address;
      description
        "The Interface Primary IPv4 address";
    }
    leaf interface-ipv6-address {
      type inet:ipv6-address;
      description
        "The Interface linklocal IPv6 address";
    }
    leaf virtual-mac-address {
      type yang:mac-address;
      description
        "Virtual mac address";
    }
    leaf virtual-mac-address-state {
      type Vrrp-vmac-state;
      description
        "Virtual mac address state";
    }
    leaf-list operational-address {
      type inet:ipv4-address;
      description
        "Operational IPv4 VRRP addresses";
    }
    leaf-list ipv4-configured-down-address {
      type inet:ipv4-address;
      description
        "IPv4 Configured but Down VRRP addresses";
    }
    list ipv6-operational-address {
      description
        "IPv6 Operational VRRP addresses";
      uses IPV6-BAG-ADDR;
    }
    list ipv6-configured-down-address {
      description
        "IPv6 Configured but Down VRRP addresses";
      uses IPV6-BAG-ADDR;
    }
    list track-item-info {
      description
        "Track Item Info";
      uses VRRP-TRACKITEM-INFO;
    }
    list state-change-history {
      description
        "State change history";
      uses VRRP-STATE-CHANGE-INFO-TYPE;
    }
  }

  grouping VRRP-TRACKITEM-INFO {
    description
      "Tracked item information";
    leaf interface {
      type xr:Interface-name;
      description
        "IM Interface";
    }
    leaf virtual-router-id-xr {
      type uint32;
      description
        "Virtual Router ID";
    }
    leaf tracked-item-type {
      type uint16;
      description
        "Type of tracked item";
    }
    leaf tracked-item-index {
      type string {
        length "0..32";
      }
      description
        "Tracked item index";
    }
    leaf state {
      type uint8;
      description
        "State of the tracked item";
    }
    leaf priority {
      type uint8;
      description
        "Priority weight of item";
    }
  }

  grouping VRRP-SUMMARY-INFO {
    description
      "VRRP summary statistics";
    leaf ipv4-sessions-master-owner {
      type uint32;
      description
        "Number of IPv4 sessions in MASTER (owner) state";
    }
    leaf ipv4-sessions-master {
      type uint32;
      description
        "Number of IPv4 sessions in MASTER state";
    }
    leaf ipv4-sessions-backup {
      type uint32;
      description
        "Number of IPv4 sessions in BACKUP state";
    }
    leaf ipv4-sessions-init {
      type uint32;
      description
        "Number of IPv4 sessions in INIT state";
    }
    leaf ipv4-slaves-master {
      type uint32;
      description
        "Number of IPv4 slaves in MASTER state";
    }
    leaf ipv4-slaves-backup {
      type uint32;
      description
        "Number of IPv4 slaves in BACKUP state";
    }
    leaf ipv4-slaves-init {
      type uint32;
      description
        "Number of IPv4 slaves in INIT state";
    }
    leaf ipv4-virtual-ip-addresses-master-owner-up {
      type uint32;
      description
        "Number of UP IPv4 Virtual IP Addresses on
         virtual routers in MASTER (owner) state";
    }
    leaf ipv4-virtual-ip-addresses-master-owner-down {
      type uint32;
      description
        "Number of DOWN IPv4 Virtual IP Addresses on
         virtual routers in MASTER (owner) state";
    }
    leaf ipv4-virtual-ip-addresses-master-up {
      type uint32;
      description
        "Number of UP IPv4 Virtual IP Addresses on
         virtual routers in MASTER state";
    }
    leaf ipv4-virtual-ip-addresses-master-down {
      type uint32;
      description
        "Number of DOWN IPv4 Virtual IP Addresses on
         virtual routers in MASTER state";
    }
    leaf ipv4-virtual-ip-addresses-backup-up {
      type uint32;
      description
        "Number of UP IPv4 Virtual IP Addresses on
         virtual routers in BACKUP state";
    }
    leaf ipv4-virtual-ip-addresses-backup-down {
      type uint32;
      description
        "Number of DOWN IPv4 Virtual IP Addresses on
         virtual routers in BACKUP state";
    }
    leaf ipv4-virtual-ip-addresses-init-up {
      type uint32;
      description
        "Number of UP IPv4 Virtual IP Addresses on
         virtual routers in INIT state";
    }
    leaf ipv4-virtual-ip-addresses-init-down {
      type uint32;
      description
        "Number of DOWN IPv4 Virtual IP Addresses on
         virtual routers in INIT state";
    }
    leaf ipv6-sessions-master-owner {
      type uint32;
      description
        "Number of IPv6 sessions in MASTER (owner) state";
    }
    leaf ipv6-sessions-master {
      type uint32;
      description
        "Number of IPv6 sessions in MASTER state";
    }
    leaf ipv6-sessions-backup {
      type uint32;
      description
        "Number of IPv6 sessions in BACKUP state";
    }
    leaf ipv6-sessions-init {
      type uint32;
      description
        "Number of IPv6 sessions in INIT state";
    }
    leaf ipv6-slaves-master {
      type uint32;
      description
        "Number of IPv6 slaves in MASTER state";
    }
    leaf ipv6-slaves-backup {
      type uint32;
      description
        "Number of IPv6 slaves in BACKUP state";
    }
    leaf ipv6-slaves-init {
      type uint32;
      description
        "Number of IPv6 slaves in INIT state";
    }
    leaf ipv6-virtual-ip-addresses-master-owner-up {
      type uint32;
      description
        "Number of UP IPv6 Virtual IP Addresses on
         virtual routers in MASTER (owner) state";
    }
    leaf ipv6-virtual-ip-addresses-master-owner-down {
      type uint32;
      description
        "Number of DOWN IPv6 Virtual IP Addresses on
         virtual routers in MASTER (owner) state";
    }
    leaf ipv6-virtual-ip-addresses-master-up {
      type uint32;
      description
        "Number of UP IPv6 Virtual IP Addresses on
         virtual routers in MASTER state";
    }
    leaf ipv6-virtual-ip-addresses-master-down {
      type uint32;
      description
        "Number of DOWN IPv6 Virtual IP Addresses on
         virtual routers in MASTER state";
    }
    leaf ipv6-virtual-ip-addresses-backup-up {
      type uint32;
      description
        "Number of UP IPv6 Virtual IP Addresses on
         virtual routers in BACKUP state";
    }
    leaf ipv6-virtual-ip-addresses-backup-down {
      type uint32;
      description
        "Number of DOWN IPv6 Virtual IP Addresses on
         virtual routers in BACKUP state";
    }
    leaf ipv6-virtual-ip-addresses-init-up {
      type uint32;
      description
        "Number of UP IPv6 Virtual IP Addresses on
         virtual routers in INIT state";
    }
    leaf ipv6-virtual-ip-addresses-init-down {
      type uint32;
      description
        "Number of DOWN IPv6 Virtual IP Addresses on
         virtual routers in INIT state";
    }
    leaf interfaces-ipv4-state-up {
      type uint32;
      description
        "Number of VRRP interfaces with IPv4 caps in UP
         state";
    }
    leaf interfaces-ipv4-state-down {
      type uint32;
      description
        "Number of VRRP interfaces with IPv4 caps in DOWN
         state";
    }
    leaf tracked-interfaces-ipv4-state-up {
      type uint32;
      description
        "Number of tracked interfaces with IPv4 caps in
         UP state";
    }
    leaf tracked-interfaces-ipv4-state-down {
      type uint32;
      description
        "Number of tracked interfaces with IPv4 caps in
         DOWN state";
    }
    leaf interfaces-ipv6-state-up {
      type uint32;
      description
        "Number of VRRP interfaces with IPv6 caps in UP
         state";
    }
    leaf interfaces-ipv6-state-down {
      type uint32;
      description
        "Number of VRRP interfaces with IPv6 caps in DOWN
         state";
    }
    leaf tracked-interfaces-ipv6-state-up {
      type uint32;
      description
        "Number of tracked interfaces with IPv6 caps in
         UP state";
    }
    leaf tracked-interfaces-ipv6-state-down {
      type uint32;
      description
        "Number of tracked interfaces with IPv6 caps in
         DOWN state";
    }
    leaf tracked-objects-state-up {
      type uint32;
      description
        "Number of tracked objects in UP state";
    }
    leaf tracked-objects-state-down {
      type uint32;
      description
        "Number of tracked objects in DOWN state";
    }
    leaf bfd-sessions-up {
      type uint32;
      description
        "Number of VRRP IPv4 BFD sessions in UP state";
    }
    leaf bfd-sessions-down {
      type uint32;
      description
        "Number of VRRP IPv4 BFD sessions in DOWN state";
    }
    leaf bfd-session-inactive {
      type uint32;
      description
        "Number of VRRP IPv4 BFD sessions in INACTIVE
         state";
    }
    leaf ipv6bfd-sessions-up {
      type uint32;
      description
        "Number of VRRP IPv6 BFD sessions in UP state";
    }
    leaf ipv6bfd-sessions-down {
      type uint32;
      description
        "Number of VRRP IPv6 BFD sessions in DOWN state";
    }
    leaf ipv6bfd-session-inactive {
      type uint32;
      description
        "Number of VRRP IPv6 BFD sessions in INACTIVE
         state";
    }
  }
}

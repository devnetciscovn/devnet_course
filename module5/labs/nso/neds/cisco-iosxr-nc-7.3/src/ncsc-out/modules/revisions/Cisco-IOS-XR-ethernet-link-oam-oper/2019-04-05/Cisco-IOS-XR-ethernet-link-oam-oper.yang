module Cisco-IOS-XR-ethernet-link-oam-oper {
  // Generated by yanger -t ncs
  tailf:mount-id "cisco-iosxr-nc-7.3:cisco-iosxr-nc-7.3";
  tailf:ncs-device-type "netconf";

  namespace "http://cisco.com/ns/yang/Cisco-IOS-XR-ethernet-link-oam-oper";
  prefix ethernet-link-oam-oper;

  import Cisco-IOS-XR-types {
    prefix xr;
  }
  import cisco-semver {
    prefix semver;
  }
  include Cisco-IOS-XR-ethernet-link-oam-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-link-oam package operational data.

     This module contains definitions
     for the following management objects:
       ether-link-oam: Ethernet Link OAM operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container 'ether-link-oam'
  }
  augment "/ncs:devices/ncs:device/ncs:live-status" {
    container ether-link-oam {
      tailf:ncs-device-type "netconf";
      tailf:display-when "not(../../ncs:module) or ../../ncs:module[ncs:name='Cisco-IOS-XR-ethernet-link-oam-oper'] or (../../ncs:live-status-protocol[not(ncs:capability)]) or (../../ncs:live-status-protocol/ncs:capability/ncs:module[.='Cisco-IOS-XR-ethernet-link-oam-oper'])";
      description
        "Ethernet Link OAM operational data";
      container discovery-info-interfaces {
        description
          "Table of Ethernet Link OAM enabled interfaces
           within Discovery Info container";
        list discovery-info-interface {
          key "member-interface";
          description
            "Ethernet Link OAM interface to get Discovery
             Info for";
          leaf member-interface {
            type xr:live_ncs_Interface-name;
            description
              "Member Interface";
          }
          uses live_ncs_ELOD-DISCOVERY-INFO;
        }
      }
      container interface-state-interfaces {
        description
          "Table of Ethernet Link OAM enabled interfaces
           within Interface State container";
        list interface-state-interface {
          key "member-interface";
          description
            "Ethernet Link OAM interface to get Interface
             State for";
          leaf member-interface {
            type xr:live_ncs_Interface-name;
            description
              "Member Interface";
          }
          uses live_ncs_ELOD-INTERFACE-STATE;
        }
      }
      container running-config-interfaces {
        description
          "Table of Ethernet Link OAM enabled interfaces
           within Running Config container";
        list running-config-interface {
          key "member-interface";
          description
            "Ethernet Link OAM interface to get Running
             Config for";
          leaf member-interface {
            type xr:live_ncs_Interface-name;
            description
              "Member Interface";
          }
          uses live_ncs_ELOD-RUNNING-CONFIG;
        }
      }
      container nodes {
        description
          "Node table for node-specific operational data";
        list node {
          key "node-name";
          description
            "Node-specific data for a particular node";
          container summary {
            description
              "Ethernet Link OAM Summary information for the
               entire node";
            uses live_ncs_ELOD-SUMMARY-INFO;
          }
          leaf node-name {
            type xr:live_ncs_Node-id;
            description
              "Node";
          }
        }
      }
      container event-log-entry-interfaces {
        description
          "Table of Ethernet Link OAM enabled interfaces
           within Event Log Entry container";
        list event-log-entry-interface {
          key "member-interface";
          description
            "Ethernet Link OAM enabled interface to get
             Event Log Entry for";
          container event-log-entry-indexes {
            description
              "Table of Ethernet Link OAM Event Log entries
               on the interface";
            list event-log-entry-index {
              key "event-log-entry-index";
              description
                "Ethernet Link OAM Event Log Entry Index to
                 get data for";
              leaf event-log-entry-index {
                type xr:live_ncs_Cisco-ios-xr-string;
                description
                  "Event Log Entry index";
              }
              uses live_ncs_ELOD-LOG-ENTRY;
            }
          }
          leaf member-interface {
            type xr:live_ncs_Interface-name;
            description
              "Member Interface";
          }
        }
      }
      container stats-interfaces {
        description
          "Table of Ethernet Link OAM enabled interfaces
           within Stats container";
        list stats-interface {
          key "member-interface";
          description
            "Ethernet Link OAM interface to get Stats for";
          leaf member-interface {
            type xr:live_ncs_Interface-name;
            description
              "Member Interface";
          }
          uses live_ncs_ELOD-STATS;
        }
      }
    }
  }
  augment "/ncs:devices/ncs:template/ncs:ned-id/ncs:config" {
    // NCS drop config false container 'ether-link-oam'
  }
}

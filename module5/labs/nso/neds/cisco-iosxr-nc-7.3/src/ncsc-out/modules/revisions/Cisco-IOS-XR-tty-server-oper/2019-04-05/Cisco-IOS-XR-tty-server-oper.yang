module Cisco-IOS-XR-tty-server-oper {
  // Generated by yanger -t ncs
  tailf:mount-id "cisco-iosxr-nc-7.3:cisco-iosxr-nc-7.3";
  tailf:ncs-device-type "netconf";

  namespace "http://cisco.com/ns/yang/Cisco-IOS-XR-tty-server-oper";
  prefix tty-server-oper;

  import Cisco-IOS-XR-types {
    prefix xr;
  }
  import cisco-semver {
    prefix semver;
  }
  import Cisco-IOS-XR-tty-management-datatypes {
    prefix dt1;
  }
  include Cisco-IOS-XR-tty-server-oper-sub5 {
    revision-date 2019-04-05;
  }
  include Cisco-IOS-XR-tty-server-oper-sub4 {
    revision-date 2019-04-05;
  }
  include Cisco-IOS-XR-tty-server-oper-sub3 {
    revision-date 2019-04-05;
  }
  include Cisco-IOS-XR-tty-server-oper-sub2 {
    revision-date 2019-04-05;
  }
  include Cisco-IOS-XR-tty-server-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tty-server package operational data.

     This module contains definitions
     for the following management objects:
       tty: TTY Line Configuration

     Copyright (c) 2013-2019 by Cisco Systems, Inc.
     All rights reserved.";

  revision 2019-04-05 {
    description
      "Establish semantic version baseline.";
    semver:module-version "1.0.0";
  }
  revision 2019-02-25 {
    description
      "Fixed unconstrained data type issues";
  }
  revision 2017-09-07 {
    description
      "Fixed type translation error.";
  }
  revision 2015-07-30 {
    description
      "Descriptions updated.";
  }
  revision 2015-01-07 {
    description
      "IOS XR 5.3.1 revision.";
  }

  typedef ncs_template_Line-state {
    type string;
    description
      "Line state";
  }

  typedef ncs_template_Session-operation {
    type string;
    description
      "Session operation";
  }

  typedef ncs_rpc_notif_Line-state {
    type enumeration {
      enum "none" {
        value 0;
        description
          "Line not connected";
      }
      enum "registered" {
        value 1;
        description
          "Line registered";
      }
      enum "in-use" {
        value 2;
        description
          "Line active and in use";
      }
    }
    description
      "Line state";
  }

  typedef ncs_rpc_notif_Session-operation {
    type enumeration {
      enum "none" {
        value 0;
        description
          "No sessions on the line";
      }
      enum "setup" {
        value 1;
        description
          "Session getting set up";
      }
      enum "shell" {
        value 2;
        description
          "Session active with a shell";
      }
      enum "transitioning" {
        value 3;
        description
          "Session in transitioning phase";
      }
      enum "packet" {
        value 4;
        description
          "Session ready to receive packets";
      }
    }
    description
      "Session operation";
  }

  typedef live_ncs_Line-state {
    type enumeration {
      enum "none" {
        value 0;
        description
          "Line not connected";
      }
      enum "registered" {
        value 1;
        description
          "Line registered";
      }
      enum "in-use" {
        value 2;
        description
          "Line active and in use";
      }
    }
    description
      "Line state";
  }

  typedef live_ncs_Session-operation {
    type enumeration {
      enum "none" {
        value 0;
        description
          "No sessions on the line";
      }
      enum "setup" {
        value 1;
        description
          "Session getting set up";
      }
      enum "shell" {
        value 2;
        description
          "Session active with a shell";
      }
      enum "transitioning" {
        value 3;
        description
          "Session in transitioning phase";
      }
      enum "packet" {
        value 4;
        description
          "Session ready to receive packets";
      }
    }
    description
      "Session operation";
  }

  typedef Line-state {
    type enumeration {
      enum "none" {
        value 0;
        description
          "Line not connected";
      }
      enum "registered" {
        value 1;
        description
          "Line registered";
      }
      enum "in-use" {
        value 2;
        description
          "Line active and in use";
      }
    }
    description
      "Line state";
  }

  typedef Session-operation {
    type enumeration {
      enum "none" {
        value 0;
        description
          "No sessions on the line";
      }
      enum "setup" {
        value 1;
        description
          "Session getting set up";
      }
      enum "shell" {
        value 2;
        description
          "Session active with a shell";
      }
      enum "transitioning" {
        value 3;
        description
          "Session in transitioning phase";
      }
      enum "packet" {
        value 4;
        description
          "Session ready to receive packets";
      }
    }
    description
      "Session operation";
  }

  grouping ncs_template_STATE {
    description
      "Common node of console-line, vty-line,
       auxiliary-line";
    container state {
      description
        "Line state information";
      container template {
        description
          "Information related to template applied to the
           line";
        leaf name {
          type xr:ncs_template_Cisco-ios-xr-string;
          description
            "Name of the template";
        }
      }
      container general {
        description
          "General information";
        leaf operation {
          type ncs_template_Session-operation;
          description
            "application running of on the tty line";
        }
        leaf general-state {
          type ncs_template_Line-state;
          description
            "State of the line";
        }
      }
    }
  }

  grouping ncs_template_GENERAL-STATISTICS {
    description
      "Common node of console-statistics, vty-statistics
       , auxiliary-statistics";
    container general-statistics {
      description
        "General statistics of line";
      uses ncs_template_TTY-GENERAL-STATS;
    }
  }

  grouping ncs_template_AAA {
    description
      "Common node of console-statistics, vty-statistics
       , auxiliary-statistics";
    container aaa {
      description
        "AAA related statistics";
      uses ncs_template_TTY-AAA-STATS;
    }
  }

  grouping ncs_template_RS232 {
    description
      "Common node of console-statistics,
       auxiliary-statistics";
    container rs232 {
      description
        "RS232 statistics of console line";
      uses ncs_template_TTY-RS232-STATS;
    }
  }

  grouping ncs_template_EXEC {
    description
      "Common node of console-statistics, vty-statistics
       , auxiliary-statistics";
    container exec {
      description
        "Exec related statistics";
      uses ncs_template_TTY-EXEC-PROP-STATS;
    }
  }

  grouping ncs_template_CONFIGURATION {
    description
      "Common node of console-line, vty-line,
       auxiliary-line";
    container configuration {
      description
        "Configuration information of the line";
      container connection-configuration {
        description
          "Conection configuration information";
        container transport-input {
          description
            "Protocols to use when connecting to the
             terminal server";
          leaf select {
            type dt1:ncs_template_Tty-transport-protocol-select;
            // NCS drop default statement
            description
              "Choose transport protocols";
          }
          leaf protocol1 {
            // NCS drop when statement
            type dt1:ncs_template_Tty-transport-protocol;
            description
              "Transport protocol1";
          }
          leaf protocol2 {
            // NCS drop when statement
            type dt1:ncs_template_Tty-transport-protocol;
            description
              "Transport protocol2";
          }
          leaf none {
            type string;
            description
              "Not used";
          }
        }
        leaf acl-out {
          type xr:ncs_template_Cisco-ios-xr-string;
          description
            "ACL for outbound traffic";
        }
        leaf acl-in {
          type xr:ncs_template_Cisco-ios-xr-string;
          description
            "ACL for inbound traffic";
        }
      }
    }
  }

  grouping ncs_rpc_notif_STATE {
    description
      "Common node of console-line, vty-line,
       auxiliary-line";
    container state {
      description
        "Line state information";
      container template {
        description
          "Information related to template applied to the
           line";
        leaf name {
          type xr:ncs_rpc_notif_Cisco-ios-xr-string;
          description
            "Name of the template";
        }
      }
      container general {
        description
          "General information";
        leaf operation {
          type ncs_rpc_notif_Session-operation;
          description
            "application running of on the tty line";
        }
        leaf general-state {
          type ncs_rpc_notif_Line-state;
          description
            "State of the line";
        }
      }
    }
  }

  grouping ncs_rpc_notif_GENERAL-STATISTICS {
    description
      "Common node of console-statistics, vty-statistics
       , auxiliary-statistics";
    container general-statistics {
      description
        "General statistics of line";
      uses ncs_rpc_notif_TTY-GENERAL-STATS;
    }
  }

  grouping ncs_rpc_notif_AAA {
    description
      "Common node of console-statistics, vty-statistics
       , auxiliary-statistics";
    container aaa {
      description
        "AAA related statistics";
      uses ncs_rpc_notif_TTY-AAA-STATS;
    }
  }

  grouping ncs_rpc_notif_RS232 {
    description
      "Common node of console-statistics,
       auxiliary-statistics";
    container rs232 {
      description
        "RS232 statistics of console line";
      uses ncs_rpc_notif_TTY-RS232-STATS;
    }
  }

  grouping ncs_rpc_notif_EXEC {
    description
      "Common node of console-statistics, vty-statistics
       , auxiliary-statistics";
    container exec {
      description
        "Exec related statistics";
      uses ncs_rpc_notif_TTY-EXEC-PROP-STATS;
    }
  }

  grouping ncs_rpc_notif_CONFIGURATION {
    description
      "Common node of console-line, vty-line,
       auxiliary-line";
    container configuration {
      description
        "Configuration information of the line";
      container connection-configuration {
        description
          "Conection configuration information";
        container transport-input {
          description
            "Protocols to use when connecting to the
             terminal server";
          leaf select {
            type dt1:ncs_rpc_notif_Tty-transport-protocol-select;
            default "all";
            description
              "Choose transport protocols";
          }
          leaf protocol1 {
            when "../select = 'some'" {
              tailf:xpath-root 3;
              description
                "../Select = Some";
            }
            type dt1:ncs_rpc_notif_Tty-transport-protocol;
            description
              "Transport protocol1";
          }
          leaf protocol2 {
            when "../select = 'some'" {
              tailf:xpath-root 3;
              description
                "../Select = Some";
            }
            type dt1:ncs_rpc_notif_Tty-transport-protocol;
            description
              "Transport protocol2";
          }
          leaf none {
            type uint32 {
              range "0..4294967295";
            }
            description
              "Not used";
          }
        }
        leaf acl-out {
          type xr:ncs_rpc_notif_Cisco-ios-xr-string;
          description
            "ACL for outbound traffic";
        }
        leaf acl-in {
          type xr:ncs_rpc_notif_Cisco-ios-xr-string;
          description
            "ACL for inbound traffic";
        }
      }
    }
  }

  grouping live_ncs_STATE {
    description
      "Common node of console-line, vty-line,
       auxiliary-line";
    container state {
      description
        "Line state information";
      container template {
        description
          "Information related to template applied to the
           line";
        leaf name {
          type xr:live_ncs_Cisco-ios-xr-string;
          description
            "Name of the template";
        }
      }
      container general {
        description
          "General information";
        leaf operation {
          type live_ncs_Session-operation;
          description
            "application running of on the tty line";
        }
        leaf general-state {
          type live_ncs_Line-state;
          description
            "State of the line";
        }
      }
    }
  }

  grouping live_ncs_GENERAL-STATISTICS {
    description
      "Common node of console-statistics, vty-statistics
       , auxiliary-statistics";
    container general-statistics {
      description
        "General statistics of line";
      uses live_ncs_TTY-GENERAL-STATS;
    }
  }

  grouping live_ncs_AAA {
    description
      "Common node of console-statistics, vty-statistics
       , auxiliary-statistics";
    container aaa {
      description
        "AAA related statistics";
      uses live_ncs_TTY-AAA-STATS;
    }
  }

  grouping live_ncs_RS232 {
    description
      "Common node of console-statistics,
       auxiliary-statistics";
    container rs232 {
      description
        "RS232 statistics of console line";
      uses live_ncs_TTY-RS232-STATS;
    }
  }

  grouping live_ncs_EXEC {
    description
      "Common node of console-statistics, vty-statistics
       , auxiliary-statistics";
    container exec {
      description
        "Exec related statistics";
      uses live_ncs_TTY-EXEC-PROP-STATS;
    }
  }

  grouping live_ncs_CONFIGURATION {
    description
      "Common node of console-line, vty-line,
       auxiliary-line";
    container configuration {
      description
        "Configuration information of the line";
      container connection-configuration {
        description
          "Conection configuration information";
        container transport-input {
          description
            "Protocols to use when connecting to the
             terminal server";
          leaf select {
            type dt1:live_ncs_Tty-transport-protocol-select;
            // NCS drop default statement
            description
              "Choose transport protocols";
          }
          leaf protocol1 {
            // NCS drop when statement
            type dt1:live_ncs_Tty-transport-protocol;
            description
              "Transport protocol1";
          }
          leaf protocol2 {
            // NCS drop when statement
            type dt1:live_ncs_Tty-transport-protocol;
            description
              "Transport protocol2";
          }
          leaf none {
            type uint32 {
              range "0..4294967295";
            }
            description
              "Not used";
          }
        }
        leaf acl-out {
          type xr:live_ncs_Cisco-ios-xr-string;
          description
            "ACL for outbound traffic";
        }
        leaf acl-in {
          type xr:live_ncs_Cisco-ios-xr-string;
          description
            "ACL for inbound traffic";
        }
      }
    }
  }

  grouping STATE {
    description
      "Common node of console-line, vty-line,
       auxiliary-line";
    container state {
      description
        "Line state information";
      container template {
        description
          "Information related to template applied to the
           line";
        leaf name {
          type xr:Cisco-ios-xr-string {
            length "1..990";
          }
          description
            "Name of the template";
        }
      }
      container general {
        description
          "General information";
        leaf operation {
          type Session-operation;
          description
            "application running of on the tty line";
        }
        leaf general-state {
          type Line-state;
          description
            "State of the line";
        }
      }
    }
  }

  grouping GENERAL-STATISTICS {
    description
      "Common node of console-statistics, vty-statistics
       , auxiliary-statistics";
    container general-statistics {
      description
        "General statistics of line";
      uses TTY-GENERAL-STATS;
    }
  }

  grouping AAA {
    description
      "Common node of console-statistics, vty-statistics
       , auxiliary-statistics";
    container aaa {
      description
        "AAA related statistics";
      uses TTY-AAA-STATS;
    }
  }

  grouping RS232 {
    description
      "Common node of console-statistics,
       auxiliary-statistics";
    container rs232 {
      description
        "RS232 statistics of console line";
      uses TTY-RS232-STATS;
    }
  }

  grouping EXEC {
    description
      "Common node of console-statistics, vty-statistics
       , auxiliary-statistics";
    container exec {
      description
        "Exec related statistics";
      uses TTY-EXEC-PROP-STATS;
    }
  }

  grouping CONFIGURATION {
    description
      "Common node of console-line, vty-line,
       auxiliary-line";
    container configuration {
      description
        "Configuration information of the line";
      container connection-configuration {
        description
          "Conection configuration information";
        container transport-input {
          description
            "Protocols to use when connecting to the
             terminal server";
          leaf select {
            type dt1:Tty-transport-protocol-select;
            default "all";
            description
              "Choose transport protocols";
          }
          leaf protocol1 {
            when "../select = 'some'" {
              tailf:xpath-root 3;
              description
                "../Select = Some";
            }
            type dt1:Tty-transport-protocol;
            description
              "Transport protocol1";
          }
          leaf protocol2 {
            when "../select = 'some'" {
              tailf:xpath-root 3;
              description
                "../Select = Some";
            }
            type dt1:Tty-transport-protocol;
            description
              "Transport protocol2";
          }
          leaf none {
            type uint32 {
              range "0..4294967295";
            }
            description
              "Not used";
          }
        }
        leaf acl-out {
          type xr:Cisco-ios-xr-string {
            length "1..64";
          }
          description
            "ACL for outbound traffic";
        }
        leaf acl-in {
          type xr:Cisco-ios-xr-string {
            length "1..64";
          }
          description
            "ACL for inbound traffic";
        }
      }
    }
  }

  augment "/ncs:devices/ncs:device/ncs:config" {
    // NCS drop config false container tty
  }
  augment "/ncs:devices/ncs:device/ncs:live-status" {
    container tty {
      tailf:ncs-device-type "netconf";
      tailf:display-when "not(../../ncs:module) or ../../ncs:module[ncs:name='Cisco-IOS-XR-tty-server-oper'] or (../../ncs:live-status-protocol[not(ncs:capability)]) or (../../ncs:live-status-protocol/ncs:capability/ncs:module[.='Cisco-IOS-XR-tty-server-oper'])";
      description
        "TTY Line Configuration";
      container console-nodes {
        description
          "List of Nodes for console";
        list console-node {
          key "id";
          description
            "Console line configuration on a node";
          container console-line {
            description
              "Details about console line";
            container console-statistics {
              description
                "Statistics of the console line";
              uses live_ncs_RS232;
              uses live_ncs_GENERAL-STATISTICS;
              uses live_ncs_EXEC;
              uses live_ncs_AAA;
            }
            uses live_ncs_STATE;
            uses live_ncs_CONFIGURATION;
          }
          leaf id {
            type xr:live_ncs_Node-id;
            description
              "Node ID";
          }
        }
      }
      container vty-lines {
        description
          "List of VTY lines";
        list vty-line {
          key "line-number";
          description
            "VTY Line";
          container vty-statistics {
            description
              "Statistics of the VTY line";
            container connection {
              description
                "Connection related statistics";
              uses live_ncs_TTY-CONNECTION-STATS;
            }
            uses live_ncs_GENERAL-STATISTICS;
            uses live_ncs_EXEC;
            uses live_ncs_AAA;
          }
          leaf line-number {
            type uint32 {
              range "0..4294967295";
            }
            description
              "VTY Line number";
          }
          uses live_ncs_STATE;
          uses live_ncs_CONFIGURATION;
        }
      }
      container auxiliary-nodes {
        description
          "List of Nodes attached with an auxiliary line";
        list auxiliary-node {
          key "id";
          description
            "Line configuration on a node";
          container auxiliary-line {
            description
              "Details about auxiliary line";
            container auxiliary-statistics {
              description
                "Statistics of the auxiliary line";
              uses live_ncs_RS232;
              uses live_ncs_GENERAL-STATISTICS;
              uses live_ncs_EXEC;
              uses live_ncs_AAA;
            }
            uses live_ncs_STATE;
            uses live_ncs_CONFIGURATION;
          }
          leaf id {
            type xr:live_ncs_Node-id;
            description
              "Node ID";
          }
        }
      }
    }
  }
  augment "/ncs:devices/ncs:template/ncs:ned-id/ncs:config" {
    // NCS drop config false container tty
  }
}

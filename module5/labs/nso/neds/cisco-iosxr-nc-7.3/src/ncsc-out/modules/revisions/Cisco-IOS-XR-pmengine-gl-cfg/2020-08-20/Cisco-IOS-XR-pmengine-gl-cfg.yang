module Cisco-IOS-XR-pmengine-gl-cfg {
  // Generated by yanger -t ncs
  tailf:mount-id "cisco-iosxr-nc-7.3:cisco-iosxr-nc-7.3";
  tailf:ncs-device-type "netconf";

  namespace "http://cisco.com/ns/yang/Cisco-IOS-XR-pmengine-gl-cfg";
  prefix pmengine-gl-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pmengine-gl package configuration.

     This module contains definitions
     for the following management objects:
       performance-monitor: Configure flex-bin interval

     Copyright (c) 2013-2020 by Cisco Systems, Inc.
     All rights reserved.";

  revision 2020-08-20 {
    description
      "Added new global config for flexbin interval.";
    semver:module-version "1.0.0";
  }
  revision 2019-04-05 {
    description
      "Establish semantic version baseline.";
  }
  revision 2015-11-09 {
    description
      "IOS XR 6.0 revision.";
  }

  augment "/ncs:devices/ncs:device/ncs:config" {
    container performance-monitor {
      tailf:ncs-device-type "netconf";
      tailf:display-when "not(../../ncs:module) or ../../ncs:module[ncs:name='Cisco-IOS-XR-pmengine-gl-cfg']";
      description
        "Configure flex-bin interval";
      container flex-bin {
        description
          "Configure flex-bin interval";
        leaf interval {
          type uint32 {
            range "1..10";
          }
          units "second";
          description
            "Configure the flex-bin interval in seconds <1
             ,10>";
        }
      }
    }
  }
  augment "/ncs:devices/ncs:device/ncs:live-status" {
    container performance-monitor {
      tailf:ncs-device-type "netconf";
      tailf:display-when "not(../../ncs:module) or ../../ncs:module[ncs:name='Cisco-IOS-XR-pmengine-gl-cfg'] or (../../ncs:live-status-protocol[not(ncs:capability)]) or (../../ncs:live-status-protocol/ncs:capability/ncs:module[.='Cisco-IOS-XR-pmengine-gl-cfg'])";
      description
        "Configure flex-bin interval";
      container flex-bin {
        description
          "Configure flex-bin interval";
        leaf interval {
          type uint32 {
            range "1..10";
          }
          units "second";
          description
            "Configure the flex-bin interval in seconds <1
             ,10>";
        }
      }
    }
  }
  augment "/ncs:devices/ncs:template/ncs:ned-id/ncs:config" {
    container performance-monitor {
      description
        "Configure flex-bin interval";
      container flex-bin {
        description
          "Configure flex-bin interval";
        leaf interval {
          type string;
          units "second";
          description
            "Configure the flex-bin interval in seconds <1
             ,10>";
        }
      }
    }
  }
}

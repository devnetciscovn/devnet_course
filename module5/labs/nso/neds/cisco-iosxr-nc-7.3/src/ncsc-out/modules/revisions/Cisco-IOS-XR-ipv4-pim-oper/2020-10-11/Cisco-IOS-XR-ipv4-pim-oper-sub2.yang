submodule Cisco-IOS-XR-ipv4-pim-oper-sub2 {
  // Generated by yanger -t ncs
  tailf:mount-id "cisco-iosxr-nc-7.3:cisco-iosxr-nc-7.3";

  belongs-to Cisco-IOS-XR-ipv4-pim-oper {
    prefix Cisco-IOS-XR-ipv4-pim-oper;
  }

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv4-pim package operational data.

     This model is deprecated and is replaced by
     Cisco-IOS-XR-pim-oper.yang which will provide the
     compatible functionalities.

     Copyright (c) 2013-2020 by Cisco Systems, Inc.
     All rights reserved.";

  revision 2020-10-11 {
    description
      "Changes to IOS-XR PIM oper";
    semver:module-version "2.1.0";
  }
  revision 2019-10-31 {
    description
      "Changes to IOS-XR PIM oper
       2019-08-27
       Providing pim information";
    semver:module-version "2.0.0";
  }
  revision 2019-04-05 {
    description
      "Establish semantic version baseline.";
    semver:module-version "1.0.0";
  }
  revision 2017-09-07 {
    description
      "Fixed type translation error.";
  }
  revision 2017-06-26 {
    description
      "Change identifiers to be more readable.";
  }
  revision 2017-05-27 {
    description
      "Removed deprecated leaves under traffic-counters. Added missing leaves under context. Removed checkpoint-statistics container because the corresponding CLI command requires cisco-support permissions.";
  }
  revision 2015-11-09 {
    description
      "IOS XR 6.0 revision.";
  }

  typedef ncs_template_Ipv6-address {
    type string;
    description
      "IPV6 Address type";
  }

  typedef ncs_template_Pim-afi {
    type string;
    description
      "Address family";
  }

  typedef ncs_template_Pim-interface {
    type string;
    description
      "Interface Type";
  }

  typedef ncs_rpc_notif_Ipv6-address {
    type inet:ipv6-address;
    description
      "IPV6 Address type";
  }

  typedef ncs_rpc_notif_Pim-afi {
    type enumeration {
      enum "ipv4-unicast" {
        value 0;
        description
          "IP v4 unicast";
      }
      enum "ipv6-unicast" {
        value 1;
        description
          "IP v6 unicast";
      }
    }
    description
      "Address family";
  }

  typedef ncs_rpc_notif_Pim-interface {
    type enumeration {
      enum "encap-interface" {
        value 0;
        description
          "Encap Interface";
      }
      enum "decap-interface" {
        value 1;
        description
          "Decap Interface";
      }
      enum "mdt-interface" {
        value 2;
        description
          "MDT Interface";
      }
    }
    description
      "Interface Type";
  }

  typedef live_ncs_Ipv6-address {
    type inet:ipv6-address;
    description
      "IPV6 Address type";
  }

  typedef live_ncs_Pim-afi {
    type enumeration {
      enum "ipv4-unicast" {
        value 0;
        description
          "IP v4 unicast";
      }
      enum "ipv6-unicast" {
        value 1;
        description
          "IP v6 unicast";
      }
    }
    description
      "Address family";
  }

  typedef live_ncs_Pim-interface {
    type enumeration {
      enum "encap-interface" {
        value 0;
        description
          "Encap Interface";
      }
      enum "decap-interface" {
        value 1;
        description
          "Decap Interface";
      }
      enum "mdt-interface" {
        value 2;
        description
          "MDT Interface";
      }
    }
    description
      "Interface Type";
  }

  typedef Ipv6-address {
    type inet:ipv6-address;
    description
      "IPV6 Address type";
  }

  typedef Pim-afi {
    type enumeration {
      enum "ipv4-unicast" {
        value 0;
        description
          "IP v4 unicast";
      }
      enum "ipv6-unicast" {
        value 1;
        description
          "IP v6 unicast";
      }
    }
    description
      "Address family";
  }

  typedef Pim-interface {
    type enumeration {
      enum "encap-interface" {
        value 0;
        description
          "Encap Interface";
      }
      enum "decap-interface" {
        value 1;
        description
          "Decap Interface";
      }
      enum "mdt-interface" {
        value 2;
        description
          "MDT Interface";
      }
    }
    description
      "Interface Type";
  }

  grouping ncs_template_PIM-MA-SUMMARY {
    description
      "PIM MA Summary";
    leaf is-im-connection-open {
      type string;
      description
        "IM Connection Open";
    }
    leaf is-netio-connection-open {
      type string;
      description
        "Netio Connection Open";
    }
    leaf is-edm-connection-open {
      type string;
      description
        "EDM Connection Open";
    }
    leaf is-standby-edm-connection-open {
      type string;
      description
        "Standby EDM Connection Open";
    }
    leaf encap-interface-count {
      type string;
      description
        "Encap Interface Count";
    }
    leaf decap-interface-count {
      type string;
      description
        "Decap Interface Count";
    }
    leaf mdt-interface-count {
      type string;
      description
        "MDT Interface Count";
    }
  }

  grouping ncs_template_PIM-ADDRTYPE {
    description
      "PIM ADDRTYPE";
    leaf af-name {
      type ncs_template_Pim-afi;
      description
        "AFName";
    }
    leaf ipv4-address {
      // NCS drop when statement
      type string;
      description
        "IPv4 Address";
    }
    leaf ipv6-address {
      // NCS drop when statement
      type ncs_template_Ipv6-address;
      description
        "IPV6 Address";
    }
  }

  grouping ncs_template_PIM-MA-IDB {
    description
      "PIM MA interface";
    container rp-address {
      description
        "RP Address";
      uses ncs_template_PIM-ADDRTYPE;
    }
    container source-address {
      description
        "Source Address";
      uses ncs_template_PIM-ADDRTYPE;
    }
    leaf interface-name-xr {
      type xr:ncs_template_Interface-name;
      description
        "Interface Name";
    }
    leaf vrf-name {
      type string;
      description
        "VRF Name";
    }
    leaf interface-type {
      type ncs_template_Pim-interface;
      description
        "Interface Type";
    }
  }

  grouping ncs_rpc_notif_PIM-MA-SUMMARY {
    description
      "PIM MA Summary";
    leaf is-im-connection-open {
      type boolean;
      description
        "IM Connection Open";
    }
    leaf is-netio-connection-open {
      type boolean;
      description
        "Netio Connection Open";
    }
    leaf is-edm-connection-open {
      type boolean;
      description
        "EDM Connection Open";
    }
    leaf is-standby-edm-connection-open {
      type boolean;
      description
        "Standby EDM Connection Open";
    }
    leaf encap-interface-count {
      type uint32;
      description
        "Encap Interface Count";
    }
    leaf decap-interface-count {
      type uint32;
      description
        "Decap Interface Count";
    }
    leaf mdt-interface-count {
      type uint32;
      description
        "MDT Interface Count";
    }
  }

  grouping ncs_rpc_notif_PIM-ADDRTYPE {
    description
      "PIM ADDRTYPE";
    leaf af-name {
      type ncs_rpc_notif_Pim-afi;
      description
        "AFName";
    }
    leaf ipv4-address {
      when "../af-name = 'ipv4-unicast'" {
        tailf:xpath-root 3;
        description
          "../AFName = 'IPv4Unicast'";
      }
      type inet:ipv4-address;
      description
        "IPv4 Address";
    }
    leaf ipv6-address {
      when "../af-name = 'ipv6-unicast'" {
        tailf:xpath-root 3;
        description
          "../AFName = 'IPv6Unicast'";
      }
      type ncs_rpc_notif_Ipv6-address;
      description
        "IPV6 Address";
    }
  }

  grouping ncs_rpc_notif_PIM-MA-IDB {
    description
      "PIM MA interface";
    container rp-address {
      description
        "RP Address";
      uses ncs_rpc_notif_PIM-ADDRTYPE;
    }
    container source-address {
      description
        "Source Address";
      uses ncs_rpc_notif_PIM-ADDRTYPE;
    }
    leaf interface-name-xr {
      type xr:ncs_rpc_notif_Interface-name;
      description
        "Interface Name";
    }
    leaf vrf-name {
      type string;
      description
        "VRF Name";
    }
    leaf interface-type {
      type ncs_rpc_notif_Pim-interface;
      description
        "Interface Type";
    }
  }

  grouping live_ncs_PIM-MA-SUMMARY {
    description
      "PIM MA Summary";
    leaf is-im-connection-open {
      type boolean;
      description
        "IM Connection Open";
    }
    leaf is-netio-connection-open {
      type boolean;
      description
        "Netio Connection Open";
    }
    leaf is-edm-connection-open {
      type boolean;
      description
        "EDM Connection Open";
    }
    leaf is-standby-edm-connection-open {
      type boolean;
      description
        "Standby EDM Connection Open";
    }
    leaf encap-interface-count {
      type uint32;
      description
        "Encap Interface Count";
    }
    leaf decap-interface-count {
      type uint32;
      description
        "Decap Interface Count";
    }
    leaf mdt-interface-count {
      type uint32;
      description
        "MDT Interface Count";
    }
  }

  grouping live_ncs_PIM-ADDRTYPE {
    description
      "PIM ADDRTYPE";
    leaf af-name {
      type live_ncs_Pim-afi;
      description
        "AFName";
    }
    leaf ipv4-address {
      // NCS drop when statement
      type inet:ipv4-address;
      description
        "IPv4 Address";
    }
    leaf ipv6-address {
      // NCS drop when statement
      type live_ncs_Ipv6-address;
      description
        "IPV6 Address";
    }
  }

  grouping live_ncs_PIM-MA-IDB {
    description
      "PIM MA interface";
    container rp-address {
      description
        "RP Address";
      uses live_ncs_PIM-ADDRTYPE;
    }
    container source-address {
      description
        "Source Address";
      uses live_ncs_PIM-ADDRTYPE;
    }
    leaf interface-name-xr {
      type xr:live_ncs_Interface-name;
      description
        "Interface Name";
    }
    leaf vrf-name {
      type string;
      description
        "VRF Name";
    }
    leaf interface-type {
      type live_ncs_Pim-interface;
      description
        "Interface Type";
    }
  }

  grouping PIM-MA-SUMMARY {
    description
      "PIM MA Summary";
    leaf is-im-connection-open {
      type boolean;
      description
        "IM Connection Open";
    }
    leaf is-netio-connection-open {
      type boolean;
      description
        "Netio Connection Open";
    }
    leaf is-edm-connection-open {
      type boolean;
      description
        "EDM Connection Open";
    }
    leaf is-standby-edm-connection-open {
      type boolean;
      description
        "Standby EDM Connection Open";
    }
    leaf encap-interface-count {
      type uint32;
      description
        "Encap Interface Count";
    }
    leaf decap-interface-count {
      type uint32;
      description
        "Decap Interface Count";
    }
    leaf mdt-interface-count {
      type uint32;
      description
        "MDT Interface Count";
    }
  }

  grouping PIM-ADDRTYPE {
    description
      "PIM ADDRTYPE";
    leaf af-name {
      type Pim-afi;
      description
        "AFName";
    }
    leaf ipv4-address {
      when "../af-name = 'ipv4-unicast'" {
        tailf:xpath-root 3;
        description
          "../AFName = 'IPv4Unicast'";
      }
      type inet:ipv4-address;
      description
        "IPv4 Address";
    }
    leaf ipv6-address {
      when "../af-name = 'ipv6-unicast'" {
        tailf:xpath-root 3;
        description
          "../AFName = 'IPv6Unicast'";
      }
      type Ipv6-address;
      description
        "IPV6 Address";
    }
  }

  grouping PIM-MA-IDB {
    description
      "PIM MA interface";
    container rp-address {
      description
        "RP Address";
      uses PIM-ADDRTYPE;
    }
    container source-address {
      description
        "Source Address";
      uses PIM-ADDRTYPE;
    }
    leaf interface-name-xr {
      type xr:Interface-name;
      description
        "Interface Name";
    }
    leaf vrf-name {
      type string;
      description
        "VRF Name";
    }
    leaf interface-type {
      type Pim-interface;
      description
        "Interface Type";
    }
  }
}

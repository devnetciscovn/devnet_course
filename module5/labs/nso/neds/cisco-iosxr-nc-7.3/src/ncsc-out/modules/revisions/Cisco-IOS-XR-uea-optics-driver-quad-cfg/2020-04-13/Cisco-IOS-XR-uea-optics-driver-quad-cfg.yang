module Cisco-IOS-XR-uea-optics-driver-quad-cfg {
  // Generated by yanger -t ncs
  tailf:mount-id "cisco-iosxr-nc-7.3:cisco-iosxr-nc-7.3";
  tailf:ncs-device-type "netconf";

  namespace "http://cisco.com/ns/yang/Cisco-IOS-XR-uea-optics-driver-quad-cfg";
  prefix uea-optics-driver-quad-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR uea-optics-driver-quad package configuration.

     This module contains definitions
     for the following management objects:
       node: HW module Quad Config

     Copyright (c) 2013-2020 by Cisco Systems, Inc.
     All rights reserved.";

  revision 2020-04-13 {
    description
      "Schema added.";
    semver:module-version "1.0.0";
  }
  revision 2019-04-05 {
    description
      "Establish semantic version baseline.";
  }
  revision 2015-11-09 {
    description
      "IOS XR 6.0 revision.";
  }

  augment "/ncs:devices/ncs:device/ncs:config" {
    container node {
      tailf:ncs-device-type "netconf";
      tailf:display-when "not(../../ncs:module) or ../../ncs:module[ncs:name='Cisco-IOS-XR-uea-optics-driver-quad-cfg']";
      description
        "HW module Quad Config";
      container slot-configs {
        description
          "slot configuration";
        list slot-config {
          key "id2";
          description
            "none";
          container quad-configs {
            description
              "quad configuration";
            list quad-config {
              key "id1";
              description
                "none";
              container mode {
                description
                  "select mode 10g or 25g or 50g for a
                   quad(group of 4 ports).";
                leaf speed {
                  type string;
                  description
                    "speed 10g or 25g or 50g";
                }
              }
              leaf id1 {
                type uint32;
                description
                  "none";
              }
            }
          }
          leaf id2 {
            type uint32;
            description
              "none";
          }
        }
      }
    }
  }
  augment "/ncs:devices/ncs:device/ncs:live-status" {
    container node {
      tailf:ncs-device-type "netconf";
      tailf:display-when "not(../../ncs:module) or ../../ncs:module[ncs:name='Cisco-IOS-XR-uea-optics-driver-quad-cfg'] or (../../ncs:live-status-protocol[not(ncs:capability)]) or (../../ncs:live-status-protocol/ncs:capability/ncs:module[.='Cisco-IOS-XR-uea-optics-driver-quad-cfg'])";
      description
        "HW module Quad Config";
      container slot-configs {
        description
          "slot configuration";
        list slot-config {
          key "id2";
          description
            "none";
          container quad-configs {
            description
              "quad configuration";
            list quad-config {
              key "id1";
              description
                "none";
              container mode {
                description
                  "select mode 10g or 25g or 50g for a
                   quad(group of 4 ports).";
                leaf speed {
                  type string;
                  description
                    "speed 10g or 25g or 50g";
                }
              }
              leaf id1 {
                type uint32;
                description
                  "none";
              }
            }
          }
          leaf id2 {
            type uint32;
            description
              "none";
          }
        }
      }
    }
  }
  augment "/ncs:devices/ncs:template/ncs:ned-id/ncs:config" {
    container node {
      description
        "HW module Quad Config";
      container slot-configs {
        description
          "slot configuration";
        list slot-config {
          // NCS patched for predictable order
          ordered-by user;
          key "id2";
          description
            "none";
          container quad-configs {
            description
              "quad configuration";
            list quad-config {
              // NCS patched for predictable order
              ordered-by user;
              key "id1";
              description
                "none";
              container mode {
                description
                  "select mode 10g or 25g or 50g for a
                   quad(group of 4 ports).";
                leaf speed {
                  type string;
                  description
                    "speed 10g or 25g or 50g";
                }
              }
              leaf id1 {
                type string;
                description
                  "none";
              }
            }
          }
          leaf id2 {
            type string;
            description
              "none";
          }
        }
      }
    }
  }
}

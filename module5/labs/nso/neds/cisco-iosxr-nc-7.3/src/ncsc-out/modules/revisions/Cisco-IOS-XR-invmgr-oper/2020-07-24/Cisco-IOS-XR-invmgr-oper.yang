module Cisco-IOS-XR-invmgr-oper {
  // Generated by yanger -t ncs
  tailf:mount-id "cisco-iosxr-nc-7.3:cisco-iosxr-nc-7.3";
  tailf:ncs-device-type "netconf";

  namespace "http://cisco.com/ns/yang/Cisco-IOS-XR-invmgr-oper";
  prefix invmgr-oper;

  import Cisco-IOS-XR-types {
    prefix xr;
  }
  import cisco-semver {
    prefix semver;
  }
  include Cisco-IOS-XR-invmgr-oper-sub4 {
    revision-date 2020-07-24;
  }
  include Cisco-IOS-XR-invmgr-oper-sub3 {
    revision-date 2020-07-24;
  }
  include Cisco-IOS-XR-invmgr-oper-sub2 {
    revision-date 2020-07-24;
  }
  include Cisco-IOS-XR-invmgr-oper-sub1 {
    revision-date 2020-07-24;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR invmgr package operational data.

     This module contains definitions
     for the following management objects:
       inventory: Inventory information

     Copyright (c) 2013-2020 by Cisco Systems, Inc.
     All rights reserved.";

  revision 2020-07-24 {
    description
      "IOS XR 7.0.14 revision. Modified eeprom_bag to match eXR
       2020-07-24
         Addition of revision to match LNT.";
    semver:module-version "3.0.0";
  }
  revision 2020-05-08 {
    description
      "Deprecated Inventory:Rack container.
       2020-03-30
       Changed threshold-value type to int32.
       2019-10-07
       Added pluggable-info bag.
       2019-10-04
       Removed slot-info, vm-done bags.";
    semver:module-version "2.0.0";
  }
  revision 2019-04-05 {
    description
      "Establish semantic version baseline.";
    semver:module-version "1.0.0";
  }
  revision 2019-03-21 {
    description
      "Resolved string constraints issue.";
  }
  revision 2018-08-03 {
    description
      "Added slot-info and parent-info bags.";
  }
  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  grouping ncs_template_THRESH-BAG {
    description
      "Common node of minor-lo, minor-hi, major-lo,
       major-hi, critical-lo, critical-hi";
    container thresh-bag {
      status deprecated;
      description
        "Environment threshold info";
      uses ncs_template_ENVMON-THRESHOLD-INFO;
    }
  }

  grouping ncs_template_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ncs_template_ENVMON-THRESHOLD-INFO;
    }
  }

  grouping ncs_template_ATTRIBUTES {
    description
      "Common node of rack, slot, tsi1, tsi2, tsi3, tsi4
       , tsi5, tsi6, tsi7, tsi8, tsi9, tsi10, tsi11";
    container attributes {
      status deprecated;
      description
        "Shows the different attributes or status of each
         entity or component in inventory";
      container inv-basic-bag {
        status deprecated;
        description
          "Inventory Basic Bag";
        uses ncs_template_INV-PHY-ENTITY-BASIC-INFO;
      }
      container env-sensor-info {
        status deprecated;
        description
          "Environment sensor info";
        uses ncs_template_ENVMON-SENSOR-INFO;
      }
      container pwg-info {
        status deprecated;
        description
          "Inventory EDM PWG info";
        uses ncs_template_INV-PWG-INFO;
      }
      container env-sensor-info-xml {
        status deprecated;
        description
          "Environment sensor info XML";
        uses ncs_template_ENVMON-SENSOR-INFO-XML;
      }
      container inv-asset-bag {
        status deprecated;
        description
          "Inventory Asset Bag";
        uses ncs_template_INV-PHY-ENTITY-ASSET-INFO;
      }
      container threshold {
        status deprecated;
        description
          "Temperature alarm data for platform components";
        container major-lo {
          status deprecated;
          description
            "Major Low";
          uses ncs_template_INVMGR-EXT1-OPER-THRESH-BAG;
        }
        container critical-hi {
          status deprecated;
          description
            "Critical High";
          uses ncs_template_INVMGR-EXT1-OPER-THRESH-BAG;
        }
        container minor-hi {
          status deprecated;
          description
            "Minor High";
          uses ncs_template_INVMGR-EXT1-OPER-THRESH-BAG;
        }
        container major-hi {
          status deprecated;
          description
            "Major High";
          uses ncs_template_INVMGR-EXT1-OPER-THRESH-BAG;
        }
        container critical-lo {
          status deprecated;
          description
            "Critical Low";
          uses ncs_template_INVMGR-EXT1-OPER-THRESH-BAG;
        }
        container minor-lo {
          status deprecated;
          description
            "Minor Low";
          uses ncs_template_INVMGR-EXT1-OPER-THRESH-BAG;
        }
      }
      container fru-info {
        status deprecated;
        description
          "Inventory EDM FRU info";
        uses ncs_template_INV-CARD-FRU-INFO;
      }
      container inv-eeprom-info {
        status deprecated;
        description
          "Inventory EDM EEPROM Information Bag";
        uses ncs_template_INVMGR-EEPROM-OPAQUE-DATA;
      }
    }
  }

  grouping ncs_template_SLOT {
    description
      "Common node of powershelf, fantray, entity";
    list slot {
      // NCS patched for predictable order
      ordered-by user;
      key "name";
      status deprecated;
      description
        "Slot number";
      container tsi1s {
        status deprecated;
        description
          "Entity Level 1";
        list tsi1 {
          // NCS patched for predictable order
          ordered-by user;
          key "name";
          status deprecated;
          description
            "TSI1";
          container tsi2s {
            status deprecated;
            description
              "Entity Level 2";
            list tsi2 {
              // NCS patched for predictable order
              ordered-by user;
              key "name";
              status deprecated;
              description
                "TSI2";
              container tsi3s {
                status deprecated;
                description
                  "Entity Level 3";
                list tsi3 {
                  // NCS patched for predictable order
                  ordered-by user;
                  key "name";
                  status deprecated;
                  description
                    "TSI3";
                  container tsi4s {
                    status deprecated;
                    description
                      "Entity Level 4";
                    list tsi4 {
                      // NCS patched for predictable order
                      ordered-by user;
                      key "name";
                      status deprecated;
                      description
                        "TSI4";
                      container tsi5s {
                        status deprecated;
                        description
                          "Entity Level 5";
                        list tsi5 {
                          // NCS patched for predictable order
                          ordered-by user;
                          key "name";
                          status deprecated;
                          description
                            "TSI5";
                          container tsi6s {
                            status deprecated;
                            description
                              "Entity Level 6";
                            list tsi6 {
                              // NCS patched for predictable order
                              ordered-by user;
                              key "name";
                              status deprecated;
                              description
                                "TSI6";
                              container tsi7s {
                                status deprecated;
                                description
                                  "Entity Level 7";
                                list tsi7 {
                                  // NCS patched for predictable order
                                  ordered-by user;
                                  key "name";
                                  status deprecated;
                                  description
                                    "TSI7";
                                  container tsi8s {
                                    status deprecated;
                                    description
                                      "Entity Level 8";
                                    list tsi8 {
                                      // NCS patched for predictable order
                                      ordered-by user;
                                      key "name";
                                      status deprecated;
                                      description
                                        "TSI8";
                                      container tsi9s {
                                        status deprecated;
                                        description
                                          "Entity Level 9";
                                        list tsi9 {
                                          // NCS patched for predictable order
                                          ordered-by user;
                                          key "name";
                                          status deprecated;
                                          description
                                            "TSI9";
                                          container tsi10s {
                                            status deprecated;
                                            description
                                              "Entity Level 10";
                                            list tsi10 {
                                              // NCS patched for predictable order
                                              ordered-by user;
                                              key "name";
                                              status deprecated;
                                              description
                                                "TSI10";
                                              container tsi11s {
                                                status deprecated;
                                                description
                                                  "Entity Level 11";
                                                list tsi11 {
                                                  // NCS patched for predictable order
                                                  ordered-by user;
                                                  key "name";
                                                  status deprecated;
                                                  description
                                                    "TSI11";
                                                  leaf name {
                                                    type xr:ncs_template_Cisco-ios-xr-string;
                                                    description
                                                      "TSI11";
                                                  }
                                                  uses ncs_template_ATTRIBUTES;
                                                }
                                              }
                                              leaf name {
                                                type xr:ncs_template_Cisco-ios-xr-string;
                                                description
                                                  "TSI10";
                                              }
                                              uses ncs_template_ATTRIBUTES;
                                            }
                                          }
                                          leaf name {
                                            type xr:ncs_template_Cisco-ios-xr-string;
                                            description
                                              "TSI9";
                                          }
                                          uses ncs_template_ATTRIBUTES;
                                        }
                                      }
                                      leaf name {
                                        type xr:ncs_template_Cisco-ios-xr-string;
                                        description
                                          "TSI8";
                                      }
                                      uses ncs_template_ATTRIBUTES;
                                    }
                                  }
                                  leaf name {
                                    type xr:ncs_template_Cisco-ios-xr-string;
                                    description
                                      "TSI7";
                                  }
                                  uses ncs_template_ATTRIBUTES;
                                }
                              }
                              leaf name {
                                type xr:ncs_template_Cisco-ios-xr-string;
                                description
                                  "TSI6";
                              }
                              uses ncs_template_ATTRIBUTES;
                            }
                          }
                          leaf name {
                            type xr:ncs_template_Cisco-ios-xr-string;
                            description
                              "TSI5";
                          }
                          uses ncs_template_ATTRIBUTES;
                        }
                      }
                      leaf name {
                        type xr:ncs_template_Cisco-ios-xr-string;
                        description
                          "TSI4";
                      }
                      uses ncs_template_ATTRIBUTES;
                    }
                  }
                  leaf name {
                    type xr:ncs_template_Cisco-ios-xr-string;
                    description
                      "TSI3";
                  }
                  uses ncs_template_ATTRIBUTES;
                }
              }
              leaf name {
                type xr:ncs_template_Cisco-ios-xr-string;
                description
                  "TSI2";
              }
              uses ncs_template_ATTRIBUTES;
            }
          }
          leaf name {
            type xr:ncs_template_Cisco-ios-xr-string;
            description
              "TSI1";
          }
          uses ncs_template_ATTRIBUTES;
        }
      }
      leaf name {
        type xr:ncs_template_Cisco-ios-xr-string;
        description
          "Slot name";
      }
      uses ncs_template_ATTRIBUTES;
    }
  }

  grouping ncs_rpc_notif_THRESH-BAG {
    description
      "Common node of minor-lo, minor-hi, major-lo,
       major-hi, critical-lo, critical-hi";
    container thresh-bag {
      status deprecated;
      description
        "Environment threshold info";
      uses ncs_rpc_notif_ENVMON-THRESHOLD-INFO;
    }
  }

  grouping ncs_rpc_notif_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ncs_rpc_notif_ENVMON-THRESHOLD-INFO;
    }
  }

  grouping ncs_rpc_notif_ATTRIBUTES {
    description
      "Common node of rack, slot, tsi1, tsi2, tsi3, tsi4
       , tsi5, tsi6, tsi7, tsi8, tsi9, tsi10, tsi11";
    container attributes {
      status deprecated;
      description
        "Shows the different attributes or status of each
         entity or component in inventory";
      container inv-basic-bag {
        status deprecated;
        description
          "Inventory Basic Bag";
        uses ncs_rpc_notif_INV-PHY-ENTITY-BASIC-INFO;
      }
      container env-sensor-info {
        status deprecated;
        description
          "Environment sensor info";
        uses ncs_rpc_notif_ENVMON-SENSOR-INFO;
      }
      container pwg-info {
        status deprecated;
        description
          "Inventory EDM PWG info";
        uses ncs_rpc_notif_INV-PWG-INFO;
      }
      container env-sensor-info-xml {
        status deprecated;
        description
          "Environment sensor info XML";
        uses ncs_rpc_notif_ENVMON-SENSOR-INFO-XML;
      }
      container inv-asset-bag {
        status deprecated;
        description
          "Inventory Asset Bag";
        uses ncs_rpc_notif_INV-PHY-ENTITY-ASSET-INFO;
      }
      container threshold {
        status deprecated;
        description
          "Temperature alarm data for platform components";
        container major-lo {
          status deprecated;
          description
            "Major Low";
          uses ncs_rpc_notif_INVMGR-EXT1-OPER-THRESH-BAG;
        }
        container critical-hi {
          status deprecated;
          description
            "Critical High";
          uses ncs_rpc_notif_INVMGR-EXT1-OPER-THRESH-BAG;
        }
        container minor-hi {
          status deprecated;
          description
            "Minor High";
          uses ncs_rpc_notif_INVMGR-EXT1-OPER-THRESH-BAG;
        }
        container major-hi {
          status deprecated;
          description
            "Major High";
          uses ncs_rpc_notif_INVMGR-EXT1-OPER-THRESH-BAG;
        }
        container critical-lo {
          status deprecated;
          description
            "Critical Low";
          uses ncs_rpc_notif_INVMGR-EXT1-OPER-THRESH-BAG;
        }
        container minor-lo {
          status deprecated;
          description
            "Minor Low";
          uses ncs_rpc_notif_INVMGR-EXT1-OPER-THRESH-BAG;
        }
      }
      container fru-info {
        status deprecated;
        description
          "Inventory EDM FRU info";
        uses ncs_rpc_notif_INV-CARD-FRU-INFO;
      }
      container inv-eeprom-info {
        status deprecated;
        description
          "Inventory EDM EEPROM Information Bag";
        uses ncs_rpc_notif_INVMGR-EEPROM-OPAQUE-DATA;
      }
    }
  }

  grouping ncs_rpc_notif_SLOT {
    description
      "Common node of powershelf, fantray, entity";
    list slot {
      key "name";
      status deprecated;
      description
        "Slot number";
      container tsi1s {
        status deprecated;
        description
          "Entity Level 1";
        list tsi1 {
          key "name";
          status deprecated;
          description
            "TSI1";
          container tsi2s {
            status deprecated;
            description
              "Entity Level 2";
            list tsi2 {
              key "name";
              status deprecated;
              description
                "TSI2";
              container tsi3s {
                status deprecated;
                description
                  "Entity Level 3";
                list tsi3 {
                  key "name";
                  status deprecated;
                  description
                    "TSI3";
                  container tsi4s {
                    status deprecated;
                    description
                      "Entity Level 4";
                    list tsi4 {
                      key "name";
                      status deprecated;
                      description
                        "TSI4";
                      container tsi5s {
                        status deprecated;
                        description
                          "Entity Level 5";
                        list tsi5 {
                          key "name";
                          status deprecated;
                          description
                            "TSI5";
                          container tsi6s {
                            status deprecated;
                            description
                              "Entity Level 6";
                            list tsi6 {
                              key "name";
                              status deprecated;
                              description
                                "TSI6";
                              container tsi7s {
                                status deprecated;
                                description
                                  "Entity Level 7";
                                list tsi7 {
                                  key "name";
                                  status deprecated;
                                  description
                                    "TSI7";
                                  container tsi8s {
                                    status deprecated;
                                    description
                                      "Entity Level 8";
                                    list tsi8 {
                                      key "name";
                                      status deprecated;
                                      description
                                        "TSI8";
                                      container tsi9s {
                                        status deprecated;
                                        description
                                          "Entity Level 9";
                                        list tsi9 {
                                          key "name";
                                          status deprecated;
                                          description
                                            "TSI9";
                                          container tsi10s {
                                            status deprecated;
                                            description
                                              "Entity Level 10";
                                            list tsi10 {
                                              key "name";
                                              status deprecated;
                                              description
                                                "TSI10";
                                              container tsi11s {
                                                status deprecated;
                                                description
                                                  "Entity Level 11";
                                                list tsi11 {
                                                  key "name";
                                                  status deprecated;
                                                  description
                                                    "TSI11";
                                                  leaf name {
                                                    type xr:ncs_rpc_notif_Cisco-ios-xr-string;
                                                    description
                                                      "TSI11";
                                                  }
                                                  uses ncs_rpc_notif_ATTRIBUTES;
                                                }
                                              }
                                              leaf name {
                                                type xr:ncs_rpc_notif_Cisco-ios-xr-string;
                                                description
                                                  "TSI10";
                                              }
                                              uses ncs_rpc_notif_ATTRIBUTES;
                                            }
                                          }
                                          leaf name {
                                            type xr:ncs_rpc_notif_Cisco-ios-xr-string;
                                            description
                                              "TSI9";
                                          }
                                          uses ncs_rpc_notif_ATTRIBUTES;
                                        }
                                      }
                                      leaf name {
                                        type xr:ncs_rpc_notif_Cisco-ios-xr-string;
                                        description
                                          "TSI8";
                                      }
                                      uses ncs_rpc_notif_ATTRIBUTES;
                                    }
                                  }
                                  leaf name {
                                    type xr:ncs_rpc_notif_Cisco-ios-xr-string;
                                    description
                                      "TSI7";
                                  }
                                  uses ncs_rpc_notif_ATTRIBUTES;
                                }
                              }
                              leaf name {
                                type xr:ncs_rpc_notif_Cisco-ios-xr-string;
                                description
                                  "TSI6";
                              }
                              uses ncs_rpc_notif_ATTRIBUTES;
                            }
                          }
                          leaf name {
                            type xr:ncs_rpc_notif_Cisco-ios-xr-string;
                            description
                              "TSI5";
                          }
                          uses ncs_rpc_notif_ATTRIBUTES;
                        }
                      }
                      leaf name {
                        type xr:ncs_rpc_notif_Cisco-ios-xr-string;
                        description
                          "TSI4";
                      }
                      uses ncs_rpc_notif_ATTRIBUTES;
                    }
                  }
                  leaf name {
                    type xr:ncs_rpc_notif_Cisco-ios-xr-string;
                    description
                      "TSI3";
                  }
                  uses ncs_rpc_notif_ATTRIBUTES;
                }
              }
              leaf name {
                type xr:ncs_rpc_notif_Cisco-ios-xr-string;
                description
                  "TSI2";
              }
              uses ncs_rpc_notif_ATTRIBUTES;
            }
          }
          leaf name {
            type xr:ncs_rpc_notif_Cisco-ios-xr-string;
            description
              "TSI1";
          }
          uses ncs_rpc_notif_ATTRIBUTES;
        }
      }
      leaf name {
        type xr:ncs_rpc_notif_Cisco-ios-xr-string;
        description
          "Slot name";
      }
      uses ncs_rpc_notif_ATTRIBUTES;
    }
  }

  grouping live_ncs_THRESH-BAG {
    description
      "Common node of minor-lo, minor-hi, major-lo,
       major-hi, critical-lo, critical-hi";
    container thresh-bag {
      status deprecated;
      description
        "Environment threshold info";
      uses live_ncs_ENVMON-THRESHOLD-INFO;
    }
  }

  grouping live_ncs_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses live_ncs_ENVMON-THRESHOLD-INFO;
    }
  }

  grouping live_ncs_ATTRIBUTES {
    description
      "Common node of rack, slot, tsi1, tsi2, tsi3, tsi4
       , tsi5, tsi6, tsi7, tsi8, tsi9, tsi10, tsi11";
    container attributes {
      status deprecated;
      description
        "Shows the different attributes or status of each
         entity or component in inventory";
      container inv-basic-bag {
        status deprecated;
        description
          "Inventory Basic Bag";
        uses live_ncs_INV-PHY-ENTITY-BASIC-INFO;
      }
      container env-sensor-info {
        status deprecated;
        description
          "Environment sensor info";
        uses live_ncs_ENVMON-SENSOR-INFO;
      }
      container pwg-info {
        status deprecated;
        description
          "Inventory EDM PWG info";
        uses live_ncs_INV-PWG-INFO;
      }
      container env-sensor-info-xml {
        status deprecated;
        description
          "Environment sensor info XML";
        uses live_ncs_ENVMON-SENSOR-INFO-XML;
      }
      container inv-asset-bag {
        status deprecated;
        description
          "Inventory Asset Bag";
        uses live_ncs_INV-PHY-ENTITY-ASSET-INFO;
      }
      container threshold {
        status deprecated;
        description
          "Temperature alarm data for platform components";
        container major-lo {
          status deprecated;
          description
            "Major Low";
          uses live_ncs_INVMGR-EXT1-OPER-THRESH-BAG;
        }
        container critical-hi {
          status deprecated;
          description
            "Critical High";
          uses live_ncs_INVMGR-EXT1-OPER-THRESH-BAG;
        }
        container minor-hi {
          status deprecated;
          description
            "Minor High";
          uses live_ncs_INVMGR-EXT1-OPER-THRESH-BAG;
        }
        container major-hi {
          status deprecated;
          description
            "Major High";
          uses live_ncs_INVMGR-EXT1-OPER-THRESH-BAG;
        }
        container critical-lo {
          status deprecated;
          description
            "Critical Low";
          uses live_ncs_INVMGR-EXT1-OPER-THRESH-BAG;
        }
        container minor-lo {
          status deprecated;
          description
            "Minor Low";
          uses live_ncs_INVMGR-EXT1-OPER-THRESH-BAG;
        }
      }
      container fru-info {
        status deprecated;
        description
          "Inventory EDM FRU info";
        uses live_ncs_INV-CARD-FRU-INFO;
      }
      container inv-eeprom-info {
        status deprecated;
        description
          "Inventory EDM EEPROM Information Bag";
        uses live_ncs_INVMGR-EEPROM-OPAQUE-DATA;
      }
    }
  }

  grouping live_ncs_SLOT {
    description
      "Common node of powershelf, fantray, entity";
    list slot {
      key "name";
      status deprecated;
      description
        "Slot number";
      container tsi1s {
        status deprecated;
        description
          "Entity Level 1";
        list tsi1 {
          key "name";
          status deprecated;
          description
            "TSI1";
          container tsi2s {
            status deprecated;
            description
              "Entity Level 2";
            list tsi2 {
              key "name";
              status deprecated;
              description
                "TSI2";
              container tsi3s {
                status deprecated;
                description
                  "Entity Level 3";
                list tsi3 {
                  key "name";
                  status deprecated;
                  description
                    "TSI3";
                  container tsi4s {
                    status deprecated;
                    description
                      "Entity Level 4";
                    list tsi4 {
                      key "name";
                      status deprecated;
                      description
                        "TSI4";
                      container tsi5s {
                        status deprecated;
                        description
                          "Entity Level 5";
                        list tsi5 {
                          key "name";
                          status deprecated;
                          description
                            "TSI5";
                          container tsi6s {
                            status deprecated;
                            description
                              "Entity Level 6";
                            list tsi6 {
                              key "name";
                              status deprecated;
                              description
                                "TSI6";
                              container tsi7s {
                                status deprecated;
                                description
                                  "Entity Level 7";
                                list tsi7 {
                                  key "name";
                                  status deprecated;
                                  description
                                    "TSI7";
                                  container tsi8s {
                                    status deprecated;
                                    description
                                      "Entity Level 8";
                                    list tsi8 {
                                      key "name";
                                      status deprecated;
                                      description
                                        "TSI8";
                                      container tsi9s {
                                        status deprecated;
                                        description
                                          "Entity Level 9";
                                        list tsi9 {
                                          key "name";
                                          status deprecated;
                                          description
                                            "TSI9";
                                          container tsi10s {
                                            status deprecated;
                                            description
                                              "Entity Level 10";
                                            list tsi10 {
                                              key "name";
                                              status deprecated;
                                              description
                                                "TSI10";
                                              container tsi11s {
                                                status deprecated;
                                                description
                                                  "Entity Level 11";
                                                list tsi11 {
                                                  key "name";
                                                  status deprecated;
                                                  description
                                                    "TSI11";
                                                  leaf name {
                                                    type xr:live_ncs_Cisco-ios-xr-string;
                                                    description
                                                      "TSI11";
                                                  }
                                                  uses live_ncs_ATTRIBUTES;
                                                }
                                              }
                                              leaf name {
                                                type xr:live_ncs_Cisco-ios-xr-string;
                                                description
                                                  "TSI10";
                                              }
                                              uses live_ncs_ATTRIBUTES;
                                            }
                                          }
                                          leaf name {
                                            type xr:live_ncs_Cisco-ios-xr-string;
                                            description
                                              "TSI9";
                                          }
                                          uses live_ncs_ATTRIBUTES;
                                        }
                                      }
                                      leaf name {
                                        type xr:live_ncs_Cisco-ios-xr-string;
                                        description
                                          "TSI8";
                                      }
                                      uses live_ncs_ATTRIBUTES;
                                    }
                                  }
                                  leaf name {
                                    type xr:live_ncs_Cisco-ios-xr-string;
                                    description
                                      "TSI7";
                                  }
                                  uses live_ncs_ATTRIBUTES;
                                }
                              }
                              leaf name {
                                type xr:live_ncs_Cisco-ios-xr-string;
                                description
                                  "TSI6";
                              }
                              uses live_ncs_ATTRIBUTES;
                            }
                          }
                          leaf name {
                            type xr:live_ncs_Cisco-ios-xr-string;
                            description
                              "TSI5";
                          }
                          uses live_ncs_ATTRIBUTES;
                        }
                      }
                      leaf name {
                        type xr:live_ncs_Cisco-ios-xr-string;
                        description
                          "TSI4";
                      }
                      uses live_ncs_ATTRIBUTES;
                    }
                  }
                  leaf name {
                    type xr:live_ncs_Cisco-ios-xr-string;
                    description
                      "TSI3";
                  }
                  uses live_ncs_ATTRIBUTES;
                }
              }
              leaf name {
                type xr:live_ncs_Cisco-ios-xr-string;
                description
                  "TSI2";
              }
              uses live_ncs_ATTRIBUTES;
            }
          }
          leaf name {
            type xr:live_ncs_Cisco-ios-xr-string;
            description
              "TSI1";
          }
          uses live_ncs_ATTRIBUTES;
        }
      }
      leaf name {
        type xr:live_ncs_Cisco-ios-xr-string;
        description
          "Slot name";
      }
      uses live_ncs_ATTRIBUTES;
    }
  }

  grouping THRESH-BAG {
    description
      "Common node of minor-lo, minor-hi, major-lo,
       major-hi, critical-lo, critical-hi";
    container thresh-bag {
      status deprecated;
      description
        "Environment threshold info";
      uses ENVMON-THRESHOLD-INFO;
    }
  }

  grouping INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ENVMON-THRESHOLD-INFO;
    }
  }

  grouping ATTRIBUTES {
    description
      "Common node of rack, slot, tsi1, tsi2, tsi3, tsi4
       , tsi5, tsi6, tsi7, tsi8, tsi9, tsi10, tsi11";
    container attributes {
      status deprecated;
      description
        "Shows the different attributes or status of each
         entity or component in inventory";
      container inv-basic-bag {
        status deprecated;
        description
          "Inventory Basic Bag";
        uses INV-PHY-ENTITY-BASIC-INFO;
      }
      container env-sensor-info {
        status deprecated;
        description
          "Environment sensor info";
        uses ENVMON-SENSOR-INFO;
      }
      container pwg-info {
        status deprecated;
        description
          "Inventory EDM PWG info";
        uses INV-PWG-INFO;
      }
      container env-sensor-info-xml {
        status deprecated;
        description
          "Environment sensor info XML";
        uses ENVMON-SENSOR-INFO-XML;
      }
      container inv-asset-bag {
        status deprecated;
        description
          "Inventory Asset Bag";
        uses INV-PHY-ENTITY-ASSET-INFO;
      }
      container threshold {
        status deprecated;
        description
          "Temperature alarm data for platform components";
        container major-lo {
          status deprecated;
          description
            "Major Low";
          uses INVMGR-EXT1-OPER-THRESH-BAG;
        }
        container critical-hi {
          status deprecated;
          description
            "Critical High";
          uses INVMGR-EXT1-OPER-THRESH-BAG;
        }
        container minor-hi {
          status deprecated;
          description
            "Minor High";
          uses INVMGR-EXT1-OPER-THRESH-BAG;
        }
        container major-hi {
          status deprecated;
          description
            "Major High";
          uses INVMGR-EXT1-OPER-THRESH-BAG;
        }
        container critical-lo {
          status deprecated;
          description
            "Critical Low";
          uses INVMGR-EXT1-OPER-THRESH-BAG;
        }
        container minor-lo {
          status deprecated;
          description
            "Minor Low";
          uses INVMGR-EXT1-OPER-THRESH-BAG;
        }
      }
      container fru-info {
        status deprecated;
        description
          "Inventory EDM FRU info";
        uses INV-CARD-FRU-INFO;
      }
      container inv-eeprom-info {
        status deprecated;
        description
          "Inventory EDM EEPROM Information Bag";
        uses INVMGR-EEPROM-OPAQUE-DATA;
      }
    }
  }

  grouping SLOT {
    description
      "Common node of powershelf, fantray, entity";
    list slot {
      key "name";
      status deprecated;
      description
        "Slot number";
      container tsi1s {
        status deprecated;
        description
          "Entity Level 1";
        list tsi1 {
          key "name";
          status deprecated;
          description
            "TSI1";
          container tsi2s {
            status deprecated;
            description
              "Entity Level 2";
            list tsi2 {
              key "name";
              status deprecated;
              description
                "TSI2";
              container tsi3s {
                status deprecated;
                description
                  "Entity Level 3";
                list tsi3 {
                  key "name";
                  status deprecated;
                  description
                    "TSI3";
                  container tsi4s {
                    status deprecated;
                    description
                      "Entity Level 4";
                    list tsi4 {
                      key "name";
                      status deprecated;
                      description
                        "TSI4";
                      container tsi5s {
                        status deprecated;
                        description
                          "Entity Level 5";
                        list tsi5 {
                          key "name";
                          status deprecated;
                          description
                            "TSI5";
                          container tsi6s {
                            status deprecated;
                            description
                              "Entity Level 6";
                            list tsi6 {
                              key "name";
                              status deprecated;
                              description
                                "TSI6";
                              container tsi7s {
                                status deprecated;
                                description
                                  "Entity Level 7";
                                list tsi7 {
                                  key "name";
                                  status deprecated;
                                  description
                                    "TSI7";
                                  container tsi8s {
                                    status deprecated;
                                    description
                                      "Entity Level 8";
                                    list tsi8 {
                                      key "name";
                                      status deprecated;
                                      description
                                        "TSI8";
                                      container tsi9s {
                                        status deprecated;
                                        description
                                          "Entity Level 9";
                                        list tsi9 {
                                          key "name";
                                          status deprecated;
                                          description
                                            "TSI9";
                                          container tsi10s {
                                            status deprecated;
                                            description
                                              "Entity Level 10";
                                            list tsi10 {
                                              key "name";
                                              status deprecated;
                                              description
                                                "TSI10";
                                              container tsi11s {
                                                status deprecated;
                                                description
                                                  "Entity Level 11";
                                                list tsi11 {
                                                  key "name";
                                                  status deprecated;
                                                  description
                                                    "TSI11";
                                                  leaf name {
                                                    type xr:Cisco-ios-xr-string;
                                                    description
                                                      "TSI11";
                                                  }
                                                  uses ATTRIBUTES;
                                                }
                                              }
                                              leaf name {
                                                type xr:Cisco-ios-xr-string;
                                                description
                                                  "TSI10";
                                              }
                                              uses ATTRIBUTES;
                                            }
                                          }
                                          leaf name {
                                            type xr:Cisco-ios-xr-string;
                                            description
                                              "TSI9";
                                          }
                                          uses ATTRIBUTES;
                                        }
                                      }
                                      leaf name {
                                        type xr:Cisco-ios-xr-string;
                                        description
                                          "TSI8";
                                      }
                                      uses ATTRIBUTES;
                                    }
                                  }
                                  leaf name {
                                    type xr:Cisco-ios-xr-string;
                                    description
                                      "TSI7";
                                  }
                                  uses ATTRIBUTES;
                                }
                              }
                              leaf name {
                                type xr:Cisco-ios-xr-string;
                                description
                                  "TSI6";
                              }
                              uses ATTRIBUTES;
                            }
                          }
                          leaf name {
                            type xr:Cisco-ios-xr-string;
                            description
                              "TSI5";
                          }
                          uses ATTRIBUTES;
                        }
                      }
                      leaf name {
                        type xr:Cisco-ios-xr-string;
                        description
                          "TSI4";
                      }
                      uses ATTRIBUTES;
                    }
                  }
                  leaf name {
                    type xr:Cisco-ios-xr-string;
                    description
                      "TSI3";
                  }
                  uses ATTRIBUTES;
                }
              }
              leaf name {
                type xr:Cisco-ios-xr-string;
                description
                  "TSI2";
              }
              uses ATTRIBUTES;
            }
          }
          leaf name {
            type xr:Cisco-ios-xr-string;
            description
              "TSI1";
          }
          uses ATTRIBUTES;
        }
      }
      leaf name {
        type xr:Cisco-ios-xr-string;
        description
          "Slot name";
      }
      uses ATTRIBUTES;
    }
  }

  augment "/ncs:devices/ncs:device/ncs:config" {
    // NCS drop config false container inventory
  }
  augment "/ncs:devices/ncs:device/ncs:live-status" {
    container inventory {
      tailf:ncs-device-type "netconf";
      tailf:display-when "not(../../ncs:module) or ../../ncs:module[ncs:name='Cisco-IOS-XR-invmgr-oper'] or (../../ncs:live-status-protocol[not(ncs:capability)]) or (../../ncs:live-status-protocol/ncs:capability/ncs:module[.='Cisco-IOS-XR-invmgr-oper'])";
      description
        "Inventory information";
      container entities {
        description
          "Entities Table";
        list entity {
          key "name";
          description
            "Entity name";
          container parent-info {
            description
              "Inventory parent name info";
            uses live_ncs_INV-PARENT-INFO;
          }
          container subentities {
            description
              "SubEntities Table";
            list subentity {
              key "name";
              description
                "Subentity Bag";
              leaf name {
                type string {
                  length "1..100";
                }
                description
                  "Subentity name";
              }
              uses live_ncs_SUBENTITY-INFO;
            }
          }
          container attributes {
            description
              "Shows the different attributes or status of
               each entity or component in inventory";
            container inv-basic-bag {
              description
                "Inventory Basic Bag";
              uses live_ncs_INV-PHY-ENTITY-BASIC-INFO;
            }
            container vm-node-id {
              description
                "VM Node ID Tuple";
              uses live_ncs_VM-NODEID-INFO;
            }
            container threshold {
              description
                "Temperature alarm data for platform
                 components";
              container minor-hi {
                description
                  "Minor High";
                uses live_ncs_INVMGR-EXT1-OPER-THRESH-BAG;
              }
              container major-hi {
                description
                  "Major High";
                uses live_ncs_INVMGR-EXT1-OPER-THRESH-BAG;
              }
              container minor-lo {
                description
                  "Minor Low";
                uses live_ncs_INVMGR-EXT1-OPER-THRESH-BAG;
              }
              container major-lo {
                description
                  "Major Low";
                uses live_ncs_INVMGR-EXT1-OPER-THRESH-BAG;
              }
              container critical-hi {
                description
                  "Critical High";
                uses live_ncs_INVMGR-EXT1-OPER-THRESH-BAG;
              }
              container critical-lo {
                description
                  "Critical Low";
                uses live_ncs_INVMGR-EXT1-OPER-THRESH-BAG;
              }
            }
            container fru-info {
              description
                "Inventory EDM FRU info";
              uses live_ncs_INV-CARD-FRU-INFO;
            }
            container pluggable-info {
              description
                "Info of supported interaces for pluggable
                 type";
              uses live_ncs_PLUGGABLE-INFO;
            }
            container inv-asset-bag {
              description
                "Inventory Asset Bag";
              uses live_ncs_INV-PHY-ENTITY-ASSET-INFO;
            }
            container env-sensor-info {
              description
                "Environment sensor info";
              uses live_ncs_ENVMON-SENSOR-INFO;
            }
            container node-id {
              description
                "Node ID Tuple";
              uses live_ncs_NODEID-INFO;
            }
            container inv-eeprom-info {
              description
                "Inventory EDM EEPROM Information Bag";
              uses live_ncs_INVMGR-EEPROM-OPAQUE-DATA;
            }
          }
          leaf name {
            type string {
              length "1..100";
            }
            description
              "Entity name";
          }
        }
      }
      container racks {
        status deprecated;
        description
          "RackTable";
        list rack {
          key "name";
          status deprecated;
          description
            "Rack name";
          container entity {
            status deprecated;
            description
              "Entity information";
            uses live_ncs_SLOT;
          }
          container powershelf {
            status deprecated;
            description
              "Powershelf information";
            uses live_ncs_SLOT;
          }
          container fantray {
            status deprecated;
            description
              "Fantray information";
            uses live_ncs_SLOT;
          }
          leaf name {
            type xr:live_ncs_Cisco-ios-xr-string;
            description
              "Rack name";
          }
          uses live_ncs_ATTRIBUTES;
        }
      }
    }
  }
  augment "/ncs:devices/ncs:template/ncs:ned-id/ncs:config" {
    // NCS drop config false container inventory
  }
}

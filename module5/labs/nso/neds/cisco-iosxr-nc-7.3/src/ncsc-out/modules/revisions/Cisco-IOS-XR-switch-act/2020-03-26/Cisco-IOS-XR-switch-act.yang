module Cisco-IOS-XR-switch-act {
  // Generated by yanger -t ncs
  tailf:mount-id "cisco-iosxr-nc-7.3:cisco-iosxr-nc-7.3";
  tailf:ncs-device-type "netconf";

  namespace "http://cisco.com/ns/yang/Cisco-IOS-XR-switch-act";
  prefix switch-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller ethernet switch.

     Copyright (c) 2019-2020 by Cisco Systems, Inc.
     All rights reserved.";

  revision 2020-03-26 {
    description
      "Added an entry for clear controller switch txq.";
    semver:module-version "1.0.0";
  }
  revision 2019-04-05 {
    description
      "Establish semantic version baseline.";
  }
  revision 2019-02-14 {
    description
      "Initial revision.";
  }

  augment "/ncs:devices/ncs:device/ncs:rpc" {
    container rpc-clear-switch-txq-statistics {
      tailf:ncs-device-type "netconf";
      tailf:display-when "not(../../ncs:module) or ../../ncs:module[ncs:name='Cisco-IOS-XR-switch-act']";
      tailf:action clear-switch-txq-statistics {
        tailf:actionpoint ncsproxy {
          tailf:internal;
        }
        description
          "Clear switch txq statistics";
        input {
          leaf instance {
            type string;
            mandatory true;
            description
              "Location information for switch, XR node identifier e.g. 0/RP0/CPU0, 0/0/CPU0";
          }
          leaf port {
            type uint16 {
              range "0..65534";
            }
            description
              "Port number";
          }
        }
      }
    }
  }
  augment "/ncs:devices/ncs:device-group/ncs:ned-id/ncs:rpc" {
    container rpc-clear-switch-txq-statistics {
      tailf:ncs-device-type "netconf";
      tailf:display-when "/ncs:devices/ncs:device[ncs:name=current()/../../../ncs:member]/ncs:module[ncs:name='Cisco-IOS-XR-switch-act']";
      tailf:action clear-switch-txq-statistics {
        tailf:actionpoint ncsproxy {
          tailf:internal;
        }
        description
          "Clear switch txq statistics";
        input {
          leaf instance {
            type string;
            mandatory true;
            description
              "Location information for switch, XR node identifier e.g. 0/RP0/CPU0, 0/0/CPU0";
          }
          leaf port {
            type uint16 {
              range "0..65534";
            }
            description
              "Port number";
          }
        }
      }
    }
  }
  augment "/ncs:devices/ncs:device/ncs:rpc" {
    container rpc-set-switch-port-reset {
      tailf:ncs-device-type "netconf";
      tailf:display-when "not(../../ncs:module) or ../../ncs:module[ncs:name='Cisco-IOS-XR-switch-act']";
      tailf:action set-switch-port-reset {
        tailf:actionpoint ncsproxy {
          tailf:internal;
        }
        description
          "Set port reset";
        input {
          leaf instance {
            type string;
            mandatory true;
            description
              "Location information for switch, XR node identifier e.g. 0/RP0/CPU0, 0/0/CPU0";
          }
          leaf port {
            type uint16 {
              range "0..65534";
            }
            mandatory true;
            description
              "Port number";
          }
        }
      }
    }
  }
  augment "/ncs:devices/ncs:device-group/ncs:ned-id/ncs:rpc" {
    container rpc-set-switch-port-reset {
      tailf:ncs-device-type "netconf";
      tailf:display-when "/ncs:devices/ncs:device[ncs:name=current()/../../../ncs:member]/ncs:module[ncs:name='Cisco-IOS-XR-switch-act']";
      tailf:action set-switch-port-reset {
        tailf:actionpoint ncsproxy {
          tailf:internal;
        }
        description
          "Set port reset";
        input {
          leaf instance {
            type string;
            mandatory true;
            description
              "Location information for switch, XR node identifier e.g. 0/RP0/CPU0, 0/0/CPU0";
          }
          leaf port {
            type uint16 {
              range "0..65534";
            }
            mandatory true;
            description
              "Port number";
          }
        }
      }
    }
  }
  augment "/ncs:devices/ncs:device/ncs:rpc" {
    container rpc-clear-switch-statistics {
      tailf:ncs-device-type "netconf";
      tailf:display-when "not(../../ncs:module) or ../../ncs:module[ncs:name='Cisco-IOS-XR-switch-act']";
      tailf:action clear-switch-statistics {
        tailf:actionpoint ncsproxy {
          tailf:internal;
        }
        description
          "Clear switch statistics";
        input {
          leaf instance {
            type string;
            mandatory true;
            description
              "Location information for switch, XR node identifier e.g. 0/RP0/CPU0, 0/0/CPU0";
          }
        }
      }
    }
  }
  augment "/ncs:devices/ncs:device-group/ncs:ned-id/ncs:rpc" {
    container rpc-clear-switch-statistics {
      tailf:ncs-device-type "netconf";
      tailf:display-when "/ncs:devices/ncs:device[ncs:name=current()/../../../ncs:member]/ncs:module[ncs:name='Cisco-IOS-XR-switch-act']";
      tailf:action clear-switch-statistics {
        tailf:actionpoint ncsproxy {
          tailf:internal;
        }
        description
          "Clear switch statistics";
        input {
          leaf instance {
            type string;
            mandatory true;
            description
              "Location information for switch, XR node identifier e.g. 0/RP0/CPU0, 0/0/CPU0";
          }
        }
      }
    }
  }
  augment "/ncs:devices/ncs:device/ncs:rpc" {
    container rpc-clear-switch-policing-statistics {
      tailf:ncs-device-type "netconf";
      tailf:display-when "not(../../ncs:module) or ../../ncs:module[ncs:name='Cisco-IOS-XR-switch-act']";
      tailf:action clear-switch-policing-statistics {
        tailf:actionpoint ncsproxy {
          tailf:internal;
        }
        description
          "Clear switch policing statistics";
        input {
          leaf instance {
            type string;
            mandatory true;
            description
              "Location information for switch, XR node identifier e.g. 0/RP0/CPU0, 0/0/CPU0";
          }
          leaf port {
            type uint16 {
              range "0..65534";
            }
            description
              "Port number";
          }
        }
      }
    }
  }
  augment "/ncs:devices/ncs:device-group/ncs:ned-id/ncs:rpc" {
    container rpc-clear-switch-policing-statistics {
      tailf:ncs-device-type "netconf";
      tailf:display-when "/ncs:devices/ncs:device[ncs:name=current()/../../../ncs:member]/ncs:module[ncs:name='Cisco-IOS-XR-switch-act']";
      tailf:action clear-switch-policing-statistics {
        tailf:actionpoint ncsproxy {
          tailf:internal;
        }
        description
          "Clear switch policing statistics";
        input {
          leaf instance {
            type string;
            mandatory true;
            description
              "Location information for switch, XR node identifier e.g. 0/RP0/CPU0, 0/0/CPU0";
          }
          leaf port {
            type uint16 {
              range "0..65534";
            }
            description
              "Port number";
          }
        }
      }
    }
  }
  augment "/ncs:devices/ncs:device/ncs:rpc" {
    container rpc-clear-switch-fdb {
      tailf:ncs-device-type "netconf";
      tailf:display-when "not(../../ncs:module) or ../../ncs:module[ncs:name='Cisco-IOS-XR-switch-act']";
      tailf:action clear-switch-fdb {
        tailf:actionpoint ncsproxy {
          tailf:internal;
        }
        description
          "Clear switch forwarding database";
        input {
          leaf instance {
            type string;
            mandatory true;
            description
              "Location information for switch, XR node identifier e.g. 0/RP0/CPU0, 0/0/CPU0";
          }
        }
      }
    }
  }
  augment "/ncs:devices/ncs:device-group/ncs:ned-id/ncs:rpc" {
    container rpc-clear-switch-fdb {
      tailf:ncs-device-type "netconf";
      tailf:display-when "/ncs:devices/ncs:device[ncs:name=current()/../../../ncs:member]/ncs:module[ncs:name='Cisco-IOS-XR-switch-act']";
      tailf:action clear-switch-fdb {
        tailf:actionpoint ncsproxy {
          tailf:internal;
        }
        description
          "Clear switch forwarding database";
        input {
          leaf instance {
            type string;
            mandatory true;
            description
              "Location information for switch, XR node identifier e.g. 0/RP0/CPU0, 0/0/CPU0";
          }
        }
      }
    }
  }
  augment "/ncs:devices/ncs:device/ncs:rpc" {
    container rpc-clear-switch-bridge-statistics {
      tailf:ncs-device-type "netconf";
      tailf:display-when "not(../../ncs:module) or ../../ncs:module[ncs:name='Cisco-IOS-XR-switch-act']";
      tailf:action clear-switch-bridge-statistics {
        tailf:actionpoint ncsproxy {
          tailf:internal;
        }
        description
          "Clear switch bridge statistics";
        input {
          leaf instance {
            type string;
            mandatory true;
            description
              "Location information for switch, XR node identifier e.g. 0/RP0/CPU0, 0/0/CPU0";
          }
        }
      }
    }
  }
  augment "/ncs:devices/ncs:device-group/ncs:ned-id/ncs:rpc" {
    container rpc-clear-switch-bridge-statistics {
      tailf:ncs-device-type "netconf";
      tailf:display-when "/ncs:devices/ncs:device[ncs:name=current()/../../../ncs:member]/ncs:module[ncs:name='Cisco-IOS-XR-switch-act']";
      tailf:action clear-switch-bridge-statistics {
        tailf:actionpoint ncsproxy {
          tailf:internal;
        }
        description
          "Clear switch bridge statistics";
        input {
          leaf instance {
            type string;
            mandatory true;
            description
              "Location information for switch, XR node identifier e.g. 0/RP0/CPU0, 0/0/CPU0";
          }
        }
      }
    }
  }
}

submodule Cisco-IOS-XR-asr9k-lc-fca-oper-sub2 {
  // Generated by yanger -t ncs
  tailf:mount-id "cisco-iosxr-nc-7.3:cisco-iosxr-nc-7.3";

  belongs-to Cisco-IOS-XR-asr9k-lc-fca-oper {
    prefix Cisco-IOS-XR-asr9k-lc-fca-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-lc-fca package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_LDA-IFSUBSYS-STATE-EDM-INFO {
    description
      "LDA ifsubsys state";
    leaf bay {
      type string;
      description
        "bay";
    }
    leaf ifsubsys {
      type string;
      description
        "ifsubsys";
    }
    leaf if-state {
      type string;
      description
        "if state";
    }
    leaf if-event {
      type string;
      description
        "if event";
    }
    leaf ep-type {
      type string;
      description
        "ep type";
    }
    leaf ep-state {
      type string;
      description
        "ep state";
    }
    leaf ep-presence {
      type string;
      description
        "ep presence";
    }
    leaf ep-idprom-major {
      type string;
      description
        "ep idprom major";
    }
    leaf ep-idprom-minor {
      type string;
      description
        "ep idprom minor";
    }
    leaf ep-idprom-data {
      type string;
      description
        "ep idprom data";
    }
  }

  grouping ncs_rpc_notif_LDA-IFSUBSYS-STATE-EDM-INFO {
    description
      "LDA ifsubsys state";
    leaf bay {
      type uint32;
      description
        "bay";
    }
    leaf ifsubsys {
      type uint32;
      description
        "ifsubsys";
    }
    leaf if-state {
      type uint8;
      description
        "if state";
    }
    leaf if-event {
      type uint8;
      description
        "if event";
    }
    leaf ep-type {
      type uint32;
      description
        "ep type";
    }
    leaf ep-state {
      type uint8;
      description
        "ep state";
    }
    leaf ep-presence {
      type uint8;
      description
        "ep presence";
    }
    leaf ep-idprom-major {
      type uint8;
      description
        "ep idprom major";
    }
    leaf ep-idprom-minor {
      type uint8;
      description
        "ep idprom minor";
    }
    leaf ep-idprom-data {
      type string {
        length "0..256";
      }
      description
        "ep idprom data";
    }
  }

  grouping live_ncs_LDA-IFSUBSYS-STATE-EDM-INFO {
    description
      "LDA ifsubsys state";
    leaf bay {
      type uint32;
      description
        "bay";
    }
    leaf ifsubsys {
      type uint32;
      description
        "ifsubsys";
    }
    leaf if-state {
      type uint8;
      description
        "if state";
    }
    leaf if-event {
      type uint8;
      description
        "if event";
    }
    leaf ep-type {
      type uint32;
      description
        "ep type";
    }
    leaf ep-state {
      type uint8;
      description
        "ep state";
    }
    leaf ep-presence {
      type uint8;
      description
        "ep presence";
    }
    leaf ep-idprom-major {
      type uint8;
      description
        "ep idprom major";
    }
    leaf ep-idprom-minor {
      type uint8;
      description
        "ep idprom minor";
    }
    leaf ep-idprom-data {
      type string {
        length "0..256";
      }
      description
        "ep idprom data";
    }
  }

  grouping LDA-IFSUBSYS-STATE-EDM-INFO {
    description
      "LDA ifsubsys state";
    leaf bay {
      type uint32;
      description
        "bay";
    }
    leaf ifsubsys {
      type uint32;
      description
        "ifsubsys";
    }
    leaf if-state {
      type uint8;
      description
        "if state";
    }
    leaf if-event {
      type uint8;
      description
        "if event";
    }
    leaf ep-type {
      type uint32;
      description
        "ep type";
    }
    leaf ep-state {
      type uint8;
      description
        "ep state";
    }
    leaf ep-presence {
      type uint8;
      description
        "ep presence";
    }
    leaf ep-idprom-major {
      type uint8;
      description
        "ep idprom major";
    }
    leaf ep-idprom-minor {
      type uint8;
      description
        "ep idprom minor";
    }
    leaf ep-idprom-data {
      type string {
        length "0..256";
      }
      description
        "ep idprom data";
    }
  }
}

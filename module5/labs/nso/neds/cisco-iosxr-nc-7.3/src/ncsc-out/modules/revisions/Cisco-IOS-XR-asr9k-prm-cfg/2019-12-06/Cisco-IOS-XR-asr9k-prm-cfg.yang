module Cisco-IOS-XR-asr9k-prm-cfg {
  // Generated by yanger -t ncs
  tailf:mount-id "cisco-iosxr-nc-7.3:cisco-iosxr-nc-7.3";
  tailf:ncs-device-type "netconf";

  namespace "http://cisco.com/ns/yang/Cisco-IOS-XR-asr9k-prm-cfg";
  prefix asr9k-prm-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-prm package configuration.

     This module contains definitions
     for the following management objects:
       hardware-module-buffer-carve-mode: Buffer carve mode in
         hardware module port(s)
       hardware-module-qos-mode: QoS mode in hardware module port(s)
       hardware-module-processor: Processor configuration
       hardware-module-reset: Reset configuration
       hardware-module-tcp-mss-adjust: TCP MSS Adjust value in
         hardware module
       hardware-module-tcam: TCAM
       hardware-module-profile: Memory resource configuration
       hardware-module-efd: EFD (Early Fast Discard)
       hardware-module-all-qos-mode: Global qos-mode in hardware
         module

     Copyright (c) 2013-2019 by Cisco Systems, Inc.
     All rights reserved.";

  revision 2019-12-06 {
    description
      "Use the correct profile schema for exr and cxr";
    semver:module-version "1.0.0";
  }
  revision 2019-04-05 {
    description
      "Establish semantic version baseline.";
  }
  revision 2015-11-09 {
    description
      "IOS XR 6.0 revision.";
  }

  typedef ncs_template_Prm-config-scale-profile {
    type string;
    description
      "Prm config scale profile";
  }

  typedef ncs_template_Prm-config-internal-tcam-part-profile {
    type string;
    description
      "Prm config internal tcam part profile";
  }

  typedef ncs_template_Asr9k-efd-burst-absorption {
    type string;
    description
      "Asr9k efd burst absorption";
  }

  typedef ncs_template_Prm-processor-config {
    type string;
    description
      "Prm processor config";
  }

  typedef ncs_template_Asr9k-efd-operation {
    type string;
    description
      "Asr9k efd operation";
  }

  typedef ncs_template_Asr9k-efd-mode {
    type string;
    description
      "Asr9k efd mode";
  }

  typedef ncs_template_Prm-tcam-profile {
    type string;
    description
      "Prm tcam profile";
  }

  typedef ncs_rpc_notif_Prm-config-scale-profile {
    type enumeration {
      enum "default" {
        value 0;
        description
          "Default scale profile";
      }
      enum "l2" {
        value 1;
        description
          "L2 scale profile";
      }
      enum "l3" {
        value 2;
        description
          "L3 scale profile";
      }
      enum "l3xl" {
        value 3;
        description
          "L3XL scale profile";
      }
      enum "evpnconv" {
        value 5;
        description
          "EVPN convergence scale profile";
      }
    }
    description
      "Prm config scale profile";
  }

  typedef ncs_rpc_notif_Prm-config-internal-tcam-part-profile {
    type enumeration {
      enum "to-default" {
        value 0;
        description
          "default internal tcam partitions (L2 1k, V4 24k
           , V6 1.75k entries): Tomahawk";
      }
      enum "to-profile-se1" {
        value 1;
        description
          "Set internal tcam partitions for service edge
           (L2 4k, V4 15k, V6 3.25k entries): Tomahawk";
      }
    }
    description
      "Prm config internal tcam part profile";
  }

  typedef ncs_rpc_notif_Asr9k-efd-burst-absorption {
    type enumeration {
      enum "disable" {
        value 0;
        description
          "Use default RFD settings";
      }
      enum "enable" {
        value 1;
        description
          "Use Burst Absorption RFD settings";
      }
    }
    description
      "Asr9k efd burst absorption";
  }

  typedef ncs_rpc_notif_Prm-processor-config {
    type enumeration {
      enum "mode-default" {
        value 0;
        description
          "Default cluster setting";
      }
      enum "mode-full" {
        value 1;
        description
          "Full cluster setting";
      }
    }
    description
      "Prm processor config";
  }

  typedef ncs_rpc_notif_Asr9k-efd-operation {
    type enumeration {
      enum "less-than" {
        value 2;
        description
          "Less than";
      }
      enum "greater-than-or-equal" {
        value 3;
        description
          "Greater than or equal";
      }
    }
    description
      "Asr9k efd operation";
  }

  typedef ncs_rpc_notif_Asr9k-efd-mode {
    type enumeration {
      enum "only-outer-encap" {
        value 0;
        description
          "Only check outer encap";
      }
      enum "include-inner-encap" {
        value 1;
        description
          "Check outer and inner encap";
      }
    }
    description
      "Asr9k efd mode";
  }

  typedef ncs_rpc_notif_Prm-tcam-profile {
    type enumeration {
      enum "profile0" {
        value 0;
        description
          "Profile 0";
      }
      enum "profile1" {
        value 1;
        description
          "Profile 1";
      }
      enum "profile2" {
        value 2;
        description
          "Profile 2";
      }
    }
    description
      "Prm tcam profile";
  }

  typedef live_ncs_Prm-config-scale-profile {
    type enumeration {
      enum "default" {
        value 0;
        description
          "Default scale profile";
      }
      enum "l2" {
        value 1;
        description
          "L2 scale profile";
      }
      enum "l3" {
        value 2;
        description
          "L3 scale profile";
      }
      enum "l3xl" {
        value 3;
        description
          "L3XL scale profile";
      }
      enum "evpnconv" {
        value 5;
        description
          "EVPN convergence scale profile";
      }
    }
    description
      "Prm config scale profile";
  }

  typedef live_ncs_Prm-config-internal-tcam-part-profile {
    type enumeration {
      enum "to-default" {
        value 0;
        description
          "default internal tcam partitions (L2 1k, V4 24k
           , V6 1.75k entries): Tomahawk";
      }
      enum "to-profile-se1" {
        value 1;
        description
          "Set internal tcam partitions for service edge
           (L2 4k, V4 15k, V6 3.25k entries): Tomahawk";
      }
    }
    description
      "Prm config internal tcam part profile";
  }

  typedef live_ncs_Asr9k-efd-burst-absorption {
    type enumeration {
      enum "disable" {
        value 0;
        description
          "Use default RFD settings";
      }
      enum "enable" {
        value 1;
        description
          "Use Burst Absorption RFD settings";
      }
    }
    description
      "Asr9k efd burst absorption";
  }

  typedef live_ncs_Prm-processor-config {
    type enumeration {
      enum "mode-default" {
        value 0;
        description
          "Default cluster setting";
      }
      enum "mode-full" {
        value 1;
        description
          "Full cluster setting";
      }
    }
    description
      "Prm processor config";
  }

  typedef live_ncs_Asr9k-efd-operation {
    type enumeration {
      enum "less-than" {
        value 2;
        description
          "Less than";
      }
      enum "greater-than-or-equal" {
        value 3;
        description
          "Greater than or equal";
      }
    }
    description
      "Asr9k efd operation";
  }

  typedef live_ncs_Asr9k-efd-mode {
    type enumeration {
      enum "only-outer-encap" {
        value 0;
        description
          "Only check outer encap";
      }
      enum "include-inner-encap" {
        value 1;
        description
          "Check outer and inner encap";
      }
    }
    description
      "Asr9k efd mode";
  }

  typedef live_ncs_Prm-tcam-profile {
    type enumeration {
      enum "profile0" {
        value 0;
        description
          "Profile 0";
      }
      enum "profile1" {
        value 1;
        description
          "Profile 1";
      }
      enum "profile2" {
        value 2;
        description
          "Profile 2";
      }
    }
    description
      "Prm tcam profile";
  }

  typedef Prm-config-scale-profile {
    type enumeration {
      enum "default" {
        value 0;
        description
          "Default scale profile";
      }
      enum "l2" {
        value 1;
        description
          "L2 scale profile";
      }
      enum "l3" {
        value 2;
        description
          "L3 scale profile";
      }
      enum "l3xl" {
        value 3;
        description
          "L3XL scale profile";
      }
      enum "evpnconv" {
        value 5;
        description
          "EVPN convergence scale profile";
      }
    }
    description
      "Prm config scale profile";
  }

  typedef Prm-config-internal-tcam-part-profile {
    type enumeration {
      enum "to-default" {
        value 0;
        description
          "default internal tcam partitions (L2 1k, V4 24k
           , V6 1.75k entries): Tomahawk";
      }
      enum "to-profile-se1" {
        value 1;
        description
          "Set internal tcam partitions for service edge
           (L2 4k, V4 15k, V6 3.25k entries): Tomahawk";
      }
    }
    description
      "Prm config internal tcam part profile";
  }

  typedef Asr9k-efd-burst-absorption {
    type enumeration {
      enum "disable" {
        value 0;
        description
          "Use default RFD settings";
      }
      enum "enable" {
        value 1;
        description
          "Use Burst Absorption RFD settings";
      }
    }
    description
      "Asr9k efd burst absorption";
  }

  typedef Prm-processor-config {
    type enumeration {
      enum "mode-default" {
        value 0;
        description
          "Default cluster setting";
      }
      enum "mode-full" {
        value 1;
        description
          "Full cluster setting";
      }
    }
    description
      "Prm processor config";
  }

  typedef Asr9k-efd-operation {
    type enumeration {
      enum "less-than" {
        value 2;
        description
          "Less than";
      }
      enum "greater-than-or-equal" {
        value 3;
        description
          "Greater than or equal";
      }
    }
    description
      "Asr9k efd operation";
  }

  typedef Asr9k-efd-mode {
    type enumeration {
      enum "only-outer-encap" {
        value 0;
        description
          "Only check outer encap";
      }
      enum "include-inner-encap" {
        value 1;
        description
          "Check outer and inner encap";
      }
    }
    description
      "Asr9k efd mode";
  }

  typedef Prm-tcam-profile {
    type enumeration {
      enum "profile0" {
        value 0;
        description
          "Profile 0";
      }
      enum "profile1" {
        value 1;
        description
          "Profile 1";
      }
      enum "profile2" {
        value 2;
        description
          "Profile 2";
      }
    }
    description
      "Prm tcam profile";
  }

  grouping ncs_template_VLAN-COS {
    description
      "Common node of node, node-all";
    container vlan-cos {
      presence "Indicates a vlan-cos node is configured.";
      description
        "EFD VLAN parameters";
      leaf cos {
        type string;
        // NCS drop mandatory statement
        description
          "VLAN COS threshold";
      }
      leaf operation {
        type ncs_template_Asr9k-efd-operation;
        // NCS drop default statement
        description
          "VLAN operation";
      }
    }
  }

  grouping ncs_template_IP-PRECEDENCE {
    description
      "Common node of node, node-all";
    container ip-precedence {
      presence "Indicates a ip-precedence node is configured.";
      description
        "EFD IP parameters";
      leaf precedence {
        type string;
        // NCS drop mandatory statement
        description
          "IP TOS precedence threshold";
      }
      leaf operation {
        type ncs_template_Asr9k-efd-operation;
        // NCS drop default statement
        description
          "IP operation";
      }
    }
  }

  grouping ncs_template_IP-PRIORITY-MASK {
    description
      "Common node of node, node-all";
    container ip-priority-mask {
      presence "enable ip-priority-mask";
      description
        "IP Priority Mask";
      leaf prec0 {
        type string;
        // NCS drop default statement
        description
          "Prec";
      }
      leaf prec1 {
        type string;
        // NCS drop default statement
        description
          "Prec";
      }
      leaf prec2 {
        type string;
        // NCS drop default statement
        description
          "Prec";
      }
      leaf prec3 {
        type string;
        // NCS drop default statement
        description
          "Prec";
      }
      leaf prec4 {
        type string;
        // NCS drop default statement
        description
          "Prec";
      }
      leaf prec5 {
        type string;
        // NCS drop default statement
        description
          "Prec";
      }
      leaf prec6 {
        type string;
        // NCS drop default statement
        description
          "Prec";
      }
      leaf prec7 {
        type string;
        // NCS drop default statement
        description
          "Prec";
      }
    }
  }

  grouping ncs_template_VLAN-PRIORITY-MASK {
    description
      "Common node of node, node-all";
    container vlan-priority-mask {
      presence "enable vlan-priority-mask";
      description
        "VLAN Priority Mask";
      leaf prec0 {
        type string;
        // NCS drop default statement
        description
          "Prec";
      }
      leaf prec1 {
        type string;
        // NCS drop default statement
        description
          "Prec";
      }
      leaf prec2 {
        type string;
        // NCS drop default statement
        description
          "Prec";
      }
      leaf prec3 {
        type string;
        // NCS drop default statement
        description
          "Prec";
      }
      leaf prec4 {
        type string;
        // NCS drop default statement
        description
          "Prec";
      }
      leaf prec5 {
        type string;
        // NCS drop default statement
        description
          "Prec";
      }
      leaf prec6 {
        type string;
        // NCS drop default statement
        description
          "Prec";
      }
      leaf prec7 {
        type string;
        // NCS drop default statement
        description
          "Prec";
      }
    }
  }

  grouping ncs_template_MPLS-PRIORITY-MASK {
    description
      "Common node of node, node-all";
    container mpls-priority-mask {
      presence "enable mpls-priority-mask";
      description
        "MPLS Priority Mask";
      leaf prec0 {
        type string;
        // NCS drop default statement
        description
          "Prec";
      }
      leaf prec1 {
        type string;
        // NCS drop default statement
        description
          "Prec";
      }
      leaf prec2 {
        type string;
        // NCS drop default statement
        description
          "Prec";
      }
      leaf prec3 {
        type string;
        // NCS drop default statement
        description
          "Prec";
      }
      leaf prec4 {
        type string;
        // NCS drop default statement
        description
          "Prec";
      }
      leaf prec5 {
        type string;
        // NCS drop default statement
        description
          "Prec";
      }
      leaf prec6 {
        type string;
        // NCS drop default statement
        description
          "Prec";
      }
      leaf prec7 {
        type string;
        // NCS drop default statement
        description
          "Prec";
      }
    }
  }

  grouping ncs_template_BURST-ABSORPTION {
    description
      "Common node of node, node-all";
    leaf burst-absorption {
      type ncs_template_Asr9k-efd-burst-absorption;
      description
        "EFD burst absorption parameter.";
    }
  }

  grouping ncs_template_ENABLE {
    description
      "Common node of node, node-all";
    leaf enable {
      type empty;
      description
        "Enable EFD for this node";
    }
  }

  grouping ncs_template_MODE {
    description
      "Common node of node, node-all";
    leaf mode {
      type ncs_template_Asr9k-efd-mode;
      description
        "EFD mode parameter.";
    }
  }

  grouping ncs_template_MPLS-EXP {
    description
      "Common node of node, node-all";
    container mpls-exp {
      presence "Indicates a mpls-exp node is configured.";
      description
        "EFD MPLS parameters";
      leaf exp {
        type string;
        // NCS drop mandatory statement
        description
          "MPLS EXP threshold";
      }
      leaf operation {
        type ncs_template_Asr9k-efd-operation;
        // NCS drop default statement
        description
          "MPLS operation";
      }
    }
  }

  grouping ncs_rpc_notif_VLAN-COS {
    description
      "Common node of node, node-all";
    container vlan-cos {
      presence "Indicates a vlan-cos node is configured.";
      description
        "EFD VLAN parameters";
      leaf cos {
        type uint32 {
          range "0..7";
        }
        mandatory true;
        description
          "VLAN COS threshold";
      }
      leaf operation {
        type ncs_rpc_notif_Asr9k-efd-operation;
        default "greater-than-or-equal";
        description
          "VLAN operation";
      }
    }
  }

  grouping ncs_rpc_notif_IP-PRECEDENCE {
    description
      "Common node of node, node-all";
    container ip-precedence {
      presence "Indicates a ip-precedence node is configured.";
      description
        "EFD IP parameters";
      leaf precedence {
        type uint32 {
          range "0..7";
        }
        mandatory true;
        description
          "IP TOS precedence threshold";
      }
      leaf operation {
        type ncs_rpc_notif_Asr9k-efd-operation;
        default "greater-than-or-equal";
        description
          "IP operation";
      }
    }
  }

  grouping ncs_rpc_notif_IP-PRIORITY-MASK {
    description
      "Common node of node, node-all";
    container ip-priority-mask {
      presence "enable ip-priority-mask";
      description
        "IP Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping ncs_rpc_notif_VLAN-PRIORITY-MASK {
    description
      "Common node of node, node-all";
    container vlan-priority-mask {
      presence "enable vlan-priority-mask";
      description
        "VLAN Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping ncs_rpc_notif_MPLS-PRIORITY-MASK {
    description
      "Common node of node, node-all";
    container mpls-priority-mask {
      presence "enable mpls-priority-mask";
      description
        "MPLS Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping ncs_rpc_notif_BURST-ABSORPTION {
    description
      "Common node of node, node-all";
    leaf burst-absorption {
      type ncs_rpc_notif_Asr9k-efd-burst-absorption;
      description
        "EFD burst absorption parameter.";
    }
  }

  grouping ncs_rpc_notif_ENABLE {
    description
      "Common node of node, node-all";
    leaf enable {
      type empty;
      description
        "Enable EFD for this node";
    }
  }

  grouping ncs_rpc_notif_MODE {
    description
      "Common node of node, node-all";
    leaf mode {
      type ncs_rpc_notif_Asr9k-efd-mode;
      description
        "EFD mode parameter.";
    }
  }

  grouping ncs_rpc_notif_MPLS-EXP {
    description
      "Common node of node, node-all";
    container mpls-exp {
      presence "Indicates a mpls-exp node is configured.";
      description
        "EFD MPLS parameters";
      leaf exp {
        type uint32 {
          range "0..7";
        }
        mandatory true;
        description
          "MPLS EXP threshold";
      }
      leaf operation {
        type ncs_rpc_notif_Asr9k-efd-operation;
        default "greater-than-or-equal";
        description
          "MPLS operation";
      }
    }
  }

  grouping live_ncs_VLAN-COS {
    description
      "Common node of node, node-all";
    container vlan-cos {
      presence "Indicates a vlan-cos node is configured.";
      description
        "EFD VLAN parameters";
      leaf cos {
        type uint32 {
          range "0..7";
        }
        // NCS drop mandatory statement
        description
          "VLAN COS threshold";
      }
      leaf operation {
        type live_ncs_Asr9k-efd-operation;
        // NCS drop default statement
        description
          "VLAN operation";
      }
    }
  }

  grouping live_ncs_IP-PRECEDENCE {
    description
      "Common node of node, node-all";
    container ip-precedence {
      presence "Indicates a ip-precedence node is configured.";
      description
        "EFD IP parameters";
      leaf precedence {
        type uint32 {
          range "0..7";
        }
        // NCS drop mandatory statement
        description
          "IP TOS precedence threshold";
      }
      leaf operation {
        type live_ncs_Asr9k-efd-operation;
        // NCS drop default statement
        description
          "IP operation";
      }
    }
  }

  grouping live_ncs_IP-PRIORITY-MASK {
    description
      "Common node of node, node-all";
    container ip-priority-mask {
      presence "enable ip-priority-mask";
      description
        "IP Priority Mask";
      leaf prec0 {
        type uint32 {
          range "0..1";
        }
        // NCS drop default statement
        description
          "Prec";
      }
      leaf prec1 {
        type uint32 {
          range "0..1";
        }
        // NCS drop default statement
        description
          "Prec";
      }
      leaf prec2 {
        type uint32 {
          range "0..1";
        }
        // NCS drop default statement
        description
          "Prec";
      }
      leaf prec3 {
        type uint32 {
          range "0..1";
        }
        // NCS drop default statement
        description
          "Prec";
      }
      leaf prec4 {
        type uint32 {
          range "0..1";
        }
        // NCS drop default statement
        description
          "Prec";
      }
      leaf prec5 {
        type uint32 {
          range "0..1";
        }
        // NCS drop default statement
        description
          "Prec";
      }
      leaf prec6 {
        type uint32 {
          range "0..1";
        }
        // NCS drop default statement
        description
          "Prec";
      }
      leaf prec7 {
        type uint32 {
          range "0..1";
        }
        // NCS drop default statement
        description
          "Prec";
      }
    }
  }

  grouping live_ncs_VLAN-PRIORITY-MASK {
    description
      "Common node of node, node-all";
    container vlan-priority-mask {
      presence "enable vlan-priority-mask";
      description
        "VLAN Priority Mask";
      leaf prec0 {
        type uint32 {
          range "0..1";
        }
        // NCS drop default statement
        description
          "Prec";
      }
      leaf prec1 {
        type uint32 {
          range "0..1";
        }
        // NCS drop default statement
        description
          "Prec";
      }
      leaf prec2 {
        type uint32 {
          range "0..1";
        }
        // NCS drop default statement
        description
          "Prec";
      }
      leaf prec3 {
        type uint32 {
          range "0..1";
        }
        // NCS drop default statement
        description
          "Prec";
      }
      leaf prec4 {
        type uint32 {
          range "0..1";
        }
        // NCS drop default statement
        description
          "Prec";
      }
      leaf prec5 {
        type uint32 {
          range "0..1";
        }
        // NCS drop default statement
        description
          "Prec";
      }
      leaf prec6 {
        type uint32 {
          range "0..1";
        }
        // NCS drop default statement
        description
          "Prec";
      }
      leaf prec7 {
        type uint32 {
          range "0..1";
        }
        // NCS drop default statement
        description
          "Prec";
      }
    }
  }

  grouping live_ncs_MPLS-PRIORITY-MASK {
    description
      "Common node of node, node-all";
    container mpls-priority-mask {
      presence "enable mpls-priority-mask";
      description
        "MPLS Priority Mask";
      leaf prec0 {
        type uint32 {
          range "0..1";
        }
        // NCS drop default statement
        description
          "Prec";
      }
      leaf prec1 {
        type uint32 {
          range "0..1";
        }
        // NCS drop default statement
        description
          "Prec";
      }
      leaf prec2 {
        type uint32 {
          range "0..1";
        }
        // NCS drop default statement
        description
          "Prec";
      }
      leaf prec3 {
        type uint32 {
          range "0..1";
        }
        // NCS drop default statement
        description
          "Prec";
      }
      leaf prec4 {
        type uint32 {
          range "0..1";
        }
        // NCS drop default statement
        description
          "Prec";
      }
      leaf prec5 {
        type uint32 {
          range "0..1";
        }
        // NCS drop default statement
        description
          "Prec";
      }
      leaf prec6 {
        type uint32 {
          range "0..1";
        }
        // NCS drop default statement
        description
          "Prec";
      }
      leaf prec7 {
        type uint32 {
          range "0..1";
        }
        // NCS drop default statement
        description
          "Prec";
      }
    }
  }

  grouping live_ncs_BURST-ABSORPTION {
    description
      "Common node of node, node-all";
    leaf burst-absorption {
      type live_ncs_Asr9k-efd-burst-absorption;
      description
        "EFD burst absorption parameter.";
    }
  }

  grouping live_ncs_ENABLE {
    description
      "Common node of node, node-all";
    leaf enable {
      type empty;
      description
        "Enable EFD for this node";
    }
  }

  grouping live_ncs_MODE {
    description
      "Common node of node, node-all";
    leaf mode {
      type live_ncs_Asr9k-efd-mode;
      description
        "EFD mode parameter.";
    }
  }

  grouping live_ncs_MPLS-EXP {
    description
      "Common node of node, node-all";
    container mpls-exp {
      presence "Indicates a mpls-exp node is configured.";
      description
        "EFD MPLS parameters";
      leaf exp {
        type uint32 {
          range "0..7";
        }
        // NCS drop mandatory statement
        description
          "MPLS EXP threshold";
      }
      leaf operation {
        type live_ncs_Asr9k-efd-operation;
        // NCS drop default statement
        description
          "MPLS operation";
      }
    }
  }

  grouping VLAN-COS {
    description
      "Common node of node, node-all";
    container vlan-cos {
      presence "Indicates a vlan-cos node is configured.";
      description
        "EFD VLAN parameters";
      leaf cos {
        type uint32 {
          range "0..7";
        }
        mandatory true;
        description
          "VLAN COS threshold";
      }
      leaf operation {
        type Asr9k-efd-operation;
        default "greater-than-or-equal";
        description
          "VLAN operation";
      }
    }
  }

  grouping IP-PRECEDENCE {
    description
      "Common node of node, node-all";
    container ip-precedence {
      presence "Indicates a ip-precedence node is configured.";
      description
        "EFD IP parameters";
      leaf precedence {
        type uint32 {
          range "0..7";
        }
        mandatory true;
        description
          "IP TOS precedence threshold";
      }
      leaf operation {
        type Asr9k-efd-operation;
        default "greater-than-or-equal";
        description
          "IP operation";
      }
    }
  }

  grouping IP-PRIORITY-MASK {
    description
      "Common node of node, node-all";
    container ip-priority-mask {
      presence "enable ip-priority-mask";
      description
        "IP Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping VLAN-PRIORITY-MASK {
    description
      "Common node of node, node-all";
    container vlan-priority-mask {
      presence "enable vlan-priority-mask";
      description
        "VLAN Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping MPLS-PRIORITY-MASK {
    description
      "Common node of node, node-all";
    container mpls-priority-mask {
      presence "enable mpls-priority-mask";
      description
        "MPLS Priority Mask";
      leaf prec0 {
        type uint32 {
          range "0..1";
        }
        default "0";
        description
          "Prec";
      }
      leaf prec1 {
        type uint32 {
          range "0..1";
        }
        default "0";
        description
          "Prec";
      }
      leaf prec2 {
        type uint32 {
          range "0..1";
        }
        default "0";
        description
          "Prec";
      }
      leaf prec3 {
        type uint32 {
          range "0..1";
        }
        default "0";
        description
          "Prec";
      }
      leaf prec4 {
        type uint32 {
          range "0..1";
        }
        default "0";
        description
          "Prec";
      }
      leaf prec5 {
        type uint32 {
          range "0..1";
        }
        default "0";
        description
          "Prec";
      }
      leaf prec6 {
        type uint32 {
          range "0..1";
        }
        default "0";
        description
          "Prec";
      }
      leaf prec7 {
        type uint32 {
          range "0..1";
        }
        default "0";
        description
          "Prec";
      }
    }
  }

  grouping BURST-ABSORPTION {
    description
      "Common node of node, node-all";
    leaf burst-absorption {
      type Asr9k-efd-burst-absorption;
      description
        "EFD burst absorption parameter.";
    }
  }

  grouping ENABLE {
    description
      "Common node of node, node-all";
    leaf enable {
      type empty;
      description
        "Enable EFD for this node";
    }
  }

  grouping MODE {
    description
      "Common node of node, node-all";
    leaf mode {
      type Asr9k-efd-mode;
      description
        "EFD mode parameter.";
    }
  }

  grouping MPLS-EXP {
    description
      "Common node of node, node-all";
    container mpls-exp {
      presence "Indicates a mpls-exp node is configured.";
      description
        "EFD MPLS parameters";
      leaf exp {
        type uint32 {
          range "0..7";
        }
        mandatory true;
        description
          "MPLS EXP threshold";
      }
      leaf operation {
        type Asr9k-efd-operation;
        default "greater-than-or-equal";
        description
          "MPLS operation";
      }
    }
  }

  augment "/ncs:devices/ncs:device/ncs:config" {
    container hardware-module-buffer-carve-mode {
      tailf:ncs-device-type "netconf";
      tailf:display-when "not(../../ncs:module) or ../../ncs:module[ncs:name='Cisco-IOS-XR-asr9k-prm-cfg']";
      description
        "Buffer carve mode in hardware module port(s)";
      container nodes {
        description
          "Buffer carve applicable nodes";
        list node {
          key "node-name";
          description
            "A node";
          leaf static {
            type empty;
            description
              "Enable Static Buffer carve mode";
          }
          leaf node-name {
            type xr:Node-id;
            description
              "Node ID";
          }
        }
      }
    }
    container hardware-module-qos-mode {
      tailf:ncs-device-type "netconf";
      tailf:display-when "not(../../ncs:module) or ../../ncs:module[ncs:name='Cisco-IOS-XR-asr9k-prm-cfg']";
      description
        "QoS mode in hardware module port(s)";
      container nodes {
        description
          "QoS applicable nodes";
        list node {
          key "node-name";
          description
            "A node";
          leaf child-shaping-disable {
            type empty;
            description
              "Disable child level/flat policy shaping";
          }
          leaf lowburst-enable {
            type empty;
            description
              "Enable low burst mode for TM entity";
          }
          leaf node-name {
            type xr:Node-id;
            description
              "Node ID";
          }
        }
      }
    }
    container hardware-module-processor {
      tailf:ncs-device-type "netconf";
      tailf:display-when "not(../../ncs:module) or ../../ncs:module[ncs:name='Cisco-IOS-XR-asr9k-prm-cfg']";
      description
        "Processor configuration";
      container nodes {
        description
          "applicable nodeTable";
        list node {
          key "node-name";
          description
            "applicable node";
          leaf mode {
            type Prm-processor-config;
            description
              "Processor mode setting";
          }
          leaf node-name {
            type xr:Node-id;
            description
              "Node ID";
          }
        }
      }
    }
    container hardware-module-reset {
      tailf:ncs-device-type "netconf";
      tailf:display-when "not(../../ncs:module) or ../../ncs:module[ncs:name='Cisco-IOS-XR-asr9k-prm-cfg']";
      description
        "Reset configuration";
      container threshold {
        description
          "Threshold";
        container reset-infinite {
          description
            "Reset threshold value infinite";
          leaf disable-logging {
            type uint32;
            description
              "Disable np datalogging";
          }
          leaf enable-logging {
            type uint32;
            description
              "Enable np datalogging";
          }
        }
        container reset10 {
          description
            "Reset threshold value 10";
          leaf reload10 {
            type uint32;
            description
              "Reload after value of 10 reached";
          }
          leaf slice10 {
            type uint32;
            description
              "Slice down after value of 10 reached";
          }
        }
        container reset5 {
          description
            "Reset threshold value 5";
          leaf slice5 {
            type uint32;
            description
              "Slice down after value of 5 reached";
          }
          leaf reload5 {
            type uint32;
            description
              "Reload after value of 5 reached";
          }
        }
      }
    }
    container hardware-module-tcp-mss-adjust {
      tailf:ncs-device-type "netconf";
      tailf:display-when "not(../../ncs:module) or ../../ncs:module[ncs:name='Cisco-IOS-XR-asr9k-prm-cfg']";
      description
        "TCP MSS Adjust value in hardware module";
      container nodes {
        description
          "TCP MSS Adjust applicable nodes";
        list node {
          key "node-name";
          description
            "A node";
          container nps {
            description
              "TCP MSS Adjust NPs";
            list np {
              key "np-id";
              description
                "NP number";
              leaf adjust-value {
                type uint32 {
                  range "1280..1535";
                }
                units "byte";
                description
                  "TCP MSS Adjust value";
              }
              leaf np-id {
                type uint32 {
                  range "0..7";
                }
                description
                  "Number between 0-7";
              }
            }
          }
          leaf node-name {
            type xr:Node-id;
            description
              "Node ID";
          }
        }
      }
    }
    container hardware-module-tcam {
      tailf:ncs-device-type "netconf";
      tailf:display-when "not(../../ncs:module) or ../../ncs:module[ncs:name='Cisco-IOS-XR-asr9k-prm-cfg']";
      description
        "TCAM";
      container nodes {
        description
          "TCAM applicable nodes";
        list node {
          key "node-name";
          description
            "A TCAM applicable node";
          leaf profile {
            type Prm-tcam-profile;
            default "profile0";
            description
              "A TCAM partition profile";
          }
          leaf node-name {
            type xr:Node-id;
            description
              "Node ID";
          }
        }
      }
      leaf global-profile {
        type Prm-tcam-profile;
        default "profile0";
        description
          "Global TCAM partition profile for all TCAM
           applicable nodes";
      }
    }
    container hardware-module-profile {
      tailf:ncs-device-type "netconf";
      tailf:display-when "not(../../ncs:module) or ../../ncs:module[ncs:name='Cisco-IOS-XR-asr9k-prm-cfg']";
      description
        "Memory resource configuration";
      container nodes {
        description
          "TCAM partition sizing applicable nodes";
        list node {
          key "node-name";
          description
            "A TCAM partition sizing applicable node";
          container lightspeed-tcam-partition {
            description
              "Lightspeed Tcam partition profile";
            leaf v4-ing {
              type uint32 {
                range "1..13";
              }
              default "8";
              description
                "Lightspeed Tcam Block count for 160-ingress
                 region";
            }
            leaf v4-egr {
              type uint32 {
                range "1..13";
              }
              default "4";
              description
                "Lightspeed Tcam Block count for 160-egress
                 region";
            }
            leaf v6-ing {
              type uint32 {
                range "1..13";
              }
              default "3";
              description
                "Lightspeed Tcam Block count for 640-ingress
                 region";
            }
            leaf v6-egr {
              type uint32 {
                range "1..13";
              }
              default "1";
              description
                "Lightspeed Tcam Block count for 640-egress
                 region";
            }
          }
          leaf internal-tcam-partition {
            type Prm-config-internal-tcam-part-profile;
            default "to-default";
            description
              "Internal Tcam partition profile";
          }
          leaf node-name {
            type xr:Node-id;
            description
              "Node Name";
          }
        }
      }
      leaf scale-active {
        type Prm-config-scale-profile;
        default "default";
        description
          "Memory resource profile scale active";
      }
      leaf scale {
        type Prm-config-scale-profile;
        default "default";
        description
          "Memory resource profile scale";
      }
    }
    container hardware-module-efd {
      tailf:ncs-device-type "netconf";
      tailf:display-when "not(../../ncs:module) or ../../ncs:module[ncs:name='Cisco-IOS-XR-asr9k-prm-cfg']";
      description
        "EFD (Early Fast Discard)";
      container node-all {
        description
          "All nodes";
        uses VLAN-PRIORITY-MASK;
        uses IP-PRECEDENCE;
        uses VLAN-COS;
        uses ENABLE;
        uses IP-PRIORITY-MASK;
        uses MPLS-PRIORITY-MASK;
        uses MODE;
        uses BURST-ABSORPTION;
        uses MPLS-EXP;
      }
      container nodes {
        description
          "EFD applicable nodes";
        list node {
          key "node-name";
          description
            "A node";
          leaf node-name {
            type xr:Node-id;
            description
              "Node Name";
          }
          uses VLAN-PRIORITY-MASK;
          uses IP-PRECEDENCE;
          uses VLAN-COS;
          uses ENABLE;
          uses IP-PRIORITY-MASK;
          uses MPLS-PRIORITY-MASK;
          uses MODE;
          uses BURST-ABSORPTION;
          uses MPLS-EXP;
        }
      }
    }
    container hardware-module-all-qos-mode {
      tailf:ncs-device-type "netconf";
      tailf:display-when "not(../../ncs:module) or ../../ncs:module[ncs:name='Cisco-IOS-XR-asr9k-prm-cfg']";
      description
        "Global qos-mode in hardware module";
      leaf per-priority-buffer-limit {
        type empty;
        description
          "enable per-priority-buffer-limit";
      }
      leaf ingress-queue {
        type empty;
        description
          "Enable ingress queue for MOD-80 4X10G MPA or
           MOD-400 20X10G MPAor MOD-200 8X10G MPA";
      }
      leaf aggregate-bundle-mode {
        type empty;
        description
          "Enable aggregate bundle mode ";
      }
      leaf bundle-aggregate-policer-mode {
        type empty;
        description
          "Enable bundle aggregate policer mode ";
      }
      leaf wred-buffer-mode {
        type empty;
        description
          "Enable L4 wred accounting buffer mode";
      }
    }
  }
  augment "/ncs:devices/ncs:device/ncs:live-status" {
    container hardware-module-buffer-carve-mode {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "Buffer carve mode in hardware module port(s)";
      container nodes {
        description
          "Buffer carve applicable nodes";
        list node {
          key "node-name";
          description
            "A node";
          leaf static {
            type empty;
            description
              "Enable Static Buffer carve mode";
          }
          leaf node-name {
            type xr:live_ncs_Node-id;
            description
              "Node ID";
          }
        }
      }
    }
    container hardware-module-qos-mode {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "QoS mode in hardware module port(s)";
      container nodes {
        description
          "QoS applicable nodes";
        list node {
          key "node-name";
          description
            "A node";
          leaf child-shaping-disable {
            type empty;
            description
              "Disable child level/flat policy shaping";
          }
          leaf lowburst-enable {
            type empty;
            description
              "Enable low burst mode for TM entity";
          }
          leaf node-name {
            type xr:live_ncs_Node-id;
            description
              "Node ID";
          }
        }
      }
    }
    container hardware-module-processor {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "Processor configuration";
      container nodes {
        description
          "applicable nodeTable";
        list node {
          key "node-name";
          description
            "applicable node";
          leaf mode {
            type live_ncs_Prm-processor-config;
            description
              "Processor mode setting";
          }
          leaf node-name {
            type xr:live_ncs_Node-id;
            description
              "Node ID";
          }
        }
      }
    }
    container hardware-module-reset {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "Reset configuration";
      container threshold {
        description
          "Threshold";
        container reset-infinite {
          description
            "Reset threshold value infinite";
          leaf disable-logging {
            type uint32;
            description
              "Disable np datalogging";
          }
          leaf enable-logging {
            type uint32;
            description
              "Enable np datalogging";
          }
        }
        container reset10 {
          description
            "Reset threshold value 10";
          leaf reload10 {
            type uint32;
            description
              "Reload after value of 10 reached";
          }
          leaf slice10 {
            type uint32;
            description
              "Slice down after value of 10 reached";
          }
        }
        container reset5 {
          description
            "Reset threshold value 5";
          leaf slice5 {
            type uint32;
            description
              "Slice down after value of 5 reached";
          }
          leaf reload5 {
            type uint32;
            description
              "Reload after value of 5 reached";
          }
        }
      }
    }
    container hardware-module-tcp-mss-adjust {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "TCP MSS Adjust value in hardware module";
      container nodes {
        description
          "TCP MSS Adjust applicable nodes";
        list node {
          key "node-name";
          description
            "A node";
          container nps {
            description
              "TCP MSS Adjust NPs";
            list np {
              key "np-id";
              description
                "NP number";
              leaf adjust-value {
                type uint32 {
                  range "1280..1535";
                }
                units "byte";
                description
                  "TCP MSS Adjust value";
              }
              leaf np-id {
                type uint32 {
                  range "0..7";
                }
                description
                  "Number between 0-7";
              }
            }
          }
          leaf node-name {
            type xr:live_ncs_Node-id;
            description
              "Node ID";
          }
        }
      }
    }
    container hardware-module-tcam {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "TCAM";
      container nodes {
        description
          "TCAM applicable nodes";
        list node {
          key "node-name";
          description
            "A TCAM applicable node";
          leaf profile {
            type live_ncs_Prm-tcam-profile;
            // NCS drop default statement
            description
              "A TCAM partition profile";
          }
          leaf node-name {
            type xr:live_ncs_Node-id;
            description
              "Node ID";
          }
        }
      }
      leaf global-profile {
        type live_ncs_Prm-tcam-profile;
        // NCS drop default statement
        description
          "Global TCAM partition profile for all TCAM
           applicable nodes";
      }
    }
    container hardware-module-profile {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "Memory resource configuration";
      container nodes {
        description
          "TCAM partition sizing applicable nodes";
        list node {
          key "node-name";
          description
            "A TCAM partition sizing applicable node";
          container lightspeed-tcam-partition {
            description
              "Lightspeed Tcam partition profile";
            leaf v4-ing {
              type uint32 {
                range "1..13";
              }
              // NCS drop default statement
              description
                "Lightspeed Tcam Block count for 160-ingress
                 region";
            }
            leaf v4-egr {
              type uint32 {
                range "1..13";
              }
              // NCS drop default statement
              description
                "Lightspeed Tcam Block count for 160-egress
                 region";
            }
            leaf v6-ing {
              type uint32 {
                range "1..13";
              }
              // NCS drop default statement
              description
                "Lightspeed Tcam Block count for 640-ingress
                 region";
            }
            leaf v6-egr {
              type uint32 {
                range "1..13";
              }
              // NCS drop default statement
              description
                "Lightspeed Tcam Block count for 640-egress
                 region";
            }
          }
          leaf internal-tcam-partition {
            type live_ncs_Prm-config-internal-tcam-part-profile;
            // NCS drop default statement
            description
              "Internal Tcam partition profile";
          }
          leaf node-name {
            type xr:live_ncs_Node-id;
            description
              "Node Name";
          }
        }
      }
      leaf scale-active {
        type live_ncs_Prm-config-scale-profile;
        // NCS drop default statement
        description
          "Memory resource profile scale active";
      }
      leaf scale {
        type live_ncs_Prm-config-scale-profile;
        // NCS drop default statement
        description
          "Memory resource profile scale";
      }
    }
    container hardware-module-efd {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "EFD (Early Fast Discard)";
      container node-all {
        description
          "All nodes";
        uses live_ncs_VLAN-PRIORITY-MASK;
        uses live_ncs_IP-PRECEDENCE;
        uses live_ncs_VLAN-COS;
        uses live_ncs_ENABLE;
        uses live_ncs_IP-PRIORITY-MASK;
        uses live_ncs_MPLS-PRIORITY-MASK;
        uses live_ncs_MODE;
        uses live_ncs_BURST-ABSORPTION;
        uses live_ncs_MPLS-EXP;
      }
      container nodes {
        description
          "EFD applicable nodes";
        list node {
          key "node-name";
          description
            "A node";
          leaf node-name {
            type xr:live_ncs_Node-id;
            description
              "Node Name";
          }
          uses live_ncs_VLAN-PRIORITY-MASK;
          uses live_ncs_IP-PRECEDENCE;
          uses live_ncs_VLAN-COS;
          uses live_ncs_ENABLE;
          uses live_ncs_IP-PRIORITY-MASK;
          uses live_ncs_MPLS-PRIORITY-MASK;
          uses live_ncs_MODE;
          uses live_ncs_BURST-ABSORPTION;
          uses live_ncs_MPLS-EXP;
        }
      }
    }
    container hardware-module-all-qos-mode {
      tailf:ncs-device-type "netconf";
      tailf:display-when "not(../../ncs:module) or ../../ncs:module[ncs:name='Cisco-IOS-XR-asr9k-prm-cfg'] or (../../ncs:live-status-protocol[not(ncs:capability)]) or (../../ncs:live-status-protocol/ncs:capability/ncs:module[.='Cisco-IOS-XR-asr9k-prm-cfg'])";
      description
        "Global qos-mode in hardware module";
      leaf per-priority-buffer-limit {
        type empty;
        description
          "enable per-priority-buffer-limit";
      }
      leaf ingress-queue {
        type empty;
        description
          "Enable ingress queue for MOD-80 4X10G MPA or
           MOD-400 20X10G MPAor MOD-200 8X10G MPA";
      }
      leaf aggregate-bundle-mode {
        type empty;
        description
          "Enable aggregate bundle mode ";
      }
      leaf bundle-aggregate-policer-mode {
        type empty;
        description
          "Enable bundle aggregate policer mode ";
      }
      leaf wred-buffer-mode {
        type empty;
        description
          "Enable L4 wred accounting buffer mode";
      }
    }
  }
  augment "/ncs:devices/ncs:template/ncs:ned-id/ncs:config" {
    container hardware-module-buffer-carve-mode {
      description
        "Buffer carve mode in hardware module port(s)";
      container nodes {
        description
          "Buffer carve applicable nodes";
        list node {
          // NCS patched for predictable order
          ordered-by user;
          key "node-name";
          description
            "A node";
          leaf static {
            type empty;
            description
              "Enable Static Buffer carve mode";
          }
          leaf node-name {
            type xr:ncs_template_Node-id;
            description
              "Node ID";
          }
        }
      }
    }
    container hardware-module-qos-mode {
      description
        "QoS mode in hardware module port(s)";
      container nodes {
        description
          "QoS applicable nodes";
        list node {
          // NCS patched for predictable order
          ordered-by user;
          key "node-name";
          description
            "A node";
          leaf child-shaping-disable {
            type empty;
            description
              "Disable child level/flat policy shaping";
          }
          leaf lowburst-enable {
            type empty;
            description
              "Enable low burst mode for TM entity";
          }
          leaf node-name {
            type xr:ncs_template_Node-id;
            description
              "Node ID";
          }
        }
      }
    }
    container hardware-module-processor {
      description
        "Processor configuration";
      container nodes {
        description
          "applicable nodeTable";
        list node {
          // NCS patched for predictable order
          ordered-by user;
          key "node-name";
          description
            "applicable node";
          leaf mode {
            type ncs_template_Prm-processor-config;
            description
              "Processor mode setting";
          }
          leaf node-name {
            type xr:ncs_template_Node-id;
            description
              "Node ID";
          }
        }
      }
    }
    container hardware-module-reset {
      description
        "Reset configuration";
      container threshold {
        description
          "Threshold";
        container reset-infinite {
          description
            "Reset threshold value infinite";
          leaf disable-logging {
            type string;
            description
              "Disable np datalogging";
          }
          leaf enable-logging {
            type string;
            description
              "Enable np datalogging";
          }
        }
        container reset10 {
          description
            "Reset threshold value 10";
          leaf reload10 {
            type string;
            description
              "Reload after value of 10 reached";
          }
          leaf slice10 {
            type string;
            description
              "Slice down after value of 10 reached";
          }
        }
        container reset5 {
          description
            "Reset threshold value 5";
          leaf slice5 {
            type string;
            description
              "Slice down after value of 5 reached";
          }
          leaf reload5 {
            type string;
            description
              "Reload after value of 5 reached";
          }
        }
      }
    }
    container hardware-module-tcp-mss-adjust {
      description
        "TCP MSS Adjust value in hardware module";
      container nodes {
        description
          "TCP MSS Adjust applicable nodes";
        list node {
          // NCS patched for predictable order
          ordered-by user;
          key "node-name";
          description
            "A node";
          container nps {
            description
              "TCP MSS Adjust NPs";
            list np {
              // NCS patched for predictable order
              ordered-by user;
              key "np-id";
              description
                "NP number";
              leaf adjust-value {
                type string;
                units "byte";
                description
                  "TCP MSS Adjust value";
              }
              leaf np-id {
                type string;
                description
                  "Number between 0-7";
              }
            }
          }
          leaf node-name {
            type xr:ncs_template_Node-id;
            description
              "Node ID";
          }
        }
      }
    }
    container hardware-module-tcam {
      description
        "TCAM";
      container nodes {
        description
          "TCAM applicable nodes";
        list node {
          // NCS patched for predictable order
          ordered-by user;
          key "node-name";
          description
            "A TCAM applicable node";
          leaf profile {
            type ncs_template_Prm-tcam-profile;
            // NCS drop default statement
            description
              "A TCAM partition profile";
          }
          leaf node-name {
            type xr:ncs_template_Node-id;
            description
              "Node ID";
          }
        }
      }
      leaf global-profile {
        type ncs_template_Prm-tcam-profile;
        // NCS drop default statement
        description
          "Global TCAM partition profile for all TCAM
           applicable nodes";
      }
    }
    container hardware-module-profile {
      description
        "Memory resource configuration";
      container nodes {
        description
          "TCAM partition sizing applicable nodes";
        list node {
          // NCS patched for predictable order
          ordered-by user;
          key "node-name";
          description
            "A TCAM partition sizing applicable node";
          container lightspeed-tcam-partition {
            description
              "Lightspeed Tcam partition profile";
            leaf v4-ing {
              type string;
              // NCS drop default statement
              description
                "Lightspeed Tcam Block count for 160-ingress
                 region";
            }
            leaf v4-egr {
              type string;
              // NCS drop default statement
              description
                "Lightspeed Tcam Block count for 160-egress
                 region";
            }
            leaf v6-ing {
              type string;
              // NCS drop default statement
              description
                "Lightspeed Tcam Block count for 640-ingress
                 region";
            }
            leaf v6-egr {
              type string;
              // NCS drop default statement
              description
                "Lightspeed Tcam Block count for 640-egress
                 region";
            }
          }
          leaf internal-tcam-partition {
            type ncs_template_Prm-config-internal-tcam-part-profile;
            // NCS drop default statement
            description
              "Internal Tcam partition profile";
          }
          leaf node-name {
            type xr:ncs_template_Node-id;
            description
              "Node Name";
          }
        }
      }
      leaf scale-active {
        type ncs_template_Prm-config-scale-profile;
        // NCS drop default statement
        description
          "Memory resource profile scale active";
      }
      leaf scale {
        type ncs_template_Prm-config-scale-profile;
        // NCS drop default statement
        description
          "Memory resource profile scale";
      }
    }
    container hardware-module-efd {
      description
        "EFD (Early Fast Discard)";
      container node-all {
        description
          "All nodes";
        uses ncs_template_VLAN-PRIORITY-MASK;
        uses ncs_template_IP-PRECEDENCE;
        uses ncs_template_VLAN-COS;
        uses ncs_template_ENABLE;
        uses ncs_template_IP-PRIORITY-MASK;
        uses ncs_template_MPLS-PRIORITY-MASK;
        uses ncs_template_MODE;
        uses ncs_template_BURST-ABSORPTION;
        uses ncs_template_MPLS-EXP;
      }
      container nodes {
        description
          "EFD applicable nodes";
        list node {
          // NCS patched for predictable order
          ordered-by user;
          key "node-name";
          description
            "A node";
          leaf node-name {
            type xr:ncs_template_Node-id;
            description
              "Node Name";
          }
          uses ncs_template_VLAN-PRIORITY-MASK;
          uses ncs_template_IP-PRECEDENCE;
          uses ncs_template_VLAN-COS;
          uses ncs_template_ENABLE;
          uses ncs_template_IP-PRIORITY-MASK;
          uses ncs_template_MPLS-PRIORITY-MASK;
          uses ncs_template_MODE;
          uses ncs_template_BURST-ABSORPTION;
          uses ncs_template_MPLS-EXP;
        }
      }
    }
    container hardware-module-all-qos-mode {
      description
        "Global qos-mode in hardware module";
      leaf per-priority-buffer-limit {
        type empty;
        description
          "enable per-priority-buffer-limit";
      }
      leaf ingress-queue {
        type empty;
        description
          "Enable ingress queue for MOD-80 4X10G MPA or
           MOD-400 20X10G MPAor MOD-200 8X10G MPA";
      }
      leaf aggregate-bundle-mode {
        type empty;
        description
          "Enable aggregate bundle mode ";
      }
      leaf bundle-aggregate-policer-mode {
        type empty;
        description
          "Enable bundle aggregate policer mode ";
      }
      leaf wred-buffer-mode {
        type empty;
        description
          "Enable L4 wred accounting buffer mode";
      }
    }
  }
}

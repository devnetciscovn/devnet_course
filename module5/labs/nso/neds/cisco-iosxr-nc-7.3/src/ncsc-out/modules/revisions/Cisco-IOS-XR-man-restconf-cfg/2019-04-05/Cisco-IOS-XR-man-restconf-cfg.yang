module Cisco-IOS-XR-man-restconf-cfg {
  // Generated by yanger -t ncs
  tailf:mount-id "cisco-iosxr-nc-7.3:cisco-iosxr-nc-7.3";
  tailf:ncs-device-type "netconf";

  namespace "http://cisco.com/ns/yang/Cisco-IOS-XR-man-restconf-cfg";
  prefix man-restconf-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-restconf package configuration.

     This module contains definitions
     for the following management objects:
       restconf: RESTCONF configuration commands

     Copyright (c) 2013-2019 by Cisco Systems, Inc.
     All rights reserved.";

  revision 2019-04-05 {
    description
      "Establish semantic version baseline.";
    semver:module-version "1.0.0";
  }
  revision 2017-12-01 {
    description
      "Range value restrictions adjusted for open-request-limit and per-user-request-limit leafs.";
  }
  revision 2015-11-09 {
    description
      "IOS XR 6.0 revision.";
  }

  augment "/ncs:devices/ncs:device/ncs:config" {
    container restconf {
      tailf:ncs-device-type "netconf";
      tailf:display-when "not(../../ncs:module) or ../../ncs:module[ncs:name='Cisco-IOS-XR-man-restconf-cfg']";
      description
        "RESTCONF configuration commands";
      container agent {
        description
          "RESTCONF agent configuration commands";
        leaf open-request-limit {
          type uint32 {
            range "1..256";
          }
          description
            "Count of allowable concurrent restconf requests";
        }
        leaf enable {
          type empty;
          description
            "Enable RESTCONF agent";
        }
        leaf per-user-request-limit {
          type uint32 {
            range "1..256";
          }
          description
            "Count of allowable concurrent restconf requests
             per user";
        }
      }
    }
  }
  augment "/ncs:devices/ncs:device/ncs:live-status" {
    container restconf {
      tailf:ncs-device-type "netconf";
      tailf:display-when "not(../../ncs:module) or ../../ncs:module[ncs:name='Cisco-IOS-XR-man-restconf-cfg'] or (../../ncs:live-status-protocol[not(ncs:capability)]) or (../../ncs:live-status-protocol/ncs:capability/ncs:module[.='Cisco-IOS-XR-man-restconf-cfg'])";
      description
        "RESTCONF configuration commands";
      container agent {
        description
          "RESTCONF agent configuration commands";
        leaf open-request-limit {
          type uint32 {
            range "1..256";
          }
          description
            "Count of allowable concurrent restconf requests";
        }
        leaf enable {
          type empty;
          description
            "Enable RESTCONF agent";
        }
        leaf per-user-request-limit {
          type uint32 {
            range "1..256";
          }
          description
            "Count of allowable concurrent restconf requests
             per user";
        }
      }
    }
  }
  augment "/ncs:devices/ncs:template/ncs:ned-id/ncs:config" {
    container restconf {
      description
        "RESTCONF configuration commands";
      container agent {
        description
          "RESTCONF agent configuration commands";
        leaf open-request-limit {
          type string;
          description
            "Count of allowable concurrent restconf requests";
        }
        leaf enable {
          type empty;
          description
            "Enable RESTCONF agent";
        }
        leaf per-user-request-limit {
          type string;
          description
            "Count of allowable concurrent restconf requests
             per user";
        }
      }
    }
  }
}

module Cisco-IOS-XR-ifmgr-oper {
  // Generated by yanger -t ncs
  tailf:mount-id "cisco-iosxr-nc-7.3:cisco-iosxr-nc-7.3";
  tailf:ncs-device-type "netconf";

  namespace "http://cisco.com/ns/yang/Cisco-IOS-XR-ifmgr-oper";
  prefix ifmgr-oper;

  import Cisco-IOS-XR-types {
    prefix xr;
  }
  import cisco-semver {
    prefix semver;
  }
  include Cisco-IOS-XR-ifmgr-oper-sub2 {
    revision-date 2020-10-01;
  }
  include Cisco-IOS-XR-ifmgr-oper-sub1 {
    revision-date 2020-10-01;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ifmgr package operational data.

     This module contains definitions
     for the following management objects:
       interface-dampening: Interface dampening configuration for an
         interface
       interface-properties: Non feature-specific interface
         operational data

     Copyright (c) 2013-2020 by Cisco Systems, Inc.
     All rights reserved.";

  revision 2020-10-01 {
    description
      "64-bit bandwidth changes";
    semver:module-version "2.0.0";
  }
  revision 2019-12-03 {
    description
      "Updated description.";
    semver:module-version "2.0.0";
  }
  revision 2019-07-23 {
    description
      "IosApi version change
       2019-05-30
       64 bit bandwidth changes.";
    semver:module-version "1.1.0";
  }
  revision 2019-04-05 {
    description
      "Establish semantic version baseline.";
    semver:module-version "1.0.0";
  }
  revision 2015-07-30 {
    description
      "IOS XR 5.3.2 revision.";
  }
  revision 2015-01-07 {
    description
      "IOS XR 5.3.1 revision.";
  }

  grouping ncs_template_INTERFACE-TABLE {
    description
      "Common node of system-view, locationview,
       pq-node-location";
    container interfaces {
      description
        "Operational data for all interfaces and
         controllers";
      list interface {
        // NCS patched for predictable order
        ordered-by user;
        key "interface-name";
        description
          "The operational attributes for a particular
           interface";
        leaf interface-name {
          type xr:ncs_template_Interface-name;
          description
            "The name of the interface";
        }
        uses ncs_template_IMDS-IFATTR-BASE-INFO;
      }
    }
  }

  grouping ncs_rpc_notif_INTERFACE-TABLE {
    description
      "Common node of system-view, locationview,
       pq-node-location";
    container interfaces {
      description
        "Operational data for all interfaces and
         controllers";
      list interface {
        key "interface-name";
        description
          "The operational attributes for a particular
           interface";
        leaf interface-name {
          type xr:ncs_rpc_notif_Interface-name;
          description
            "The name of the interface";
        }
        uses ncs_rpc_notif_IMDS-IFATTR-BASE-INFO;
      }
    }
  }

  grouping live_ncs_INTERFACE-TABLE {
    description
      "Common node of system-view, locationview,
       pq-node-location";
    container interfaces {
      description
        "Operational data for all interfaces and
         controllers";
      list interface {
        key "interface-name";
        description
          "The operational attributes for a particular
           interface";
        leaf interface-name {
          type xr:live_ncs_Interface-name;
          description
            "The name of the interface";
        }
        uses live_ncs_IMDS-IFATTR-BASE-INFO;
      }
    }
  }

  grouping INTERFACE-TABLE {
    description
      "Common node of system-view, locationview,
       pq-node-location";
    container interfaces {
      description
        "Operational data for all interfaces and
         controllers";
      list interface {
        key "interface-name";
        description
          "The operational attributes for a particular
           interface";
        leaf interface-name {
          type xr:Interface-name;
          description
            "The name of the interface";
        }
        uses IMDS-IFATTR-BASE-INFO;
      }
    }
  }

  augment "/ncs:devices/ncs:device/ncs:config" {
    // NCS drop config false container 'interface-dampening'
    // NCS drop config false container 'interface-properties'
  }
  augment "/ncs:devices/ncs:device/ncs:live-status" {
    container interface-dampening {
      tailf:ncs-device-type "netconf";
      tailf:display-when "not(../../ncs:module) or ../../ncs:module[ncs:name='Cisco-IOS-XR-ifmgr-oper'] or (../../ncs:live-status-protocol[not(ncs:capability)]) or (../../ncs:live-status-protocol/ncs:capability/ncs:module[.='Cisco-IOS-XR-ifmgr-oper'])";
      description
        "Interface dampening configuration for an
         interface";
      container interfaces {
        description
          "The interface list for which dampening info is
           available";
        list interface {
          key "interface-name";
          description
            "The interface for which dampening info is being
             queried";
          container if-dampening {
            description
              "Dampening info for the interface";
            uses live_ncs_IM-SHOW-DAMP-INFO;
          }
          leaf interface-name {
            type xr:live_ncs_Interface-name;
            description
              "The name of the";
          }
        }
      }
      container nodes {
        description
          "The location of the interface(s) being queried";
        list node {
          key "node-name";
          description
            "The location of the interface(s) being queried";
          container show {
            description
              "Show details for the interfaces";
            container dampening {
              description
                "Dampening information of the interface(s)
                 being queried";
              container if-handles {
                description
                  "Interface handle for which dampening info
                   queried";
                list if-handle {
                  key "interface-handle-name";
                  description
                    "Dampening info for the interface handle";
                  leaf interface-handle-name {
                    type xr:live_ncs_Cisco-ios-xr-string;
                    description
                      "The interface handle";
                  }
                  uses live_ncs_IM-SHOW-DAMP-INFO;
                }
              }
              container interfaces {
                description
                  "Table of interfaces for which dampening info
                   can be queried";
                list interface {
                  key "interface-name";
                  description
                    "Dampening info for the interface";
                  leaf interface-name {
                    type xr:live_ncs_Interface-name;
                    description
                      "The name of the";
                  }
                  uses live_ncs_IM-SHOW-DAMP-INFO;
                }
              }
            }
          }
          leaf node-name {
            type xr:live_ncs_Node-id;
            description
              "The location of the interface(s)";
          }
        }
      }
    }
    container interface-properties {
      tailf:ncs-device-type "netconf";
      tailf:display-when "not(../../ncs:module) or ../../ncs:module[ncs:name='Cisco-IOS-XR-ifmgr-oper'] or (../../ncs:live-status-protocol[not(ncs:capability)]) or (../../ncs:live-status-protocol/ncs:capability/ncs:module[.='Cisco-IOS-XR-ifmgr-oper'])";
      description
        "Non feature-specific interface operational data";
      container data-nodes {
        description
          "Operational data for interfaces";
        list data-node {
          key "data-node-name";
          description
            "The location of a (D)RP in the same LR as the
             interface being queried";
          container locationviews {
            description
              "Location-specific view of interface
               operational data";
            list locationview {
              key "locationview-name";
              description
                "Operational data for all interfaces and
                 controllers on a particular node";
              leaf locationview-name {
                type xr:live_ncs_Node-id;
                description
                  "The location to filter on";
              }
              uses live_ncs_INTERFACE-TABLE;
            }
          }
          container pq-node-locations {
            description
              "Partially qualified Location-specific view of
               interface operational data";
            list pq-node-location {
              key "pq-node-name";
              description
                "Operational data for all interfaces and
                 controllers on a particular pq_node";
              leaf pq-node-name {
                type xr:live_ncs_Pq-node-id;
                description
                  "The partially qualified location to filter
                   on";
              }
              uses live_ncs_INTERFACE-TABLE;
            }
          }
          container system-view {
            description
              "System-wide view of interface operational data";
            uses live_ncs_INTERFACE-TABLE;
          }
          leaf data-node-name {
            type xr:live_ncs_Node-id;
            description
              "The location of the (D)RP";
          }
        }
      }
    }
  }
  augment "/ncs:devices/ncs:template/ncs:ned-id/ncs:config" {
    // NCS drop config false container 'interface-dampening'
    // NCS drop config false container 'interface-properties'
  }
}

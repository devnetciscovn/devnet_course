submodule Cisco-IOS-XR-aaa-locald-oper-sub1 {
  // Generated by yanger -t ncs
  tailf:mount-id "cisco-iosxr-nc-7.3:cisco-iosxr-nc-7.3";

  belongs-to Cisco-IOS-XR-aaa-locald-oper {
    prefix Cisco-IOS-XR-aaa-locald-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR aaa-locald package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Status {
    type string;
    description
      "status enum";
  }

  typedef ncs_template_String1 {
    type string;
    description
      "String1";
  }

  typedef ncs_rpc_notif_Status {
    type enumeration {
      enum "disabled" {
        value 0;
        description
          "disabled";
      }
      enum "enabled" {
        value 1;
        description
          "enabled";
      }
    }
    description
      "status enum";
  }

  typedef ncs_rpc_notif_String1 {
    type string;
    description
      "String1";
  }

  typedef live_ncs_Status {
    type enumeration {
      enum "disabled" {
        value 0;
        description
          "disabled";
      }
      enum "enabled" {
        value 1;
        description
          "enabled";
      }
    }
    description
      "status enum";
  }

  typedef live_ncs_String1 {
    type string;
    description
      "String1";
  }

  typedef Status {
    type enumeration {
      enum "disabled" {
        value 0;
        description
          "disabled";
      }
      enum "enabled" {
        value 1;
        description
          "enabled";
      }
    }
    description
      "status enum";
  }

  typedef String1 {
    type string;
    description
      "String1";
  }

  grouping ncs_template_USERGROUP-DET {
    description
      "Detailed information regarding a usergroup";
    container task-map {
      description
        "Computed task map";
      uses ncs_template_TASKMAP;
    }
    list taskgroup {
      // NCS patched for predictable order
      ordered-by user;
      description
        "Component taskgroups";
      uses ncs_template_TASKGROUP-DET;
    }
  }

  grouping ncs_template_PP-DURATION-LIMITED {
    description
      "Information about time duration";
    leaf years {
      type string;
      description
        "years";
    }
    leaf months {
      type string;
      description
        "months";
    }
    leaf days {
      type string;
      description
        "days";
    }
  }

  grouping ncs_template_PP-DURATION {
    description
      "Information about time duration";
    leaf years {
      type string;
      description
        "years";
    }
    leaf months {
      type string;
      description
        "months";
    }
    leaf days {
      type string;
      description
        "days";
    }
    leaf hours {
      type string;
      description
        "hours";
    }
    leaf mins {
      type string;
      description
        "mins";
    }
    leaf secs {
      type string;
      description
        "secs";
    }
  }

  grouping ncs_template_PP-DET {
    description
      "Detailed information about a single Password
       Policy";
    container life-time {
      description
        "Lifetime of the policy";
      uses ncs_template_PP-DURATION;
    }
    container warn-interval {
      description
        "Warninterval of the policy";
      uses ncs_template_PP-DURATION;
    }
    container lock-out-time {
      description
        "Lockout time of the policy";
      uses ncs_template_PP-DURATION;
    }
    container restrict-old-time {
      description
        "Password History validity time";
      uses ncs_template_PP-DURATION-LIMITED;
    }
    leaf min-len {
      type string;
      description
        "Min Length";
    }
    leaf max-len {
      type string;
      description
        "Max Length";
    }
    leaf spl-char {
      type string;
      description
        "Special Character length";
    }
    leaf upper-case {
      type string;
      description
        "UpperCase Character length";
    }
    leaf lower-case {
      type string;
      description
        "LowerCase Character length";
    }
    leaf numeric {
      type string;
      description
        "Numeric Character length";
    }
    leaf restrict-old-count {
      type string;
      description
        "Password History Count";
    }
    leaf min-char-change {
      type string;
      description
        "Number of different characters";
    }
    leaf num-of-users {
      type string;
      description
        "Number of users with this policy";
    }
    leaf max-fail-attempts {
      type string;
      description
        "Maximum Failure Attempts allowed";
    }
    leaf usr-count {
      type string;
      description
        "Count of users";
    }
    leaf err-count {
      type string;
      description
        "Error Count";
    }
    leaf lock-out-count {
      type string;
      description
        "Lock Out Count";
    }
    leaf max-char-repetition {
      type string;
      description
        "Number of times a character can repeat";
    }
    leaf restrict-username {
      type ncs_template_Status;
      description
        "Username restriction as password";
    }
    leaf restrict-username-reverse {
      type ncs_template_Status;
      description
        "Reversed Username restriction as password";
    }
    leaf restrict-password-reverse {
      type ncs_template_Status;
      description
        "Reversed password restriction as new password";
    }
    leaf restrict-password-advanced {
      type ncs_template_Status;
      description
        "Advanced restriction on new password";
    }
  }

  grouping ncs_template_USER-DET {
    description
      "Detailed information about a single user";
    container task-map {
      description
        "Computed taskmap";
      uses ncs_template_TASKMAP;
    }
    leaf admin-user {
      type string;
      description
        "Is admin plane user ?";
    }
    leaf first-user {
      type string;
      description
        "Is first user ?";
    }
    leaf-list usergroup {
      // NCS patched for predictable order
      ordered-by user;
      type ncs_template_String1;
      description
        "Member usergroups";
    }
  }

  grouping ncs_template_TASKID {
    description
      "Information about a single Task ID";
    leaf task-id {
      type string;
      description
        "Name of the task-id";
    }
    leaf read {
      type string;
      description
        "Is read permitted?";
    }
    leaf write {
      type string;
      description
        "Is write permitted?";
    }
    leaf execute {
      type string;
      description
        "Is execute permitted?";
    }
    leaf debug {
      type string;
      description
        "Is debug permitted?";
    }
  }

  grouping ncs_template_TASKMAP {
    description
      "Computed taskmap of a user/usergroup/taskgroup or
       Task IDs included in a taskgroup";
    list tasks {
      // NCS patched for predictable order
      ordered-by user;
      description
        "List of permitted tasks";
      uses ncs_template_TASKID;
    }
  }

  grouping ncs_template_TASKGROUP-DET {
    description
      "Detailed information regarding a taskgroup";
    container included-task-ids {
      description
        "Task-ids included";
      uses ncs_template_TASKMAP;
    }
    container task-map {
      description
        "Computed task map";
      uses ncs_template_TASKMAP;
    }
  }

  grouping ncs_template_REMOTEUSR-DET {
    description
      "Detailed information regarding a usergroup";
    leaf name {
      type string;
      description
        "Name of the usergroup";
    }
    leaf shelltype {
      type string;
      description
        "Shell-type of user";
    }
    leaf directory {
      type string;
      description
        "Directory of user";
    }
    leaf authenmethod {
      type string;
      description
        "Authentication method";
    }
    leaf-list usergroup {
      // NCS patched for predictable order
      ordered-by user;
      type ncs_template_String1;
      description
        "Component usergroups";
    }
    leaf-list taskmap {
      // NCS patched for predictable order
      ordered-by user;
      type ncs_template_String1;
      description
        "Task map details";
    }
  }

  grouping ncs_template_SYSTEM-SUPPORTED-TASKS {
    description
      "List of all tasks available in the system";
    leaf-list task-id {
      // NCS patched for predictable order
      ordered-by user;
      type ncs_template_String1;
      description
        "Names of available task-ids";
    }
  }

  grouping ncs_rpc_notif_USERGROUP-DET {
    description
      "Detailed information regarding a usergroup";
    container task-map {
      description
        "Computed task map";
      uses ncs_rpc_notif_TASKMAP;
    }
    list taskgroup {
      description
        "Component taskgroups";
      uses ncs_rpc_notif_TASKGROUP-DET;
    }
  }

  grouping ncs_rpc_notif_PP-DURATION-LIMITED {
    description
      "Information about time duration";
    leaf years {
      type uint8;
      description
        "years";
    }
    leaf months {
      type uint8;
      description
        "months";
    }
    leaf days {
      type uint8;
      description
        "days";
    }
  }

  grouping ncs_rpc_notif_PP-DURATION {
    description
      "Information about time duration";
    leaf years {
      type uint8;
      description
        "years";
    }
    leaf months {
      type uint8;
      description
        "months";
    }
    leaf days {
      type uint8;
      description
        "days";
    }
    leaf hours {
      type uint8;
      description
        "hours";
    }
    leaf mins {
      type uint8;
      description
        "mins";
    }
    leaf secs {
      type uint8;
      description
        "secs";
    }
  }

  grouping ncs_rpc_notif_PP-DET {
    description
      "Detailed information about a single Password
       Policy";
    container life-time {
      description
        "Lifetime of the policy";
      uses ncs_rpc_notif_PP-DURATION;
    }
    container warn-interval {
      description
        "Warninterval of the policy";
      uses ncs_rpc_notif_PP-DURATION;
    }
    container lock-out-time {
      description
        "Lockout time of the policy";
      uses ncs_rpc_notif_PP-DURATION;
    }
    container restrict-old-time {
      description
        "Password History validity time";
      uses ncs_rpc_notif_PP-DURATION-LIMITED;
    }
    leaf min-len {
      type uint8;
      description
        "Min Length";
    }
    leaf max-len {
      type uint8;
      description
        "Max Length";
    }
    leaf spl-char {
      type uint8;
      description
        "Special Character length";
    }
    leaf upper-case {
      type uint8;
      description
        "UpperCase Character length";
    }
    leaf lower-case {
      type uint8;
      description
        "LowerCase Character length";
    }
    leaf numeric {
      type uint8;
      description
        "Numeric Character length";
    }
    leaf restrict-old-count {
      type uint8;
      description
        "Password History Count";
    }
    leaf min-char-change {
      type uint8;
      description
        "Number of different characters";
    }
    leaf num-of-users {
      type uint8;
      description
        "Number of users with this policy";
    }
    leaf max-fail-attempts {
      type uint32;
      description
        "Maximum Failure Attempts allowed";
    }
    leaf usr-count {
      type uint8;
      description
        "Count of users";
    }
    leaf err-count {
      type uint8;
      description
        "Error Count";
    }
    leaf lock-out-count {
      type uint8;
      description
        "Lock Out Count";
    }
    leaf max-char-repetition {
      type uint8;
      description
        "Number of times a character can repeat";
    }
    leaf restrict-username {
      type ncs_rpc_notif_Status;
      description
        "Username restriction as password";
    }
    leaf restrict-username-reverse {
      type ncs_rpc_notif_Status;
      description
        "Reversed Username restriction as password";
    }
    leaf restrict-password-reverse {
      type ncs_rpc_notif_Status;
      description
        "Reversed password restriction as new password";
    }
    leaf restrict-password-advanced {
      type ncs_rpc_notif_Status;
      description
        "Advanced restriction on new password";
    }
  }

  grouping ncs_rpc_notif_USER-DET {
    description
      "Detailed information about a single user";
    container task-map {
      description
        "Computed taskmap";
      uses ncs_rpc_notif_TASKMAP;
    }
    leaf admin-user {
      type boolean;
      description
        "Is admin plane user ?";
    }
    leaf first-user {
      type boolean;
      description
        "Is first user ?";
    }
    leaf-list usergroup {
      type ncs_rpc_notif_String1;
      description
        "Member usergroups";
    }
  }

  grouping ncs_rpc_notif_TASKID {
    description
      "Information about a single Task ID";
    leaf task-id {
      type string;
      description
        "Name of the task-id";
    }
    leaf read {
      type boolean;
      description
        "Is read permitted?";
    }
    leaf write {
      type boolean;
      description
        "Is write permitted?";
    }
    leaf execute {
      type boolean;
      description
        "Is execute permitted?";
    }
    leaf debug {
      type boolean;
      description
        "Is debug permitted?";
    }
  }

  grouping ncs_rpc_notif_TASKMAP {
    description
      "Computed taskmap of a user/usergroup/taskgroup or
       Task IDs included in a taskgroup";
    list tasks {
      description
        "List of permitted tasks";
      uses ncs_rpc_notif_TASKID;
    }
  }

  grouping ncs_rpc_notif_TASKGROUP-DET {
    description
      "Detailed information regarding a taskgroup";
    container included-task-ids {
      description
        "Task-ids included";
      uses ncs_rpc_notif_TASKMAP;
    }
    container task-map {
      description
        "Computed task map";
      uses ncs_rpc_notif_TASKMAP;
    }
  }

  grouping ncs_rpc_notif_REMOTEUSR-DET {
    description
      "Detailed information regarding a usergroup";
    leaf name {
      type string;
      description
        "Name of the usergroup";
    }
    leaf shelltype {
      type string;
      description
        "Shell-type of user";
    }
    leaf directory {
      type string;
      description
        "Directory of user";
    }
    leaf authenmethod {
      type int32;
      description
        "Authentication method";
    }
    leaf-list usergroup {
      type ncs_rpc_notif_String1;
      description
        "Component usergroups";
    }
    leaf-list taskmap {
      type ncs_rpc_notif_String1;
      description
        "Task map details";
    }
  }

  grouping ncs_rpc_notif_SYSTEM-SUPPORTED-TASKS {
    description
      "List of all tasks available in the system";
    leaf-list task-id {
      type ncs_rpc_notif_String1;
      description
        "Names of available task-ids";
    }
  }

  grouping live_ncs_USERGROUP-DET {
    description
      "Detailed information regarding a usergroup";
    container task-map {
      description
        "Computed task map";
      uses live_ncs_TASKMAP;
    }
    list taskgroup {
      description
        "Component taskgroups";
      uses live_ncs_TASKGROUP-DET;
    }
  }

  grouping live_ncs_PP-DURATION-LIMITED {
    description
      "Information about time duration";
    leaf years {
      type uint8;
      description
        "years";
    }
    leaf months {
      type uint8;
      description
        "months";
    }
    leaf days {
      type uint8;
      description
        "days";
    }
  }

  grouping live_ncs_PP-DURATION {
    description
      "Information about time duration";
    leaf years {
      type uint8;
      description
        "years";
    }
    leaf months {
      type uint8;
      description
        "months";
    }
    leaf days {
      type uint8;
      description
        "days";
    }
    leaf hours {
      type uint8;
      description
        "hours";
    }
    leaf mins {
      type uint8;
      description
        "mins";
    }
    leaf secs {
      type uint8;
      description
        "secs";
    }
  }

  grouping live_ncs_PP-DET {
    description
      "Detailed information about a single Password
       Policy";
    container life-time {
      description
        "Lifetime of the policy";
      uses live_ncs_PP-DURATION;
    }
    container warn-interval {
      description
        "Warninterval of the policy";
      uses live_ncs_PP-DURATION;
    }
    container lock-out-time {
      description
        "Lockout time of the policy";
      uses live_ncs_PP-DURATION;
    }
    container restrict-old-time {
      description
        "Password History validity time";
      uses live_ncs_PP-DURATION-LIMITED;
    }
    leaf min-len {
      type uint8;
      description
        "Min Length";
    }
    leaf max-len {
      type uint8;
      description
        "Max Length";
    }
    leaf spl-char {
      type uint8;
      description
        "Special Character length";
    }
    leaf upper-case {
      type uint8;
      description
        "UpperCase Character length";
    }
    leaf lower-case {
      type uint8;
      description
        "LowerCase Character length";
    }
    leaf numeric {
      type uint8;
      description
        "Numeric Character length";
    }
    leaf restrict-old-count {
      type uint8;
      description
        "Password History Count";
    }
    leaf min-char-change {
      type uint8;
      description
        "Number of different characters";
    }
    leaf num-of-users {
      type uint8;
      description
        "Number of users with this policy";
    }
    leaf max-fail-attempts {
      type uint32;
      description
        "Maximum Failure Attempts allowed";
    }
    leaf usr-count {
      type uint8;
      description
        "Count of users";
    }
    leaf err-count {
      type uint8;
      description
        "Error Count";
    }
    leaf lock-out-count {
      type uint8;
      description
        "Lock Out Count";
    }
    leaf max-char-repetition {
      type uint8;
      description
        "Number of times a character can repeat";
    }
    leaf restrict-username {
      type live_ncs_Status;
      description
        "Username restriction as password";
    }
    leaf restrict-username-reverse {
      type live_ncs_Status;
      description
        "Reversed Username restriction as password";
    }
    leaf restrict-password-reverse {
      type live_ncs_Status;
      description
        "Reversed password restriction as new password";
    }
    leaf restrict-password-advanced {
      type live_ncs_Status;
      description
        "Advanced restriction on new password";
    }
  }

  grouping live_ncs_USER-DET {
    description
      "Detailed information about a single user";
    container task-map {
      description
        "Computed taskmap";
      uses live_ncs_TASKMAP;
    }
    leaf admin-user {
      type boolean;
      description
        "Is admin plane user ?";
    }
    leaf first-user {
      type boolean;
      description
        "Is first user ?";
    }
    leaf-list usergroup {
      type live_ncs_String1;
      description
        "Member usergroups";
    }
  }

  grouping live_ncs_TASKID {
    description
      "Information about a single Task ID";
    leaf task-id {
      type string;
      description
        "Name of the task-id";
    }
    leaf read {
      type boolean;
      description
        "Is read permitted?";
    }
    leaf write {
      type boolean;
      description
        "Is write permitted?";
    }
    leaf execute {
      type boolean;
      description
        "Is execute permitted?";
    }
    leaf debug {
      type boolean;
      description
        "Is debug permitted?";
    }
  }

  grouping live_ncs_TASKMAP {
    description
      "Computed taskmap of a user/usergroup/taskgroup or
       Task IDs included in a taskgroup";
    list tasks {
      description
        "List of permitted tasks";
      uses live_ncs_TASKID;
    }
  }

  grouping live_ncs_TASKGROUP-DET {
    description
      "Detailed information regarding a taskgroup";
    container included-task-ids {
      description
        "Task-ids included";
      uses live_ncs_TASKMAP;
    }
    container task-map {
      description
        "Computed task map";
      uses live_ncs_TASKMAP;
    }
  }

  grouping live_ncs_REMOTEUSR-DET {
    description
      "Detailed information regarding a usergroup";
    leaf name {
      type string;
      description
        "Name of the usergroup";
    }
    leaf shelltype {
      type string;
      description
        "Shell-type of user";
    }
    leaf directory {
      type string;
      description
        "Directory of user";
    }
    leaf authenmethod {
      type int32;
      description
        "Authentication method";
    }
    leaf-list usergroup {
      type live_ncs_String1;
      description
        "Component usergroups";
    }
    leaf-list taskmap {
      type live_ncs_String1;
      description
        "Task map details";
    }
  }

  grouping live_ncs_SYSTEM-SUPPORTED-TASKS {
    description
      "List of all tasks available in the system";
    leaf-list task-id {
      type live_ncs_String1;
      description
        "Names of available task-ids";
    }
  }

  grouping USERGROUP-DET {
    description
      "Detailed information regarding a usergroup";
    container task-map {
      description
        "Computed task map";
      uses TASKMAP;
    }
    list taskgroup {
      description
        "Component taskgroups";
      uses TASKGROUP-DET;
    }
  }

  grouping PP-DURATION-LIMITED {
    description
      "Information about time duration";
    leaf years {
      type uint8;
      description
        "years";
    }
    leaf months {
      type uint8;
      description
        "months";
    }
    leaf days {
      type uint8;
      description
        "days";
    }
  }

  grouping PP-DURATION {
    description
      "Information about time duration";
    leaf years {
      type uint8;
      description
        "years";
    }
    leaf months {
      type uint8;
      description
        "months";
    }
    leaf days {
      type uint8;
      description
        "days";
    }
    leaf hours {
      type uint8;
      description
        "hours";
    }
    leaf mins {
      type uint8;
      description
        "mins";
    }
    leaf secs {
      type uint8;
      description
        "secs";
    }
  }

  grouping PP-DET {
    description
      "Detailed information about a single Password
       Policy";
    container life-time {
      description
        "Lifetime of the policy";
      uses PP-DURATION;
    }
    container warn-interval {
      description
        "Warninterval of the policy";
      uses PP-DURATION;
    }
    container lock-out-time {
      description
        "Lockout time of the policy";
      uses PP-DURATION;
    }
    container restrict-old-time {
      description
        "Password History validity time";
      uses PP-DURATION-LIMITED;
    }
    leaf min-len {
      type uint8;
      description
        "Min Length";
    }
    leaf max-len {
      type uint8;
      description
        "Max Length";
    }
    leaf spl-char {
      type uint8;
      description
        "Special Character length";
    }
    leaf upper-case {
      type uint8;
      description
        "UpperCase Character length";
    }
    leaf lower-case {
      type uint8;
      description
        "LowerCase Character length";
    }
    leaf numeric {
      type uint8;
      description
        "Numeric Character length";
    }
    leaf restrict-old-count {
      type uint8;
      description
        "Password History Count";
    }
    leaf min-char-change {
      type uint8;
      description
        "Number of different characters";
    }
    leaf num-of-users {
      type uint8;
      description
        "Number of users with this policy";
    }
    leaf max-fail-attempts {
      type uint32;
      description
        "Maximum Failure Attempts allowed";
    }
    leaf usr-count {
      type uint8;
      description
        "Count of users";
    }
    leaf err-count {
      type uint8;
      description
        "Error Count";
    }
    leaf lock-out-count {
      type uint8;
      description
        "Lock Out Count";
    }
    leaf max-char-repetition {
      type uint8;
      description
        "Number of times a character can repeat";
    }
    leaf restrict-username {
      type Status;
      description
        "Username restriction as password";
    }
    leaf restrict-username-reverse {
      type Status;
      description
        "Reversed Username restriction as password";
    }
    leaf restrict-password-reverse {
      type Status;
      description
        "Reversed password restriction as new password";
    }
    leaf restrict-password-advanced {
      type Status;
      description
        "Advanced restriction on new password";
    }
  }

  grouping USER-DET {
    description
      "Detailed information about a single user";
    container task-map {
      description
        "Computed taskmap";
      uses TASKMAP;
    }
    leaf admin-user {
      type boolean;
      description
        "Is admin plane user ?";
    }
    leaf first-user {
      type boolean;
      description
        "Is first user ?";
    }
    leaf-list usergroup {
      type String1;
      description
        "Member usergroups";
    }
  }

  grouping TASKID {
    description
      "Information about a single Task ID";
    leaf task-id {
      type string;
      description
        "Name of the task-id";
    }
    leaf read {
      type boolean;
      description
        "Is read permitted?";
    }
    leaf write {
      type boolean;
      description
        "Is write permitted?";
    }
    leaf execute {
      type boolean;
      description
        "Is execute permitted?";
    }
    leaf debug {
      type boolean;
      description
        "Is debug permitted?";
    }
  }

  grouping TASKMAP {
    description
      "Computed taskmap of a user/usergroup/taskgroup or
       Task IDs included in a taskgroup";
    list tasks {
      description
        "List of permitted tasks";
      uses TASKID;
    }
  }

  grouping TASKGROUP-DET {
    description
      "Detailed information regarding a taskgroup";
    container included-task-ids {
      description
        "Task-ids included";
      uses TASKMAP;
    }
    container task-map {
      description
        "Computed task map";
      uses TASKMAP;
    }
  }

  grouping REMOTEUSR-DET {
    description
      "Detailed information regarding a usergroup";
    leaf name {
      type string;
      description
        "Name of the usergroup";
    }
    leaf shelltype {
      type string;
      description
        "Shell-type of user";
    }
    leaf directory {
      type string;
      description
        "Directory of user";
    }
    leaf authenmethod {
      type int32;
      description
        "Authentication method";
    }
    leaf-list usergroup {
      type String1;
      description
        "Component usergroups";
    }
    leaf-list taskmap {
      type String1;
      description
        "Task map details";
    }
  }

  grouping SYSTEM-SUPPORTED-TASKS {
    description
      "List of all tasks available in the system";
    leaf-list task-id {
      type String1;
      description
        "Names of available task-ids";
    }
  }
}

module Cisco-IOS-XR-infra-script-mgmt-act {
  // Generated by yanger -t ncs
  tailf:mount-id "cisco-iosxr-nc-7.3:cisco-iosxr-nc-7.3";
  tailf:ncs-device-type "netconf";

  namespace "http://cisco.com/ns/yang/Cisco-IOS-XR-infra-script-mgmt-act";
  prefix script-mgmt-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2020-2021 by Cisco Systems, Inc.
     All rights reserved.";

  revision 2020-10-12 {
    description
      "Added container for filenames";
    semver:module-version "1.0.0";
  }
  revision 2020-10-09 {
    description
      "Added grouping for checksum";
  }
  revision 2020-10-09 {
    description
      "Added grouping for file list";
  }
  revision 2020-10-09 {
    description
      "Separated leaf-list into individual leafs";
  }
  revision 2020-10-08 {
    description
      "Initial version";
  }

  grouping ncs_template_FILE-NAME-LIST {
    description
      "list of input files to add or remove, only 1 is required for command";
    leaf file-name-1 {
      type string;
      // NCS drop mandatory statement
      description
        "filename 1";
    }
    leaf file-name-2 {
      type string;
      description
        "filename 2";
    }
    leaf file-name-3 {
      type string;
      description
        "filename 3";
    }
    leaf file-name-4 {
      type string;
      description
        "filename 4";
    }
    leaf file-name-5 {
      type string;
      description
        "filename 5";
    }
    leaf file-name-6 {
      type string;
      description
        "filename 6";
    }
    leaf file-name-7 {
      type string;
      description
        "filename 7";
    }
    leaf file-name-8 {
      type string;
      description
        "filename 8";
    }
    leaf file-name-9 {
      type string;
      description
        "filename 9";
    }
    leaf file-name-10 {
      type string;
      description
        "filename 10";
    }
  }

  grouping ncs_template_CHECKSUM-GROUP {
    description
      "checksum helper group";
    leaf type {
      type string;
      // NCS drop mandatory statement
      description
        "<exec, eem, config, process>";
    }
    leaf source {
      type string;
      // NCS drop mandatory statement
      description
        "http:<server>[;<vrf>]/full_path_to_repo";
    }
    leaf file-name-1 {
      type string;
      // NCS drop mandatory statement
      description
        "List of file-names (max 10)";
    }
    leaf checksum-1 {
      type string;
      // NCS drop mandatory statement
      description
        "List of checksums (max 10)";
    }
  }

  grouping ncs_template_CHECKSUM-GROUP-2 {
    description
      "checksum helper group";
    uses ncs_template_CHECKSUM-GROUP;
    leaf file-name-2 {
      type string;
      // NCS drop mandatory statement
      description
        "List of file-names (max 10)";
    }
    leaf checksum-2 {
      type string;
      // NCS drop mandatory statement
      description
        "List of checksums (max 10)";
    }
  }

  grouping ncs_template_CHECKSUM-GROUP-3 {
    description
      "checksum helper group";
    uses ncs_template_CHECKSUM-GROUP-2;
    leaf file-name-3 {
      type string;
      // NCS drop mandatory statement
      description
        "List of file-names (max 10)";
    }
    leaf checksum-3 {
      type string;
      // NCS drop mandatory statement
      description
        "List of checksums (max 10)";
    }
  }

  grouping ncs_template_CHECKSUM-GROUP-4 {
    description
      "checksum helper group";
    uses ncs_template_CHECKSUM-GROUP-3;
    leaf file-name-4 {
      type string;
      // NCS drop mandatory statement
      description
        "List of file-names (max 10)";
    }
    leaf checksum-4 {
      type string;
      // NCS drop mandatory statement
      description
        "List of checksums (max 10)";
    }
  }

  grouping ncs_template_CHECKSUM-GROUP-5 {
    description
      "checksum helper group";
    uses ncs_template_CHECKSUM-GROUP-4;
    leaf file-name-5 {
      type string;
      // NCS drop mandatory statement
      description
        "List of file-names (max 10)";
    }
    leaf checksum-5 {
      type string;
      // NCS drop mandatory statement
      description
        "List of checksums (max 10)";
    }
  }

  grouping ncs_template_CHECKSUM-GROUP-6 {
    description
      "checksum helper group";
    uses ncs_template_CHECKSUM-GROUP-5;
    leaf file-name-6 {
      type string;
      // NCS drop mandatory statement
      description
        "List of file-names (max 10)";
    }
    leaf checksum-6 {
      type string;
      // NCS drop mandatory statement
      description
        "List of checksums (max 10)";
    }
  }

  grouping ncs_template_CHECKSUM-GROUP-7 {
    description
      "checksum helper group";
    uses ncs_template_CHECKSUM-GROUP-6;
    leaf file-name-7 {
      type string;
      // NCS drop mandatory statement
      description
        "List of file-names (max 10)";
    }
    leaf checksum-7 {
      type string;
      // NCS drop mandatory statement
      description
        "List of checksums (max 10)";
    }
  }

  grouping ncs_template_CHECKSUM-GROUP-8 {
    description
      "checksum helper group";
    uses ncs_template_CHECKSUM-GROUP-7;
    leaf file-name-8 {
      type string;
      // NCS drop mandatory statement
      description
        "List of file-names (max 10)";
    }
    leaf checksum-8 {
      type string;
      // NCS drop mandatory statement
      description
        "List of checksums (max 10)";
    }
  }

  grouping ncs_template_CHECKSUM-GROUP-9 {
    description
      "checksum helper group";
    uses ncs_template_CHECKSUM-GROUP-8;
    leaf file-name-9 {
      type string;
      // NCS drop mandatory statement
      description
        "List of file-names (max 10)";
    }
    leaf checksum-9 {
      type string;
      // NCS drop mandatory statement
      description
        "List of checksums (max 10)";
    }
  }

  grouping ncs_template_CHECKSUM-GROUP-10 {
    description
      "checksum helper group";
    uses ncs_template_CHECKSUM-GROUP-9;
    leaf file-name-10 {
      type string;
      // NCS drop mandatory statement
      description
        "List of file-names (max 10)";
    }
    leaf checksum-10 {
      type string;
      // NCS drop mandatory statement
      description
        "List of checksums (max 10)";
    }
  }

  grouping ncs_rpc_notif_FILE-NAME-LIST {
    description
      "list of input files to add or remove, only 1 is required for command";
    leaf file-name-1 {
      type string {
        length "1..224";
      }
      mandatory true;
      description
        "filename 1";
    }
    leaf file-name-2 {
      type string;
      description
        "filename 2";
    }
    leaf file-name-3 {
      type string;
      description
        "filename 3";
    }
    leaf file-name-4 {
      type string;
      description
        "filename 4";
    }
    leaf file-name-5 {
      type string;
      description
        "filename 5";
    }
    leaf file-name-6 {
      type string;
      description
        "filename 6";
    }
    leaf file-name-7 {
      type string;
      description
        "filename 7";
    }
    leaf file-name-8 {
      type string;
      description
        "filename 8";
    }
    leaf file-name-9 {
      type string;
      description
        "filename 9";
    }
    leaf file-name-10 {
      type string;
      description
        "filename 10";
    }
  }

  grouping ncs_rpc_notif_CHECKSUM-GROUP {
    description
      "checksum helper group";
    leaf type {
      type string;
      mandatory true;
      description
        "<exec, eem, config, process>";
    }
    leaf source {
      type string {
        length "1..512";
      }
      mandatory true;
      description
        "http:<server>[;<vrf>]/full_path_to_repo";
    }
    leaf file-name-1 {
      type string {
        length "1..224";
      }
      mandatory true;
      description
        "List of file-names (max 10)";
    }
    leaf checksum-1 {
      type string {
        length "1..64";
      }
      mandatory true;
      description
        "List of checksums (max 10)";
    }
  }

  grouping ncs_rpc_notif_CHECKSUM-GROUP-2 {
    description
      "checksum helper group";
    uses ncs_rpc_notif_CHECKSUM-GROUP;
    leaf file-name-2 {
      type string {
        length "1..224";
      }
      mandatory true;
      description
        "List of file-names (max 10)";
    }
    leaf checksum-2 {
      type string {
        length "1..64";
      }
      mandatory true;
      description
        "List of checksums (max 10)";
    }
  }

  grouping ncs_rpc_notif_CHECKSUM-GROUP-3 {
    description
      "checksum helper group";
    uses ncs_rpc_notif_CHECKSUM-GROUP-2;
    leaf file-name-3 {
      type string {
        length "1..224";
      }
      mandatory true;
      description
        "List of file-names (max 10)";
    }
    leaf checksum-3 {
      type string {
        length "1..64";
      }
      mandatory true;
      description
        "List of checksums (max 10)";
    }
  }

  grouping ncs_rpc_notif_CHECKSUM-GROUP-4 {
    description
      "checksum helper group";
    uses ncs_rpc_notif_CHECKSUM-GROUP-3;
    leaf file-name-4 {
      type string {
        length "1..224";
      }
      mandatory true;
      description
        "List of file-names (max 10)";
    }
    leaf checksum-4 {
      type string {
        length "1..64";
      }
      mandatory true;
      description
        "List of checksums (max 10)";
    }
  }

  grouping ncs_rpc_notif_CHECKSUM-GROUP-5 {
    description
      "checksum helper group";
    uses ncs_rpc_notif_CHECKSUM-GROUP-4;
    leaf file-name-5 {
      type string {
        length "1..224";
      }
      mandatory true;
      description
        "List of file-names (max 10)";
    }
    leaf checksum-5 {
      type string {
        length "1..64";
      }
      mandatory true;
      description
        "List of checksums (max 10)";
    }
  }

  grouping ncs_rpc_notif_CHECKSUM-GROUP-6 {
    description
      "checksum helper group";
    uses ncs_rpc_notif_CHECKSUM-GROUP-5;
    leaf file-name-6 {
      type string {
        length "1..224";
      }
      mandatory true;
      description
        "List of file-names (max 10)";
    }
    leaf checksum-6 {
      type string {
        length "1..64";
      }
      mandatory true;
      description
        "List of checksums (max 10)";
    }
  }

  grouping ncs_rpc_notif_CHECKSUM-GROUP-7 {
    description
      "checksum helper group";
    uses ncs_rpc_notif_CHECKSUM-GROUP-6;
    leaf file-name-7 {
      type string {
        length "1..224";
      }
      mandatory true;
      description
        "List of file-names (max 10)";
    }
    leaf checksum-7 {
      type string {
        length "1..64";
      }
      mandatory true;
      description
        "List of checksums (max 10)";
    }
  }

  grouping ncs_rpc_notif_CHECKSUM-GROUP-8 {
    description
      "checksum helper group";
    uses ncs_rpc_notif_CHECKSUM-GROUP-7;
    leaf file-name-8 {
      type string {
        length "1..224";
      }
      mandatory true;
      description
        "List of file-names (max 10)";
    }
    leaf checksum-8 {
      type string {
        length "1..64";
      }
      mandatory true;
      description
        "List of checksums (max 10)";
    }
  }

  grouping ncs_rpc_notif_CHECKSUM-GROUP-9 {
    description
      "checksum helper group";
    uses ncs_rpc_notif_CHECKSUM-GROUP-8;
    leaf file-name-9 {
      type string {
        length "1..224";
      }
      mandatory true;
      description
        "List of file-names (max 10)";
    }
    leaf checksum-9 {
      type string {
        length "1..64";
      }
      mandatory true;
      description
        "List of checksums (max 10)";
    }
  }

  grouping ncs_rpc_notif_CHECKSUM-GROUP-10 {
    description
      "checksum helper group";
    uses ncs_rpc_notif_CHECKSUM-GROUP-9;
    leaf file-name-10 {
      type string {
        length "1..224";
      }
      mandatory true;
      description
        "List of file-names (max 10)";
    }
    leaf checksum-10 {
      type string {
        length "1..64";
      }
      mandatory true;
      description
        "List of checksums (max 10)";
    }
  }

  grouping live_ncs_FILE-NAME-LIST {
    description
      "list of input files to add or remove, only 1 is required for command";
    leaf file-name-1 {
      type string {
        length "1..224";
      }
      // NCS drop mandatory statement
      description
        "filename 1";
    }
    leaf file-name-2 {
      type string;
      description
        "filename 2";
    }
    leaf file-name-3 {
      type string;
      description
        "filename 3";
    }
    leaf file-name-4 {
      type string;
      description
        "filename 4";
    }
    leaf file-name-5 {
      type string;
      description
        "filename 5";
    }
    leaf file-name-6 {
      type string;
      description
        "filename 6";
    }
    leaf file-name-7 {
      type string;
      description
        "filename 7";
    }
    leaf file-name-8 {
      type string;
      description
        "filename 8";
    }
    leaf file-name-9 {
      type string;
      description
        "filename 9";
    }
    leaf file-name-10 {
      type string;
      description
        "filename 10";
    }
  }

  grouping live_ncs_CHECKSUM-GROUP {
    description
      "checksum helper group";
    leaf type {
      type string;
      // NCS drop mandatory statement
      description
        "<exec, eem, config, process>";
    }
    leaf source {
      type string {
        length "1..512";
      }
      // NCS drop mandatory statement
      description
        "http:<server>[;<vrf>]/full_path_to_repo";
    }
    leaf file-name-1 {
      type string {
        length "1..224";
      }
      // NCS drop mandatory statement
      description
        "List of file-names (max 10)";
    }
    leaf checksum-1 {
      type string {
        length "1..64";
      }
      // NCS drop mandatory statement
      description
        "List of checksums (max 10)";
    }
  }

  grouping live_ncs_CHECKSUM-GROUP-2 {
    description
      "checksum helper group";
    uses live_ncs_CHECKSUM-GROUP;
    leaf file-name-2 {
      type string {
        length "1..224";
      }
      // NCS drop mandatory statement
      description
        "List of file-names (max 10)";
    }
    leaf checksum-2 {
      type string {
        length "1..64";
      }
      // NCS drop mandatory statement
      description
        "List of checksums (max 10)";
    }
  }

  grouping live_ncs_CHECKSUM-GROUP-3 {
    description
      "checksum helper group";
    uses live_ncs_CHECKSUM-GROUP-2;
    leaf file-name-3 {
      type string {
        length "1..224";
      }
      // NCS drop mandatory statement
      description
        "List of file-names (max 10)";
    }
    leaf checksum-3 {
      type string {
        length "1..64";
      }
      // NCS drop mandatory statement
      description
        "List of checksums (max 10)";
    }
  }

  grouping live_ncs_CHECKSUM-GROUP-4 {
    description
      "checksum helper group";
    uses live_ncs_CHECKSUM-GROUP-3;
    leaf file-name-4 {
      type string {
        length "1..224";
      }
      // NCS drop mandatory statement
      description
        "List of file-names (max 10)";
    }
    leaf checksum-4 {
      type string {
        length "1..64";
      }
      // NCS drop mandatory statement
      description
        "List of checksums (max 10)";
    }
  }

  grouping live_ncs_CHECKSUM-GROUP-5 {
    description
      "checksum helper group";
    uses live_ncs_CHECKSUM-GROUP-4;
    leaf file-name-5 {
      type string {
        length "1..224";
      }
      // NCS drop mandatory statement
      description
        "List of file-names (max 10)";
    }
    leaf checksum-5 {
      type string {
        length "1..64";
      }
      // NCS drop mandatory statement
      description
        "List of checksums (max 10)";
    }
  }

  grouping live_ncs_CHECKSUM-GROUP-6 {
    description
      "checksum helper group";
    uses live_ncs_CHECKSUM-GROUP-5;
    leaf file-name-6 {
      type string {
        length "1..224";
      }
      // NCS drop mandatory statement
      description
        "List of file-names (max 10)";
    }
    leaf checksum-6 {
      type string {
        length "1..64";
      }
      // NCS drop mandatory statement
      description
        "List of checksums (max 10)";
    }
  }

  grouping live_ncs_CHECKSUM-GROUP-7 {
    description
      "checksum helper group";
    uses live_ncs_CHECKSUM-GROUP-6;
    leaf file-name-7 {
      type string {
        length "1..224";
      }
      // NCS drop mandatory statement
      description
        "List of file-names (max 10)";
    }
    leaf checksum-7 {
      type string {
        length "1..64";
      }
      // NCS drop mandatory statement
      description
        "List of checksums (max 10)";
    }
  }

  grouping live_ncs_CHECKSUM-GROUP-8 {
    description
      "checksum helper group";
    uses live_ncs_CHECKSUM-GROUP-7;
    leaf file-name-8 {
      type string {
        length "1..224";
      }
      // NCS drop mandatory statement
      description
        "List of file-names (max 10)";
    }
    leaf checksum-8 {
      type string {
        length "1..64";
      }
      // NCS drop mandatory statement
      description
        "List of checksums (max 10)";
    }
  }

  grouping live_ncs_CHECKSUM-GROUP-9 {
    description
      "checksum helper group";
    uses live_ncs_CHECKSUM-GROUP-8;
    leaf file-name-9 {
      type string {
        length "1..224";
      }
      // NCS drop mandatory statement
      description
        "List of file-names (max 10)";
    }
    leaf checksum-9 {
      type string {
        length "1..64";
      }
      // NCS drop mandatory statement
      description
        "List of checksums (max 10)";
    }
  }

  grouping live_ncs_CHECKSUM-GROUP-10 {
    description
      "checksum helper group";
    uses live_ncs_CHECKSUM-GROUP-9;
    leaf file-name-10 {
      type string {
        length "1..224";
      }
      // NCS drop mandatory statement
      description
        "List of file-names (max 10)";
    }
    leaf checksum-10 {
      type string {
        length "1..64";
      }
      // NCS drop mandatory statement
      description
        "List of checksums (max 10)";
    }
  }

  grouping FILE-NAME-LIST {
    description
      "list of input files to add or remove, only 1 is required for command";
    leaf file-name-1 {
      type string {
        length "1..224";
      }
      mandatory true;
      description
        "filename 1";
    }
    leaf file-name-2 {
      type string;
      description
        "filename 2";
    }
    leaf file-name-3 {
      type string;
      description
        "filename 3";
    }
    leaf file-name-4 {
      type string;
      description
        "filename 4";
    }
    leaf file-name-5 {
      type string;
      description
        "filename 5";
    }
    leaf file-name-6 {
      type string;
      description
        "filename 6";
    }
    leaf file-name-7 {
      type string;
      description
        "filename 7";
    }
    leaf file-name-8 {
      type string;
      description
        "filename 8";
    }
    leaf file-name-9 {
      type string;
      description
        "filename 9";
    }
    leaf file-name-10 {
      type string;
      description
        "filename 10";
    }
  }

  grouping CHECKSUM-GROUP {
    description
      "checksum helper group";
    leaf type {
      type string;
      mandatory true;
      description
        "<exec, eem, config, process>";
    }
    leaf source {
      type string {
        length "1..512";
      }
      mandatory true;
      description
        "http:<server>[;<vrf>]/full_path_to_repo";
    }
    leaf file-name-1 {
      type string {
        length "1..224";
      }
      mandatory true;
      description
        "List of file-names (max 10)";
    }
    leaf checksum-1 {
      type string {
        length "1..64";
      }
      mandatory true;
      description
        "List of checksums (max 10)";
    }
  }

  grouping CHECKSUM-GROUP-2 {
    description
      "checksum helper group";
    uses CHECKSUM-GROUP;
    leaf file-name-2 {
      type string {
        length "1..224";
      }
      mandatory true;
      description
        "List of file-names (max 10)";
    }
    leaf checksum-2 {
      type string {
        length "1..64";
      }
      mandatory true;
      description
        "List of checksums (max 10)";
    }
  }

  grouping CHECKSUM-GROUP-3 {
    description
      "checksum helper group";
    uses CHECKSUM-GROUP-2;
    leaf file-name-3 {
      type string {
        length "1..224";
      }
      mandatory true;
      description
        "List of file-names (max 10)";
    }
    leaf checksum-3 {
      type string {
        length "1..64";
      }
      mandatory true;
      description
        "List of checksums (max 10)";
    }
  }

  grouping CHECKSUM-GROUP-4 {
    description
      "checksum helper group";
    uses CHECKSUM-GROUP-3;
    leaf file-name-4 {
      type string {
        length "1..224";
      }
      mandatory true;
      description
        "List of file-names (max 10)";
    }
    leaf checksum-4 {
      type string {
        length "1..64";
      }
      mandatory true;
      description
        "List of checksums (max 10)";
    }
  }

  grouping CHECKSUM-GROUP-5 {
    description
      "checksum helper group";
    uses CHECKSUM-GROUP-4;
    leaf file-name-5 {
      type string {
        length "1..224";
      }
      mandatory true;
      description
        "List of file-names (max 10)";
    }
    leaf checksum-5 {
      type string {
        length "1..64";
      }
      mandatory true;
      description
        "List of checksums (max 10)";
    }
  }

  grouping CHECKSUM-GROUP-6 {
    description
      "checksum helper group";
    uses CHECKSUM-GROUP-5;
    leaf file-name-6 {
      type string {
        length "1..224";
      }
      mandatory true;
      description
        "List of file-names (max 10)";
    }
    leaf checksum-6 {
      type string {
        length "1..64";
      }
      mandatory true;
      description
        "List of checksums (max 10)";
    }
  }

  grouping CHECKSUM-GROUP-7 {
    description
      "checksum helper group";
    uses CHECKSUM-GROUP-6;
    leaf file-name-7 {
      type string {
        length "1..224";
      }
      mandatory true;
      description
        "List of file-names (max 10)";
    }
    leaf checksum-7 {
      type string {
        length "1..64";
      }
      mandatory true;
      description
        "List of checksums (max 10)";
    }
  }

  grouping CHECKSUM-GROUP-8 {
    description
      "checksum helper group";
    uses CHECKSUM-GROUP-7;
    leaf file-name-8 {
      type string {
        length "1..224";
      }
      mandatory true;
      description
        "List of file-names (max 10)";
    }
    leaf checksum-8 {
      type string {
        length "1..64";
      }
      mandatory true;
      description
        "List of checksums (max 10)";
    }
  }

  grouping CHECKSUM-GROUP-9 {
    description
      "checksum helper group";
    uses CHECKSUM-GROUP-8;
    leaf file-name-9 {
      type string {
        length "1..224";
      }
      mandatory true;
      description
        "List of file-names (max 10)";
    }
    leaf checksum-9 {
      type string {
        length "1..64";
      }
      mandatory true;
      description
        "List of checksums (max 10)";
    }
  }

  grouping CHECKSUM-GROUP-10 {
    description
      "checksum helper group";
    uses CHECKSUM-GROUP-9;
    leaf file-name-10 {
      type string {
        length "1..224";
      }
      mandatory true;
      description
        "List of file-names (max 10)";
    }
    leaf checksum-10 {
      type string {
        length "1..64";
      }
      mandatory true;
      description
        "List of checksums (max 10)";
    }
  }

  augment "/ncs:devices/ncs:device/ncs:rpc" {
    container rpc-script-run-arguments-log-level-log-path-max-runtime {
      tailf:ncs-device-type "netconf";
      tailf:display-when "not(../../ncs:module) or ../../ncs:module[ncs:name='Cisco-IOS-XR-infra-script-mgmt-act']";
      tailf:action script-run-arguments-log-level-log-path-max-runtime {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-level <log-level> log-path <log-path> max-runtime <max-runtime>";
      }
    }
  }
  augment "/ncs:devices/ncs:device-group/ncs:ned-id/ncs:rpc" {
    container rpc-script-run-arguments-log-level-log-path-max-runtime {
      tailf:ncs-device-type "netconf";
      tailf:display-when "/ncs:devices/ncs:device[ncs:name=current()/../../../ncs:member]/ncs:module[ncs:name='Cisco-IOS-XR-infra-script-mgmt-act']";
      tailf:action script-run-arguments-log-level-log-path-max-runtime {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-level <log-level> log-path <log-path> max-runtime <max-runtime>";
      }
    }
  }
  augment "/ncs:devices/ncs:device/ncs:rpc" {
    container rpc-script-run-arguments-description-log-path-max-runtime {
      tailf:ncs-device-type "netconf";
      tailf:display-when "not(../../ncs:module) or ../../ncs:module[ncs:name='Cisco-IOS-XR-infra-script-mgmt-act']";
      tailf:action script-run-arguments-description-log-path-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> log-path <log-path> max-runtime <max-runtime>";
      }
    }
  }
  augment "/ncs:devices/ncs:device-group/ncs:ned-id/ncs:rpc" {
    container rpc-script-run-arguments-description-log-path-max-runtime {
      tailf:ncs-device-type "netconf";
      tailf:display-when "/ncs:devices/ncs:device[ncs:name=current()/../../../ncs:member]/ncs:module[ncs:name='Cisco-IOS-XR-infra-script-mgmt-act']";
      tailf:action script-run-arguments-description-log-path-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> log-path <log-path> max-runtime <max-runtime>";
      }
    }
  }
  augment "/ncs:devices/ncs:device/ncs:rpc" {
    container rpc-script-run-arguments-description-log-level-max-runtime {
      tailf:ncs-device-type "netconf";
      tailf:display-when "not(../../ncs:module) or ../../ncs:module[ncs:name='Cisco-IOS-XR-infra-script-mgmt-act']";
      tailf:action script-run-arguments-description-log-level-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> log-level <log-level> max-runtime <max-runtime>";
      }
    }
  }
  augment "/ncs:devices/ncs:device-group/ncs:ned-id/ncs:rpc" {
    container rpc-script-run-arguments-description-log-level-max-runtime {
      tailf:ncs-device-type "netconf";
      tailf:display-when "/ncs:devices/ncs:device[ncs:name=current()/../../../ncs:member]/ncs:module[ncs:name='Cisco-IOS-XR-infra-script-mgmt-act']";
      tailf:action script-run-arguments-description-log-level-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> log-level <log-level> max-runtime <max-runtime>";
      }
    }
  }
  augment "/ncs:devices/ncs:device/ncs:rpc" {
    container rpc-script-run-arguments-description-log-level-log-path {
      tailf:ncs-device-type "netconf";
      tailf:display-when "not(../../ncs:module) or ../../ncs:module[ncs:name='Cisco-IOS-XR-infra-script-mgmt-act']";
      tailf:action script-run-arguments-description-log-level-log-path {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background description <description> log-level <log-level> log-path <log-path>";
      }
    }
  }
  augment "/ncs:devices/ncs:device-group/ncs:ned-id/ncs:rpc" {
    container rpc-script-run-arguments-description-log-level-log-path {
      tailf:ncs-device-type "netconf";
      tailf:display-when "/ncs:devices/ncs:device[ncs:name=current()/../../../ncs:member]/ncs:module[ncs:name='Cisco-IOS-XR-infra-script-mgmt-act']";
      tailf:action script-run-arguments-description-log-level-log-path {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background description <description> log-level <log-level> log-path <log-path>";
      }
    }
  }
  augment "/ncs:devices/ncs:device/ncs:rpc" {
    container rpc-script-run-arguments-log-path-max-runtime {
      tailf:ncs-device-type "netconf";
      tailf:display-when "not(../../ncs:module) or ../../ncs:module[ncs:name='Cisco-IOS-XR-infra-script-mgmt-act']";
      tailf:action script-run-arguments-log-path-max-runtime {
        tailf:actionpoint ncsproxy {
          tailf:internal;
        }
        description
          "Script run";
        input {
          leaf name {
            type string {
              length "1..224";
            }
            mandatory true;
            description
              "Script name";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-path <log-path> max-runtime <max-runtime>";
      }
    }
  }
  augment "/ncs:devices/ncs:device-group/ncs:ned-id/ncs:rpc" {
    container rpc-script-run-arguments-log-path-max-runtime {
      tailf:ncs-device-type "netconf";
      tailf:display-when "/ncs:devices/ncs:device[ncs:name=current()/../../../ncs:member]/ncs:module[ncs:name='Cisco-IOS-XR-infra-script-mgmt-act']";
      tailf:action script-run-arguments-log-path-max-runtime {
        tailf:actionpoint ncsproxy {
          tailf:internal;
        }
        description
          "Script run";
        input {
          leaf name {
            type string {
              length "1..224";
            }
            mandatory true;
            description
              "Script name";
          }
          leaf log-path {
            type string {
              length "1..512";
            }
            mandatory true;
            description
              "log-path";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-path <log-path> max-runtime <max-runtime>";
      }
    }
  }
  augment "/ncs:devices/ncs:device/ncs:rpc" {
    container rpc-script-run-arguments-log-level-max-runtime {
      tailf:ncs-device-type "netconf";
      tailf:display-when "not(../../ncs:module) or ../../ncs:module[ncs:name='Cisco-IOS-XR-infra-script-mgmt-act']";
      tailf:action script-run-arguments-log-level-max-runtime {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-level <log-level> max-runtime <max-runtime>";
      }
    }
  }
  augment "/ncs:devices/ncs:device-group/ncs:ned-id/ncs:rpc" {
    container rpc-script-run-arguments-log-level-max-runtime {
      tailf:ncs-device-type "netconf";
      tailf:display-when "/ncs:devices/ncs:device[ncs:name=current()/../../../ncs:member]/ncs:module[ncs:name='Cisco-IOS-XR-infra-script-mgmt-act']";
      tailf:action script-run-arguments-log-level-max-runtime {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background log-level <log-level> max-runtime <max-runtime>";
      }
    }
  }
  augment "/ncs:devices/ncs:device/ncs:rpc" {
    container rpc-script-run-arguments-log-level-log-path {
      tailf:ncs-device-type "netconf";
      tailf:display-when "not(../../ncs:module) or ../../ncs:module[ncs:name='Cisco-IOS-XR-infra-script-mgmt-act']";
      tailf:action script-run-arguments-log-level-log-path {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background log-level <log-level> log-path <log-path>";
      }
    }
  }
  augment "/ncs:devices/ncs:device-group/ncs:ned-id/ncs:rpc" {
    container rpc-script-run-arguments-log-level-log-path {
      tailf:ncs-device-type "netconf";
      tailf:display-when "/ncs:devices/ncs:device[ncs:name=current()/../../../ncs:member]/ncs:module[ncs:name='Cisco-IOS-XR-infra-script-mgmt-act']";
      tailf:action script-run-arguments-log-level-log-path {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background log-level <log-level> log-path <log-path>";
      }
    }
  }
  augment "/ncs:devices/ncs:device/ncs:rpc" {
    container rpc-script-run-arguments-description-max-runtime {
      tailf:ncs-device-type "netconf";
      tailf:display-when "not(../../ncs:module) or ../../ncs:module[ncs:name='Cisco-IOS-XR-infra-script-mgmt-act']";
      tailf:action script-run-arguments-description-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> max-runtime <max-runtime>";
      }
    }
  }
  augment "/ncs:devices/ncs:device-group/ncs:ned-id/ncs:rpc" {
    container rpc-script-run-arguments-description-max-runtime {
      tailf:ncs-device-type "netconf";
      tailf:display-when "/ncs:devices/ncs:device[ncs:name=current()/../../../ncs:member]/ncs:module[ncs:name='Cisco-IOS-XR-infra-script-mgmt-act']";
      tailf:action script-run-arguments-description-max-runtime {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background description <description> max-runtime <max-runtime>";
      }
    }
  }
  augment "/ncs:devices/ncs:device/ncs:rpc" {
    container rpc-script-run-arguments-description-log-path {
      tailf:ncs-device-type "netconf";
      tailf:display-when "not(../../ncs:module) or ../../ncs:module[ncs:name='Cisco-IOS-XR-infra-script-mgmt-act']";
      tailf:action script-run-arguments-description-log-path {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background description <description> log-path <log-path>";
      }
    }
  }
  augment "/ncs:devices/ncs:device-group/ncs:ned-id/ncs:rpc" {
    container rpc-script-run-arguments-description-log-path {
      tailf:ncs-device-type "netconf";
      tailf:display-when "/ncs:devices/ncs:device[ncs:name=current()/../../../ncs:member]/ncs:module[ncs:name='Cisco-IOS-XR-infra-script-mgmt-act']";
      tailf:action script-run-arguments-description-log-path {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background description <description> log-path <log-path>";
      }
    }
  }
  augment "/ncs:devices/ncs:device/ncs:rpc" {
    container rpc-script-run-arguments-description-log-level {
      tailf:ncs-device-type "netconf";
      tailf:display-when "not(../../ncs:module) or ../../ncs:module[ncs:name='Cisco-IOS-XR-infra-script-mgmt-act']";
      tailf:action script-run-arguments-description-log-level {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf argument-list {
            type string {
              length "1..512";
            }
            mandatory true;
            description
              "Arguments as a string";
          }
        }
        csc:xr-task "root-lr";
        csc:cli-command "script run nooutput <name> arguments <argument-list> background description <description> log-level <log-level>";
      }
    }
  }
  augment "/ncs:devices/ncs:device-group/ncs:ned-id/ncs:rpc" {
    container rpc-script-run-arguments-description-log-level {
      tailf:ncs-device-type "netconf";
      tailf:display-when "/ncs:devices/ncs:device[ncs:name=current()/../../../ncs:member]/ncs:module[ncs:name='Cisco-IOS-XR-infra-script-mgmt-act']";
      tailf:action script-run-arguments-description-log-level {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "log-level";
          }
          leaf argument-list {
            type string {
              length "1..512";
            }
            mandatory true;
            description
              "Arguments as a string";
          }
        }
        csc:xr-task "root-lr";
        csc:cli-command "script run nooutput <name> arguments <argument-list> background description <description> log-level <log-level>";
      }
    }
  }
  augment "/ncs:devices/ncs:device/ncs:rpc" {
    container rpc-script-run-arguments-max-runtime {
      tailf:ncs-device-type "netconf";
      tailf:display-when "not(../../ncs:module) or ../../ncs:module[ncs:name='Cisco-IOS-XR-infra-script-mgmt-act']";
      tailf:action script-run-arguments-max-runtime {
        tailf:actionpoint ncsproxy {
          tailf:internal;
        }
        description
          "Script run";
        input {
          leaf name {
            type string {
              length "1..224";
            }
            mandatory true;
            description
              "Script name";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background max-runtime <max-runtime>";
      }
    }
  }
  augment "/ncs:devices/ncs:device-group/ncs:ned-id/ncs:rpc" {
    container rpc-script-run-arguments-max-runtime {
      tailf:ncs-device-type "netconf";
      tailf:display-when "/ncs:devices/ncs:device[ncs:name=current()/../../../ncs:member]/ncs:module[ncs:name='Cisco-IOS-XR-infra-script-mgmt-act']";
      tailf:action script-run-arguments-max-runtime {
        tailf:actionpoint ncsproxy {
          tailf:internal;
        }
        description
          "Script run";
        input {
          leaf name {
            type string {
              length "1..224";
            }
            mandatory true;
            description
              "Script name";
          }
          leaf max-runtime {
            type string {
              length "1..512";
            }
            mandatory true;
            description
              "max-runtime";
          }
          leaf argument-list {
            type string {
              length "1..512";
            }
            mandatory true;
            description
              "Arguments as a string";
          }
        }
        csc:xr-task "root-lr";
        csc:cli-command "script run nooutput <name> arguments <argument-list> background max-runtime <max-runtime>";
      }
    }
  }
  augment "/ncs:devices/ncs:device/ncs:rpc" {
    container rpc-script-run-arguments-log-path {
      tailf:ncs-device-type "netconf";
      tailf:display-when "not(../../ncs:module) or ../../ncs:module[ncs:name='Cisco-IOS-XR-infra-script-mgmt-act']";
      tailf:action script-run-arguments-log-path {
        tailf:actionpoint ncsproxy {
          tailf:internal;
        }
        description
          "Script run";
        input {
          leaf name {
            type string {
              length "1..224";
            }
            mandatory true;
            description
              "Script name";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background log-path <log-path>";
      }
    }
  }
  augment "/ncs:devices/ncs:device-group/ncs:ned-id/ncs:rpc" {
    container rpc-script-run-arguments-log-path {
      tailf:ncs-device-type "netconf";
      tailf:display-when "/ncs:devices/ncs:device[ncs:name=current()/../../../ncs:member]/ncs:module[ncs:name='Cisco-IOS-XR-infra-script-mgmt-act']";
      tailf:action script-run-arguments-log-path {
        tailf:actionpoint ncsproxy {
          tailf:internal;
        }
        description
          "Script run";
        input {
          leaf name {
            type string {
              length "1..224";
            }
            mandatory true;
            description
              "Script name";
          }
          leaf log-path {
            type string {
              length "1..512";
            }
            mandatory true;
            description
              "log-path";
          }
          leaf argument-list {
            type string {
              length "1..512";
            }
            mandatory true;
            description
              "Arguments as a string";
          }
        }
        csc:xr-task "root-lr";
        csc:cli-command "script run nooutput <name> arguments <argument-list> background log-path <log-path>";
      }
    }
  }
  augment "/ncs:devices/ncs:device/ncs:rpc" {
    container rpc-script-run-arguments-log-level {
      tailf:ncs-device-type "netconf";
      tailf:display-when "not(../../ncs:module) or ../../ncs:module[ncs:name='Cisco-IOS-XR-infra-script-mgmt-act']";
      tailf:action script-run-arguments-log-level {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf argument-list {
            type string {
              length "1..512";
            }
            mandatory true;
            description
              "Arguments as a string";
          }
        }
        csc:xr-task "root-lr";
        csc:cli-command "script run nooutput <name> arguments <argument-list> background log-level <log-level>";
      }
    }
  }
  augment "/ncs:devices/ncs:device-group/ncs:ned-id/ncs:rpc" {
    container rpc-script-run-arguments-log-level {
      tailf:ncs-device-type "netconf";
      tailf:display-when "/ncs:devices/ncs:device[ncs:name=current()/../../../ncs:member]/ncs:module[ncs:name='Cisco-IOS-XR-infra-script-mgmt-act']";
      tailf:action script-run-arguments-log-level {
        tailf:actionpoint ncsproxy {
          tailf:internal;
        }
        description
          "Script run";
        input {
          leaf name {
            type string {
              length "1..224";
            }
            mandatory true;
            description
              "Script name";
          }
          leaf log-level {
            type string {
              length "1..512";
            }
            mandatory true;
            description
              "log-level";
          }
          leaf argument-list {
            type string {
              length "1..512";
            }
            mandatory true;
            description
              "Arguments as a string";
          }
        }
        csc:xr-task "root-lr";
        csc:cli-command "script run nooutput <name> arguments <argument-list> background log-level <log-level>";
      }
    }
  }
  augment "/ncs:devices/ncs:device/ncs:rpc" {
    container rpc-script-run-arguments-description {
      tailf:ncs-device-type "netconf";
      tailf:display-when "not(../../ncs:module) or ../../ncs:module[ncs:name='Cisco-IOS-XR-infra-script-mgmt-act']";
      tailf:action script-run-arguments-description {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf argument-list {
            type string {
              length "1..512";
            }
            mandatory true;
            description
              "Arguments as a string";
          }
        }
        csc:xr-task "root-lr";
        csc:cli-command "script run nooutput <name> arguments <argument-list> background description <description>";
      }
    }
  }
  augment "/ncs:devices/ncs:device-group/ncs:ned-id/ncs:rpc" {
    container rpc-script-run-arguments-description {
      tailf:ncs-device-type "netconf";
      tailf:display-when "/ncs:devices/ncs:device[ncs:name=current()/../../../ncs:member]/ncs:module[ncs:name='Cisco-IOS-XR-infra-script-mgmt-act']";
      tailf:action script-run-arguments-description {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf argument-list {
            type string {
              length "1..512";
            }
            mandatory true;
            description
              "Arguments as a string";
          }
        }
        csc:xr-task "root-lr";
        csc:cli-command "script run nooutput <name> arguments <argument-list> background description <description>";
      }
    }
  }
  augment "/ncs:devices/ncs:device/ncs:rpc" {
    container rpc-script-run-arguments-optional-args {
      tailf:ncs-device-type "netconf";
      tailf:display-when "not(../../ncs:module) or ../../ncs:module[ncs:name='Cisco-IOS-XR-infra-script-mgmt-act']";
      tailf:action script-run-arguments-optional-args {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "description";
          }
          leaf max-runtime {
            type string {
              length "1..512";
            }
            mandatory true;
            description
              "description";
          }
          leaf argument-list {
            type string {
              length "1..512";
            }
            mandatory true;
            description
              "Arguments as a string";
          }
        }
        csc:xr-task "root-lr";
        csc:cli-command "script run nooutput <name> arguments <argument-list> background description <description> log-level <log-level> log-path <log-path> max-runtime <max-runtime>";
      }
    }
  }
  augment "/ncs:devices/ncs:device-group/ncs:ned-id/ncs:rpc" {
    container rpc-script-run-arguments-optional-args {
      tailf:ncs-device-type "netconf";
      tailf:display-when "/ncs:devices/ncs:device[ncs:name=current()/../../../ncs:member]/ncs:module[ncs:name='Cisco-IOS-XR-infra-script-mgmt-act']";
      tailf:action script-run-arguments-optional-args {
        tailf:actionpoint ncsproxy {
          tailf:internal;
        }
        description
          "Script run";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "description";
          }
          leaf max-runtime {
            type string {
              length "1..512";
            }
            mandatory true;
            description
              "description";
          }
          leaf argument-list {
            type string {
              length "1..512";
            }
            mandatory true;
            description
              "Arguments as a string";
          }
        }
        csc:xr-task "root-lr";
        csc:cli-command "script run nooutput <name> arguments <argument-list> background description <description> log-level <log-level> log-path <log-path> max-runtime <max-runtime>";
      }
    }
  }
  augment "/ncs:devices/ncs:device/ncs:rpc" {
    container rpc-script-run-optional-args-log-level-log-path-max-runtime {
      tailf:ncs-device-type "netconf";
      tailf:display-when "not(../../ncs:module) or ../../ncs:module[ncs:name='Cisco-IOS-XR-infra-script-mgmt-act']";
      tailf:action script-run-optional-args-log-level-log-path-max-runtime {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background log-level <log-level> log-path <log-path> max-runtime <max-runtime>";
      }
    }
  }
  augment "/ncs:devices/ncs:device-group/ncs:ned-id/ncs:rpc" {
    container rpc-script-run-optional-args-log-level-log-path-max-runtime {
      tailf:ncs-device-type "netconf";
      tailf:display-when "/ncs:devices/ncs:device[ncs:name=current()/../../../ncs:member]/ncs:module[ncs:name='Cisco-IOS-XR-infra-script-mgmt-act']";
      tailf:action script-run-optional-args-log-level-log-path-max-runtime {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background log-level <log-level> log-path <log-path> max-runtime <max-runtime>";
      }
    }
  }
  augment "/ncs:devices/ncs:device/ncs:rpc" {
    container rpc-script-run-optional-args-description-log-path-max-runtime {
      tailf:ncs-device-type "netconf";
      tailf:display-when "not(../../ncs:module) or ../../ncs:module[ncs:name='Cisco-IOS-XR-infra-script-mgmt-act']";
      tailf:action script-run-optional-args-description-log-path-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background description <description> log-path <log-path> max-runtime <max-runtime>";
      }
    }
  }
  augment "/ncs:devices/ncs:device-group/ncs:ned-id/ncs:rpc" {
    container rpc-script-run-optional-args-description-log-path-max-runtime {
      tailf:ncs-device-type "netconf";
      tailf:display-when "/ncs:devices/ncs:device[ncs:name=current()/../../../ncs:member]/ncs:module[ncs:name='Cisco-IOS-XR-infra-script-mgmt-act']";
      tailf:action script-run-optional-args-description-log-path-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background description <description> log-path <log-path> max-runtime <max-runtime>";
      }
    }
  }
  augment "/ncs:devices/ncs:device/ncs:rpc" {
    container rpc-script-run-optional-args-description-log-level-max-runtime {
      tailf:ncs-device-type "netconf";
      tailf:display-when "not(../../ncs:module) or ../../ncs:module[ncs:name='Cisco-IOS-XR-infra-script-mgmt-act']";
      tailf:action script-run-optional-args-description-log-level-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf max-runtime {
            type string {
              length "1..512";
            }
            mandatory true;
            description
              "max-runtime";
          }
        }
        csc:xr-task "root-lr";
        csc:cli-command "script run nooutput <name> background description <description> log-level <log-level> max-runtime <max-runtime>";
      }
    }
  }
  augment "/ncs:devices/ncs:device-group/ncs:ned-id/ncs:rpc" {
    container rpc-script-run-optional-args-description-log-level-max-runtime {
      tailf:ncs-device-type "netconf";
      tailf:display-when "/ncs:devices/ncs:device[ncs:name=current()/../../../ncs:member]/ncs:module[ncs:name='Cisco-IOS-XR-infra-script-mgmt-act']";
      tailf:action script-run-optional-args-description-log-level-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf max-runtime {
            type string {
              length "1..512";
            }
            mandatory true;
            description
              "max-runtime";
          }
        }
        csc:xr-task "root-lr";
        csc:cli-command "script run nooutput <name> background description <description> log-level <log-level> max-runtime <max-runtime>";
      }
    }
  }
  augment "/ncs:devices/ncs:device/ncs:rpc" {
    container rpc-script-run-optional-args-description-log-level-log-path {
      tailf:ncs-device-type "netconf";
      tailf:display-when "not(../../ncs:module) or ../../ncs:module[ncs:name='Cisco-IOS-XR-infra-script-mgmt-act']";
      tailf:action script-run-optional-args-description-log-level-log-path {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "log-path";
          }
        }
        csc:xr-task "root-lr";
        csc:cli-command "script run nooutput <name> background description <description> log-level <log-level> log-path <log-path>";
      }
    }
  }
  augment "/ncs:devices/ncs:device-group/ncs:ned-id/ncs:rpc" {
    container rpc-script-run-optional-args-description-log-level-log-path {
      tailf:ncs-device-type "netconf";
      tailf:display-when "/ncs:devices/ncs:device[ncs:name=current()/../../../ncs:member]/ncs:module[ncs:name='Cisco-IOS-XR-infra-script-mgmt-act']";
      tailf:action script-run-optional-args-description-log-level-log-path {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "log-path";
          }
        }
        csc:xr-task "root-lr";
        csc:cli-command "script run nooutput <name> background description <description> log-level <log-level> log-path <log-path>";
      }
    }
  }
  augment "/ncs:devices/ncs:device/ncs:rpc" {
    container rpc-script-run-optional-args-log-path-max-runtime {
      tailf:ncs-device-type "netconf";
      tailf:display-when "not(../../ncs:module) or ../../ncs:module[ncs:name='Cisco-IOS-XR-infra-script-mgmt-act']";
      tailf:action script-run-optional-args-log-path-max-runtime {
        tailf:actionpoint ncsproxy {
          tailf:internal;
        }
        description
          "optional args";
        input {
          leaf name {
            type string {
              length "1..224";
            }
            mandatory true;
            description
              "Script name";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background log-path <log-path> max-runtime <max-runtime>";
      }
    }
  }
  augment "/ncs:devices/ncs:device-group/ncs:ned-id/ncs:rpc" {
    container rpc-script-run-optional-args-log-path-max-runtime {
      tailf:ncs-device-type "netconf";
      tailf:display-when "/ncs:devices/ncs:device[ncs:name=current()/../../../ncs:member]/ncs:module[ncs:name='Cisco-IOS-XR-infra-script-mgmt-act']";
      tailf:action script-run-optional-args-log-path-max-runtime {
        tailf:actionpoint ncsproxy {
          tailf:internal;
        }
        description
          "optional args";
        input {
          leaf name {
            type string {
              length "1..224";
            }
            mandatory true;
            description
              "Script name";
          }
          leaf log-path {
            type string {
              length "1..512";
            }
            mandatory true;
            description
              "log-path";
          }
          leaf max-runtime {
            type string {
              length "1..512";
            }
            mandatory true;
            description
              "max-runtime";
          }
        }
        csc:xr-task "root-lr";
        csc:cli-command "script run nooutput <name> background log-path <log-path> max-runtime <max-runtime>";
      }
    }
  }
  augment "/ncs:devices/ncs:device/ncs:rpc" {
    container rpc-script-run-optional-args-log-level-max-runtime {
      tailf:ncs-device-type "netconf";
      tailf:display-when "not(../../ncs:module) or ../../ncs:module[ncs:name='Cisco-IOS-XR-infra-script-mgmt-act']";
      tailf:action script-run-optional-args-log-level-max-runtime {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
          leaf max-runtime {
            type string {
              length "1..512";
            }
            mandatory true;
            description
              "max-runtime";
          }
        }
        csc:xr-task "root-lr";
        csc:cli-command "script run nooutput <name> background log-level <log-level> max-runtime <max-runtime>";
      }
    }
  }
  augment "/ncs:devices/ncs:device-group/ncs:ned-id/ncs:rpc" {
    container rpc-script-run-optional-args-log-level-max-runtime {
      tailf:ncs-device-type "netconf";
      tailf:display-when "/ncs:devices/ncs:device[ncs:name=current()/../../../ncs:member]/ncs:module[ncs:name='Cisco-IOS-XR-infra-script-mgmt-act']";
      tailf:action script-run-optional-args-log-level-max-runtime {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
          leaf max-runtime {
            type string {
              length "1..512";
            }
            mandatory true;
            description
              "max-runtime";
          }
        }
        csc:xr-task "root-lr";
        csc:cli-command "script run nooutput <name> background log-level <log-level> max-runtime <max-runtime>";
      }
    }
  }
  augment "/ncs:devices/ncs:device/ncs:rpc" {
    container rpc-script-run-optional-args-log-level-log-path {
      tailf:ncs-device-type "netconf";
      tailf:display-when "not(../../ncs:module) or ../../ncs:module[ncs:name='Cisco-IOS-XR-infra-script-mgmt-act']";
      tailf:action script-run-optional-args-log-level-log-path {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
        }
        csc:xr-task "root-lr";
        csc:cli-command "script run nooutput <name> background log-level <log-level> log-path <log-path>";
      }
    }
  }
  augment "/ncs:devices/ncs:device-group/ncs:ned-id/ncs:rpc" {
    container rpc-script-run-optional-args-log-level-log-path {
      tailf:ncs-device-type "netconf";
      tailf:display-when "/ncs:devices/ncs:device[ncs:name=current()/../../../ncs:member]/ncs:module[ncs:name='Cisco-IOS-XR-infra-script-mgmt-act']";
      tailf:action script-run-optional-args-log-level-log-path {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
          leaf log-path {
            type string {
              length "1..512";
            }
            mandatory true;
            description
              "log-path";
          }
        }
        csc:xr-task "root-lr";
        csc:cli-command "script run nooutput <name> background log-level <log-level> log-path <log-path>";
      }
    }
  }
  augment "/ncs:devices/ncs:device/ncs:rpc" {
    container rpc-script-run-optional-args-description-max-runtime {
      tailf:ncs-device-type "netconf";
      tailf:display-when "not(../../ncs:module) or ../../ncs:module[ncs:name='Cisco-IOS-XR-infra-script-mgmt-act']";
      tailf:action script-run-optional-args-description-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf max-runtime {
            type string {
              length "1..512";
            }
            mandatory true;
            description
              "max-runtime";
          }
        }
        csc:xr-task "root-lr";
        csc:cli-command "script run nooutput <name> background description <description> max-runtime <max-runtime>";
      }
    }
  }
  augment "/ncs:devices/ncs:device-group/ncs:ned-id/ncs:rpc" {
    container rpc-script-run-optional-args-description-max-runtime {
      tailf:ncs-device-type "netconf";
      tailf:display-when "/ncs:devices/ncs:device[ncs:name=current()/../../../ncs:member]/ncs:module[ncs:name='Cisco-IOS-XR-infra-script-mgmt-act']";
      tailf:action script-run-optional-args-description-max-runtime {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf max-runtime {
            type string {
              length "1..512";
            }
            mandatory true;
            description
              "max-runtime";
          }
        }
        csc:xr-task "root-lr";
        csc:cli-command "script run nooutput <name> background description <description> max-runtime <max-runtime>";
      }
    }
  }
  augment "/ncs:devices/ncs:device/ncs:rpc" {
    container rpc-script-run-optional-args-description-log-path {
      tailf:ncs-device-type "netconf";
      tailf:display-when "not(../../ncs:module) or ../../ncs:module[ncs:name='Cisco-IOS-XR-infra-script-mgmt-act']";
      tailf:action script-run-optional-args-description-log-path {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
        }
        csc:xr-task "root-lr";
        csc:cli-command "script run nooutput <name> background description <description> log-path <log-path>";
      }
    }
  }
  augment "/ncs:devices/ncs:device-group/ncs:ned-id/ncs:rpc" {
    container rpc-script-run-optional-args-description-log-path {
      tailf:ncs-device-type "netconf";
      tailf:display-when "/ncs:devices/ncs:device[ncs:name=current()/../../../ncs:member]/ncs:module[ncs:name='Cisco-IOS-XR-infra-script-mgmt-act']";
      tailf:action script-run-optional-args-description-log-path {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-path {
            type string {
              length "1..512";
            }
            mandatory true;
            description
              "log-path";
          }
        }
        csc:xr-task "root-lr";
        csc:cli-command "script run nooutput <name> background description <description> log-path <log-path>";
      }
    }
  }
  augment "/ncs:devices/ncs:device/ncs:rpc" {
    container rpc-script-run-optional-args-description-log-level {
      tailf:ncs-device-type "netconf";
      tailf:display-when "not(../../ncs:module) or ../../ncs:module[ncs:name='Cisco-IOS-XR-infra-script-mgmt-act']";
      tailf:action script-run-optional-args-description-log-level {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
        }
        csc:xr-task "root-lr";
        csc:cli-command "script run nooutput <name> background description <description> log-level <log-level>";
      }
    }
  }
  augment "/ncs:devices/ncs:device-group/ncs:ned-id/ncs:rpc" {
    container rpc-script-run-optional-args-description-log-level {
      tailf:ncs-device-type "netconf";
      tailf:display-when "/ncs:devices/ncs:device[ncs:name=current()/../../../ncs:member]/ncs:module[ncs:name='Cisco-IOS-XR-infra-script-mgmt-act']";
      tailf:action script-run-optional-args-description-log-level {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
        }
        csc:xr-task "root-lr";
        csc:cli-command "script run nooutput <name> background description <description> log-level <log-level>";
      }
    }
  }
  augment "/ncs:devices/ncs:device/ncs:rpc" {
    container rpc-script-run-optional-args-max-runtime {
      tailf:ncs-device-type "netconf";
      tailf:display-when "not(../../ncs:module) or ../../ncs:module[ncs:name='Cisco-IOS-XR-infra-script-mgmt-act']";
      tailf:action script-run-optional-args-max-runtime {
        tailf:actionpoint ncsproxy {
          tailf:internal;
        }
        description
          "optional args";
        input {
          leaf name {
            type string {
              length "1..224";
            }
            mandatory true;
            description
              "Script name";
          }
          leaf max-runtime {
            type string {
              length "1..512";
            }
            mandatory true;
            description
              "max-runtime";
          }
        }
        csc:xr-task "root-lr";
        csc:cli-command "script run nooutput <name> background max-runtime <max-runtime>";
      }
    }
  }
  augment "/ncs:devices/ncs:device-group/ncs:ned-id/ncs:rpc" {
    container rpc-script-run-optional-args-max-runtime {
      tailf:ncs-device-type "netconf";
      tailf:display-when "/ncs:devices/ncs:device[ncs:name=current()/../../../ncs:member]/ncs:module[ncs:name='Cisco-IOS-XR-infra-script-mgmt-act']";
      tailf:action script-run-optional-args-max-runtime {
        tailf:actionpoint ncsproxy {
          tailf:internal;
        }
        description
          "optional args";
        input {
          leaf name {
            type string {
              length "1..224";
            }
            mandatory true;
            description
              "Script name";
          }
          leaf max-runtime {
            type string {
              length "1..512";
            }
            mandatory true;
            description
              "max-runtime";
          }
        }
        csc:xr-task "root-lr";
        csc:cli-command "script run nooutput <name> background max-runtime <max-runtime>";
      }
    }
  }
  augment "/ncs:devices/ncs:device/ncs:rpc" {
    container rpc-script-run-optional-args-log-path {
      tailf:ncs-device-type "netconf";
      tailf:display-when "not(../../ncs:module) or ../../ncs:module[ncs:name='Cisco-IOS-XR-infra-script-mgmt-act']";
      tailf:action script-run-optional-args-log-path {
        tailf:actionpoint ncsproxy {
          tailf:internal;
        }
        description
          "optional args";
        input {
          leaf name {
            type string {
              length "1..224";
            }
            mandatory true;
            description
              "Script name";
          }
          leaf log-path {
            type string {
              length "1..512";
            }
            mandatory true;
            description
              "log-path";
          }
        }
        csc:xr-task "root-lr";
        csc:cli-command "script run nooutput <name> background log-path <log-path>";
      }
    }
  }
  augment "/ncs:devices/ncs:device-group/ncs:ned-id/ncs:rpc" {
    container rpc-script-run-optional-args-log-path {
      tailf:ncs-device-type "netconf";
      tailf:display-when "/ncs:devices/ncs:device[ncs:name=current()/../../../ncs:member]/ncs:module[ncs:name='Cisco-IOS-XR-infra-script-mgmt-act']";
      tailf:action script-run-optional-args-log-path {
        tailf:actionpoint ncsproxy {
          tailf:internal;
        }
        description
          "optional args";
        input {
          leaf name {
            type string {
              length "1..224";
            }
            mandatory true;
            description
              "Script name";
          }
          leaf log-path {
            type string {
              length "1..512";
            }
            mandatory true;
            description
              "log-path";
          }
        }
        csc:xr-task "root-lr";
        csc:cli-command "script run nooutput <name> background log-path <log-path>";
      }
    }
  }
  augment "/ncs:devices/ncs:device/ncs:rpc" {
    container rpc-script-run-optional-args-log-level {
      tailf:ncs-device-type "netconf";
      tailf:display-when "not(../../ncs:module) or ../../ncs:module[ncs:name='Cisco-IOS-XR-infra-script-mgmt-act']";
      tailf:action script-run-optional-args-log-level {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
        }
        csc:xr-task "root-lr";
        csc:cli-command "script run nooutput <name> background log-level <log-level>";
      }
    }
  }
  augment "/ncs:devices/ncs:device-group/ncs:ned-id/ncs:rpc" {
    container rpc-script-run-optional-args-log-level {
      tailf:ncs-device-type "netconf";
      tailf:display-when "/ncs:devices/ncs:device[ncs:name=current()/../../../ncs:member]/ncs:module[ncs:name='Cisco-IOS-XR-infra-script-mgmt-act']";
      tailf:action script-run-optional-args-log-level {
        tailf:actionpoint ncsproxy {
          tailf:internal;
        }
        description
          "optional args";
        input {
          leaf name {
            type string {
              length "1..224";
            }
            mandatory true;
            description
              "Script name";
          }
          leaf log-level {
            type string {
              length "1..512";
            }
            mandatory true;
            description
              "log-level";
          }
        }
        csc:xr-task "root-lr";
        csc:cli-command "script run nooutput <name> background log-level <log-level>";
      }
    }
  }
  augment "/ncs:devices/ncs:device/ncs:rpc" {
    container rpc-script-run-optional-args-description {
      tailf:ncs-device-type "netconf";
      tailf:display-when "not(../../ncs:module) or ../../ncs:module[ncs:name='Cisco-IOS-XR-infra-script-mgmt-act']";
      tailf:action script-run-optional-args-description {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
        }
        csc:xr-task "root-lr";
        csc:cli-command "script run nooutput <name> background description <description>";
      }
    }
  }
  augment "/ncs:devices/ncs:device-group/ncs:ned-id/ncs:rpc" {
    container rpc-script-run-optional-args-description {
      tailf:ncs-device-type "netconf";
      tailf:display-when "/ncs:devices/ncs:device[ncs:name=current()/../../../ncs:member]/ncs:module[ncs:name='Cisco-IOS-XR-infra-script-mgmt-act']";
      tailf:action script-run-optional-args-description {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
        }
        csc:xr-task "root-lr";
        csc:cli-command "script run nooutput <name> background description <description>";
      }
    }
  }
  augment "/ncs:devices/ncs:device/ncs:rpc" {
    container rpc-script-run-optional-args-all {
      tailf:ncs-device-type "netconf";
      tailf:display-when "not(../../ncs:module) or ../../ncs:module[ncs:name='Cisco-IOS-XR-infra-script-mgmt-act']";
      tailf:action script-run-optional-args-all {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "description";
          }
          leaf max-runtime {
            type string {
              length "1..512";
            }
            mandatory true;
            description
              "description";
          }
        }
        csc:xr-task "root-lr";
        csc:cli-command "script run nooutput <name> background description <description> log-level <log-level> log-path <log-path> max-runtime <max-runtime>";
      }
    }
  }
  augment "/ncs:devices/ncs:device-group/ncs:ned-id/ncs:rpc" {
    container rpc-script-run-optional-args-all {
      tailf:ncs-device-type "netconf";
      tailf:display-when "/ncs:devices/ncs:device[ncs:name=current()/../../../ncs:member]/ncs:module[ncs:name='Cisco-IOS-XR-infra-script-mgmt-act']";
      tailf:action script-run-optional-args-all {
        tailf:actionpoint ncsproxy {
          tailf:internal;
        }
        description
          "optional args";
        input {
          leaf name {
            type string {
              length "1..224";
            }
            mandatory true;
            description
              "Script name";
          }
          leaf description {
            type string {
              length "1..512";
            }
            mandatory true;
            description
              "description";
          }
          leaf log-level {
            type string {
              length "1..512";
            }
            mandatory true;
            description
              "description";
          }
          leaf log-path {
            type string {
              length "1..512";
            }
            mandatory true;
            description
              "description";
          }
          leaf max-runtime {
            type string {
              length "1..512";
            }
            mandatory true;
            description
              "description";
          }
        }
        csc:xr-task "root-lr";
        csc:cli-command "script run nooutput <name> background description <description> log-level <log-level> log-path <log-path> max-runtime <max-runtime>";
      }
    }
  }
  augment "/ncs:devices/ncs:device/ncs:rpc" {
    container rpc-script-run-arguments {
      tailf:ncs-device-type "netconf";
      tailf:display-when "not(../../ncs:module) or ../../ncs:module[ncs:name='Cisco-IOS-XR-infra-script-mgmt-act']";
      tailf:action script-run-arguments {
        tailf:actionpoint ncsproxy {
          tailf:internal;
        }
        description
          "Script run";
        input {
          leaf name {
            type string {
              length "1..224";
            }
            mandatory true;
            description
              "Script name";
          }
          leaf argument-list {
            type string {
              length "1..512";
            }
            mandatory true;
            description
              "Arguments as a string";
          }
        }
        csc:xr-task "root-lr";
        csc:cli-command "script run nooutput <name> arguments <argument-list> background";
      }
    }
  }
  augment "/ncs:devices/ncs:device-group/ncs:ned-id/ncs:rpc" {
    container rpc-script-run-arguments {
      tailf:ncs-device-type "netconf";
      tailf:display-when "/ncs:devices/ncs:device[ncs:name=current()/../../../ncs:member]/ncs:module[ncs:name='Cisco-IOS-XR-infra-script-mgmt-act']";
      tailf:action script-run-arguments {
        tailf:actionpoint ncsproxy {
          tailf:internal;
        }
        description
          "Script run";
        input {
          leaf name {
            type string {
              length "1..224";
            }
            mandatory true;
            description
              "Script name";
          }
          leaf argument-list {
            type string {
              length "1..512";
            }
            mandatory true;
            description
              "Arguments as a string";
          }
        }
        csc:xr-task "root-lr";
        csc:cli-command "script run nooutput <name> arguments <argument-list> background";
      }
    }
  }
  augment "/ncs:devices/ncs:device/ncs:rpc" {
    container rpc-script-run {
      tailf:ncs-device-type "netconf";
      tailf:display-when "not(../../ncs:module) or ../../ncs:module[ncs:name='Cisco-IOS-XR-infra-script-mgmt-act']";
      tailf:action script-run {
        tailf:actionpoint ncsproxy {
          tailf:internal;
        }
        description
          "Script run";
        input {
          leaf name {
            type string {
              length "1..224";
            }
            mandatory true;
            description
              "Script name";
          }
        }
        csc:xr-task "root-lr";
        csc:cli-command "script run nooutput <name> background";
      }
    }
  }
  augment "/ncs:devices/ncs:device-group/ncs:ned-id/ncs:rpc" {
    container rpc-script-run {
      tailf:ncs-device-type "netconf";
      tailf:display-when "/ncs:devices/ncs:device[ncs:name=current()/../../../ncs:member]/ncs:module[ncs:name='Cisco-IOS-XR-infra-script-mgmt-act']";
      tailf:action script-run {
        tailf:actionpoint ncsproxy {
          tailf:internal;
        }
        description
          "Script run";
        input {
          leaf name {
            type string {
              length "1..224";
            }
            mandatory true;
            description
              "Script name";
          }
        }
        csc:xr-task "root-lr";
        csc:cli-command "script run nooutput <name> background";
      }
    }
  }
  augment "/ncs:devices/ncs:device/ncs:rpc" {
    container rpc-script-stop-request-description {
      tailf:ncs-device-type "netconf";
      tailf:display-when "not(../../ncs:module) or ../../ncs:module[ncs:name='Cisco-IOS-XR-infra-script-mgmt-act']";
      tailf:action script-stop-request-description {
        tailf:actionpoint ncsproxy {
          tailf:internal;
        }
        description
          "Stop OP script execution";
        input {
          leaf request {
            type uint32;
            mandatory true;
            description
              "Request ID of job in request queue";
          }
          leaf description {
            type string {
              length "1..512";
            }
            mandatory true;
            description
              "Description";
          }
        }
        csc:xr-task "basic-services";
        csc:cli-command "script stop nooutput <request> <description>";
      }
    }
  }
  augment "/ncs:devices/ncs:device-group/ncs:ned-id/ncs:rpc" {
    container rpc-script-stop-request-description {
      tailf:ncs-device-type "netconf";
      tailf:display-when "/ncs:devices/ncs:device[ncs:name=current()/../../../ncs:member]/ncs:module[ncs:name='Cisco-IOS-XR-infra-script-mgmt-act']";
      tailf:action script-stop-request-description {
        tailf:actionpoint ncsproxy {
          tailf:internal;
        }
        description
          "Stop OP script execution";
        input {
          leaf request {
            type uint32;
            mandatory true;
            description
              "Request ID of job in request queue";
          }
          leaf description {
            type string {
              length "1..512";
            }
            mandatory true;
            description
              "Description";
          }
        }
        csc:xr-task "basic-services";
        csc:cli-command "script stop nooutput <request> <description>";
      }
    }
  }
  augment "/ncs:devices/ncs:device/ncs:rpc" {
    container rpc-script-stop-request {
      tailf:ncs-device-type "netconf";
      tailf:display-when "not(../../ncs:module) or ../../ncs:module[ncs:name='Cisco-IOS-XR-infra-script-mgmt-act']";
      tailf:action script-stop-request {
        tailf:actionpoint ncsproxy {
          tailf:internal;
        }
        description
          "Stop OP script execution";
        input {
          leaf request {
            type uint32;
            mandatory true;
            description
              "Request ID of job in request queue";
          }
        }
        csc:xr-task "basic-services";
        csc:cli-command "script stop nooutput <request>";
      }
    }
  }
  augment "/ncs:devices/ncs:device-group/ncs:ned-id/ncs:rpc" {
    container rpc-script-stop-request {
      tailf:ncs-device-type "netconf";
      tailf:display-when "/ncs:devices/ncs:device[ncs:name=current()/../../../ncs:member]/ncs:module[ncs:name='Cisco-IOS-XR-infra-script-mgmt-act']";
      tailf:action script-stop-request {
        tailf:actionpoint ncsproxy {
          tailf:internal;
        }
        description
          "Stop OP script execution";
        input {
          leaf request {
            type uint32;
            mandatory true;
            description
              "Request ID of job in request queue";
          }
        }
        csc:xr-task "basic-services";
        csc:cli-command "script stop nooutput <request>";
      }
    }
  }
  augment "/ncs:devices/ncs:device/ncs:rpc" {
    container rpc-script-remove-type {
      tailf:ncs-device-type "netconf";
      tailf:display-when "not(../../ncs:module) or ../../ncs:module[ncs:name='Cisco-IOS-XR-infra-script-mgmt-act']";
      tailf:action script-remove-type {
        tailf:actionpoint ncsproxy {
          tailf:internal;
        }
        description
          "Remove script from script repository.
           select script-type.
          ";
        input {
          leaf type {
            type string {
              length "1..512";
            }
            mandatory true;
            description
              "<exec, eem, config, process>";
          }
          uses ncs_rpc_notif_FILE-NAME-LIST;
        }
        csc:xr-task "basic-services";
        csc:cli-command "script remove <type> nooutput <file-name-1> <file-name-2> <file-name-3> <file-name-4> <file-name-5> <file-name-6> <file-name-7> <file-name-8> <file-name-9> <file-name-10>";
      }
    }
  }
  augment "/ncs:devices/ncs:device-group/ncs:ned-id/ncs:rpc" {
    container rpc-script-remove-type {
      tailf:ncs-device-type "netconf";
      tailf:display-when "/ncs:devices/ncs:device[ncs:name=current()/../../../ncs:member]/ncs:module[ncs:name='Cisco-IOS-XR-infra-script-mgmt-act']";
      tailf:action script-remove-type {
        tailf:actionpoint ncsproxy {
          tailf:internal;
        }
        description
          "Remove script from script repository.
           select script-type.
          ";
        input {
          leaf type {
            type string {
              length "1..512";
            }
            mandatory true;
            description
              "<exec, eem, config, process>";
          }
          uses ncs_rpc_notif_FILE-NAME-LIST;
        }
        csc:xr-task "basic-services";
        csc:cli-command "script remove <type> nooutput <file-name-1> <file-name-2> <file-name-3> <file-name-4> <file-name-5> <file-name-6> <file-name-7> <file-name-8> <file-name-9> <file-name-10>";
      }
    }
  }
  augment "/ncs:devices/ncs:device/ncs:rpc" {
    container rpc-script-add-type-source-checksum-10 {
      tailf:ncs-device-type "netconf";
      tailf:display-when "not(../../ncs:module) or ../../ncs:module[ncs:name='Cisco-IOS-XR-infra-script-mgmt-act']";
      tailf:action script-add-type-source-checksum-10 {
        tailf:actionpoint ncsproxy {
          tailf:internal;
        }
        description
          "Add script to script repository.
           select script-type.
           source location of script to download.
           -http: <server>[;<vrf>]/full_path_to_repo
          ";
        input {
          uses ncs_rpc_notif_CHECKSUM-GROUP-10;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8> <file-name-9> checksum <checksum-9> <file-name-10> checksum <checksum-10>";
      }
    }
  }
  augment "/ncs:devices/ncs:device-group/ncs:ned-id/ncs:rpc" {
    container rpc-script-add-type-source-checksum-10 {
      tailf:ncs-device-type "netconf";
      tailf:display-when "/ncs:devices/ncs:device[ncs:name=current()/../../../ncs:member]/ncs:module[ncs:name='Cisco-IOS-XR-infra-script-mgmt-act']";
      tailf:action script-add-type-source-checksum-10 {
        tailf:actionpoint ncsproxy {
          tailf:internal;
        }
        description
          "Add script to script repository.
           select script-type.
           source location of script to download.
           -http: <server>[;<vrf>]/full_path_to_repo
          ";
        input {
          uses ncs_rpc_notif_CHECKSUM-GROUP-10;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8> <file-name-9> checksum <checksum-9> <file-name-10> checksum <checksum-10>";
      }
    }
  }
  augment "/ncs:devices/ncs:device/ncs:rpc" {
    container rpc-script-add-type-source-checksum-9 {
      tailf:ncs-device-type "netconf";
      tailf:display-when "not(../../ncs:module) or ../../ncs:module[ncs:name='Cisco-IOS-XR-infra-script-mgmt-act']";
      tailf:action script-add-type-source-checksum-9 {
        tailf:actionpoint ncsproxy {
          tailf:internal;
        }
        description
          "Add script to script repository.
           select script-type.
           source location of script to download.
           -http: <server>[;<vrf>]/full_path_to_repo
          ";
        input {
          uses ncs_rpc_notif_CHECKSUM-GROUP-9;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8> <file-name-9> checksum <checksum-9>";
      }
    }
  }
  augment "/ncs:devices/ncs:device-group/ncs:ned-id/ncs:rpc" {
    container rpc-script-add-type-source-checksum-9 {
      tailf:ncs-device-type "netconf";
      tailf:display-when "/ncs:devices/ncs:device[ncs:name=current()/../../../ncs:member]/ncs:module[ncs:name='Cisco-IOS-XR-infra-script-mgmt-act']";
      tailf:action script-add-type-source-checksum-9 {
        tailf:actionpoint ncsproxy {
          tailf:internal;
        }
        description
          "Add script to script repository.
           select script-type.
           source location of script to download.
           -http: <server>[;<vrf>]/full_path_to_repo
          ";
        input {
          uses ncs_rpc_notif_CHECKSUM-GROUP-9;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8> <file-name-9> checksum <checksum-9>";
      }
    }
  }
  augment "/ncs:devices/ncs:device/ncs:rpc" {
    container rpc-script-add-type-source-checksum-8 {
      tailf:ncs-device-type "netconf";
      tailf:display-when "not(../../ncs:module) or ../../ncs:module[ncs:name='Cisco-IOS-XR-infra-script-mgmt-act']";
      tailf:action script-add-type-source-checksum-8 {
        tailf:actionpoint ncsproxy {
          tailf:internal;
        }
        description
          "Add script to script repository.
           select script-type.
           source location of script to download.
           -http: <server>[;<vrf>]/full_path_to_repo
          ";
        input {
          uses ncs_rpc_notif_CHECKSUM-GROUP-8;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8>";
      }
    }
  }
  augment "/ncs:devices/ncs:device-group/ncs:ned-id/ncs:rpc" {
    container rpc-script-add-type-source-checksum-8 {
      tailf:ncs-device-type "netconf";
      tailf:display-when "/ncs:devices/ncs:device[ncs:name=current()/../../../ncs:member]/ncs:module[ncs:name='Cisco-IOS-XR-infra-script-mgmt-act']";
      tailf:action script-add-type-source-checksum-8 {
        tailf:actionpoint ncsproxy {
          tailf:internal;
        }
        description
          "Add script to script repository.
           select script-type.
           source location of script to download.
           -http: <server>[;<vrf>]/full_path_to_repo
          ";
        input {
          uses ncs_rpc_notif_CHECKSUM-GROUP-8;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7> <file-name-8> checksum <checksum-8>";
      }
    }
  }
  augment "/ncs:devices/ncs:device/ncs:rpc" {
    container rpc-script-add-type-source-checksum-7 {
      tailf:ncs-device-type "netconf";
      tailf:display-when "not(../../ncs:module) or ../../ncs:module[ncs:name='Cisco-IOS-XR-infra-script-mgmt-act']";
      tailf:action script-add-type-source-checksum-7 {
        tailf:actionpoint ncsproxy {
          tailf:internal;
        }
        description
          "Add script to script repository.
           select script-type.
           source location of script to download.
           -http: <server>[;<vrf>]/full_path_to_repo
          ";
        input {
          uses ncs_rpc_notif_CHECKSUM-GROUP-7;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7>";
      }
    }
  }
  augment "/ncs:devices/ncs:device-group/ncs:ned-id/ncs:rpc" {
    container rpc-script-add-type-source-checksum-7 {
      tailf:ncs-device-type "netconf";
      tailf:display-when "/ncs:devices/ncs:device[ncs:name=current()/../../../ncs:member]/ncs:module[ncs:name='Cisco-IOS-XR-infra-script-mgmt-act']";
      tailf:action script-add-type-source-checksum-7 {
        tailf:actionpoint ncsproxy {
          tailf:internal;
        }
        description
          "Add script to script repository.
           select script-type.
           source location of script to download.
           -http: <server>[;<vrf>]/full_path_to_repo
          ";
        input {
          uses ncs_rpc_notif_CHECKSUM-GROUP-7;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6> <file-name-7> checksum <checksum-7>";
      }
    }
  }
  augment "/ncs:devices/ncs:device/ncs:rpc" {
    container rpc-script-add-type-source-checksum-6 {
      tailf:ncs-device-type "netconf";
      tailf:display-when "not(../../ncs:module) or ../../ncs:module[ncs:name='Cisco-IOS-XR-infra-script-mgmt-act']";
      tailf:action script-add-type-source-checksum-6 {
        tailf:actionpoint ncsproxy {
          tailf:internal;
        }
        description
          "Add script to script repository.
           select script-type.
           source location of script to download.
           -http: <server>[;<vrf>]/full_path_to_repo
          ";
        input {
          uses ncs_rpc_notif_CHECKSUM-GROUP-6;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6>";
      }
    }
  }
  augment "/ncs:devices/ncs:device-group/ncs:ned-id/ncs:rpc" {
    container rpc-script-add-type-source-checksum-6 {
      tailf:ncs-device-type "netconf";
      tailf:display-when "/ncs:devices/ncs:device[ncs:name=current()/../../../ncs:member]/ncs:module[ncs:name='Cisco-IOS-XR-infra-script-mgmt-act']";
      tailf:action script-add-type-source-checksum-6 {
        tailf:actionpoint ncsproxy {
          tailf:internal;
        }
        description
          "Add script to script repository.
           select script-type.
           source location of script to download.
           -http: <server>[;<vrf>]/full_path_to_repo
          ";
        input {
          uses ncs_rpc_notif_CHECKSUM-GROUP-6;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5> <file-name-6> checksum <checksum-6>";
      }
    }
  }
  augment "/ncs:devices/ncs:device/ncs:rpc" {
    container rpc-script-add-type-source-checksum-5 {
      tailf:ncs-device-type "netconf";
      tailf:display-when "not(../../ncs:module) or ../../ncs:module[ncs:name='Cisco-IOS-XR-infra-script-mgmt-act']";
      tailf:action script-add-type-source-checksum-5 {
        tailf:actionpoint ncsproxy {
          tailf:internal;
        }
        description
          "Add script to script repository.
           select script-type.
           source location of script to download.
           -http: <server>[;<vrf>]/full_path_to_repo
          ";
        input {
          uses ncs_rpc_notif_CHECKSUM-GROUP-5;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5>";
      }
    }
  }
  augment "/ncs:devices/ncs:device-group/ncs:ned-id/ncs:rpc" {
    container rpc-script-add-type-source-checksum-5 {
      tailf:ncs-device-type "netconf";
      tailf:display-when "/ncs:devices/ncs:device[ncs:name=current()/../../../ncs:member]/ncs:module[ncs:name='Cisco-IOS-XR-infra-script-mgmt-act']";
      tailf:action script-add-type-source-checksum-5 {
        tailf:actionpoint ncsproxy {
          tailf:internal;
        }
        description
          "Add script to script repository.
           select script-type.
           source location of script to download.
           -http: <server>[;<vrf>]/full_path_to_repo
          ";
        input {
          uses ncs_rpc_notif_CHECKSUM-GROUP-5;
        }
        csc:xr-task "basic-services";
        csc:cli-command "script add <type> nooutput <source> <file-name-1> checksum <checksum-1> <file-name-2> checksum <checksum-2> <file-name-3> checksum <checksum-3> <file-name-4> checksum <checksum-4> <file-name-5> checksum <checksum-5>";
      }
    }
  }
  augment "/ncs:devices/ncs:device/ncs:rpc" {
    container rpc-script-add-type-source-checksum-4 {
      tailf:ncs-device-type "netconf";
      tailf:display-when "not(../../ncs:module) or ../../ncs:module[ncs:name='Cisco-IOS-XR-infra-script-mgmt-act']";
      tailf:action script-add-type-source-checksum-4 {
        tailf:actionpoint ncsproxy {
          tailf:internal;
        }
        description
          "Add script to script repository.
           select script-type.
           source location of script to download.
           -http: <server>[;<vrf>]/full_path_to_repo
          ";
        input {
          uses ncs_rpc_notif_CHECKSUM-GROUP-4;
        }
        csc:xr-task "basic-services";
        csc:cli-command "script add <type> nooutput <source> <file-name-1> checksum <checksum-1> <file-name-2> checksum <checksum-2> <file-name-3> checksum <checksum-3> <file-name-4> checksum <checksum-4>";
      }
    }
  }
  augment "/ncs:devices/ncs:device-group/ncs:ned-id/ncs:rpc" {
    container rpc-script-add-type-source-checksum-4 {
      tailf:ncs-device-type "netconf";
      tailf:display-when "/ncs:devices/ncs:device[ncs:name=current()/../../../ncs:member]/ncs:module[ncs:name='Cisco-IOS-XR-infra-script-mgmt-act']";
      tailf:action script-add-type-source-checksum-4 {
        tailf:actionpoint ncsproxy {
          tailf:internal;
        }
        description
          "Add script to script repository.
           select script-type.
           source location of script to download.
           -http: <server>[;<vrf>]/full_path_to_repo
          ";
        input {
          uses ncs_rpc_notif_CHECKSUM-GROUP-4;
        }
        csc:xr-task "basic-services";
        csc:cli-command "script add <type> nooutput <source> <file-name-1> checksum <checksum-1> <file-name-2> checksum <checksum-2> <file-name-3> checksum <checksum-3> <file-name-4> checksum <checksum-4>";
      }
    }
  }
  augment "/ncs:devices/ncs:device/ncs:rpc" {
    container rpc-script-add-type-source-checksum-3 {
      tailf:ncs-device-type "netconf";
      tailf:display-when "not(../../ncs:module) or ../../ncs:module[ncs:name='Cisco-IOS-XR-infra-script-mgmt-act']";
      tailf:action script-add-type-source-checksum-3 {
        tailf:actionpoint ncsproxy {
          tailf:internal;
        }
        description
          "Add script to script repository.
           select script-type.
           source location of script to download.
           -http: <server>[;<vrf>]/full_path_to_repo
          ";
        input {
          uses ncs_rpc_notif_CHECKSUM-GROUP-3;
        }
        csc:xr-task "basic-services";
        csc:cli-command "script add <type> nooutput <source> <file-name-1> checksum <checksum-1> <file-name-2> checksum <checksum-2> <file-name-3> checksum <checksum-3>";
      }
    }
  }
  augment "/ncs:devices/ncs:device-group/ncs:ned-id/ncs:rpc" {
    container rpc-script-add-type-source-checksum-3 {
      tailf:ncs-device-type "netconf";
      tailf:display-when "/ncs:devices/ncs:device[ncs:name=current()/../../../ncs:member]/ncs:module[ncs:name='Cisco-IOS-XR-infra-script-mgmt-act']";
      tailf:action script-add-type-source-checksum-3 {
        tailf:actionpoint ncsproxy {
          tailf:internal;
        }
        description
          "Add script to script repository.
           select script-type.
           source location of script to download.
           -http: <server>[;<vrf>]/full_path_to_repo
          ";
        input {
          uses ncs_rpc_notif_CHECKSUM-GROUP-3;
        }
        csc:xr-task "basic-services";
        csc:cli-command "script add <type> nooutput <source> <file-name-1> checksum <checksum-1> <file-name-2> checksum <checksum-2> <file-name-3> checksum <checksum-3>";
      }
    }
  }
  augment "/ncs:devices/ncs:device/ncs:rpc" {
    container rpc-script-add-type-source-checksum-2 {
      tailf:ncs-device-type "netconf";
      tailf:display-when "not(../../ncs:module) or ../../ncs:module[ncs:name='Cisco-IOS-XR-infra-script-mgmt-act']";
      tailf:action script-add-type-source-checksum-2 {
        tailf:actionpoint ncsproxy {
          tailf:internal;
        }
        description
          "Add script to script repository.
           select script-type.
           source location of script to download.
           -http: <server>[;<vrf>]/full_path_to_repo
          ";
        input {
          uses ncs_rpc_notif_CHECKSUM-GROUP-2;
        }
        csc:xr-task "basic-services";
        csc:cli-command "script add <type> nooutput <source> <file-name-1> checksum <checksum-1> <file-name-2> checksum <checksum-2>";
      }
    }
  }
  augment "/ncs:devices/ncs:device-group/ncs:ned-id/ncs:rpc" {
    container rpc-script-add-type-source-checksum-2 {
      tailf:ncs-device-type "netconf";
      tailf:display-when "/ncs:devices/ncs:device[ncs:name=current()/../../../ncs:member]/ncs:module[ncs:name='Cisco-IOS-XR-infra-script-mgmt-act']";
      tailf:action script-add-type-source-checksum-2 {
        tailf:actionpoint ncsproxy {
          tailf:internal;
        }
        description
          "Add script to script repository.
           select script-type.
           source location of script to download.
           -http: <server>[;<vrf>]/full_path_to_repo
          ";
        input {
          uses ncs_rpc_notif_CHECKSUM-GROUP-2;
        }
        csc:xr-task "basic-services";
        csc:cli-command "script add <type> nooutput <source> <file-name-1> checksum <checksum-1> <file-name-2> checksum <checksum-2>";
      }
    }
  }
  augment "/ncs:devices/ncs:device/ncs:rpc" {
    container rpc-script-add-type-source-checksum {
      tailf:ncs-device-type "netconf";
      tailf:display-when "not(../../ncs:module) or ../../ncs:module[ncs:name='Cisco-IOS-XR-infra-script-mgmt-act']";
      tailf:action script-add-type-source-checksum {
        tailf:actionpoint ncsproxy {
          tailf:internal;
        }
        description
          "Add script to script repository.
           select script-type.
           source location of script to download.
           -http: <server>[;<vrf>]/full_path_to_repo
          ";
        input {
          uses ncs_rpc_notif_CHECKSUM-GROUP;
        }
        csc:xr-task "basic-services";
        csc:cli-command "script add <type> nooutput <source> <file-name-1> checksum <checksum-1>";
      }
    }
  }
  augment "/ncs:devices/ncs:device-group/ncs:ned-id/ncs:rpc" {
    container rpc-script-add-type-source-checksum {
      tailf:ncs-device-type "netconf";
      tailf:display-when "/ncs:devices/ncs:device[ncs:name=current()/../../../ncs:member]/ncs:module[ncs:name='Cisco-IOS-XR-infra-script-mgmt-act']";
      tailf:action script-add-type-source-checksum {
        tailf:actionpoint ncsproxy {
          tailf:internal;
        }
        description
          "Add script to script repository.
           select script-type.
           source location of script to download.
           -http: <server>[;<vrf>]/full_path_to_repo
          ";
        input {
          uses ncs_rpc_notif_CHECKSUM-GROUP;
        }
        csc:xr-task "basic-services";
        csc:cli-command "script add <type> nooutput <source> <file-name-1> checksum <checksum-1>";
      }
    }
  }
  augment "/ncs:devices/ncs:device/ncs:rpc" {
    container rpc-script-add-type-source {
      tailf:ncs-device-type "netconf";
      tailf:display-when "not(../../ncs:module) or ../../ncs:module[ncs:name='Cisco-IOS-XR-infra-script-mgmt-act']";
      tailf:action script-add-type-source {
        tailf:actionpoint ncsproxy {
          tailf:internal;
        }
        description
          "Add script to script repository.
           select script-type.
           source location of script to download.
           -file: must be a subdirectory of '/harddisk:/'
           -http: <server>[;<vrf>]/full_path_to_repo
          ";
        input {
          leaf type {
            type string {
              length "1..512";
            }
            mandatory true;
            description
              "<exec, eem, config, process>";
          }
          leaf source {
            type string {
              length "1..512";
            }
            mandatory true;
            description
              "http:<server>[;<vrf>]/full_path_to_repo";
          }
          uses ncs_rpc_notif_FILE-NAME-LIST;
        }
        csc:xr-task "basic-services";
        csc:cli-command "script add <type> nooutput <source> <file-name-1> <file-name-2> <file-name-3> <file-name-4> <file-name-5> <file-name-6> <file-name-7> <file-name-8> <file-name-9> <file-name-10>";
      }
    }
  }
  augment "/ncs:devices/ncs:device-group/ncs:ned-id/ncs:rpc" {
    container rpc-script-add-type-source {
      tailf:ncs-device-type "netconf";
      tailf:display-when "/ncs:devices/ncs:device[ncs:name=current()/../../../ncs:member]/ncs:module[ncs:name='Cisco-IOS-XR-infra-script-mgmt-act']";
      tailf:action script-add-type-source {
        tailf:actionpoint ncsproxy {
          tailf:internal;
        }
        description
          "Add script to script repository.
           select script-type.
           source location of script to download.
           -file: must be a subdirectory of '/harddisk:/'
           -http: <server>[;<vrf>]/full_path_to_repo
          ";
        input {
          leaf type {
            type string {
              length "1..512";
            }
            mandatory true;
            description
              "<exec, eem, config, process>";
          }
          leaf source {
            type string {
              length "1..512";
            }
            mandatory true;
            description
              "http:<server>[;<vrf>]/full_path_to_repo";
          }
          uses ncs_rpc_notif_FILE-NAME-LIST;
        }
        csc:xr-task "basic-services";
        csc:cli-command "script add <type> nooutput <source> <file-name-1> <file-name-2> <file-name-3> <file-name-4> <file-name-5> <file-name-6> <file-name-7> <file-name-8> <file-name-9> <file-name-10>";
      }
    }
  }
}

submodule Cisco-IOS-XR-fpmgr-oper-sub1 {
  // Generated by yanger -t ncs
  tailf:mount-id "cisco-iosxr-nc-7.3:cisco-iosxr-nc-7.3";

  belongs-to Cisco-IOS-XR-fpmgr-oper {
    prefix Cisco-IOS-XR-fpmgr-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR fpmgr package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_FP-SHOW-DEFAULT-PROFILE {
    description
      "fp show default profile";
    leaf fault-tag {
      type string;
      description
        "fault tag";
    }
    leaf sas-severity {
      type string;
      description
        "default SAS Severity";
    }
    leaf nsas-severity {
      type string;
      description
        "default NSAS Severity ";
    }
  }

  grouping ncs_template_FP-SHOW-DEFAULT-PROFILE-LIST {
    description
      "fp show default profile";
    list fault-tag {
      // NCS patched for predictable order
      ordered-by user;
      description
        "default profile list";
      uses ncs_template_FP-SHOW-DEFAULT-PROFILE;
    }
  }

  grouping ncs_template_FP-SHOW-FP-FAULT-TAG {
    description
      "fp show fault tag";
    leaf fault-tag {
      type string;
      description
        "fault tag";
    }
  }

  grouping ncs_template_FP-SHOW-FP-FAULT-TAG-LIST {
    description
      "fp show fault tags";
    list fault-tag {
      // NCS patched for predictable order
      ordered-by user;
      description
        "fault tag list";
      uses ncs_template_FP-SHOW-FP-FAULT-TAG;
    }
  }

  grouping ncs_template_FP-SHOW-FP-DETAIL-DATA {
    description
      "fp show fault profile detail data";
    leaf profile-id {
      type string;
      description
        "fault profile id";
    }
    leaf profile-name {
      type string;
      description
        "profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type string;
      description
        "number of entities";
    }
  }

  grouping ncs_template_FP-SHOW-FP-DETAIL {
    description
      "fp show fault profile detail info ";
    list detail-info {
      // NCS patched for predictable order
      ordered-by user;
      description
        "fault profile detail info";
      uses ncs_template_FP-SHOW-FP-DETAIL-DATA;
    }
  }

  grouping ncs_template_FP-SHOW-FP-STATISTIC-DATA {
    description
      "fp show fault profile statistic data";
    leaf profile-id {
      type string;
      description
        "fault profile id";
    }
    leaf root-entity {
      type string;
      description
        "root entity name";
    }
    leaf entity-count {
      type string;
      description
        "number of entities";
    }
  }

  grouping ncs_template_FP-SHOW-FP-LOCATION-NAME {
    description
      "fp show line card location name string";
    leaf location-name {
      type string;
      description
        "line card name";
    }
  }

  grouping ncs_template_FP-SHOW-FP-LOCATION-NAME-LIST {
    description
      "fp show line card location name string list";
    list location-name {
      // NCS patched for predictable order
      ordered-by user;
      description
        "line card name list";
      uses ncs_template_FP-SHOW-FP-LOCATION-NAME;
    }
  }

  grouping ncs_template_FP-SHOW-FP-INTERNAL-DATA {
    description
      "fp show fault profile internal data";
    leaf profile-id {
      type string;
      description
        "fault profile id";
    }
    leaf profile-name-xr {
      type string;
      description
        "fault profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type string;
      description
        "number of entities";
    }
    leaf subsystem {
      type string;
      description
        "sub system";
    }
  }

  grouping ncs_template_FP-SHOW-FP-BRIEF-DATA {
    description
      "fp show fault profile brief data";
    leaf profile-id {
      type string;
      description
        "fault prfoile id";
    }
    leaf profile-name {
      type string;
      description
        "fault profile name";
    }
    leaf description {
      type string;
      description
        "fault profile description";
    }
  }

  grouping ncs_template_FP-SHOW-FP-BRIEF {
    description
      "fp show fault profile brief info";
    list brief-info {
      // NCS patched for predictable order
      ordered-by user;
      description
        "fault profile brief info";
      uses ncs_template_FP-SHOW-FP-BRIEF-DATA;
    }
  }

  grouping ncs_rpc_notif_FP-SHOW-DEFAULT-PROFILE {
    description
      "fp show default profile";
    leaf fault-tag {
      type string;
      description
        "fault tag";
    }
    leaf sas-severity {
      type string;
      description
        "default SAS Severity";
    }
    leaf nsas-severity {
      type string;
      description
        "default NSAS Severity ";
    }
  }

  grouping ncs_rpc_notif_FP-SHOW-DEFAULT-PROFILE-LIST {
    description
      "fp show default profile";
    list fault-tag {
      description
        "default profile list";
      uses ncs_rpc_notif_FP-SHOW-DEFAULT-PROFILE;
    }
  }

  grouping ncs_rpc_notif_FP-SHOW-FP-FAULT-TAG {
    description
      "fp show fault tag";
    leaf fault-tag {
      type string;
      description
        "fault tag";
    }
  }

  grouping ncs_rpc_notif_FP-SHOW-FP-FAULT-TAG-LIST {
    description
      "fp show fault tags";
    list fault-tag {
      description
        "fault tag list";
      uses ncs_rpc_notif_FP-SHOW-FP-FAULT-TAG;
    }
  }

  grouping ncs_rpc_notif_FP-SHOW-FP-DETAIL-DATA {
    description
      "fp show fault profile detail data";
    leaf profile-id {
      type int32;
      description
        "fault profile id";
    }
    leaf profile-name {
      type string;
      description
        "profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
  }

  grouping ncs_rpc_notif_FP-SHOW-FP-DETAIL {
    description
      "fp show fault profile detail info ";
    list detail-info {
      description
        "fault profile detail info";
      uses ncs_rpc_notif_FP-SHOW-FP-DETAIL-DATA;
    }
  }

  grouping ncs_rpc_notif_FP-SHOW-FP-STATISTIC-DATA {
    description
      "fp show fault profile statistic data";
    leaf profile-id {
      type int32;
      description
        "fault profile id";
    }
    leaf root-entity {
      type string;
      description
        "root entity name";
    }
    leaf entity-count {
      type int32;
      description
        "number of entities";
    }
  }

  grouping ncs_rpc_notif_FP-SHOW-FP-LOCATION-NAME {
    description
      "fp show line card location name string";
    leaf location-name {
      type string;
      description
        "line card name";
    }
  }

  grouping ncs_rpc_notif_FP-SHOW-FP-LOCATION-NAME-LIST {
    description
      "fp show line card location name string list";
    list location-name {
      description
        "line card name list";
      uses ncs_rpc_notif_FP-SHOW-FP-LOCATION-NAME;
    }
  }

  grouping ncs_rpc_notif_FP-SHOW-FP-INTERNAL-DATA {
    description
      "fp show fault profile internal data";
    leaf profile-id {
      type int32;
      description
        "fault profile id";
    }
    leaf profile-name-xr {
      type string;
      description
        "fault profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
    leaf subsystem {
      type string;
      description
        "sub system";
    }
  }

  grouping ncs_rpc_notif_FP-SHOW-FP-BRIEF-DATA {
    description
      "fp show fault profile brief data";
    leaf profile-id {
      type int32;
      description
        "fault prfoile id";
    }
    leaf profile-name {
      type string;
      description
        "fault profile name";
    }
    leaf description {
      type string;
      description
        "fault profile description";
    }
  }

  grouping ncs_rpc_notif_FP-SHOW-FP-BRIEF {
    description
      "fp show fault profile brief info";
    list brief-info {
      description
        "fault profile brief info";
      uses ncs_rpc_notif_FP-SHOW-FP-BRIEF-DATA;
    }
  }

  grouping live_ncs_FP-SHOW-DEFAULT-PROFILE {
    description
      "fp show default profile";
    leaf fault-tag {
      type string;
      description
        "fault tag";
    }
    leaf sas-severity {
      type string;
      description
        "default SAS Severity";
    }
    leaf nsas-severity {
      type string;
      description
        "default NSAS Severity ";
    }
  }

  grouping live_ncs_FP-SHOW-DEFAULT-PROFILE-LIST {
    description
      "fp show default profile";
    list fault-tag {
      description
        "default profile list";
      uses live_ncs_FP-SHOW-DEFAULT-PROFILE;
    }
  }

  grouping live_ncs_FP-SHOW-FP-FAULT-TAG {
    description
      "fp show fault tag";
    leaf fault-tag {
      type string;
      description
        "fault tag";
    }
  }

  grouping live_ncs_FP-SHOW-FP-FAULT-TAG-LIST {
    description
      "fp show fault tags";
    list fault-tag {
      description
        "fault tag list";
      uses live_ncs_FP-SHOW-FP-FAULT-TAG;
    }
  }

  grouping live_ncs_FP-SHOW-FP-DETAIL-DATA {
    description
      "fp show fault profile detail data";
    leaf profile-id {
      type int32;
      description
        "fault profile id";
    }
    leaf profile-name {
      type string;
      description
        "profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
  }

  grouping live_ncs_FP-SHOW-FP-DETAIL {
    description
      "fp show fault profile detail info ";
    list detail-info {
      description
        "fault profile detail info";
      uses live_ncs_FP-SHOW-FP-DETAIL-DATA;
    }
  }

  grouping live_ncs_FP-SHOW-FP-STATISTIC-DATA {
    description
      "fp show fault profile statistic data";
    leaf profile-id {
      type int32;
      description
        "fault profile id";
    }
    leaf root-entity {
      type string;
      description
        "root entity name";
    }
    leaf entity-count {
      type int32;
      description
        "number of entities";
    }
  }

  grouping live_ncs_FP-SHOW-FP-LOCATION-NAME {
    description
      "fp show line card location name string";
    leaf location-name {
      type string;
      description
        "line card name";
    }
  }

  grouping live_ncs_FP-SHOW-FP-LOCATION-NAME-LIST {
    description
      "fp show line card location name string list";
    list location-name {
      description
        "line card name list";
      uses live_ncs_FP-SHOW-FP-LOCATION-NAME;
    }
  }

  grouping live_ncs_FP-SHOW-FP-INTERNAL-DATA {
    description
      "fp show fault profile internal data";
    leaf profile-id {
      type int32;
      description
        "fault profile id";
    }
    leaf profile-name-xr {
      type string;
      description
        "fault profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
    leaf subsystem {
      type string;
      description
        "sub system";
    }
  }

  grouping live_ncs_FP-SHOW-FP-BRIEF-DATA {
    description
      "fp show fault profile brief data";
    leaf profile-id {
      type int32;
      description
        "fault prfoile id";
    }
    leaf profile-name {
      type string;
      description
        "fault profile name";
    }
    leaf description {
      type string;
      description
        "fault profile description";
    }
  }

  grouping live_ncs_FP-SHOW-FP-BRIEF {
    description
      "fp show fault profile brief info";
    list brief-info {
      description
        "fault profile brief info";
      uses live_ncs_FP-SHOW-FP-BRIEF-DATA;
    }
  }

  grouping FP-SHOW-DEFAULT-PROFILE {
    description
      "fp show default profile";
    leaf fault-tag {
      type string;
      description
        "fault tag";
    }
    leaf sas-severity {
      type string;
      description
        "default SAS Severity";
    }
    leaf nsas-severity {
      type string;
      description
        "default NSAS Severity ";
    }
  }

  grouping FP-SHOW-DEFAULT-PROFILE-LIST {
    description
      "fp show default profile";
    list fault-tag {
      description
        "default profile list";
      uses FP-SHOW-DEFAULT-PROFILE;
    }
  }

  grouping FP-SHOW-FP-FAULT-TAG {
    description
      "fp show fault tag";
    leaf fault-tag {
      type string;
      description
        "fault tag";
    }
  }

  grouping FP-SHOW-FP-FAULT-TAG-LIST {
    description
      "fp show fault tags";
    list fault-tag {
      description
        "fault tag list";
      uses FP-SHOW-FP-FAULT-TAG;
    }
  }

  grouping FP-SHOW-FP-DETAIL-DATA {
    description
      "fp show fault profile detail data";
    leaf profile-id {
      type int32;
      description
        "fault profile id";
    }
    leaf profile-name {
      type string;
      description
        "profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
  }

  grouping FP-SHOW-FP-DETAIL {
    description
      "fp show fault profile detail info ";
    list detail-info {
      description
        "fault profile detail info";
      uses FP-SHOW-FP-DETAIL-DATA;
    }
  }

  grouping FP-SHOW-FP-STATISTIC-DATA {
    description
      "fp show fault profile statistic data";
    leaf profile-id {
      type int32;
      description
        "fault profile id";
    }
    leaf root-entity {
      type string;
      description
        "root entity name";
    }
    leaf entity-count {
      type int32;
      description
        "number of entities";
    }
  }

  grouping FP-SHOW-FP-LOCATION-NAME {
    description
      "fp show line card location name string";
    leaf location-name {
      type string;
      description
        "line card name";
    }
  }

  grouping FP-SHOW-FP-LOCATION-NAME-LIST {
    description
      "fp show line card location name string list";
    list location-name {
      description
        "line card name list";
      uses FP-SHOW-FP-LOCATION-NAME;
    }
  }

  grouping FP-SHOW-FP-INTERNAL-DATA {
    description
      "fp show fault profile internal data";
    leaf profile-id {
      type int32;
      description
        "fault profile id";
    }
    leaf profile-name-xr {
      type string;
      description
        "fault profile name";
    }
    leaf profile-type {
      type string;
      description
        "profile type";
    }
    leaf location {
      type string;
      description
        "location name";
    }
    leaf status {
      type string;
      description
        "fault profile status";
    }
    leaf root-entity {
      type string;
      description
        "root entity name";
    }
    leaf entity-count {
      type int32;
      description
        "number of entities";
    }
    leaf subsystem {
      type string;
      description
        "sub system";
    }
  }

  grouping FP-SHOW-FP-BRIEF-DATA {
    description
      "fp show fault profile brief data";
    leaf profile-id {
      type int32;
      description
        "fault prfoile id";
    }
    leaf profile-name {
      type string;
      description
        "fault profile name";
    }
    leaf description {
      type string;
      description
        "fault profile description";
    }
  }

  grouping FP-SHOW-FP-BRIEF {
    description
      "fp show fault profile brief info";
    list brief-info {
      description
        "fault profile brief info";
      uses FP-SHOW-FP-BRIEF-DATA;
    }
  }
}

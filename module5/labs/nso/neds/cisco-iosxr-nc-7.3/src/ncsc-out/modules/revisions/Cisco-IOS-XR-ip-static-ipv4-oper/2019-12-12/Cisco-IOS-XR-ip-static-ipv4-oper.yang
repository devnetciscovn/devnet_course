module Cisco-IOS-XR-ip-static-ipv4-oper {
  // Generated by yanger -t ncs
  tailf:mount-id "cisco-iosxr-nc-7.3:cisco-iosxr-nc-7.3";
  tailf:ncs-device-type "netconf";

  namespace "http://cisco.com/ns/yang/Cisco-IOS-XR-ip-static-ipv4-oper";
  prefix ip-static-ipv4-oper;

  import Cisco-IOS-XR-types {
    prefix xr;
  }
  import cisco-semver {
    prefix semver;
  }
  include Cisco-IOS-XR-ip-static-ipv4-oper-sub1 {
    revision-date 2019-12-12;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-static-ipv4 package operational data.

     This module contains definitions
     for the following management objects:
       ipv4-local: Local Routing Information
       ipv4-static: Static Routing Information
       ipv4-connected: Connected Routing Information

     Copyright (c) 2013-2019 by Cisco Systems, Inc.
     All rights reserved.";

  revision 2019-12-12 {
    description
      "Added leaf node for FlexAlgo for srv6";
    semver:module-version "1.1.0";
  }
  revision 2019-06-01 {
    description
      "Added oper ipv4 support for fridb, colocation, sr-policy
       2019-05-13
       Added ipv4 support for bfd sessions, object track database and segment routing";
    semver:module-version "1.1.0";
  }
  revision 2019-04-05 {
    description
      "Establish semantic version baseline.";
    semver:module-version "1.0.0";
  }
  revision 2019-01-03 {
    description
      "Added oper ipv4 support";
  }
  revision 2015-11-09 {
    description
      "IOS XR 6.0 revision.";
  }

  typedef ncs_template_Safi {
    type string;
    description
      "Safi";
  }

  typedef ncs_template_Afi {
    type string;
    description
      "Afi";
  }

  typedef ncs_template_Ipv4friafi {
    type string;
    description
      "Ipv4friafi";
  }

  typedef ncs_template_Ipv4frisafi {
    type string;
    description
      "Ipv4frisafi";
  }

  typedef ncs_rpc_notif_Safi {
    type enumeration {
      enum "unicast" {
        value 1;
        description
          "unicast type";
      }
      enum "multicast" {
        value 2;
        description
          "multicast type";
      }
    }
    description
      "Safi";
  }

  typedef ncs_rpc_notif_Afi {
    type enumeration {
      enum "ipv4" {
        value 1;
        description
          "ipv4 addressfamily";
      }
      enum "ipv6" {
        value 2;
        description
          "ipv6 addressfamily";
      }
    }
    description
      "Afi";
  }

  typedef ncs_rpc_notif_Ipv4friafi {
    type enumeration {
      enum "ipv4" {
        value 1;
        description
          "ipv4 addressfamily";
      }
      enum "ipv6" {
        value 2;
        description
          "ipv6 addressfamily";
      }
    }
    description
      "Ipv4friafi";
  }

  typedef ncs_rpc_notif_Ipv4frisafi {
    type enumeration {
      enum "unicast" {
        value 1;
        description
          "unicast type";
      }
      enum "multicast" {
        value 2;
        description
          "multicast type";
      }
    }
    description
      "Ipv4frisafi";
  }

  typedef live_ncs_Safi {
    type enumeration {
      enum "unicast" {
        value 1;
        description
          "unicast type";
      }
      enum "multicast" {
        value 2;
        description
          "multicast type";
      }
    }
    description
      "Safi";
  }

  typedef live_ncs_Afi {
    type enumeration {
      enum "ipv4" {
        value 1;
        description
          "ipv4 addressfamily";
      }
      enum "ipv6" {
        value 2;
        description
          "ipv6 addressfamily";
      }
    }
    description
      "Afi";
  }

  typedef live_ncs_Ipv4friafi {
    type enumeration {
      enum "ipv4" {
        value 1;
        description
          "ipv4 addressfamily";
      }
      enum "ipv6" {
        value 2;
        description
          "ipv6 addressfamily";
      }
    }
    description
      "Ipv4friafi";
  }

  typedef live_ncs_Ipv4frisafi {
    type enumeration {
      enum "unicast" {
        value 1;
        description
          "unicast type";
      }
      enum "multicast" {
        value 2;
        description
          "multicast type";
      }
    }
    description
      "Ipv4frisafi";
  }

  typedef Safi {
    type enumeration {
      enum "unicast" {
        value 1;
        description
          "unicast type";
      }
      enum "multicast" {
        value 2;
        description
          "multicast type";
      }
    }
    description
      "Safi";
  }

  typedef Afi {
    type enumeration {
      enum "ipv4" {
        value 1;
        description
          "ipv4 addressfamily";
      }
      enum "ipv6" {
        value 2;
        description
          "ipv6 addressfamily";
      }
    }
    description
      "Afi";
  }

  typedef Ipv4friafi {
    type enumeration {
      enum "ipv4" {
        value 1;
        description
          "ipv4 addressfamily";
      }
      enum "ipv6" {
        value 2;
        description
          "ipv6 addressfamily";
      }
    }
    description
      "Ipv4friafi";
  }

  typedef Ipv4frisafi {
    type enumeration {
      enum "unicast" {
        value 1;
        description
          "unicast type";
      }
      enum "multicast" {
        value 2;
        description
          "multicast type";
      }
    }
    description
      "Ipv4frisafi";
  }

  grouping ncs_template_TOPO-VRF-TABLE {
    description
      "Common node of ipv4-static, ipv4-local,
       ipv4-connected";
    container topo-vrfs {
      description
        "vrf list for Topology";
      list topo-vrf {
        // NCS patched for predictable order
        ordered-by user;
        key "vrf-name";
        description
          "vrf name";
        leaf vrf-name {
          type xr:ncs_template_Cisco-ios-xr-string;
          description
            "The name of thei vrf";
        }
        list topo-table {
          // NCS patched for predictable order
          ordered-by user;
          key "table-name";
          description
            "Topology table name";
          leaf table-name {
            type xr:ncs_template_Cisco-ios-xr-string;
            description
              "The name of the atble";
          }
          list topo-afi {
            // NCS patched for predictable order
            ordered-by user;
            key "afi";
            description
              "Topology address family type";
            leaf afi {
              type ncs_template_Afi;
              description
                "IPv4 AFI";
            }
            list topo-safi {
              // NCS patched for predictable order
              ordered-by user;
              key "safi";
              description
                "Topology SAFI type";
              container destinations {
                description
                  "route info";
                list destination {
                  // NCS patched for predictable order
                  ordered-by user;
                  description
                    "Destinatioin address and prefix length";
                  leaf prefix {
                    type xr:ncs_template_Cisco-ios-xr-string;
                    description
                      "detaination address prefix";
                  }
                  leaf prefix-length {
                    type xr:ncs_template_Hex-integer;
                    description
                      "detaination prefix length";
                  }
                  uses ncs_template_IPV4-STATIC-ROUTE-BD;
                }
              }
              leaf safi {
                type ncs_template_Safi;
                description
                  "IPv4 SAFI";
              }
            }
          }
        }
      }
    }
  }

  grouping ncs_template_NHVRF-TABLE {
    description
      "Common node of ipv4-static, ipv4-local,
       ipv4-connected";
    container nhvrfs {
      description
        "next-hop's vrf list";
      list nhvrf {
        // NCS patched for predictable order
        ordered-by user;
        key "vrf-name";
        description
          "vrf name";
        leaf vrf-name {
          type xr:ncs_template_Cisco-ios-xr-string;
          description
            "The name of thei vrf";
        }
        list nh-table {
          // NCS patched for predictable order
          ordered-by user;
          key "table-name";
          description
            "next-hop table name";
          leaf table-name {
            type xr:ncs_template_Cisco-ios-xr-string;
            description
              "The name of the atble";
          }
          list nhafi {
            // NCS patched for predictable order
            ordered-by user;
            key "afi";
            description
              "next-hop address family type";
            leaf afi {
              type ncs_template_Afi;
              description
                "IPv4 AFI";
            }
            list nhsafi {
              // NCS patched for predictable order
              ordered-by user;
              key "safi";
              description
                "next-hop safi(unicat|multicast) type";
              container nh-addresses {
                description
                  "next hop Database";
                list nh-address {
                  // NCS patched for predictable order
                  ordered-by user;
                  key "next-hop-addr";
                  description
                    "next-hop address to display";
                  leaf next-hop-addr {
                    type xr:ncs_template_Cisco-ios-xr-string;
                    description
                      "next hop address";
                  }
                  uses ncs_template_IPV4-STATIC-NHDB-BD;
                }
              }
              leaf safi {
                type ncs_template_Safi;
                description
                  "IPv4 SAFI";
              }
            }
          }
        }
      }
    }
  }

  grouping ncs_template_TABLE {
    description
      "Common node of ipv4-static, ipv4-local,
       ipv4-connected";
    container table-ids {
      description
        "list of Tables";
      list table-id {
        // NCS patched for predictable order
        ordered-by user;
        key "table-id";
        description
          "Table ID to display";
        leaf table-id {
          type xr:ncs_template_Hex-integer;
          description
            "Table ID";
        }
        uses ncs_template_IP-STATIC-TDB-BD;
      }
    }
  }

  grouping ncs_template_BFDVRF-TABLE {
    description
      "Common node of ipv4-static, ipv4-local,
       ipv4-connected";
    container bfdvrfs {
      description
        "BFD's vrf list";
      list bfdvrf {
        // NCS patched for predictable order
        ordered-by user;
        key "vrf-name";
        description
          "vrf name";
        leaf vrf-name {
          type xr:ncs_template_Cisco-ios-xr-string;
          description
            "The name of the vrf";
        }
        list bfd-table {
          // NCS patched for predictable order
          ordered-by user;
          key "table-name";
          description
            "BFD table name";
          leaf table-name {
            type xr:ncs_template_Cisco-ios-xr-string;
            description
              "The name of the table";
          }
          list bfdafi {
            // NCS patched for predictable order
            ordered-by user;
            key "afi";
            description
              "BFD address family type";
            leaf afi {
              type ncs_template_Afi;
              description
                "IPv4 AFI";
            }
            list bfdsafi {
              // NCS patched for predictable order
              ordered-by user;
              key "safi";
              description
                "BFD safi(unicat|multicast) type";
              container bfd-addresses {
                description
                  "list of BFD sessions";
                list bfd-address {
                  // NCS patched for predictable order
                  ordered-by user;
                  key "bfd-next-hop-addr";
                  description
                    "BFD next-hop address to display";
                  leaf bfd-next-hop-addr {
                    type xr:ncs_template_Cisco-ios-xr-string;
                    description
                      "BFD next hop address";
                  }
                  uses ncs_template_IPV4-STATIC-NHDB-BFD-BD;
                }
              }
              leaf safi {
                type ncs_template_Safi;
                description
                  "IPv4 SAFI";
              }
            }
          }
        }
      }
    }
  }

  grouping ncs_template_IPV4-IF-DB {
    description
      "Common node of ipv4-static, ipv4-local,
       ipv4-connected";
    container ipv4vrfs {
      description
        "ipv4 interface database";
      list ipv4vrf {
        // NCS patched for predictable order
        ordered-by user;
        key "vrf-name";
        description
          "vrf name";
        leaf vrf-name {
          type xr:ncs_template_Cisco-ios-xr-string;
          description
            "The name of the";
        }
        list ipv4-table {
          // NCS patched for predictable order
          ordered-by user;
          key "table-name";
          description
            "table name";
          leaf table-name {
            type xr:ncs_template_Cisco-ios-xr-string;
            description
              "The name of the atble";
          }
          list ipv4afi {
            // NCS patched for predictable order
            ordered-by user;
            key "afi";
            description
              "address family type";
            leaf afi {
              type ncs_template_Afi;
              description
                "IPv4 AFI";
            }
            list ipv4safi {
              // NCS patched for predictable order
              ordered-by user;
              key "safi";
              description
                "unicast|multicast";
              leaf safi {
                type ncs_template_Safi;
                description
                  "IPv4 SAFI";
              }
              list ipv4-interface {
                // NCS patched for predictable order
                ordered-by user;
                key "interface-name";
                description
                  "Interface to display";
                leaf interface-name {
                  type xr:ncs_template_Interface-name;
                  description
                    "Interface name";
                }
                uses ncs_template_IPV4-STATIC-IDB-BD;
              }
            }
          }
        }
      }
    }
  }

  grouping ncs_template_TABLE-EVENTS {
    description
      "Common node of ipv4-static, ipv4-local,
       ipv4-connected";
    container table-events-ids {
      description
        "list of Tables";
      list table-events-id {
        // NCS patched for predictable order
        ordered-by user;
        key "table-id";
        description
          "Table ID to display events info";
        leaf table-id {
          type xr:ncs_template_Hex-integer;
          description
            "Table ID";
        }
        uses ncs_template_EVT-HIST-INFO;
      }
    }
  }

  grouping ncs_template_IPV4FRIDB {
    description
      "Common node of ipv4-local, ipv4-connected";
    container ipv4fridbvrfs {
      description
        "ipv4 forward database";
      list ipv4fridbvrf {
        // NCS patched for predictable order
        ordered-by user;
        key "vrf-name";
        description
          "vrf name";
        leaf vrf-name {
          type xr:ncs_template_Cisco-ios-xr-string;
          description
            "Forward DB vrf name";
        }
        list ipv4fridb-table {
          // NCS patched for predictable order
          ordered-by user;
          key "table-name";
          description
            "table name";
          leaf table-name {
            type xr:ncs_template_Cisco-ios-xr-string;
            description
              "The name of the forward DB table";
          }
          list ipv4fridbafi {
            // NCS patched for predictable order
            ordered-by user;
            key "afitype";
            description
              "address family type";
            leaf afitype {
              type ncs_template_Ipv4friafi;
              description
                "IPv4 AFI";
            }
            list ipv4fridbsafi {
              // NCS patched for predictable order
              ordered-by user;
              key "safitype";
              description
                "unicast|multicast";
              leaf safitype {
                type ncs_template_Ipv4frisafi;
                description
                  "IPv4 SAFI";
              }
              list ipv4fridb-interface {
                // NCS patched for predictable order
                ordered-by user;
                key "interface-name";
                description
                  "forward DB Interface to display";
                leaf interface-name {
                  type xr:ncs_template_Interface-name;
                  description
                    "forward DB Interface name";
                }
                uses ncs_template_IP-STATIC-FRIDB-BD;
              }
            }
          }
        }
      }
    }
  }

  grouping ncs_rpc_notif_TOPO-VRF-TABLE {
    description
      "Common node of ipv4-static, ipv4-local,
       ipv4-connected";
    container topo-vrfs {
      description
        "vrf list for Topology";
      list topo-vrf {
        key "vrf-name";
        description
          "vrf name";
        leaf vrf-name {
          type xr:ncs_rpc_notif_Cisco-ios-xr-string;
          description
            "The name of thei vrf";
        }
        list topo-table {
          key "table-name";
          description
            "Topology table name";
          leaf table-name {
            type xr:ncs_rpc_notif_Cisco-ios-xr-string;
            description
              "The name of the atble";
          }
          list topo-afi {
            key "afi";
            description
              "Topology address family type";
            leaf afi {
              type ncs_rpc_notif_Afi;
              description
                "IPv4 AFI";
            }
            list topo-safi {
              key "safi";
              description
                "Topology SAFI type";
              container destinations {
                description
                  "route info";
                list destination {
                  description
                    "Destinatioin address and prefix length";
                  leaf prefix {
                    type xr:ncs_rpc_notif_Cisco-ios-xr-string;
                    description
                      "detaination address prefix";
                  }
                  leaf prefix-length {
                    type xr:ncs_rpc_notif_Hex-integer;
                    description
                      "detaination prefix length";
                  }
                  uses ncs_rpc_notif_IPV4-STATIC-ROUTE-BD;
                }
              }
              leaf safi {
                type ncs_rpc_notif_Safi;
                description
                  "IPv4 SAFI";
              }
            }
          }
        }
      }
    }
  }

  grouping ncs_rpc_notif_NHVRF-TABLE {
    description
      "Common node of ipv4-static, ipv4-local,
       ipv4-connected";
    container nhvrfs {
      description
        "next-hop's vrf list";
      list nhvrf {
        key "vrf-name";
        description
          "vrf name";
        leaf vrf-name {
          type xr:ncs_rpc_notif_Cisco-ios-xr-string;
          description
            "The name of thei vrf";
        }
        list nh-table {
          key "table-name";
          description
            "next-hop table name";
          leaf table-name {
            type xr:ncs_rpc_notif_Cisco-ios-xr-string;
            description
              "The name of the atble";
          }
          list nhafi {
            key "afi";
            description
              "next-hop address family type";
            leaf afi {
              type ncs_rpc_notif_Afi;
              description
                "IPv4 AFI";
            }
            list nhsafi {
              key "safi";
              description
                "next-hop safi(unicat|multicast) type";
              container nh-addresses {
                description
                  "next hop Database";
                list nh-address {
                  key "next-hop-addr";
                  description
                    "next-hop address to display";
                  leaf next-hop-addr {
                    type xr:ncs_rpc_notif_Cisco-ios-xr-string;
                    description
                      "next hop address";
                  }
                  uses ncs_rpc_notif_IPV4-STATIC-NHDB-BD;
                }
              }
              leaf safi {
                type ncs_rpc_notif_Safi;
                description
                  "IPv4 SAFI";
              }
            }
          }
        }
      }
    }
  }

  grouping ncs_rpc_notif_TABLE {
    description
      "Common node of ipv4-static, ipv4-local,
       ipv4-connected";
    container table-ids {
      description
        "list of Tables";
      list table-id {
        key "table-id";
        description
          "Table ID to display";
        leaf table-id {
          type xr:ncs_rpc_notif_Hex-integer;
          description
            "Table ID";
        }
        uses ncs_rpc_notif_IP-STATIC-TDB-BD;
      }
    }
  }

  grouping ncs_rpc_notif_BFDVRF-TABLE {
    description
      "Common node of ipv4-static, ipv4-local,
       ipv4-connected";
    container bfdvrfs {
      description
        "BFD's vrf list";
      list bfdvrf {
        key "vrf-name";
        description
          "vrf name";
        leaf vrf-name {
          type xr:ncs_rpc_notif_Cisco-ios-xr-string;
          description
            "The name of the vrf";
        }
        list bfd-table {
          key "table-name";
          description
            "BFD table name";
          leaf table-name {
            type xr:ncs_rpc_notif_Cisco-ios-xr-string;
            description
              "The name of the table";
          }
          list bfdafi {
            key "afi";
            description
              "BFD address family type";
            leaf afi {
              type ncs_rpc_notif_Afi;
              description
                "IPv4 AFI";
            }
            list bfdsafi {
              key "safi";
              description
                "BFD safi(unicat|multicast) type";
              container bfd-addresses {
                description
                  "list of BFD sessions";
                list bfd-address {
                  key "bfd-next-hop-addr";
                  description
                    "BFD next-hop address to display";
                  leaf bfd-next-hop-addr {
                    type xr:ncs_rpc_notif_Cisco-ios-xr-string;
                    description
                      "BFD next hop address";
                  }
                  uses ncs_rpc_notif_IPV4-STATIC-NHDB-BFD-BD;
                }
              }
              leaf safi {
                type ncs_rpc_notif_Safi;
                description
                  "IPv4 SAFI";
              }
            }
          }
        }
      }
    }
  }

  grouping ncs_rpc_notif_IPV4-IF-DB {
    description
      "Common node of ipv4-static, ipv4-local,
       ipv4-connected";
    container ipv4vrfs {
      description
        "ipv4 interface database";
      list ipv4vrf {
        key "vrf-name";
        description
          "vrf name";
        leaf vrf-name {
          type xr:ncs_rpc_notif_Cisco-ios-xr-string;
          description
            "The name of the";
        }
        list ipv4-table {
          key "table-name";
          description
            "table name";
          leaf table-name {
            type xr:ncs_rpc_notif_Cisco-ios-xr-string;
            description
              "The name of the atble";
          }
          list ipv4afi {
            key "afi";
            description
              "address family type";
            leaf afi {
              type ncs_rpc_notif_Afi;
              description
                "IPv4 AFI";
            }
            list ipv4safi {
              key "safi";
              description
                "unicast|multicast";
              leaf safi {
                type ncs_rpc_notif_Safi;
                description
                  "IPv4 SAFI";
              }
              list ipv4-interface {
                key "interface-name";
                description
                  "Interface to display";
                leaf interface-name {
                  type xr:ncs_rpc_notif_Interface-name;
                  description
                    "Interface name";
                }
                uses ncs_rpc_notif_IPV4-STATIC-IDB-BD;
              }
            }
          }
        }
      }
    }
  }

  grouping ncs_rpc_notif_TABLE-EVENTS {
    description
      "Common node of ipv4-static, ipv4-local,
       ipv4-connected";
    container table-events-ids {
      description
        "list of Tables";
      list table-events-id {
        key "table-id";
        description
          "Table ID to display events info";
        leaf table-id {
          type xr:ncs_rpc_notif_Hex-integer;
          description
            "Table ID";
        }
        uses ncs_rpc_notif_EVT-HIST-INFO;
      }
    }
  }

  grouping ncs_rpc_notif_IPV4FRIDB {
    description
      "Common node of ipv4-local, ipv4-connected";
    container ipv4fridbvrfs {
      description
        "ipv4 forward database";
      list ipv4fridbvrf {
        key "vrf-name";
        description
          "vrf name";
        leaf vrf-name {
          type xr:ncs_rpc_notif_Cisco-ios-xr-string;
          description
            "Forward DB vrf name";
        }
        list ipv4fridb-table {
          key "table-name";
          description
            "table name";
          leaf table-name {
            type xr:ncs_rpc_notif_Cisco-ios-xr-string;
            description
              "The name of the forward DB table";
          }
          list ipv4fridbafi {
            key "afitype";
            description
              "address family type";
            leaf afitype {
              type ncs_rpc_notif_Ipv4friafi;
              description
                "IPv4 AFI";
            }
            list ipv4fridbsafi {
              key "safitype";
              description
                "unicast|multicast";
              leaf safitype {
                type ncs_rpc_notif_Ipv4frisafi;
                description
                  "IPv4 SAFI";
              }
              list ipv4fridb-interface {
                key "interface-name";
                description
                  "forward DB Interface to display";
                leaf interface-name {
                  type xr:ncs_rpc_notif_Interface-name;
                  description
                    "forward DB Interface name";
                }
                uses ncs_rpc_notif_IP-STATIC-FRIDB-BD;
              }
            }
          }
        }
      }
    }
  }

  grouping live_ncs_TOPO-VRF-TABLE {
    description
      "Common node of ipv4-static, ipv4-local,
       ipv4-connected";
    container topo-vrfs {
      description
        "vrf list for Topology";
      list topo-vrf {
        key "vrf-name";
        description
          "vrf name";
        leaf vrf-name {
          type xr:live_ncs_Cisco-ios-xr-string;
          description
            "The name of thei vrf";
        }
        list topo-table {
          key "table-name";
          description
            "Topology table name";
          leaf table-name {
            type xr:live_ncs_Cisco-ios-xr-string;
            description
              "The name of the atble";
          }
          list topo-afi {
            key "afi";
            description
              "Topology address family type";
            leaf afi {
              type live_ncs_Afi;
              description
                "IPv4 AFI";
            }
            list topo-safi {
              key "safi";
              description
                "Topology SAFI type";
              container destinations {
                description
                  "route info";
                list destination {
                  description
                    "Destinatioin address and prefix length";
                  leaf prefix {
                    type xr:live_ncs_Cisco-ios-xr-string;
                    description
                      "detaination address prefix";
                  }
                  leaf prefix-length {
                    type xr:live_ncs_Hex-integer;
                    description
                      "detaination prefix length";
                  }
                  uses live_ncs_IPV4-STATIC-ROUTE-BD;
                }
              }
              leaf safi {
                type live_ncs_Safi;
                description
                  "IPv4 SAFI";
              }
            }
          }
        }
      }
    }
  }

  grouping live_ncs_NHVRF-TABLE {
    description
      "Common node of ipv4-static, ipv4-local,
       ipv4-connected";
    container nhvrfs {
      description
        "next-hop's vrf list";
      list nhvrf {
        key "vrf-name";
        description
          "vrf name";
        leaf vrf-name {
          type xr:live_ncs_Cisco-ios-xr-string;
          description
            "The name of thei vrf";
        }
        list nh-table {
          key "table-name";
          description
            "next-hop table name";
          leaf table-name {
            type xr:live_ncs_Cisco-ios-xr-string;
            description
              "The name of the atble";
          }
          list nhafi {
            key "afi";
            description
              "next-hop address family type";
            leaf afi {
              type live_ncs_Afi;
              description
                "IPv4 AFI";
            }
            list nhsafi {
              key "safi";
              description
                "next-hop safi(unicat|multicast) type";
              container nh-addresses {
                description
                  "next hop Database";
                list nh-address {
                  key "next-hop-addr";
                  description
                    "next-hop address to display";
                  leaf next-hop-addr {
                    type xr:live_ncs_Cisco-ios-xr-string;
                    description
                      "next hop address";
                  }
                  uses live_ncs_IPV4-STATIC-NHDB-BD;
                }
              }
              leaf safi {
                type live_ncs_Safi;
                description
                  "IPv4 SAFI";
              }
            }
          }
        }
      }
    }
  }

  grouping live_ncs_TABLE {
    description
      "Common node of ipv4-static, ipv4-local,
       ipv4-connected";
    container table-ids {
      description
        "list of Tables";
      list table-id {
        key "table-id";
        description
          "Table ID to display";
        leaf table-id {
          type xr:live_ncs_Hex-integer;
          description
            "Table ID";
        }
        uses live_ncs_IP-STATIC-TDB-BD;
      }
    }
  }

  grouping live_ncs_BFDVRF-TABLE {
    description
      "Common node of ipv4-static, ipv4-local,
       ipv4-connected";
    container bfdvrfs {
      description
        "BFD's vrf list";
      list bfdvrf {
        key "vrf-name";
        description
          "vrf name";
        leaf vrf-name {
          type xr:live_ncs_Cisco-ios-xr-string;
          description
            "The name of the vrf";
        }
        list bfd-table {
          key "table-name";
          description
            "BFD table name";
          leaf table-name {
            type xr:live_ncs_Cisco-ios-xr-string;
            description
              "The name of the table";
          }
          list bfdafi {
            key "afi";
            description
              "BFD address family type";
            leaf afi {
              type live_ncs_Afi;
              description
                "IPv4 AFI";
            }
            list bfdsafi {
              key "safi";
              description
                "BFD safi(unicat|multicast) type";
              container bfd-addresses {
                description
                  "list of BFD sessions";
                list bfd-address {
                  key "bfd-next-hop-addr";
                  description
                    "BFD next-hop address to display";
                  leaf bfd-next-hop-addr {
                    type xr:live_ncs_Cisco-ios-xr-string;
                    description
                      "BFD next hop address";
                  }
                  uses live_ncs_IPV4-STATIC-NHDB-BFD-BD;
                }
              }
              leaf safi {
                type live_ncs_Safi;
                description
                  "IPv4 SAFI";
              }
            }
          }
        }
      }
    }
  }

  grouping live_ncs_IPV4-IF-DB {
    description
      "Common node of ipv4-static, ipv4-local,
       ipv4-connected";
    container ipv4vrfs {
      description
        "ipv4 interface database";
      list ipv4vrf {
        key "vrf-name";
        description
          "vrf name";
        leaf vrf-name {
          type xr:live_ncs_Cisco-ios-xr-string;
          description
            "The name of the";
        }
        list ipv4-table {
          key "table-name";
          description
            "table name";
          leaf table-name {
            type xr:live_ncs_Cisco-ios-xr-string;
            description
              "The name of the atble";
          }
          list ipv4afi {
            key "afi";
            description
              "address family type";
            leaf afi {
              type live_ncs_Afi;
              description
                "IPv4 AFI";
            }
            list ipv4safi {
              key "safi";
              description
                "unicast|multicast";
              leaf safi {
                type live_ncs_Safi;
                description
                  "IPv4 SAFI";
              }
              list ipv4-interface {
                key "interface-name";
                description
                  "Interface to display";
                leaf interface-name {
                  type xr:live_ncs_Interface-name;
                  description
                    "Interface name";
                }
                uses live_ncs_IPV4-STATIC-IDB-BD;
              }
            }
          }
        }
      }
    }
  }

  grouping live_ncs_TABLE-EVENTS {
    description
      "Common node of ipv4-static, ipv4-local,
       ipv4-connected";
    container table-events-ids {
      description
        "list of Tables";
      list table-events-id {
        key "table-id";
        description
          "Table ID to display events info";
        leaf table-id {
          type xr:live_ncs_Hex-integer;
          description
            "Table ID";
        }
        uses live_ncs_EVT-HIST-INFO;
      }
    }
  }

  grouping live_ncs_IPV4FRIDB {
    description
      "Common node of ipv4-local, ipv4-connected";
    container ipv4fridbvrfs {
      description
        "ipv4 forward database";
      list ipv4fridbvrf {
        key "vrf-name";
        description
          "vrf name";
        leaf vrf-name {
          type xr:live_ncs_Cisco-ios-xr-string;
          description
            "Forward DB vrf name";
        }
        list ipv4fridb-table {
          key "table-name";
          description
            "table name";
          leaf table-name {
            type xr:live_ncs_Cisco-ios-xr-string;
            description
              "The name of the forward DB table";
          }
          list ipv4fridbafi {
            key "afitype";
            description
              "address family type";
            leaf afitype {
              type live_ncs_Ipv4friafi;
              description
                "IPv4 AFI";
            }
            list ipv4fridbsafi {
              key "safitype";
              description
                "unicast|multicast";
              leaf safitype {
                type live_ncs_Ipv4frisafi;
                description
                  "IPv4 SAFI";
              }
              list ipv4fridb-interface {
                key "interface-name";
                description
                  "forward DB Interface to display";
                leaf interface-name {
                  type xr:live_ncs_Interface-name;
                  description
                    "forward DB Interface name";
                }
                uses live_ncs_IP-STATIC-FRIDB-BD;
              }
            }
          }
        }
      }
    }
  }

  grouping TOPO-VRF-TABLE {
    description
      "Common node of ipv4-static, ipv4-local,
       ipv4-connected";
    container topo-vrfs {
      description
        "vrf list for Topology";
      list topo-vrf {
        key "vrf-name";
        description
          "vrf name";
        leaf vrf-name {
          type xr:Cisco-ios-xr-string;
          description
            "The name of thei vrf";
        }
        list topo-table {
          key "table-name";
          description
            "Topology table name";
          leaf table-name {
            type xr:Cisco-ios-xr-string;
            description
              "The name of the atble";
          }
          list topo-afi {
            key "afi";
            description
              "Topology address family type";
            leaf afi {
              type Afi;
              description
                "IPv4 AFI";
            }
            list topo-safi {
              key "safi";
              description
                "Topology SAFI type";
              container destinations {
                description
                  "route info";
                list destination {
                  description
                    "Destinatioin address and prefix length";
                  leaf prefix {
                    type xr:Cisco-ios-xr-string;
                    description
                      "detaination address prefix";
                  }
                  leaf prefix-length {
                    type xr:Hex-integer;
                    description
                      "detaination prefix length";
                  }
                  uses IPV4-STATIC-ROUTE-BD;
                }
              }
              leaf safi {
                type Safi;
                description
                  "IPv4 SAFI";
              }
            }
          }
        }
      }
    }
  }

  grouping NHVRF-TABLE {
    description
      "Common node of ipv4-static, ipv4-local,
       ipv4-connected";
    container nhvrfs {
      description
        "next-hop's vrf list";
      list nhvrf {
        key "vrf-name";
        description
          "vrf name";
        leaf vrf-name {
          type xr:Cisco-ios-xr-string;
          description
            "The name of thei vrf";
        }
        list nh-table {
          key "table-name";
          description
            "next-hop table name";
          leaf table-name {
            type xr:Cisco-ios-xr-string;
            description
              "The name of the atble";
          }
          list nhafi {
            key "afi";
            description
              "next-hop address family type";
            leaf afi {
              type Afi;
              description
                "IPv4 AFI";
            }
            list nhsafi {
              key "safi";
              description
                "next-hop safi(unicat|multicast) type";
              container nh-addresses {
                description
                  "next hop Database";
                list nh-address {
                  key "next-hop-addr";
                  description
                    "next-hop address to display";
                  leaf next-hop-addr {
                    type xr:Cisco-ios-xr-string;
                    description
                      "next hop address";
                  }
                  uses IPV4-STATIC-NHDB-BD;
                }
              }
              leaf safi {
                type Safi;
                description
                  "IPv4 SAFI";
              }
            }
          }
        }
      }
    }
  }

  grouping TABLE {
    description
      "Common node of ipv4-static, ipv4-local,
       ipv4-connected";
    container table-ids {
      description
        "list of Tables";
      list table-id {
        key "table-id";
        description
          "Table ID to display";
        leaf table-id {
          type xr:Hex-integer;
          description
            "Table ID";
        }
        uses IP-STATIC-TDB-BD;
      }
    }
  }

  grouping BFDVRF-TABLE {
    description
      "Common node of ipv4-static, ipv4-local,
       ipv4-connected";
    container bfdvrfs {
      description
        "BFD's vrf list";
      list bfdvrf {
        key "vrf-name";
        description
          "vrf name";
        leaf vrf-name {
          type xr:Cisco-ios-xr-string;
          description
            "The name of the vrf";
        }
        list bfd-table {
          key "table-name";
          description
            "BFD table name";
          leaf table-name {
            type xr:Cisco-ios-xr-string;
            description
              "The name of the table";
          }
          list bfdafi {
            key "afi";
            description
              "BFD address family type";
            leaf afi {
              type Afi;
              description
                "IPv4 AFI";
            }
            list bfdsafi {
              key "safi";
              description
                "BFD safi(unicat|multicast) type";
              container bfd-addresses {
                description
                  "list of BFD sessions";
                list bfd-address {
                  key "bfd-next-hop-addr";
                  description
                    "BFD next-hop address to display";
                  leaf bfd-next-hop-addr {
                    type xr:Cisco-ios-xr-string;
                    description
                      "BFD next hop address";
                  }
                  uses IPV4-STATIC-NHDB-BFD-BD;
                }
              }
              leaf safi {
                type Safi;
                description
                  "IPv4 SAFI";
              }
            }
          }
        }
      }
    }
  }

  grouping IPV4-IF-DB {
    description
      "Common node of ipv4-static, ipv4-local,
       ipv4-connected";
    container ipv4vrfs {
      description
        "ipv4 interface database";
      list ipv4vrf {
        key "vrf-name";
        description
          "vrf name";
        leaf vrf-name {
          type xr:Cisco-ios-xr-string;
          description
            "The name of the";
        }
        list ipv4-table {
          key "table-name";
          description
            "table name";
          leaf table-name {
            type xr:Cisco-ios-xr-string;
            description
              "The name of the atble";
          }
          list ipv4afi {
            key "afi";
            description
              "address family type";
            leaf afi {
              type Afi;
              description
                "IPv4 AFI";
            }
            list ipv4safi {
              key "safi";
              description
                "unicast|multicast";
              leaf safi {
                type Safi;
                description
                  "IPv4 SAFI";
              }
              list ipv4-interface {
                key "interface-name";
                description
                  "Interface to display";
                leaf interface-name {
                  type xr:Interface-name;
                  description
                    "Interface name";
                }
                uses IPV4-STATIC-IDB-BD;
              }
            }
          }
        }
      }
    }
  }

  grouping TABLE-EVENTS {
    description
      "Common node of ipv4-static, ipv4-local,
       ipv4-connected";
    container table-events-ids {
      description
        "list of Tables";
      list table-events-id {
        key "table-id";
        description
          "Table ID to display events info";
        leaf table-id {
          type xr:Hex-integer;
          description
            "Table ID";
        }
        uses EVT-HIST-INFO;
      }
    }
  }

  grouping IPV4FRIDB {
    description
      "Common node of ipv4-local, ipv4-connected";
    container ipv4fridbvrfs {
      description
        "ipv4 forward database";
      list ipv4fridbvrf {
        key "vrf-name";
        description
          "vrf name";
        leaf vrf-name {
          type xr:Cisco-ios-xr-string;
          description
            "Forward DB vrf name";
        }
        list ipv4fridb-table {
          key "table-name";
          description
            "table name";
          leaf table-name {
            type xr:Cisco-ios-xr-string;
            description
              "The name of the forward DB table";
          }
          list ipv4fridbafi {
            key "afitype";
            description
              "address family type";
            leaf afitype {
              type Ipv4friafi;
              description
                "IPv4 AFI";
            }
            list ipv4fridbsafi {
              key "safitype";
              description
                "unicast|multicast";
              leaf safitype {
                type Ipv4frisafi;
                description
                  "IPv4 SAFI";
              }
              list ipv4fridb-interface {
                key "interface-name";
                description
                  "forward DB Interface to display";
                leaf interface-name {
                  type xr:Interface-name;
                  description
                    "forward DB Interface name";
                }
                uses IP-STATIC-FRIDB-BD;
              }
            }
          }
        }
      }
    }
  }

  augment "/ncs:devices/ncs:device/ncs:config" {
    // NCS drop config false container 'ipv4-local'
    // NCS drop config false container 'ipv4-static'
    // NCS drop config false container 'ipv4-connected'
  }
  augment "/ncs:devices/ncs:device/ncs:live-status" {
    container ipv4-local {
      tailf:ncs-device-type "netconf";
      tailf:display-when "not(../../ncs:module) or ../../ncs:module[ncs:name='Cisco-IOS-XR-ip-static-ipv4-oper'] or (../../ncs:live-status-protocol[not(ncs:capability)]) or (../../ncs:live-status-protocol/ncs:capability/ncs:module[.='Cisco-IOS-XR-ip-static-ipv4-oper'])";
      description
        "Local Routing Information";
      uses live_ncs_IPV4-IF-DB;
      uses live_ncs_NHVRF-TABLE;
      uses live_ncs_IPV4FRIDB;
      uses live_ncs_TABLE-EVENTS;
      uses live_ncs_BFDVRF-TABLE;
      uses live_ncs_TOPO-VRF-TABLE;
      uses live_ncs_TABLE;
    }
    container ipv4-static {
      tailf:ncs-device-type "netconf";
      tailf:display-when "not(../../ncs:module) or ../../ncs:module[ncs:name='Cisco-IOS-XR-ip-static-ipv4-oper'] or (../../ncs:live-status-protocol[not(ncs:capability)]) or (../../ncs:live-status-protocol/ncs:capability/ncs:module[.='Cisco-IOS-XR-ip-static-ipv4-oper'])";
      description
        "Static Routing Information";
      container ipv4-sr-policy-vrfs {
        description
          "ipv4 sr-policy interface database";
        list ipv4-sr-policy-vrf {
          key "vrf-name";
          description
            "sr policy vrf name";
          leaf vrf-name {
            type xr:live_ncs_Cisco-ios-xr-string;
            description
              "The name of the vrf";
          }
          list ipv4-sr-policy-table {
            key "table-name";
            description
              "sr policy table name";
            leaf table-name {
              type xr:live_ncs_Cisco-ios-xr-string;
              description
                "The name of the table";
            }
            list ipv4-sr-policy-afi {
              key "afi";
              description
                "address family type";
              leaf afi {
                type live_ncs_Afi;
                description
                  "IPv4 AFI";
              }
              list ipv4-sr-policy-safi {
                key "safi";
                description
                  "unicast|multicast";
                leaf safi {
                  type live_ncs_Safi;
                  description
                    "IPv4 SAFI";
                }
                list ipv4-sr-policy-interface {
                  key "srpolicy";
                  description
                    "sr policy to display";
                  leaf srpolicy {
                    type xr:live_ncs_Cisco-ios-xr-string;
                    description
                      "sr policy name";
                  }
                  uses live_ncs_IPV4-STATIC-IDB-BD;
                }
              }
            }
          }
        }
      }
      container track-object-names {
        description
          "list of track objects";
        list track-object-name {
          key "ot-name";
          description
            "Track object to display";
          leaf ot-name {
            type xr:live_ncs_Cisco-ios-xr-string;
            description
              "The name of the tacking object";
          }
          uses live_ncs_IPV4-STATIC-OTDB-BD;
        }
      }
      container colocationvrf-names {
        description
          "list of colocation vrfs";
        list colocationvrf-name {
          key "vrf";
          description
            "vrf name of table id to display colocation list";
          leaf vrf {
            type xr:live_ncs_Cisco-ios-xr-string;
            description
              "vrf name";
          }
          list colocation-table {
            key "table-name";
            description
              "table name to display colocation list";
            leaf table-name {
              type xr:live_ncs_Cisco-ios-xr-string;
              description
                "table name";
            }
            list colocation-afi {
              key "afi";
              description
                "Colocation address family type";
              leaf afi {
                type live_ncs_Afi;
                description
                  "IPv4 AFI";
              }
              list colocation-safi {
                key "safi";
                description
                  "Colocation safi(unicat|multicast) type";
                container colo-table-ids {
                  description
                    "tables to display colocation list";
                  list colo-table-id {
                    key "table-id";
                    description
                      "table to display colocation list";
                    leaf table-id {
                      type xr:live_ncs_Hex-integer;
                      description
                        "Table ID";
                    }
                    uses live_ncs_IP-STATIC-COLOCATION-BD;
                  }
                }
                leaf safi {
                  type live_ncs_Safi;
                  description
                    "IPv4 SAFI";
                }
              }
            }
          }
        }
      }
      container exp-paths {
        description
          "list of isegment routes";
        list exp-path {
          key "exp-path";
          description
            "Explicit path to display";
          leaf exp-path {
            type xr:live_ncs_Cisco-ios-xr-string;
            description
              "The name of the tacking object";
          }
          uses live_ncs_IPV4-STATIC-TEDB-BD;
        }
      }
      uses live_ncs_IPV4-IF-DB;
      uses live_ncs_NHVRF-TABLE;
      uses live_ncs_TABLE-EVENTS;
      uses live_ncs_BFDVRF-TABLE;
      uses live_ncs_TOPO-VRF-TABLE;
      uses live_ncs_TABLE;
    }
    container ipv4-connected {
      tailf:ncs-device-type "netconf";
      tailf:display-when "not(../../ncs:module) or ../../ncs:module[ncs:name='Cisco-IOS-XR-ip-static-ipv4-oper'] or (../../ncs:live-status-protocol[not(ncs:capability)]) or (../../ncs:live-status-protocol/ncs:capability/ncs:module[.='Cisco-IOS-XR-ip-static-ipv4-oper'])";
      description
        "Connected Routing Information";
      uses live_ncs_IPV4-IF-DB;
      uses live_ncs_NHVRF-TABLE;
      uses live_ncs_IPV4FRIDB;
      uses live_ncs_TABLE-EVENTS;
      uses live_ncs_BFDVRF-TABLE;
      uses live_ncs_TOPO-VRF-TABLE;
      uses live_ncs_TABLE;
    }
  }
  augment "/ncs:devices/ncs:template/ncs:ned-id/ncs:config" {
    // NCS drop config false container 'ipv4-local'
    // NCS drop config false container 'ipv4-static'
    // NCS drop config false container 'ipv4-connected'
  }
}

module tailf-aaa {
  // Generated by yanger -t ncs
  tailf:mount-id "cisco-iosxr-nc-7.3:cisco-iosxr-nc-7.3";
  tailf:ncs-device-type "netconf";

  namespace "http://tail-f.com/ns/aaa/1.1";
  prefix aaa;

  import iana-crypt-hash {
    prefix ianach;
  }
  import tailf-common {
    prefix tailf;
  }
  import tailf-ncs {
    prefix ncs;
  }

  organization
    "Tail-f Systems";
  contact
    "Cisco Systems, Inc.
     Customer Service

     Postal: 170 West Tasman Drive
     San Jose, CA 95134

     Tel: +1 800 553-NETS

     E-mail: cs-yang@cisco.com";
  description
    "This module defines the Tail-f AAA data model.

     Copyright (c) 2012-2020 by Cisco Systems, Inc.
     All rights reserved.";

  revision 2019-05-04 {
    description
      "Changed passwdStr typedef to use ianach:crypt-hash instead of
       tailf:md5-digest-string.";
  }
  revision 2011-09-22 {
    description
      "Released as part of ConfD-3.7.";
  }
  revision 2010-06-17 {
    description
      "Released as part of ConfD-3.3.";
  }
  revision 2010-04-22 {
    description
      "Released as part of ConfD-3.2.1.";
  }
  revision 2010-03-18 {
    description
      "Released as part of ConfD-3.2.";
  }

  typedef ncs_template_history {
    type string;
  }

  typedef ncs_template_idle-timeout {
    type string;
  }

  typedef ncs_template_display-level {
    type string;
  }

  typedef ncs_template_dataOperationType {
    type string;
  }

  typedef ncs_template_cmdOperationType {
    type string;
  }

  typedef ncs_template_Action {
    type string;
  }

  typedef ncs_template_passwdStr {
    type ianach:ncs_template_crypt-hash;
  }

  typedef ncs_template_levelInt {
    type string;
  }

  typedef ncs_template_modeStr {
    type string;
  }

  typedef ncs_template_builtinModes {
    type string;
  }

  typedef ncs_rpc_notif_history {
    type uint64 {
      range "0 .. 8192";
    }
  }

  typedef ncs_rpc_notif_idle-timeout {
    type uint64 {
      range "0 .. 8192";
    }
  }

  typedef ncs_rpc_notif_display-level {
    type uint64 {
      range "1 .. 64";
    }
  }

  typedef ncs_rpc_notif_dataOperationType {
    type enumeration {
      enum "r";
      enum "rx";
      enum "x";
      enum "rw";
      enum "rwx";
      enum "wx";
      enum "w";
      enum "c";
      enum "cr";
      enum "cu";
      enum "cd";
      enum "cx";
      enum "cru";
      enum "crd";
      enum "crx";
      enum "cud";
      enum "cux";
      enum "cdx";
      enum "crud";
      enum "crux";
      enum "crdx";
      enum "cudx";
      enum "crudx";
      enum "ru";
      enum "rd";
      enum "rud";
      enum "rux";
      enum "rdx";
      enum "u";
      enum "ud";
      enum "ux";
      enum "d";
      enum "dx";
    }
  }

  typedef ncs_rpc_notif_cmdOperationType {
    type enumeration {
      enum "r";
      enum "rx";
      enum "x";
    }
  }

  typedef ncs_rpc_notif_Action {
    type enumeration {
      enum "accept";
      enum "reject";
      enum "accept_log";
    }
  }

  typedef ncs_rpc_notif_passwdStr {
    type ianach:ncs_rpc_notif_crypt-hash;
  }

  typedef ncs_rpc_notif_levelInt {
    type int32 {
      range "0 .. 15";
    }
  }

  typedef ncs_rpc_notif_modeStr {
    type union {
      type string;
      type ncs_rpc_notif_builtinModes;
    }
  }

  typedef ncs_rpc_notif_builtinModes {
    type enumeration {
      enum "exec";
      enum "configure";
    }
  }

  typedef live_ncs_history {
    type uint64 {
      range "0 .. 8192";
    }
  }

  typedef live_ncs_idle-timeout {
    type uint64 {
      range "0 .. 8192";
    }
  }

  typedef live_ncs_display-level {
    type uint64 {
      range "1 .. 64";
    }
  }

  typedef live_ncs_dataOperationType {
    type enumeration {
      enum "r";
      enum "rx";
      enum "x";
      enum "rw";
      enum "rwx";
      enum "wx";
      enum "w";
      enum "c";
      enum "cr";
      enum "cu";
      enum "cd";
      enum "cx";
      enum "cru";
      enum "crd";
      enum "crx";
      enum "cud";
      enum "cux";
      enum "cdx";
      enum "crud";
      enum "crux";
      enum "crdx";
      enum "cudx";
      enum "crudx";
      enum "ru";
      enum "rd";
      enum "rud";
      enum "rux";
      enum "rdx";
      enum "u";
      enum "ud";
      enum "ux";
      enum "d";
      enum "dx";
    }
  }

  typedef live_ncs_cmdOperationType {
    type enumeration {
      enum "r";
      enum "rx";
      enum "x";
    }
  }

  typedef live_ncs_Action {
    type enumeration {
      enum "accept";
      enum "reject";
      enum "accept_log";
    }
  }

  typedef live_ncs_passwdStr {
    type ianach:live_ncs_crypt-hash;
  }

  typedef live_ncs_levelInt {
    type int32 {
      range "0 .. 15";
    }
  }

  typedef live_ncs_modeStr {
    type union {
      type string;
      type live_ncs_builtinModes;
    }
  }

  typedef live_ncs_builtinModes {
    type enumeration {
      enum "exec";
      enum "configure";
    }
  }

  typedef history {
    type uint64 {
      range "0 .. 8192";
    }
  }

  typedef idle-timeout {
    type uint64 {
      range "0 .. 8192";
    }
  }

  typedef display-level {
    type uint64 {
      range "1 .. 64";
    }
  }

  typedef dataOperationType {
    type enumeration {
      enum "r";
      enum "rx";
      enum "x";
      enum "rw";
      enum "rwx";
      enum "wx";
      enum "w";
      enum "c";
      enum "cr";
      enum "cu";
      enum "cd";
      enum "cx";
      enum "cru";
      enum "crd";
      enum "crx";
      enum "cud";
      enum "cux";
      enum "cdx";
      enum "crud";
      enum "crux";
      enum "crdx";
      enum "cudx";
      enum "crudx";
      enum "ru";
      enum "rd";
      enum "rud";
      enum "rux";
      enum "rdx";
      enum "u";
      enum "ud";
      enum "ux";
      enum "d";
      enum "dx";
    }
  }

  typedef cmdOperationType {
    type enumeration {
      enum "r";
      enum "rx";
      enum "x";
    }
  }

  typedef Action {
    type enumeration {
      enum "accept";
      enum "reject";
      enum "accept_log";
    }
  }

  typedef passwdStr {
    type ianach:crypt-hash;
  }

  typedef levelInt {
    type int32 {
      range "0 .. 15";
    }
  }

  typedef modeStr {
    type union {
      type string;
      type builtinModes;
    }
  }

  typedef builtinModes {
    type enumeration {
      enum "exec";
      enum "configure";
    }
  }

  grouping ncs_template_session-params {
    leaf complete-on-space {
      type string;
    }
    leaf ignore-leading-space {
      type string;
    }
    leaf idle-timeout {
      type ncs_template_idle-timeout;
    }
    leaf paginate {
      type string;
    }
    leaf history {
      type ncs_template_history;
    }
    leaf autowizard {
      type string;
    }
    leaf show-defaults {
      type string;
    }
    leaf display-level {
      type ncs_template_display-level;
    }
    leaf prompt1 {
      type string;
    }
    leaf prompt2 {
      type string;
    }
  }

  grouping ncs_rpc_notif_session-params {
    leaf complete-on-space {
      type boolean;
    }
    leaf ignore-leading-space {
      type boolean;
    }
    leaf idle-timeout {
      type ncs_rpc_notif_idle-timeout;
    }
    leaf paginate {
      type boolean;
    }
    leaf history {
      type ncs_rpc_notif_history;
    }
    leaf autowizard {
      type boolean;
    }
    leaf show-defaults {
      type boolean;
    }
    leaf display-level {
      type ncs_rpc_notif_display-level;
    }
    leaf prompt1 {
      type string;
    }
    leaf prompt2 {
      type string;
    }
  }

  grouping live_ncs_session-params {
    leaf complete-on-space {
      type boolean;
    }
    leaf ignore-leading-space {
      type boolean;
    }
    leaf idle-timeout {
      type live_ncs_idle-timeout;
    }
    leaf paginate {
      type boolean;
    }
    leaf history {
      type live_ncs_history;
    }
    leaf autowizard {
      type boolean;
    }
    leaf show-defaults {
      type boolean;
    }
    leaf display-level {
      type live_ncs_display-level;
    }
    leaf prompt1 {
      type string;
    }
    leaf prompt2 {
      type string;
    }
  }

  grouping session-params {
    leaf complete-on-space {
      type boolean;
    }
    leaf ignore-leading-space {
      type boolean;
    }
    leaf idle-timeout {
      type idle-timeout;
    }
    leaf paginate {
      type boolean;
    }
    leaf history {
      type history;
    }
    leaf autowizard {
      type boolean;
    }
    leaf show-defaults {
      type boolean;
    }
    leaf display-level {
      type display-level;
    }
    leaf prompt1 {
      type string;
    }
    leaf prompt2 {
      type string;
    }
  }

  augment "/ncs:devices/ncs:device/ncs:config" {
    container aaa {
      tailf:ncs-device-type "netconf";
      tailf:display-when "not(../../ncs:module) or ../../ncs:module[ncs:name='tailf-aaa']";
      container authentication {
        container users {
          list user {
            key "name";
            ordered-by user;
            max-elements 1024;
            leaf name {
              type string;
            }
            leaf uid {
              type uint32;
              default "9000";
            }
            leaf gid {
              type uint32;
              default "100";
            }
            leaf password {
              type passwdStr;
              mandatory true;
            }
            leaf ssh_keydir {
              type string;
              default "/home/sshdir";
            }
            leaf homedir {
              type string;
              default "/home/homedir";
            }
          }
        }
        container groups {
          list group {
            key "name";
            max-elements 32;
            leaf name {
              type string;
            }
            leaf gid {
              type uint32;
              default "100";
            }
            leaf users {
              type string;
              default "%%__system_user__%%";
            }
          }
        }
        container login {
          container group {
            leaf tacacs {
              type empty;
            }
          }
        }
      }
      container authorization {
        container cmdrules {
          list cmdrule {
            key "index";
            leaf index {
              type uint32;
            }
            leaf context {
              type string;
              mandatory true;
            }
            leaf command {
              type string;
              mandatory true;
            }
            leaf group {
              type string;
              mandatory true;
            }
            leaf ops {
              type cmdOperationType;
              mandatory true;
            }
            leaf action {
              type Action;
              mandatory true;
            }
          }
        }
        container datarules {
          list datarule {
            key "index";
            leaf index {
              type uint32;
            }
            leaf namespace {
              type string;
              mandatory true;
            }
            leaf context {
              type string;
              default "*";
            }
            leaf keypath {
              type string;
              mandatory true;
            }
            leaf group {
              type string;
              mandatory true;
            }
            leaf ops {
              type dataOperationType;
              mandatory true;
            }
            leaf action {
              type Action;
              mandatory true;
            }
          }
        }
        container commands {
          container group {
            leaf tacacs {
              type empty;
            }
            leaf none {
              type empty;
            }
          }
        }
      }
      container accounting {
        container commands {
          container group {
            leaf tacacs {
              type empty;
            }
          }
        }
      }
      container ios {
        presence "Indicates specifc IOS settings are configured";
        list level {
          key "nr";
          min-elements 2;
          leaf nr {
            type levelInt;
          }
          leaf secret {
            type passwdStr;
          }
          leaf password {
            type passwdStr;
          }
          leaf prompt {
            type string;
            default "\\h# ";
          }
        }
        list privilege {
          key "mode";
          leaf mode {
            type modeStr;
          }
          list level {
            key "nr";
            min-elements 1;
            max-elements 15;
            leaf nr {
              type levelInt;
            }
            list command {
              key "name";
              leaf name {
                type string;
              }
            }
          }
        }
      }
    }
    list alias {
      tailf:ncs-device-type "netconf";
      tailf:display-when "not(../ncs:module) or ../ncs:module[ncs:name='tailf-aaa']";
      key "name";
      leaf name {
        type string;
      }
      leaf expansion {
        type string;
        mandatory true;
      }
    }
    container session {
      tailf:ncs-device-type "netconf";
      tailf:display-when "not(../../ncs:module) or ../../ncs:module[ncs:name='tailf-aaa']";
      uses session-params;
      presence "Indicates Global default CLI session pareameters are configured";
    }
    list user {
      tailf:ncs-device-type "netconf";
      tailf:display-when "not(../ncs:module) or ../ncs:module[ncs:name='tailf-aaa']";
      key "name";
      leaf name {
        type string;
      }
      leaf description {
        type string;
      }
      list alias {
        key "name";
        leaf name {
          type string;
        }
        leaf expansion {
          type string;
          mandatory true;
        }
      }
      container session {
        uses session-params;
      }
    }
  }
  augment "/ncs:devices/ncs:device/ncs:live-status" {
    container aaa {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      container authentication {
        container users {
          list user {
            key "name";
            ordered-by user;
            // NCS drop max-elements statement
            leaf name {
              type string;
            }
            leaf uid {
              type uint32;
              // NCS drop default statement
            }
            leaf gid {
              type uint32;
              // NCS drop default statement
            }
            leaf password {
              type live_ncs_passwdStr;
              // NCS drop mandatory statement
            }
            leaf ssh_keydir {
              type string;
              // NCS drop default statement
            }
            leaf homedir {
              type string;
              // NCS drop default statement
            }
          }
        }
        container groups {
          list group {
            key "name";
            // NCS drop max-elements statement
            leaf name {
              type string;
            }
            leaf gid {
              type uint32;
              // NCS drop default statement
            }
            leaf users {
              type string;
              // NCS drop default statement
            }
          }
        }
        container login {
          container group {
            leaf tacacs {
              type empty;
            }
          }
        }
      }
      container authorization {
        container cmdrules {
          list cmdrule {
            key "index";
            leaf index {
              type uint32;
            }
            leaf context {
              type string;
              // NCS drop mandatory statement
            }
            leaf command {
              type string;
              // NCS drop mandatory statement
            }
            leaf group {
              type string;
              // NCS drop mandatory statement
            }
            leaf ops {
              type live_ncs_cmdOperationType;
              // NCS drop mandatory statement
            }
            leaf action {
              type live_ncs_Action;
              // NCS drop mandatory statement
            }
          }
        }
        container datarules {
          list datarule {
            key "index";
            leaf index {
              type uint32;
            }
            leaf namespace {
              type string;
              // NCS drop mandatory statement
            }
            leaf context {
              type string;
              // NCS drop default statement
            }
            leaf keypath {
              type string;
              // NCS drop mandatory statement
            }
            leaf group {
              type string;
              // NCS drop mandatory statement
            }
            leaf ops {
              type live_ncs_dataOperationType;
              // NCS drop mandatory statement
            }
            leaf action {
              type live_ncs_Action;
              // NCS drop mandatory statement
            }
          }
        }
        container commands {
          container group {
            leaf tacacs {
              type empty;
            }
            leaf none {
              type empty;
            }
          }
        }
      }
      container accounting {
        container commands {
          container group {
            leaf tacacs {
              type empty;
            }
          }
        }
      }
      container ios {
        presence "Indicates specifc IOS settings are configured";
        list level {
          key "nr";
          // NCS drop min-elements statement
          leaf nr {
            type live_ncs_levelInt;
          }
          leaf secret {
            type live_ncs_passwdStr;
          }
          leaf password {
            type live_ncs_passwdStr;
          }
          leaf prompt {
            type string;
            // NCS drop default statement
          }
        }
        list privilege {
          key "mode";
          leaf mode {
            type live_ncs_modeStr;
          }
          list level {
            key "nr";
            // NCS drop min-elements statement
            // NCS drop max-elements statement
            leaf nr {
              type live_ncs_levelInt;
            }
            list command {
              key "name";
              leaf name {
                type string;
              }
            }
          }
        }
      }
    }
    list alias {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      key "name";
      leaf name {
        type string;
      }
      leaf expansion {
        type string;
        // NCS drop mandatory statement
      }
    }
    container session {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      uses live_ncs_session-params;
      presence "Indicates Global default CLI session pareameters are configured";
    }
    list user {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      key "name";
      leaf name {
        type string;
      }
      leaf description {
        type string;
      }
      list alias {
        key "name";
        leaf name {
          type string;
        }
        leaf expansion {
          type string;
          // NCS drop mandatory statement
        }
      }
      container session {
        uses live_ncs_session-params;
      }
    }
  }
  augment "/ncs:devices/ncs:template/ncs:ned-id/ncs:config" {
    container aaa {
      container authentication {
        container users {
          list user {
            // NCS patched for predictable order
            ordered-by user;
            key "name";
            // NCS drop max-elements statement
            leaf name {
              type string;
            }
            leaf uid {
              type string;
              // NCS drop default statement
            }
            leaf gid {
              type string;
              // NCS drop default statement
            }
            leaf password {
              type ncs_template_passwdStr;
              // NCS drop mandatory statement
            }
            leaf ssh_keydir {
              type string;
              // NCS drop default statement
            }
            leaf homedir {
              type string;
              // NCS drop default statement
            }
          }
        }
        container groups {
          list group {
            // NCS patched for predictable order
            ordered-by user;
            key "name";
            // NCS drop max-elements statement
            leaf name {
              type string;
            }
            leaf gid {
              type string;
              // NCS drop default statement
            }
            leaf users {
              type string;
              // NCS drop default statement
            }
          }
        }
        container login {
          container group {
            leaf tacacs {
              type empty;
            }
          }
        }
      }
      container authorization {
        container cmdrules {
          list cmdrule {
            // NCS patched for predictable order
            ordered-by user;
            key "index";
            leaf index {
              type string;
            }
            leaf context {
              type string;
              // NCS drop mandatory statement
            }
            leaf command {
              type string;
              // NCS drop mandatory statement
            }
            leaf group {
              type string;
              // NCS drop mandatory statement
            }
            leaf ops {
              type ncs_template_cmdOperationType;
              // NCS drop mandatory statement
            }
            leaf action {
              type ncs_template_Action;
              // NCS drop mandatory statement
            }
          }
        }
        container datarules {
          list datarule {
            // NCS patched for predictable order
            ordered-by user;
            key "index";
            leaf index {
              type string;
            }
            leaf namespace {
              type string;
              // NCS drop mandatory statement
            }
            leaf context {
              type string;
              // NCS drop default statement
            }
            leaf keypath {
              type string;
              // NCS drop mandatory statement
            }
            leaf group {
              type string;
              // NCS drop mandatory statement
            }
            leaf ops {
              type ncs_template_dataOperationType;
              // NCS drop mandatory statement
            }
            leaf action {
              type ncs_template_Action;
              // NCS drop mandatory statement
            }
          }
        }
        container commands {
          container group {
            leaf tacacs {
              type empty;
            }
            leaf none {
              type empty;
            }
          }
        }
      }
      container accounting {
        container commands {
          container group {
            leaf tacacs {
              type empty;
            }
          }
        }
      }
      container ios {
        presence "Indicates specifc IOS settings are configured";
        list level {
          // NCS patched for predictable order
          ordered-by user;
          key "nr";
          // NCS drop min-elements statement
          leaf nr {
            type ncs_template_levelInt;
          }
          leaf secret {
            type ncs_template_passwdStr;
          }
          leaf password {
            type ncs_template_passwdStr;
          }
          leaf prompt {
            type string;
            // NCS drop default statement
          }
        }
        list privilege {
          // NCS patched for predictable order
          ordered-by user;
          key "mode";
          leaf mode {
            type ncs_template_modeStr;
          }
          list level {
            // NCS patched for predictable order
            ordered-by user;
            key "nr";
            // NCS drop min-elements statement
            // NCS drop max-elements statement
            leaf nr {
              type ncs_template_levelInt;
            }
            list command {
              // NCS patched for predictable order
              ordered-by user;
              key "name";
              leaf name {
                type string;
              }
            }
          }
        }
      }
    }
    list alias {
      // NCS patched for predictable order
      ordered-by user;
      key "name";
      leaf name {
        type string;
      }
      leaf expansion {
        type string;
        // NCS drop mandatory statement
      }
    }
    container session {
      uses ncs_template_session-params;
      presence "Indicates Global default CLI session pareameters are configured";
    }
    list user {
      // NCS patched for predictable order
      ordered-by user;
      key "name";
      leaf name {
        type string;
      }
      leaf description {
        type string;
      }
      list alias {
        // NCS patched for predictable order
        ordered-by user;
        key "name";
        leaf name {
          type string;
        }
        leaf expansion {
          type string;
          // NCS drop mandatory statement
        }
      }
      container session {
        uses ncs_template_session-params;
      }
    }
  }
}

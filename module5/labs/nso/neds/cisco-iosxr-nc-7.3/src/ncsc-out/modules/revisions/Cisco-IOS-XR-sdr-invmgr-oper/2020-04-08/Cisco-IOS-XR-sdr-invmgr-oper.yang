module Cisco-IOS-XR-sdr-invmgr-oper {
  // Generated by yanger -t ncs
  tailf:mount-id "cisco-iosxr-nc-7.3:cisco-iosxr-nc-7.3";
  tailf:ncs-device-type "netconf";

  namespace "http://cisco.com/ns/yang/Cisco-IOS-XR-sdr-invmgr-oper";
  prefix sdr-invmgr-oper;

  import Cisco-IOS-XR-types {
    prefix xr;
  }
  import cisco-semver {
    prefix semver;
  }
  include Cisco-IOS-XR-sdr-invmgr-oper-sub1 {
    revision-date 2020-04-08;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sdr-invmgr package operational data.

     This module contains definitions
     for the following management objects:
       sdr-inventory: SDR information

     Copyright (c) 2013-2020 by Cisco Systems, Inc.
     All rights reserved.";

  revision 2020-04-08 {
    description
      "Deprecated Memory container.";
    semver:module-version "2.0.0";
  }
  revision 2019-04-05 {
    description
      "Establish semantic version baseline.";
    semver:module-version "1.0.1";
  }
  revision 2019-03-07 {
    description
      "Improved description for certain fields.";
  }
  revision 2015-11-09 {
    description
      "IOS XR 6.0 revision.";
  }

  augment "/ncs:devices/ncs:device/ncs:config" {
    // NCS drop config false container 'sdr-inventory'
  }
  augment "/ncs:devices/ncs:device/ncs:live-status" {
    container sdr-inventory {
      tailf:ncs-device-type "netconf";
      tailf:display-when "not(../../ncs:module) or ../../ncs:module[ncs:name='Cisco-IOS-XR-sdr-invmgr-oper'] or (../../ncs:live-status-protocol[not(ncs:capability)]) or (../../ncs:live-status-protocol/ncs:capability/ncs:module[.='Cisco-IOS-XR-sdr-invmgr-oper'])";
      description
        "SDR information";
      container racks {
        description
          "RackTable";
        list rack {
          key "name";
          description
            "Rack name";
          leaf name {
            type xr:live_ncs_Cisco-ios-xr-string;
            description
              "Rack name";
          }
          list slot {
            key "name";
            description
              "Slot name";
            leaf name {
              type xr:live_ncs_Cisco-ios-xr-string;
              description
                "Slot name";
            }
            list card {
              key "name";
              description
                "Card";
              container attributes {
                description
                  "Shows the different attributes or status of
                   each entity or component in inventory";
                leaf config-state-string {
                  type string {
                    length "1..100";
                  }
                  description
                    "Entity Config State String Attribute";
                }
                leaf power {
                  type uint32 {
                    range "0..4294967295";
                  }
                  // NCS drop default statement
                  description
                    "Indicate Entity Power";
                }
                leaf config-state {
                  type uint32 {
                    range "0..4294967295";
                  }
                  // NCS drop default statement
                  description
                    "Entity Config State Attribute";
                }
                leaf card-state {
                  type uint32 {
                    range "0..4294967295";
                  }
                  // NCS drop default statement
                  description
                    "Entity CardState Attribute";
                }
                leaf vm-state {
                  type uint32 {
                    range "0..4294967295";
                  }
                  // NCS drop default statement
                  description
                    "VM State information";
                }
                leaf card-admin-state {
                  type uint32 {
                    range "0..4294967295";
                  }
                  // NCS drop default statement
                  description
                    "Entity Card Admin State Attribute";
                }
                leaf card-type {
                  type uint32 {
                    range "0..4294967295";
                  }
                  // NCS drop default statement
                  description
                    "Entity CardType Attribute";
                }
                leaf card-type-string {
                  type string {
                    length "1..100";
                  }
                  description
                    "Entity Card Type String Attribute";
                }
                leaf node-name-string {
                  type xr:live_ncs_Node-id;
                  description
                    "Entity Node Name String Attribute";
                }
                leaf card-valid {
                  type uint32 {
                    range "0..4294967295";
                  }
                  // NCS drop default statement
                  description
                    "Indicates weather Entity Card is Valid";
                }
                leaf pi-slot-number {
                  type uint32 {
                    range "0..4294967295";
                  }
                  // NCS drop default statement
                  description
                    "Pi Slot Number";
                }
                leaf shutdown {
                  type uint32 {
                    range "0..4294967295";
                  }
                  // NCS drop default statement
                  description
                    "Indicates whether the Entity is in Shutdown
                     State";
                }
                leaf ctype {
                  type uint32 {
                    range "0..4294967295";
                  }
                  // NCS drop default statement
                  description
                    "Entity CType Attribute";
                }
                leaf card-state-string {
                  type string {
                    length "1..100";
                  }
                  description
                    "Entity Card State String Attribute";
                }
                leaf monitor {
                  type uint32 {
                    range "0..4294967295";
                  }
                  // NCS drop default statement
                  description
                    "Entity Monitor Attribute";
                }
              }
              leaf name {
                type xr:live_ncs_Cisco-ios-xr-string;
                description
                  "Card";
              }
            }
          }
        }
      }
      container memory {
        status deprecated;
        description
          "Memory related information";
        container racks {
          status deprecated;
          description
            "RackTable";
          list rack {
            key "name";
            status deprecated;
            description
              "Rack name";
            container node-ids {
              status deprecated;
              description
                "NodeIDTable";
              list node-id {
                key "name";
                status deprecated;
                description
                  "Inventory Admin Mempool Data  Bag";
                leaf name {
                  type xr:live_ncs_Cisco-ios-xr-string;
                  description
                    "nodeid";
                }
                uses live_ncs_INV-ADMIN-MEMPOOL-DATA;
              }
            }
            leaf name {
              type xr:live_ncs_Cisco-ios-xr-string;
              description
                "Rack name";
            }
          }
        }
      }
    }
  }
  augment "/ncs:devices/ncs:template/ncs:ned-id/ncs:config" {
    // NCS drop config false container 'sdr-inventory'
  }
}

module Cisco-IOS-XR-flowspec-cfg {
  // Generated by yanger -t ncs
  tailf:mount-id "cisco-iosxr-nc-7.3:cisco-iosxr-nc-7.3";
  tailf:ncs-device-type "netconf";

  namespace "http://cisco.com/ns/yang/Cisco-IOS-XR-flowspec-cfg";
  prefix flowspec-cfg;

  import Cisco-IOS-XR-types {
    prefix xr;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR flowspec package configuration.

     This module contains definitions
     for the following management objects:
       flow-spec: FlowSpec configuration

     This YANG module augments the
       Cisco-IOS-XR-ifmgr-cfg
     module with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Fs-vrf-af {
    type string;
    description
      "Fs vrf af";
  }

  typedef ncs_template_Fs-af-p {
    type string;
    description
      "Fs af p";
  }

  typedef ncs_template_Fs-addf {
    type string;
    description
      "Fs addf";
  }

  typedef ncs_template_Fs-vrf-af-p {
    type string;
    description
      "Fs vrf af p";
  }

  typedef ncs_rpc_notif_Fs-vrf-af {
    type enumeration {
      enum "ipv4" {
        value 1;
        description
          "IPv4 FlowSpec";
      }
      enum "ipv6" {
        value 2;
        description
          "IPv6 FlowSpec";
      }
    }
    description
      "Fs vrf af";
  }

  typedef ncs_rpc_notif_Fs-af-p {
    type enumeration {
      enum "pbr" {
        value 2;
        description
          "PBR policy type";
      }
    }
    description
      "Fs af p";
  }

  typedef ncs_rpc_notif_Fs-addf {
    type enumeration {
      enum "ipv4" {
        value 1;
        description
          "IPv4 FlowSpec";
      }
      enum "ipv6" {
        value 2;
        description
          "IPv6 FlowSpec";
      }
    }
    description
      "Fs addf";
  }

  typedef ncs_rpc_notif_Fs-vrf-af-p {
    type enumeration {
      enum "pbr" {
        value 2;
        description
          "PBR policy type";
      }
    }
    description
      "Fs vrf af p";
  }

  typedef live_ncs_Fs-vrf-af {
    type enumeration {
      enum "ipv4" {
        value 1;
        description
          "IPv4 FlowSpec";
      }
      enum "ipv6" {
        value 2;
        description
          "IPv6 FlowSpec";
      }
    }
    description
      "Fs vrf af";
  }

  typedef live_ncs_Fs-af-p {
    type enumeration {
      enum "pbr" {
        value 2;
        description
          "PBR policy type";
      }
    }
    description
      "Fs af p";
  }

  typedef live_ncs_Fs-addf {
    type enumeration {
      enum "ipv4" {
        value 1;
        description
          "IPv4 FlowSpec";
      }
      enum "ipv6" {
        value 2;
        description
          "IPv6 FlowSpec";
      }
    }
    description
      "Fs addf";
  }

  typedef live_ncs_Fs-vrf-af-p {
    type enumeration {
      enum "pbr" {
        value 2;
        description
          "PBR policy type";
      }
    }
    description
      "Fs vrf af p";
  }

  typedef Fs-vrf-af {
    type enumeration {
      enum "ipv4" {
        value 1;
        description
          "IPv4 FlowSpec";
      }
      enum "ipv6" {
        value 2;
        description
          "IPv6 FlowSpec";
      }
    }
    description
      "Fs vrf af";
  }

  typedef Fs-af-p {
    type enumeration {
      enum "pbr" {
        value 2;
        description
          "PBR policy type";
      }
    }
    description
      "Fs af p";
  }

  typedef Fs-addf {
    type enumeration {
      enum "ipv4" {
        value 1;
        description
          "IPv4 FlowSpec";
      }
      enum "ipv6" {
        value 2;
        description
          "IPv6 FlowSpec";
      }
    }
    description
      "Fs addf";
  }

  typedef Fs-vrf-af-p {
    type enumeration {
      enum "pbr" {
        value 2;
        description
          "PBR policy type";
      }
    }
    description
      "Fs vrf af p";
  }

  augment "/ncs:devices/ncs:device/ncs:config" {
    container flow-spec {
      tailf:ncs-device-type "netconf";
      tailf:display-when "not(../../ncs:module) or ../../ncs:module[ncs:name='Cisco-IOS-XR-flowspec-cfg']";
      description
        "FlowSpec configuration";
      container afs {
        description
          "Table of AF";
        list af {
          key "af-name";
          description
            "Address Family Identifier Type (IPv4/IPv6)";
          container service-policies {
            description
              "Table of ServicePolicy";
            list service-policy {
              key "policy-type policy-name";
              description
                "Service Policy configuration";
              leaf policy-type {
                type Fs-af-p;
                description
                  "Choose the Policy type";
              }
              leaf policy-name {
                type xr:Cisco-ios-xr-string;
                description
                  "Policy map name";
              }
              leaf local {
                type boolean;
                mandatory true;
                description
                  "Set constant integer";
              }
            }
          }
          leaf interface-all {
            type empty;
            description
              "Install FlowSpec policy on all interfaces";
          }
          leaf af-name {
            type Fs-addf;
            description
              "AFI type";
          }
        }
      }
      container vrfs {
        description
          "Table of VRF";
        list vrf {
          key "vrf-name";
          description
            "VRF configuration";
          container afs {
            description
              "Table of AF";
            list af {
              key "af-name";
              description
                "Address Family Identifier Type (IPv4/IPv6)";
              container service-policies {
                description
                  "Table of ServicePolicy";
                list service-policy {
                  key "policy-type policy-name";
                  description
                    "Service Policy configuration";
                  leaf policy-type {
                    type Fs-af-p;
                    description
                      "Choose the Policy type";
                  }
                  leaf policy-name {
                    type xr:Cisco-ios-xr-string;
                    description
                      "Policy map name";
                  }
                  leaf local {
                    type boolean;
                    mandatory true;
                    description
                      "Set constant integer";
                  }
                }
              }
              leaf interface-all {
                type empty;
                description
                  "Install FlowSpec policy on all interfaces";
              }
              leaf af-name {
                type Fs-vrf-af;
                description
                  "AFI type";
              }
            }
          }
          leaf vrf-name {
            type xr:Cisco-ios-xr-string {
              length "1..32";
            }
            description
              "VRF Name";
          }
        }
      }
      leaf enable {
        type empty;
        description
          "Enable FlowSpec configuration. Deletion of this
           object also causes deletion of all associated
           objects under FlowSpec.";
      }
      leaf interface-all {
        type empty;
        description
          "Install FlowSpec policy on all interfaces";
      }
    }
  }
  augment "/ncs:devices/ncs:device/ncs:live-status" {
    container flow-spec {
      tailf:ncs-device-type "netconf";
      tailf:display-when "not(../../ncs:module) or ../../ncs:module[ncs:name='Cisco-IOS-XR-flowspec-cfg'] or (../../ncs:live-status-protocol[not(ncs:capability)]) or (../../ncs:live-status-protocol/ncs:capability/ncs:module[.='Cisco-IOS-XR-flowspec-cfg'])";
      description
        "FlowSpec configuration";
      container afs {
        description
          "Table of AF";
        list af {
          key "af-name";
          description
            "Address Family Identifier Type (IPv4/IPv6)";
          container service-policies {
            description
              "Table of ServicePolicy";
            list service-policy {
              key "policy-type policy-name";
              description
                "Service Policy configuration";
              leaf policy-type {
                type live_ncs_Fs-af-p;
                description
                  "Choose the Policy type";
              }
              leaf policy-name {
                type xr:live_ncs_Cisco-ios-xr-string;
                description
                  "Policy map name";
              }
              leaf local {
                type boolean;
                // NCS drop mandatory statement
                description
                  "Set constant integer";
              }
            }
          }
          leaf interface-all {
            type empty;
            description
              "Install FlowSpec policy on all interfaces";
          }
          leaf af-name {
            type live_ncs_Fs-addf;
            description
              "AFI type";
          }
        }
      }
      container vrfs {
        description
          "Table of VRF";
        list vrf {
          key "vrf-name";
          description
            "VRF configuration";
          container afs {
            description
              "Table of AF";
            list af {
              key "af-name";
              description
                "Address Family Identifier Type (IPv4/IPv6)";
              container service-policies {
                description
                  "Table of ServicePolicy";
                list service-policy {
                  key "policy-type policy-name";
                  description
                    "Service Policy configuration";
                  leaf policy-type {
                    type live_ncs_Fs-af-p;
                    description
                      "Choose the Policy type";
                  }
                  leaf policy-name {
                    type xr:live_ncs_Cisco-ios-xr-string;
                    description
                      "Policy map name";
                  }
                  leaf local {
                    type boolean;
                    // NCS drop mandatory statement
                    description
                      "Set constant integer";
                  }
                }
              }
              leaf interface-all {
                type empty;
                description
                  "Install FlowSpec policy on all interfaces";
              }
              leaf af-name {
                type live_ncs_Fs-vrf-af;
                description
                  "AFI type";
              }
            }
          }
          leaf vrf-name {
            type xr:live_ncs_Cisco-ios-xr-string;
            description
              "VRF Name";
          }
        }
      }
      leaf enable {
        type empty;
        description
          "Enable FlowSpec configuration. Deletion of this
           object also causes deletion of all associated
           objects under FlowSpec.";
      }
      leaf interface-all {
        type empty;
        description
          "Install FlowSpec policy on all interfaces";
      }
    }
  }
  augment "/ncs:devices/ncs:template/ncs:ned-id/ncs:config" {
    container flow-spec {
      description
        "FlowSpec configuration";
      container afs {
        description
          "Table of AF";
        list af {
          // NCS patched for predictable order
          ordered-by user;
          key "af-name";
          description
            "Address Family Identifier Type (IPv4/IPv6)";
          container service-policies {
            description
              "Table of ServicePolicy";
            list service-policy {
              // NCS patched for predictable order
              ordered-by user;
              key "policy-type policy-name";
              description
                "Service Policy configuration";
              leaf policy-type {
                type ncs_template_Fs-af-p;
                description
                  "Choose the Policy type";
              }
              leaf policy-name {
                type xr:ncs_template_Cisco-ios-xr-string;
                description
                  "Policy map name";
              }
              leaf local {
                type string;
                // NCS drop mandatory statement
                description
                  "Set constant integer";
              }
            }
          }
          leaf interface-all {
            type empty;
            description
              "Install FlowSpec policy on all interfaces";
          }
          leaf af-name {
            type ncs_template_Fs-addf;
            description
              "AFI type";
          }
        }
      }
      container vrfs {
        description
          "Table of VRF";
        list vrf {
          // NCS patched for predictable order
          ordered-by user;
          key "vrf-name";
          description
            "VRF configuration";
          container afs {
            description
              "Table of AF";
            list af {
              // NCS patched for predictable order
              ordered-by user;
              key "af-name";
              description
                "Address Family Identifier Type (IPv4/IPv6)";
              container service-policies {
                description
                  "Table of ServicePolicy";
                list service-policy {
                  // NCS patched for predictable order
                  ordered-by user;
                  key "policy-type policy-name";
                  description
                    "Service Policy configuration";
                  leaf policy-type {
                    type ncs_template_Fs-af-p;
                    description
                      "Choose the Policy type";
                  }
                  leaf policy-name {
                    type xr:ncs_template_Cisco-ios-xr-string;
                    description
                      "Policy map name";
                  }
                  leaf local {
                    type string;
                    // NCS drop mandatory statement
                    description
                      "Set constant integer";
                  }
                }
              }
              leaf interface-all {
                type empty;
                description
                  "Install FlowSpec policy on all interfaces";
              }
              leaf af-name {
                type ncs_template_Fs-vrf-af;
                description
                  "AFI type";
              }
            }
          }
          leaf vrf-name {
            type xr:ncs_template_Cisco-ios-xr-string;
            description
              "VRF Name";
          }
        }
      }
      leaf enable {
        type empty;
        description
          "Enable FlowSpec configuration. Deletion of this
           object also causes deletion of all associated
           objects under FlowSpec.";
      }
      leaf interface-all {
        type empty;
        description
          "Install FlowSpec policy on all interfaces";
      }
    }
  }
  augment "/ncs:devices/ncs:template/ncs:ned-id/ncs:config/a1:interface-configurations/a1:interface-configuration" {
    description
      "This augment extends the configuration data of
       'Cisco-IOS-XR-ifmgr-cfg'";
    container ipv4-flow-spec {
      description
        "Flowspec on IPv4 interface";
      leaf enabled {
        type empty;
        description
          "Disable FlowSpec on this interface";
      }
    }
  }
  augment "/ncs:devices/ncs:device/ncs:live-status/a1:interface-configurations/a1:interface-configuration" {
    description
      "This augment extends the configuration data of
       'Cisco-IOS-XR-ifmgr-cfg'";
    container ipv4-flow-spec {
      tailf:ncs-device-type "netconf";
      tailf:display-when "not(../../../../ncs:module) or ../../../../ncs:module[ncs:name='Cisco-IOS-XR-flowspec-cfg'] or (../../../../ncs:live-status-protocol[not(ncs:capability)]) or (../../../../ncs:live-status-protocol/ncs:capability/ncs:module[.='Cisco-IOS-XR-flowspec-cfg'])";
      description
        "Flowspec on IPv4 interface";
      leaf enabled {
        type empty;
        description
          "Disable FlowSpec on this interface";
      }
    }
  }
  augment "/ncs:devices/ncs:device/ncs:config/a1:interface-configurations/a1:interface-configuration" {
    description
      "This augment extends the configuration data of
       'Cisco-IOS-XR-ifmgr-cfg'";
    container ipv4-flow-spec {
      tailf:ncs-device-type "netconf";
      tailf:display-when "not(../../../../ncs:module) or ../../../../ncs:module[ncs:name='Cisco-IOS-XR-flowspec-cfg']";
      description
        "Flowspec on IPv4 interface";
      leaf enabled {
        type empty;
        description
          "Disable FlowSpec on this interface";
      }
    }
  }
  augment "/ncs:devices/ncs:template/ncs:ned-id/ncs:config/a1:interface-configurations/a1:interface-configuration" {
    description
      "This augment extends the configuration data of
       'Cisco-IOS-XR-ifmgr-cfg'";
    container ipv6-flow-spec {
      description
        "Flowspec on IPv6 interface";
      leaf enabled {
        type empty;
        description
          "Disable flowspec on interface";
      }
    }
  }
  augment "/ncs:devices/ncs:device/ncs:live-status/a1:interface-configurations/a1:interface-configuration" {
    description
      "This augment extends the configuration data of
       'Cisco-IOS-XR-ifmgr-cfg'";
    container ipv6-flow-spec {
      tailf:ncs-device-type "netconf";
      tailf:display-when "not(../../../../ncs:module) or ../../../../ncs:module[ncs:name='Cisco-IOS-XR-flowspec-cfg'] or (../../../../ncs:live-status-protocol[not(ncs:capability)]) or (../../../../ncs:live-status-protocol/ncs:capability/ncs:module[.='Cisco-IOS-XR-flowspec-cfg'])";
      description
        "Flowspec on IPv6 interface";
      leaf enabled {
        type empty;
        description
          "Disable flowspec on interface";
      }
    }
  }
  augment "/ncs:devices/ncs:device/ncs:config/a1:interface-configurations/a1:interface-configuration" {
    description
      "This augment extends the configuration data of
       'Cisco-IOS-XR-ifmgr-cfg'";
    container ipv6-flow-spec {
      tailf:ncs-device-type "netconf";
      tailf:display-when "not(../../../../ncs:module) or ../../../../ncs:module[ncs:name='Cisco-IOS-XR-flowspec-cfg']";
      description
        "Flowspec on IPv6 interface";
      leaf enabled {
        type empty;
        description
          "Disable flowspec on interface";
      }
    }
  }
}

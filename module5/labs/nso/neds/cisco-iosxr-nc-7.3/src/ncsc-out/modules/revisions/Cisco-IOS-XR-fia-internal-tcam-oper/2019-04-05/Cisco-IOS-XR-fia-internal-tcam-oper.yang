module Cisco-IOS-XR-fia-internal-tcam-oper {
  // Generated by yanger -t ncs
  tailf:mount-id "cisco-iosxr-nc-7.3:cisco-iosxr-nc-7.3";
  tailf:ncs-device-type "netconf";

  namespace "http://cisco.com/ns/yang/Cisco-IOS-XR-fia-internal-tcam-oper";
  prefix fia-internal-tcam-oper;

  import Cisco-IOS-XR-types {
    prefix xr;
  }
  import cisco-semver {
    prefix semver;
  }
  include Cisco-IOS-XR-fia-internal-tcam-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fia-internal-tcam package operational data.

     This module contains definitions
     for the following management objects:
       controller: Controller Resources

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container controller
  }
  augment "/ncs:devices/ncs:device/ncs:live-status" {
    container controller {
      tailf:ncs-device-type "netconf";
      tailf:display-when "not(../../ncs:module) or ../../ncs:module[ncs:name='Cisco-IOS-XR-fia-internal-tcam-oper'] or (../../ncs:live-status-protocol[not(ncs:capability)]) or (../../ncs:live-status-protocol/ncs:capability/ncs:module[.='Cisco-IOS-XR-fia-internal-tcam-oper'])";
      description
        "Controller Resources";
      container dpa {
        description
          "Controller DPA operational data";
        container nodes {
          description
            "DPA data for available nodes";
          list node {
            key "node-name";
            description
              "DPA operational data for a particular node";
            container external-tcam-resources {
              description
                "External TCAM Resource Information";
              uses live_ncs_FIA-CARD-TCAM;
            }
            container internal-tcam-resources {
              description
                "Internal TCAM Resource Information";
              uses live_ncs_FIA-CARD-TCAM;
            }
            leaf node-name {
              type xr:live_ncs_Node-id;
              description
                "Node ID";
            }
          }
        }
      }
    }
  }
  augment "/ncs:devices/ncs:template/ncs:ned-id/ncs:config" {
    // NCS drop config false container controller
  }
}

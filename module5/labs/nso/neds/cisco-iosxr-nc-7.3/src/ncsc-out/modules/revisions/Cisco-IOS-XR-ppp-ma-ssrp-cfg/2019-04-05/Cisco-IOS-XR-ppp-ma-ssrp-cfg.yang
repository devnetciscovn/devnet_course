module Cisco-IOS-XR-ppp-ma-ssrp-cfg {
  // Generated by yanger -t ncs
  tailf:mount-id "cisco-iosxr-nc-7.3:cisco-iosxr-nc-7.3";
  tailf:ncs-device-type "netconf";

  namespace "http://cisco.com/ns/yang/Cisco-IOS-XR-ppp-ma-ssrp-cfg";
  prefix ppp-ma-ssrp-cfg;

  import ietf-inet-types {
    prefix inet;
  }
  import Cisco-IOS-XR-types {
    prefix xr;
  }
  import cisco-semver {
    prefix semver;
  }
  import Cisco-IOS-XR-config-mda-cfg {
    prefix a1;
  }
  import Cisco-IOS-XR-ifmgr-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ppp-ma-ssrp package configuration.

     This module contains definitions
     for the following management objects:
       ssrp: Shared plane SSRP configuration data

     This YANG module augments the
       Cisco-IOS-XR-config-mda-cfg,
       Cisco-IOS-XR-ifmgr-cfg
     modules with configuration data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    container ssrp {
      tailf:ncs-device-type "netconf";
      tailf:display-when "not(../../ncs:module) or ../../ncs:module[ncs:name='Cisco-IOS-XR-ppp-ma-ssrp-cfg']";
      description
        "Shared plane SSRP configuration data";
      container profiles {
        description
          "Table of SSRP Profiles";
        list profile {
          key "name";
          description
            "SSRP Profile configuration";
          leaf max-hops {
            type uint32 {
              range "1..255";
            }
            description
              "This specifies the maximum number of hops for
               packets on the SSO channel";
          }
          leaf peer-ipv4-address {
            type inet:ipv4-address-no-zone;
            description
              "This specifies the remote end's IPv4-address
               for the SSO channel";
          }
          leaf name {
            type xr:Cisco-ios-xr-string;
            description
              "The name of the profile";
          }
        }
      }
    }
  }
  augment "/ncs:devices/ncs:device/ncs:live-status" {
    container ssrp {
      tailf:ncs-device-type "netconf";
      tailf:display-when "not(../../ncs:module) or ../../ncs:module[ncs:name='Cisco-IOS-XR-ppp-ma-ssrp-cfg'] or (../../ncs:live-status-protocol[not(ncs:capability)]) or (../../ncs:live-status-protocol/ncs:capability/ncs:module[.='Cisco-IOS-XR-ppp-ma-ssrp-cfg'])";
      description
        "Shared plane SSRP configuration data";
      container profiles {
        description
          "Table of SSRP Profiles";
        list profile {
          key "name";
          description
            "SSRP Profile configuration";
          leaf max-hops {
            type uint32 {
              range "1..255";
            }
            description
              "This specifies the maximum number of hops for
               packets on the SSO channel";
          }
          leaf peer-ipv4-address {
            type inet:ipv4-address-no-zone;
            description
              "This specifies the remote end's IPv4-address
               for the SSO channel";
          }
          leaf name {
            type xr:live_ncs_Cisco-ios-xr-string;
            description
              "The name of the profile";
          }
        }
      }
    }
  }
  augment "/ncs:devices/ncs:template/ncs:ned-id/ncs:config" {
    container ssrp {
      description
        "Shared plane SSRP configuration data";
      container profiles {
        description
          "Table of SSRP Profiles";
        list profile {
          // NCS patched for predictable order
          ordered-by user;
          key "name";
          description
            "SSRP Profile configuration";
          leaf max-hops {
            type string;
            description
              "This specifies the maximum number of hops for
               packets on the SSO channel";
          }
          leaf peer-ipv4-address {
            type string;
            description
              "This specifies the remote end's IPv4-address
               for the SSO channel";
          }
          leaf name {
            type xr:ncs_template_Cisco-ios-xr-string;
            description
              "The name of the profile";
          }
        }
      }
    }
  }
  augment "/ncs:devices/ncs:template/ncs:ned-id/ncs:config/a2:interface-configurations/a2:interface-configuration" {
    description
      "This augment extends the configuration data of
       'Cisco-IOS-XR-ifmgr-cfg'";
    container ssrp-session {
      description
        "SSRP Config";
      container group-id {
        description
          "This specifies the SSRP group and session-id";
        leaf group {
          type string;
          description
            "SSRP Group-ID";
        }
        leaf id {
          type string;
          description
            "SSRP Session-ID";
        }
      }
    }
  }
  augment "/ncs:devices/ncs:device/ncs:live-status/a2:interface-configurations/a2:interface-configuration" {
    description
      "This augment extends the configuration data of
       'Cisco-IOS-XR-ifmgr-cfg'";
    container ssrp-session {
      tailf:ncs-device-type "netconf";
      tailf:display-when "not(../../../../ncs:module) or ../../../../ncs:module[ncs:name='Cisco-IOS-XR-ppp-ma-ssrp-cfg'] or (../../../../ncs:live-status-protocol[not(ncs:capability)]) or (../../../../ncs:live-status-protocol/ncs:capability/ncs:module[.='Cisco-IOS-XR-ppp-ma-ssrp-cfg'])";
      description
        "SSRP Config";
      container group-id {
        description
          "This specifies the SSRP group and session-id";
        leaf group {
          type uint32 {
            range "1..65535";
          }
          description
            "SSRP Group-ID";
        }
        leaf id {
          type uint32 {
            range "1..4294967295";
          }
          description
            "SSRP Session-ID";
        }
      }
    }
  }
  augment "/ncs:devices/ncs:device/ncs:config/a2:interface-configurations/a2:interface-configuration" {
    description
      "This augment extends the configuration data of
       'Cisco-IOS-XR-ifmgr-cfg'";
    container ssrp-session {
      tailf:ncs-device-type "netconf";
      tailf:display-when "not(../../../../ncs:module) or ../../../../ncs:module[ncs:name='Cisco-IOS-XR-ppp-ma-ssrp-cfg']";
      description
        "SSRP Config";
      container group-id {
        description
          "This specifies the SSRP group and session-id";
        leaf group {
          type uint32 {
            range "1..65535";
          }
          description
            "SSRP Group-ID";
        }
        leaf id {
          type uint32 {
            range "1..4294967295";
          }
          description
            "SSRP Session-ID";
        }
      }
    }
  }
  augment "/ncs:devices/ncs:template/ncs:ned-id/ncs:config/a1:active-nodes/a1:active-node" {
    description
      "This augment extends the configuration data of
       'Cisco-IOS-XR-config-mda-cfg'";
    container ssrp-group {
      description
        "Per-node SSRP configuration data";
      container groups {
        description
          "Table of SSRP Group configuration";
        list group {
          // NCS patched for predictable order
          ordered-by user;
          key "group-id";
          description
            "SSRP Group configuration";
          leaf profile {
            type string;
            description
              "This specifies the SSRP profile to use for
               this group";
          }
          leaf group-id {
            type string;
            description
              "The identifier for this group";
          }
        }
      }
    }
  }
  augment "/ncs:devices/ncs:device/ncs:live-status/a1:active-nodes/a1:active-node" {
    description
      "This augment extends the configuration data of
       'Cisco-IOS-XR-config-mda-cfg'";
    container ssrp-group {
      tailf:ncs-device-type "netconf";
      tailf:display-when "not(../../../../ncs:module) or ../../../../ncs:module[ncs:name='Cisco-IOS-XR-ppp-ma-ssrp-cfg'] or (../../../../ncs:live-status-protocol[not(ncs:capability)]) or (../../../../ncs:live-status-protocol/ncs:capability/ncs:module[.='Cisco-IOS-XR-ppp-ma-ssrp-cfg'])";
      description
        "Per-node SSRP configuration data";
      container groups {
        description
          "Table of SSRP Group configuration";
        list group {
          key "group-id";
          description
            "SSRP Group configuration";
          leaf profile {
            type string;
            description
              "This specifies the SSRP profile to use for
               this group";
          }
          leaf group-id {
            type uint32 {
              range "1..65535";
            }
            description
              "The identifier for this group";
          }
        }
      }
    }
  }
  augment "/ncs:devices/ncs:device/ncs:config/a1:active-nodes/a1:active-node" {
    description
      "This augment extends the configuration data of
       'Cisco-IOS-XR-config-mda-cfg'";
    container ssrp-group {
      tailf:ncs-device-type "netconf";
      tailf:display-when "not(../../../../ncs:module) or ../../../../ncs:module[ncs:name='Cisco-IOS-XR-ppp-ma-ssrp-cfg']";
      description
        "Per-node SSRP configuration data";
      container groups {
        description
          "Table of SSRP Group configuration";
        list group {
          key "group-id";
          description
            "SSRP Group configuration";
          leaf profile {
            type string;
            description
              "This specifies the SSRP profile to use for
               this group";
          }
          leaf group-id {
            type uint32 {
              range "1..65535";
            }
            description
              "The identifier for this group";
          }
        }
      }
    }
  }
}

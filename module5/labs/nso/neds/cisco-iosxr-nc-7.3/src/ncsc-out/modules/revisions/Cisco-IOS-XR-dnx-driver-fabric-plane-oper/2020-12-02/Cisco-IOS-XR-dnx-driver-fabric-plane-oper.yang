module Cisco-IOS-XR-dnx-driver-fabric-plane-oper {
  // Generated by yanger -t ncs
  tailf:mount-id "cisco-iosxr-nc-7.3:cisco-iosxr-nc-7.3";
  tailf:ncs-device-type "netconf";

  namespace "http://cisco.com/ns/yang/Cisco-IOS-XR-dnx-driver-fabric-plane-oper";
  prefix dnx-driver-fabric-plane-oper;

  import cisco-semver {
    prefix semver;
  }
  include Cisco-IOS-XR-dnx-driver-fabric-plane-oper-sub1 {
    revision-date 2020-12-02;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dnx-driver-fabric-plane package operational data.

     This module contains definitions
     for the following management objects:
       fabric: Admin fabric oper data

     Copyright (c) 2013-2020 by Cisco Systems, Inc.
     All rights reserved.";

  revision 2020-12-02 {
    description
      "added Ucast_lost_cells,Mcast_lost_cells and Asic_internal_drops for fsdb_plane_stats_info bag.";
    semver:module-version "1.1.0";
  }
  revision 2019-04-05 {
    description
      "Establish semantic version baseline.";
    semver:module-version "1.0.1";
  }
  revision 2015-11-09 {
    description
      "IOS XR 6.0 revision.";
  }

  augment "/ncs:devices/ncs:device/ncs:config" {
    // NCS drop config false container fabric
  }
  augment "/ncs:devices/ncs:device/ncs:live-status" {
    container fabric {
      tailf:ncs-device-type "netconf";
      tailf:display-when "not(../../ncs:module) or ../../ncs:module[ncs:name='Cisco-IOS-XR-dnx-driver-fabric-plane-oper'] or (../../ncs:live-status-protocol[not(ncs:capability)]) or (../../ncs:live-status-protocol/ncs:capability/ncs:module[.='Cisco-IOS-XR-dnx-driver-fabric-plane-oper'])";
      description
        "Admin fabric oper data";
      container plane-table {
        description
          "Plane state table for Fabric ";
        container statistics {
          description
            "Show Calvados Plane Statistics";
          uses live_ncs_FSDBB-PLANE-STATS-INFO-XML;
        }
        container plane {
          description
            "Show Calvados Plane State";
          uses live_ncs_FSDBB-PLANE-INFO-XML;
        }
      }
    }
  }
  augment "/ncs:devices/ncs:template/ncs:ned-id/ncs:config" {
    // NCS drop config false container fabric
  }
}

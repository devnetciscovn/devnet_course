module Cisco-IOS-XR-sysadmin-fabric-driver-sfe-ncs5500 {
  // Generated by yanger -t ncs
  tailf:mount-id "cisco-iosxr-nc-7.3:cisco-iosxr-nc-7.3";
  tailf:ncs-device-type "netconf";

  namespace "http://www.cisco.com/ns/yang/Cisco-IOS-XR-sysadmin-fabric-driver-sfe-ncs5500";
  prefix fabric_sfe;

  import Cisco-IOS-XR-sysadmin-fabric-types {
    prefix fabric-types;
  }
  import Cisco-IOS-XR-sysadmin-show-trace {
    prefix show-trace;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2020-07-29 {
    description
      "Implemented single fabric-type model for all platform";
    semver:module-version "2.0.0";
  }
  revision 2020-05-08 {
    description
      "Removed the usage of link_cxp_port, link_cxp_lane and asic_cardname";
    semver:module-version "1.0.0";
  }
  revision 2019-07-01 {
    description
      "Namespace and module name changed to sepcify NCS5500 platform";
    semver:module-version "1.0.0";
  }
  revision 2019-04-15 {
    description
      "Establish semantic version baseline.";
  }
  revision 2018-04-09 {
    description
      "Required changes for ConfD 6.4.5";
  }
  revision 2017-09-30 {
    description
      "Add fsm-state as a leaf to ensure compilation";
  }
  revision 2017-05-01 {
    description
      "Namespace change to comply with Cisco guidelines on namespace";
  }

  grouping ncs_template_sfe_drvr_info {
    list drvr_info {
      // NCS patched for predictable order
      ordered-by user;
      key "idx";
      leaf idx {
        type string;
      }
      leaf drv_version {
        type string;
      }
      leaf coeff_major_rev {
        type string;
      }
      leaf coeff_minor_rev {
        type string;
      }
      leaf func_role {
        type string;
      }
      leaf issu_role {
        type string;
      }
      leaf rack_name {
        type string;
      }
      leaf rack_type {
        type string;
      }
      leaf rack_num {
        type string;
      }
      leaf ip_address {
        type string;
      }
      leaf card_avail_mask {
        type string;
      }
      leaf asic_avail_mask {
        type string;
      }
      leaf exp_asic_avail_mask {
        type string;
      }
      leaf ucmc_ratio {
        type string;
      }
      leaf pm_conn_active {
        type string;
      }
      leaf platform_local_conn_active {
        type string;
      }
      leaf fsdb_conn_active {
        type string;
      }
      leaf fgid_conn_active {
        type string;
      }
      leaf cm_conn_active {
        type string;
      }
      leaf ccc_conn_active {
        type string;
      }
      leaf issu_mgr_conn_active {
        type string;
      }
      leaf peer_sfe_conn_active {
        type string;
      }
      leaf cxp_conn_active {
        type string;
      }
      leaf pm_reg_active {
        type string;
      }
      leaf platform_local_reg_active {
        type string;
      }
      leaf fsdb_reg_active {
        type string;
      }
      leaf fgid_reg_active {
        type string;
      }
      leaf cm_reg_active {
        type string;
      }
      leaf issu_mgr_reg_active {
        type string;
      }
      leaf peer_sfe_reg_active {
        type string;
      }
      leaf cxp_reg_active {
        type string;
      }
      leaf num_pm_conn_reqs {
        type string;
      }
      leaf num_platform_local_conn_reqs {
        type string;
      }
      leaf num_fsdb_conn_reqs {
        type string;
      }
      leaf num_fgid_conn_reqs {
        type string;
      }
      leaf num_fstats_conn_reqs {
        type string;
      }
      leaf num_cm_conn_reqs {
        type string;
      }
      leaf num_ccc_conn_reqs {
        type string;
      }
      leaf num_issu_mgr_conn_reqs {
        type string;
      }
      leaf num_peer_sfe_conn_reqs {
        type string;
      }
      leaf num_cxp_conn_reqs {
        type string;
      }
      leaf is_gaspp_registered {
        type string;
      }
      leaf is_cih_registered {
        type string;
      }
      leaf startup_time {
        type string;
      }
      list asic_list {
        // NCS patched for predictable order
        ordered-by user;
        key "asic_idx";
        leaf asic_idx {
          type string;
        }
        leaf asic_instance {
          type string;
        }
        leaf card_present {
          type string;
        }
        leaf card_powered {
          type string;
        }
        leaf hotplug_event {
          type string;
        }
        leaf asic_type {
          type string;
        }
        leaf asic_cardname {
          type string;
        }
        leaf admin-state {
          type string;
        }
        leaf oper_state {
          type string;
        }
        leaf fab_plane {
          type string;
        }
        leaf fab_group {
          type string;
        }
        leaf fgid_download {
          type string;
        }
        leaf asic_state {
          type string;
        }
        leaf asic_disconnect_signal {
          type string;
        }
        leaf last_init_cause {
          type string;
        }
        leaf num_pon_resets {
          type string;
        }
        leaf num_hard_resets {
          type string;
        }
      }
    }
  }

  grouping ncs_template_sfe_link_info_asic_instance {
    list instance {
      // NCS patched for predictable order
      ordered-by user;
      key "instance-id";
      leaf instance-id {
        type fabric-types:ncs_template_sfe_instance_type_ncs5500;
      }
      leaf nodeid_str {
        type string;
      }
      leaf is_show {
        type string;
      }
      list link_idx_list {
        // NCS patched for predictable order
        ordered-by user;
        key "link_idx";
        leaf link_idx {
          type string;
        }
        leaf link_id_str {
          type string;
        }
        leaf phy_link {
          type string;
        }
        leaf speed {
          type string;
        }
        leaf stage {
          type string;
        }
        leaf fab_plane {
          type string;
        }
        leaf fab_group {
          type string;
        }
        leaf flap_cnt {
          type string;
        }
        leaf num_admin_shuts {
          type string;
        }
        leaf admin-state {
          type string;
        }
        leaf oper_state {
          type string;
        }
        leaf flags {
          type string;
        }
        leaf far_end_link_fsdb {
          type string;
        }
        leaf far_end_link_hw {
          type string;
        }
        leaf link_cxp_port {
          type string;
        }
        leaf link_cxp_lane {
          type string;
        }
        leaf coeff1 {
          type string;
        }
        leaf coeff2 {
          type string;
        }
        leaf fsm_state {
          type string;
        }
        leaf TX_Control_cells_counter {
          type string;
        }
        leaf TX_Data_cell_counter {
          type string;
        }
        leaf TX_Data_byte_counter {
          type string;
        }
        leaf TX_BEC_retransmit {
          type string;
        }
        leaf TX_Asyn_fifo_rate {
          type string;
        }
        leaf RX_Control_cells_counter {
          type string;
        }
        leaf RX_Data_cell_counter {
          type string;
        }
        leaf RX_Data_byte_counter {
          type string;
        }
        leaf RX_BEC_retransmit {
          type string;
        }
        leaf RX_Asyn_fifo_rate {
          type string;
        }
        leaf RX_CRC_errors_counter {
          type string;
        }
        leaf RX_LFEC_FEC_correctable_error {
          type string;
        }
        leaf RX_LFEC_FEC_uncorrectable_errors {
          type string;
        }
        leaf RX_dropped_retransmitted_control {
          type string;
        }
        list history {
          // NCS patched for predictable order
          ordered-by user;
          key "history_idx";
          leaf history_idx {
            type string;
          }
          leaf time_stamp {
            type string;
          }
          leaf admin-state {
            type string;
          }
          leaf oper_state {
            type string;
          }
          leaf error_state {
            type string;
          }
          leaf down_reasons {
            type string;
          }
        }
      }
    }
  }

  grouping ncs_template_sfe_link_info_stats_asic_instance {
    container stats {
      container data {
        uses ncs_template_sfe_link_info_asic_instance;
      }
      container ctrl {
        uses ncs_template_sfe_link_info_asic_instance;
      }
      container all {
        uses ncs_template_sfe_link_info_asic_instance;
      }
    }
  }

  grouping ncs_template_sfe_statistics_asic_instance {
    list instance {
      // NCS patched for predictable order
      ordered-by user;
      key "instance-id";
      leaf instance-id {
        type fabric-types:ncs_template_sfe_instance_type_ncs5500;
      }
      leaf stats_output {
        type string;
      }
    }
  }

  grouping ncs_template_sfe_trace {
    container sfe_driver {
      uses show-trace:ncs_template_traceable;
    }
  }

  grouping ncs_template_sfe_parse_link_instance {
    list instance {
      // NCS patched for predictable order
      ordered-by user;
      key "instance-id";
      leaf instance-id {
        type fabric-types:ncs_template_sfe_instance_type_ncs5500;
      }
      leaf is_show {
        type string;
      }
      list link_idx_list {
        // NCS patched for predictable order
        ordered-by user;
        key "link_idx";
        leaf link_idx {
          type string;
        }
        leaf rack_id_str {
          type string;
        }
        leaf slot_id_str {
          type string;
        }
        leaf asic_inst_id {
          type string;
        }
        leaf link_num_id {
          type string;
        }
        leaf log_slot {
          type string;
        }
        leaf phy_slot {
          type string;
        }
        leaf fap_id {
          type string;
        }
        leaf unit {
          type string;
        }
        leaf sfi_id {
          type string;
        }
        leaf ip_addr {
          type string;
        }
        leaf driver_run {
          type string;
        }
      }
    }
  }

  grouping ncs_template_sfe {
    container sfe {
      description
        "Fabric SFE driver commands";
      container driver {
        list location {
          // NCS patched for predictable order
          ordered-by user;
          key "loc_str";
          leaf loc_str {
            type fabric-types:ncs_template_sfe_location_type_ncs5500;
          }
          leaf description {
            type string;
            // NCS drop default statement
          }
          uses ncs_template_sfe_drvr_info;
        }
      }
      container statistics {
        list location {
          // NCS patched for predictable order
          ordered-by user;
          key "loc_str";
          leaf loc_str {
            type fabric-types:ncs_template_sfe_location_type_ncs5500;
          }
          leaf description {
            type string;
            // NCS drop default statement
          }
          list asic_types {
            // NCS patched for predictable order
            ordered-by user;
            key "asicname";
            leaf asicname {
              type string;
            }
            list block {
              // NCS patched for predictable order
              ordered-by user;
              key "blockname";
              leaf blockname {
                type string;
              }
              uses ncs_template_sfe_statistics_asic_instance;
            }
          }
        }
      }
      container link-info {
        list location {
          // NCS patched for predictable order
          ordered-by user;
          key "loc_str";
          leaf loc_str {
            type fabric-types:ncs_template_sfe_location_type_ncs5500;
          }
          leaf description {
            type string;
            // NCS drop default statement
          }
          list rx {
            // NCS patched for predictable order
            ordered-by user;
            key "start end";
            leaf start {
              type fabric-types:ncs_template_sfe_link_type;
            }
            leaf end {
              type fabric-types:ncs_template_sfe_link_type;
            }
            container detail {
              container topo {
                uses ncs_template_sfe_link_info_asic_instance;
              }
              container flap {
                uses ncs_template_sfe_link_info_asic_instance;
              }
            }
            container topo {
              uses ncs_template_sfe_link_info_asic_instance;
            }
            container flap {
              uses ncs_template_sfe_link_info_asic_instance;
            }
            uses ncs_template_sfe_link_info_stats_asic_instance;
          }
          list tx {
            // NCS patched for predictable order
            ordered-by user;
            key "start end";
            leaf start {
              type fabric-types:ncs_template_sfe_link_type;
            }
            leaf end {
              type fabric-types:ncs_template_sfe_link_type;
            }
            container detail {
              uses ncs_template_sfe_link_info_asic_instance;
            }
            uses ncs_template_sfe_link_info_asic_instance;
            uses ncs_template_sfe_link_info_stats_asic_instance;
          }
        }
      }
      container diagshell {
        list location {
          // NCS patched for predictable order
          ordered-by user;
          key "loc_str";
          leaf loc_str {
            type fabric-types:ncs_template_sfe_location_type_ncs5500;
          }
          leaf description {
            type string;
            // NCS drop default statement
          }
          list instance {
            // NCS patched for predictable order
            ordered-by user;
            key "instance_num";
            leaf instance_num {
              type fabric-types:ncs_template_fabric_diag_shell_instance_num_type;
            }
            list diag_cmd {
              // NCS patched for predictable order
              ordered-by user;
              key "cmd_str";
              leaf cmd_str {
                type fabric-types:ncs_template_fabric_diag_shell_cmd_type;
              }
              list bytes {
                // NCS patched for predictable order
                ordered-by user;
                key "byte_idx";
                leaf byte_idx {
                  type string;
                }
                leaf data {
                  type string;
                }
              }
            }
          }
        }
      }
      container register {
        list location {
          // NCS patched for predictable order
          ordered-by user;
          key "loc_str";
          leaf loc_str {
            type fabric-types:ncs_template_sfe_location_type_ncs5500;
          }
          leaf description {
            type string;
            // NCS drop default statement
          }
          list instance {
            // NCS patched for predictable order
            ordered-by user;
            key "instance_num";
            leaf instance_num {
              type fabric-types:ncs_template_fabric_diag_shell_instance_num_type;
            }
            list bytes {
              // NCS patched for predictable order
              ordered-by user;
              key "byte_idx";
              leaf byte_idx {
                type string;
              }
              leaf data {
                type string;
              }
            }
          }
        }
      }
      container dump-file {
        list location {
          // NCS patched for predictable order
          ordered-by user;
          key "loc_str";
          leaf loc_str {
            type fabric-types:ncs_template_sfe_location_type_ncs5500;
          }
          leaf description {
            type string;
            // NCS drop default statement
          }
          list file {
            // NCS patched for predictable order
            ordered-by user;
            key "file_name";
            leaf file_name {
              type string;
            }
            list bytes {
              // NCS patched for predictable order
              ordered-by user;
              key "byte_idx";
              leaf byte_idx {
                type string;
              }
              leaf data {
                type string;
              }
            }
          }
        }
      }
      container parse {
        list location {
          // NCS patched for predictable order
          ordered-by user;
          key "loc_str";
          leaf loc_str {
            type fabric-types:ncs_template_sfe_location_type_ncs5500;
          }
          leaf description {
            type string;
            // NCS drop default statement
          }
          list link {
            // NCS patched for predictable order
            ordered-by user;
            key "start end";
            leaf start {
              type fabric-types:ncs_template_sfe_link_type;
            }
            leaf end {
              type fabric-types:ncs_template_sfe_link_type;
            }
            uses ncs_template_sfe_parse_link_instance;
          }
        }
      }
    }
    container sfe_trace {
      uses ncs_template_sfe_trace;
    }
  }

  grouping ncs_rpc_notif_sfe_drvr_info {
    list drvr_info {
      key "idx";
      leaf idx {
        type int32;
      }
      leaf drv_version {
        type uint32;
      }
      leaf coeff_major_rev {
        type uint32;
      }
      leaf coeff_minor_rev {
        type uint32;
      }
      leaf func_role {
        type string;
      }
      leaf issu_role {
        type string;
      }
      leaf rack_name {
        type string;
      }
      leaf rack_type {
        type string;
      }
      leaf rack_num {
        type string;
      }
      leaf ip_address {
        type string;
      }
      leaf card_avail_mask {
        type uint32;
      }
      leaf asic_avail_mask {
        type uint64;
      }
      leaf exp_asic_avail_mask {
        type uint64;
      }
      leaf ucmc_ratio {
        type uint32;
      }
      leaf pm_conn_active {
        type boolean;
      }
      leaf platform_local_conn_active {
        type boolean;
      }
      leaf fsdb_conn_active {
        type boolean;
      }
      leaf fgid_conn_active {
        type boolean;
      }
      leaf cm_conn_active {
        type boolean;
      }
      leaf ccc_conn_active {
        type boolean;
      }
      leaf issu_mgr_conn_active {
        type boolean;
      }
      leaf peer_sfe_conn_active {
        type boolean;
      }
      leaf cxp_conn_active {
        type boolean;
      }
      leaf pm_reg_active {
        type boolean;
      }
      leaf platform_local_reg_active {
        type boolean;
      }
      leaf fsdb_reg_active {
        type boolean;
      }
      leaf fgid_reg_active {
        type boolean;
      }
      leaf cm_reg_active {
        type boolean;
      }
      leaf issu_mgr_reg_active {
        type boolean;
      }
      leaf peer_sfe_reg_active {
        type boolean;
      }
      leaf cxp_reg_active {
        type boolean;
      }
      leaf num_pm_conn_reqs {
        type uint8;
      }
      leaf num_platform_local_conn_reqs {
        type uint8;
      }
      leaf num_fsdb_conn_reqs {
        type uint8;
      }
      leaf num_fgid_conn_reqs {
        type uint8;
      }
      leaf num_fstats_conn_reqs {
        type uint8;
      }
      leaf num_cm_conn_reqs {
        type uint8;
      }
      leaf num_ccc_conn_reqs {
        type uint8;
      }
      leaf num_issu_mgr_conn_reqs {
        type uint8;
      }
      leaf num_peer_sfe_conn_reqs {
        type uint8;
      }
      leaf num_cxp_conn_reqs {
        type uint8;
      }
      leaf is_gaspp_registered {
        type boolean;
      }
      leaf is_cih_registered {
        type boolean;
      }
      leaf startup_time {
        type string;
      }
      list asic_list {
        key "asic_idx";
        leaf asic_idx {
          type uint32;
        }
        leaf asic_instance {
          type string;
        }
        leaf card_present {
          type string;
        }
        leaf card_powered {
          type string;
        }
        leaf hotplug_event {
          type uint32;
        }
        leaf asic_type {
          type string;
        }
        leaf asic_cardname {
          type string;
        }
        leaf admin-state {
          type string;
        }
        leaf oper_state {
          type string;
        }
        leaf fab_plane {
          type string;
        }
        leaf fab_group {
          type string;
        }
        leaf fgid_download {
          type string;
        }
        leaf asic_state {
          type string;
        }
        leaf asic_disconnect_signal {
          type string;
        }
        leaf last_init_cause {
          type string;
        }
        leaf num_pon_resets {
          type uint32;
        }
        leaf num_hard_resets {
          type uint32;
        }
      }
    }
  }

  grouping ncs_rpc_notif_sfe_link_info_asic_instance {
    list instance {
      key "instance-id";
      leaf instance-id {
        type fabric-types:ncs_rpc_notif_sfe_instance_type_ncs5500;
      }
      leaf nodeid_str {
        type string;
      }
      leaf is_show {
        type boolean;
      }
      list link_idx_list {
        key "link_idx";
        leaf link_idx {
          type int64;
        }
        leaf link_id_str {
          type string;
        }
        leaf phy_link {
          type string;
        }
        leaf speed {
          type string;
        }
        leaf stage {
          type string;
        }
        leaf fab_plane {
          type uint32;
        }
        leaf fab_group {
          type uint32;
        }
        leaf flap_cnt {
          type uint32;
        }
        leaf num_admin_shuts {
          type uint32;
        }
        leaf admin-state {
          type string;
        }
        leaf oper_state {
          type string;
        }
        leaf flags {
          type string;
        }
        leaf far_end_link_fsdb {
          type string;
        }
        leaf far_end_link_hw {
          type string;
        }
        leaf link_cxp_port {
          type string;
        }
        leaf link_cxp_lane {
          type string;
        }
        leaf coeff1 {
          type uint32;
        }
        leaf coeff2 {
          type uint32;
        }
        leaf fsm_state {
          type string;
        }
        leaf TX_Control_cells_counter {
          type uint64;
        }
        leaf TX_Data_cell_counter {
          type uint64;
        }
        leaf TX_Data_byte_counter {
          type uint64;
        }
        leaf TX_BEC_retransmit {
          type uint64;
        }
        leaf TX_Asyn_fifo_rate {
          type uint64;
        }
        leaf RX_Control_cells_counter {
          type uint64;
        }
        leaf RX_Data_cell_counter {
          type uint64;
        }
        leaf RX_Data_byte_counter {
          type uint64;
        }
        leaf RX_BEC_retransmit {
          type uint64;
        }
        leaf RX_Asyn_fifo_rate {
          type uint64;
        }
        leaf RX_CRC_errors_counter {
          type uint64;
        }
        leaf RX_LFEC_FEC_correctable_error {
          type uint64;
        }
        leaf RX_LFEC_FEC_uncorrectable_errors {
          type uint64;
        }
        leaf RX_dropped_retransmitted_control {
          type uint64;
        }
        list history {
          key "history_idx";
          leaf history_idx {
            type int32;
          }
          leaf time_stamp {
            type string;
          }
          leaf admin-state {
            type string;
          }
          leaf oper_state {
            type string;
          }
          leaf error_state {
            type string;
          }
          leaf down_reasons {
            type string;
          }
        }
      }
    }
  }

  grouping ncs_rpc_notif_sfe_link_info_stats_asic_instance {
    container stats {
      container data {
        uses ncs_rpc_notif_sfe_link_info_asic_instance;
      }
      container ctrl {
        uses ncs_rpc_notif_sfe_link_info_asic_instance;
      }
      container all {
        uses ncs_rpc_notif_sfe_link_info_asic_instance;
      }
    }
  }

  grouping ncs_rpc_notif_sfe_statistics_asic_instance {
    list instance {
      key "instance-id";
      leaf instance-id {
        type fabric-types:ncs_rpc_notif_sfe_instance_type_ncs5500;
      }
      leaf stats_output {
        type string;
      }
    }
  }

  grouping ncs_rpc_notif_sfe_trace {
    container sfe_driver {
      uses show-trace:ncs_rpc_notif_traceable;
    }
  }

  grouping ncs_rpc_notif_sfe_parse_link_instance {
    list instance {
      key "instance-id";
      leaf instance-id {
        type fabric-types:ncs_rpc_notif_sfe_instance_type_ncs5500;
      }
      leaf is_show {
        type boolean;
      }
      list link_idx_list {
        key "link_idx";
        leaf link_idx {
          type int64;
        }
        leaf rack_id_str {
          type string;
        }
        leaf slot_id_str {
          type string;
        }
        leaf asic_inst_id {
          type uint32;
        }
        leaf link_num_id {
          type uint32;
        }
        leaf log_slot {
          type uint32;
        }
        leaf phy_slot {
          type uint32;
        }
        leaf fap_id {
          type uint32;
        }
        leaf unit {
          type uint32;
        }
        leaf sfi_id {
          type uint32;
        }
        leaf ip_addr {
          type string;
        }
        leaf driver_run {
          type string;
        }
      }
    }
  }

  grouping ncs_rpc_notif_sfe {
    container sfe {
      description
        "Fabric SFE driver commands";
      container driver {
        list location {
          key "loc_str";
          leaf loc_str {
            type fabric-types:ncs_rpc_notif_sfe_location_type_ncs5500;
          }
          leaf description {
            type string;
            default "location (R/S).";
          }
          uses ncs_rpc_notif_sfe_drvr_info;
        }
      }
      container statistics {
        list location {
          key "loc_str";
          leaf loc_str {
            type fabric-types:ncs_rpc_notif_sfe_location_type_ncs5500;
          }
          leaf description {
            type string;
            default "location (R/S).";
          }
          list asic_types {
            key "asicname";
            leaf asicname {
              type string;
            }
            list block {
              key "blockname";
              leaf blockname {
                type string;
              }
              uses ncs_rpc_notif_sfe_statistics_asic_instance;
            }
          }
        }
      }
      container link-info {
        list location {
          key "loc_str";
          leaf loc_str {
            type fabric-types:ncs_rpc_notif_sfe_location_type_ncs5500;
          }
          leaf description {
            type string;
            default "location (R/S)";
          }
          list rx {
            key "start end";
            leaf start {
              type fabric-types:ncs_rpc_notif_sfe_link_type;
            }
            leaf end {
              type fabric-types:ncs_rpc_notif_sfe_link_type;
            }
            container detail {
              container topo {
                uses ncs_rpc_notif_sfe_link_info_asic_instance;
              }
              container flap {
                uses ncs_rpc_notif_sfe_link_info_asic_instance;
              }
            }
            container topo {
              uses ncs_rpc_notif_sfe_link_info_asic_instance;
            }
            container flap {
              uses ncs_rpc_notif_sfe_link_info_asic_instance;
            }
            uses ncs_rpc_notif_sfe_link_info_stats_asic_instance;
          }
          list tx {
            key "start end";
            leaf start {
              type fabric-types:ncs_rpc_notif_sfe_link_type;
            }
            leaf end {
              type fabric-types:ncs_rpc_notif_sfe_link_type;
            }
            container detail {
              uses ncs_rpc_notif_sfe_link_info_asic_instance;
            }
            uses ncs_rpc_notif_sfe_link_info_asic_instance;
            uses ncs_rpc_notif_sfe_link_info_stats_asic_instance;
          }
        }
      }
      container diagshell {
        list location {
          key "loc_str";
          leaf loc_str {
            type fabric-types:ncs_rpc_notif_sfe_location_type_ncs5500;
          }
          leaf description {
            type string;
            default "location (R/S)";
          }
          list instance {
            key "instance_num";
            leaf instance_num {
              type fabric-types:ncs_rpc_notif_fabric_diag_shell_instance_num_type;
            }
            list diag_cmd {
              key "cmd_str";
              leaf cmd_str {
                type fabric-types:ncs_rpc_notif_fabric_diag_shell_cmd_type;
              }
              list bytes {
                key "byte_idx";
                leaf byte_idx {
                  type int64;
                }
                leaf data {
                  type string;
                }
              }
            }
          }
        }
      }
      container register {
        list location {
          key "loc_str";
          leaf loc_str {
            type fabric-types:ncs_rpc_notif_sfe_location_type_ncs5500;
          }
          leaf description {
            type string;
            default "location (R/S)";
          }
          list instance {
            key "instance_num";
            leaf instance_num {
              type fabric-types:ncs_rpc_notif_fabric_diag_shell_instance_num_type;
            }
            list bytes {
              key "byte_idx";
              leaf byte_idx {
                type int64;
              }
              leaf data {
                type string;
              }
            }
          }
        }
      }
      container dump-file {
        list location {
          key "loc_str";
          leaf loc_str {
            type fabric-types:ncs_rpc_notif_sfe_location_type_ncs5500;
          }
          leaf description {
            type string;
            default "location (R/S)";
          }
          list file {
            key "file_name";
            leaf file_name {
              type string;
            }
            list bytes {
              key "byte_idx";
              leaf byte_idx {
                type int64;
              }
              leaf data {
                type string;
              }
            }
          }
        }
      }
      container parse {
        list location {
          key "loc_str";
          leaf loc_str {
            type fabric-types:ncs_rpc_notif_sfe_location_type_ncs5500;
          }
          leaf description {
            type string;
            default "location (R/S)";
          }
          list link {
            key "start end";
            leaf start {
              type fabric-types:ncs_rpc_notif_sfe_link_type;
            }
            leaf end {
              type fabric-types:ncs_rpc_notif_sfe_link_type;
            }
            uses ncs_rpc_notif_sfe_parse_link_instance;
          }
        }
      }
    }
    container sfe_trace {
      uses ncs_rpc_notif_sfe_trace;
    }
  }

  grouping live_ncs_sfe_drvr_info {
    list drvr_info {
      key "idx";
      leaf idx {
        type int32;
      }
      leaf drv_version {
        type uint32;
      }
      leaf coeff_major_rev {
        type uint32;
      }
      leaf coeff_minor_rev {
        type uint32;
      }
      leaf func_role {
        type string;
      }
      leaf issu_role {
        type string;
      }
      leaf rack_name {
        type string;
      }
      leaf rack_type {
        type string;
      }
      leaf rack_num {
        type string;
      }
      leaf ip_address {
        type string;
      }
      leaf card_avail_mask {
        type uint32;
      }
      leaf asic_avail_mask {
        type uint64;
      }
      leaf exp_asic_avail_mask {
        type uint64;
      }
      leaf ucmc_ratio {
        type uint32;
      }
      leaf pm_conn_active {
        type boolean;
      }
      leaf platform_local_conn_active {
        type boolean;
      }
      leaf fsdb_conn_active {
        type boolean;
      }
      leaf fgid_conn_active {
        type boolean;
      }
      leaf cm_conn_active {
        type boolean;
      }
      leaf ccc_conn_active {
        type boolean;
      }
      leaf issu_mgr_conn_active {
        type boolean;
      }
      leaf peer_sfe_conn_active {
        type boolean;
      }
      leaf cxp_conn_active {
        type boolean;
      }
      leaf pm_reg_active {
        type boolean;
      }
      leaf platform_local_reg_active {
        type boolean;
      }
      leaf fsdb_reg_active {
        type boolean;
      }
      leaf fgid_reg_active {
        type boolean;
      }
      leaf cm_reg_active {
        type boolean;
      }
      leaf issu_mgr_reg_active {
        type boolean;
      }
      leaf peer_sfe_reg_active {
        type boolean;
      }
      leaf cxp_reg_active {
        type boolean;
      }
      leaf num_pm_conn_reqs {
        type uint8;
      }
      leaf num_platform_local_conn_reqs {
        type uint8;
      }
      leaf num_fsdb_conn_reqs {
        type uint8;
      }
      leaf num_fgid_conn_reqs {
        type uint8;
      }
      leaf num_fstats_conn_reqs {
        type uint8;
      }
      leaf num_cm_conn_reqs {
        type uint8;
      }
      leaf num_ccc_conn_reqs {
        type uint8;
      }
      leaf num_issu_mgr_conn_reqs {
        type uint8;
      }
      leaf num_peer_sfe_conn_reqs {
        type uint8;
      }
      leaf num_cxp_conn_reqs {
        type uint8;
      }
      leaf is_gaspp_registered {
        type boolean;
      }
      leaf is_cih_registered {
        type boolean;
      }
      leaf startup_time {
        type string;
      }
      list asic_list {
        key "asic_idx";
        leaf asic_idx {
          type uint32;
        }
        leaf asic_instance {
          type string;
        }
        leaf card_present {
          type string;
        }
        leaf card_powered {
          type string;
        }
        leaf hotplug_event {
          type uint32;
        }
        leaf asic_type {
          type string;
        }
        leaf asic_cardname {
          type string;
        }
        leaf admin-state {
          type string;
        }
        leaf oper_state {
          type string;
        }
        leaf fab_plane {
          type string;
        }
        leaf fab_group {
          type string;
        }
        leaf fgid_download {
          type string;
        }
        leaf asic_state {
          type string;
        }
        leaf asic_disconnect_signal {
          type string;
        }
        leaf last_init_cause {
          type string;
        }
        leaf num_pon_resets {
          type uint32;
        }
        leaf num_hard_resets {
          type uint32;
        }
      }
    }
  }

  grouping live_ncs_sfe_link_info_asic_instance {
    list instance {
      key "instance-id";
      leaf instance-id {
        type fabric-types:live_ncs_sfe_instance_type_ncs5500;
      }
      leaf nodeid_str {
        type string;
      }
      leaf is_show {
        type boolean;
      }
      list link_idx_list {
        key "link_idx";
        leaf link_idx {
          type int64;
        }
        leaf link_id_str {
          type string;
        }
        leaf phy_link {
          type string;
        }
        leaf speed {
          type string;
        }
        leaf stage {
          type string;
        }
        leaf fab_plane {
          type uint32;
        }
        leaf fab_group {
          type uint32;
        }
        leaf flap_cnt {
          type uint32;
        }
        leaf num_admin_shuts {
          type uint32;
        }
        leaf admin-state {
          type string;
        }
        leaf oper_state {
          type string;
        }
        leaf flags {
          type string;
        }
        leaf far_end_link_fsdb {
          type string;
        }
        leaf far_end_link_hw {
          type string;
        }
        leaf link_cxp_port {
          type string;
        }
        leaf link_cxp_lane {
          type string;
        }
        leaf coeff1 {
          type uint32;
        }
        leaf coeff2 {
          type uint32;
        }
        leaf fsm_state {
          type string;
        }
        leaf TX_Control_cells_counter {
          type uint64;
        }
        leaf TX_Data_cell_counter {
          type uint64;
        }
        leaf TX_Data_byte_counter {
          type uint64;
        }
        leaf TX_BEC_retransmit {
          type uint64;
        }
        leaf TX_Asyn_fifo_rate {
          type uint64;
        }
        leaf RX_Control_cells_counter {
          type uint64;
        }
        leaf RX_Data_cell_counter {
          type uint64;
        }
        leaf RX_Data_byte_counter {
          type uint64;
        }
        leaf RX_BEC_retransmit {
          type uint64;
        }
        leaf RX_Asyn_fifo_rate {
          type uint64;
        }
        leaf RX_CRC_errors_counter {
          type uint64;
        }
        leaf RX_LFEC_FEC_correctable_error {
          type uint64;
        }
        leaf RX_LFEC_FEC_uncorrectable_errors {
          type uint64;
        }
        leaf RX_dropped_retransmitted_control {
          type uint64;
        }
        list history {
          key "history_idx";
          leaf history_idx {
            type int32;
          }
          leaf time_stamp {
            type string;
          }
          leaf admin-state {
            type string;
          }
          leaf oper_state {
            type string;
          }
          leaf error_state {
            type string;
          }
          leaf down_reasons {
            type string;
          }
        }
      }
    }
  }

  grouping live_ncs_sfe_link_info_stats_asic_instance {
    container stats {
      container data {
        uses live_ncs_sfe_link_info_asic_instance;
      }
      container ctrl {
        uses live_ncs_sfe_link_info_asic_instance;
      }
      container all {
        uses live_ncs_sfe_link_info_asic_instance;
      }
    }
  }

  grouping live_ncs_sfe_statistics_asic_instance {
    list instance {
      key "instance-id";
      leaf instance-id {
        type fabric-types:live_ncs_sfe_instance_type_ncs5500;
      }
      leaf stats_output {
        type string;
      }
    }
  }

  grouping live_ncs_sfe_trace {
    container sfe_driver {
      uses show-trace:live_ncs_traceable;
    }
  }

  grouping live_ncs_sfe_parse_link_instance {
    list instance {
      key "instance-id";
      leaf instance-id {
        type fabric-types:live_ncs_sfe_instance_type_ncs5500;
      }
      leaf is_show {
        type boolean;
      }
      list link_idx_list {
        key "link_idx";
        leaf link_idx {
          type int64;
        }
        leaf rack_id_str {
          type string;
        }
        leaf slot_id_str {
          type string;
        }
        leaf asic_inst_id {
          type uint32;
        }
        leaf link_num_id {
          type uint32;
        }
        leaf log_slot {
          type uint32;
        }
        leaf phy_slot {
          type uint32;
        }
        leaf fap_id {
          type uint32;
        }
        leaf unit {
          type uint32;
        }
        leaf sfi_id {
          type uint32;
        }
        leaf ip_addr {
          type string;
        }
        leaf driver_run {
          type string;
        }
      }
    }
  }

  grouping live_ncs_sfe {
    container sfe {
      description
        "Fabric SFE driver commands";
      container driver {
        list location {
          key "loc_str";
          leaf loc_str {
            type fabric-types:live_ncs_sfe_location_type_ncs5500;
          }
          leaf description {
            type string;
            // NCS drop default statement
          }
          uses live_ncs_sfe_drvr_info;
        }
      }
      container statistics {
        list location {
          key "loc_str";
          leaf loc_str {
            type fabric-types:live_ncs_sfe_location_type_ncs5500;
          }
          leaf description {
            type string;
            // NCS drop default statement
          }
          list asic_types {
            key "asicname";
            leaf asicname {
              type string;
            }
            list block {
              key "blockname";
              leaf blockname {
                type string;
              }
              uses live_ncs_sfe_statistics_asic_instance;
            }
          }
        }
      }
      container link-info {
        list location {
          key "loc_str";
          leaf loc_str {
            type fabric-types:live_ncs_sfe_location_type_ncs5500;
          }
          leaf description {
            type string;
            // NCS drop default statement
          }
          list rx {
            key "start end";
            leaf start {
              type fabric-types:live_ncs_sfe_link_type;
            }
            leaf end {
              type fabric-types:live_ncs_sfe_link_type;
            }
            container detail {
              container topo {
                uses live_ncs_sfe_link_info_asic_instance;
              }
              container flap {
                uses live_ncs_sfe_link_info_asic_instance;
              }
            }
            container topo {
              uses live_ncs_sfe_link_info_asic_instance;
            }
            container flap {
              uses live_ncs_sfe_link_info_asic_instance;
            }
            uses live_ncs_sfe_link_info_stats_asic_instance;
          }
          list tx {
            key "start end";
            leaf start {
              type fabric-types:live_ncs_sfe_link_type;
            }
            leaf end {
              type fabric-types:live_ncs_sfe_link_type;
            }
            container detail {
              uses live_ncs_sfe_link_info_asic_instance;
            }
            uses live_ncs_sfe_link_info_asic_instance;
            uses live_ncs_sfe_link_info_stats_asic_instance;
          }
        }
      }
      container diagshell {
        list location {
          key "loc_str";
          leaf loc_str {
            type fabric-types:live_ncs_sfe_location_type_ncs5500;
          }
          leaf description {
            type string;
            // NCS drop default statement
          }
          list instance {
            key "instance_num";
            leaf instance_num {
              type fabric-types:live_ncs_fabric_diag_shell_instance_num_type;
            }
            list diag_cmd {
              key "cmd_str";
              leaf cmd_str {
                type fabric-types:live_ncs_fabric_diag_shell_cmd_type;
              }
              list bytes {
                key "byte_idx";
                leaf byte_idx {
                  type int64;
                }
                leaf data {
                  type string;
                }
              }
            }
          }
        }
      }
      container register {
        list location {
          key "loc_str";
          leaf loc_str {
            type fabric-types:live_ncs_sfe_location_type_ncs5500;
          }
          leaf description {
            type string;
            // NCS drop default statement
          }
          list instance {
            key "instance_num";
            leaf instance_num {
              type fabric-types:live_ncs_fabric_diag_shell_instance_num_type;
            }
            list bytes {
              key "byte_idx";
              leaf byte_idx {
                type int64;
              }
              leaf data {
                type string;
              }
            }
          }
        }
      }
      container dump-file {
        list location {
          key "loc_str";
          leaf loc_str {
            type fabric-types:live_ncs_sfe_location_type_ncs5500;
          }
          leaf description {
            type string;
            // NCS drop default statement
          }
          list file {
            key "file_name";
            leaf file_name {
              type string;
            }
            list bytes {
              key "byte_idx";
              leaf byte_idx {
                type int64;
              }
              leaf data {
                type string;
              }
            }
          }
        }
      }
      container parse {
        list location {
          key "loc_str";
          leaf loc_str {
            type fabric-types:live_ncs_sfe_location_type_ncs5500;
          }
          leaf description {
            type string;
            // NCS drop default statement
          }
          list link {
            key "start end";
            leaf start {
              type fabric-types:live_ncs_sfe_link_type;
            }
            leaf end {
              type fabric-types:live_ncs_sfe_link_type;
            }
            uses live_ncs_sfe_parse_link_instance;
          }
        }
      }
    }
    container sfe_trace {
      uses live_ncs_sfe_trace;
    }
  }

  grouping sfe_drvr_info {
    list drvr_info {
      key "idx";
      leaf idx {
        type int32;
      }
      leaf drv_version {
        type uint32;
      }
      leaf coeff_major_rev {
        type uint32;
      }
      leaf coeff_minor_rev {
        type uint32;
      }
      leaf func_role {
        type string;
      }
      leaf issu_role {
        type string;
      }
      leaf rack_name {
        type string;
      }
      leaf rack_type {
        type string;
      }
      leaf rack_num {
        type string;
      }
      leaf ip_address {
        type string;
      }
      leaf card_avail_mask {
        type uint32;
      }
      leaf asic_avail_mask {
        type uint64;
      }
      leaf exp_asic_avail_mask {
        type uint64;
      }
      leaf ucmc_ratio {
        type uint32;
      }
      leaf pm_conn_active {
        type boolean;
      }
      leaf platform_local_conn_active {
        type boolean;
      }
      leaf fsdb_conn_active {
        type boolean;
      }
      leaf fgid_conn_active {
        type boolean;
      }
      leaf cm_conn_active {
        type boolean;
      }
      leaf ccc_conn_active {
        type boolean;
      }
      leaf issu_mgr_conn_active {
        type boolean;
      }
      leaf peer_sfe_conn_active {
        type boolean;
      }
      leaf cxp_conn_active {
        type boolean;
      }
      leaf pm_reg_active {
        type boolean;
      }
      leaf platform_local_reg_active {
        type boolean;
      }
      leaf fsdb_reg_active {
        type boolean;
      }
      leaf fgid_reg_active {
        type boolean;
      }
      leaf cm_reg_active {
        type boolean;
      }
      leaf issu_mgr_reg_active {
        type boolean;
      }
      leaf peer_sfe_reg_active {
        type boolean;
      }
      leaf cxp_reg_active {
        type boolean;
      }
      leaf num_pm_conn_reqs {
        type uint8;
      }
      leaf num_platform_local_conn_reqs {
        type uint8;
      }
      leaf num_fsdb_conn_reqs {
        type uint8;
      }
      leaf num_fgid_conn_reqs {
        type uint8;
      }
      leaf num_fstats_conn_reqs {
        type uint8;
      }
      leaf num_cm_conn_reqs {
        type uint8;
      }
      leaf num_ccc_conn_reqs {
        type uint8;
      }
      leaf num_issu_mgr_conn_reqs {
        type uint8;
      }
      leaf num_peer_sfe_conn_reqs {
        type uint8;
      }
      leaf num_cxp_conn_reqs {
        type uint8;
      }
      leaf is_gaspp_registered {
        type boolean;
      }
      leaf is_cih_registered {
        type boolean;
      }
      leaf startup_time {
        type string;
      }
      list asic_list {
        key "asic_idx";
        leaf asic_idx {
          type uint32;
        }
        leaf asic_instance {
          type string;
        }
        leaf card_present {
          type string;
        }
        leaf card_powered {
          type string;
        }
        leaf hotplug_event {
          type uint32;
        }
        leaf asic_type {
          type string;
        }
        leaf asic_cardname {
          type string;
        }
        leaf admin-state {
          type string;
        }
        leaf oper_state {
          type string;
        }
        leaf fab_plane {
          type string;
        }
        leaf fab_group {
          type string;
        }
        leaf fgid_download {
          type string;
        }
        leaf asic_state {
          type string;
        }
        leaf asic_disconnect_signal {
          type string;
        }
        leaf last_init_cause {
          type string;
        }
        leaf num_pon_resets {
          type uint32;
        }
        leaf num_hard_resets {
          type uint32;
        }
      }
    }
  }

  grouping sfe_link_info_asic_instance {
    list instance {
      key "instance-id";
      leaf instance-id {
        type fabric-types:sfe_instance_type_ncs5500;
      }
      leaf nodeid_str {
        type string;
      }
      leaf is_show {
        type boolean;
      }
      list link_idx_list {
        key "link_idx";
        leaf link_idx {
          type int64;
        }
        leaf link_id_str {
          type string;
        }
        leaf phy_link {
          type string;
        }
        leaf speed {
          type string;
        }
        leaf stage {
          type string;
        }
        leaf fab_plane {
          type uint32;
        }
        leaf fab_group {
          type uint32;
        }
        leaf flap_cnt {
          type uint32;
        }
        leaf num_admin_shuts {
          type uint32;
        }
        leaf admin-state {
          type string;
        }
        leaf oper_state {
          type string;
        }
        leaf flags {
          type string;
        }
        leaf far_end_link_fsdb {
          type string;
        }
        leaf far_end_link_hw {
          type string;
        }
        leaf link_cxp_port {
          type string;
        }
        leaf link_cxp_lane {
          type string;
        }
        leaf coeff1 {
          type uint32;
        }
        leaf coeff2 {
          type uint32;
        }
        leaf fsm_state {
          type string;
        }
        leaf TX_Control_cells_counter {
          type uint64;
        }
        leaf TX_Data_cell_counter {
          type uint64;
        }
        leaf TX_Data_byte_counter {
          type uint64;
        }
        leaf TX_BEC_retransmit {
          type uint64;
        }
        leaf TX_Asyn_fifo_rate {
          type uint64;
        }
        leaf RX_Control_cells_counter {
          type uint64;
        }
        leaf RX_Data_cell_counter {
          type uint64;
        }
        leaf RX_Data_byte_counter {
          type uint64;
        }
        leaf RX_BEC_retransmit {
          type uint64;
        }
        leaf RX_Asyn_fifo_rate {
          type uint64;
        }
        leaf RX_CRC_errors_counter {
          type uint64;
        }
        leaf RX_LFEC_FEC_correctable_error {
          type uint64;
        }
        leaf RX_LFEC_FEC_uncorrectable_errors {
          type uint64;
        }
        leaf RX_dropped_retransmitted_control {
          type uint64;
        }
        list history {
          key "history_idx";
          leaf history_idx {
            type int32;
          }
          leaf time_stamp {
            type string;
          }
          leaf admin-state {
            type string;
          }
          leaf oper_state {
            type string;
          }
          leaf error_state {
            type string;
          }
          leaf down_reasons {
            type string;
          }
        }
      }
    }
  }

  grouping sfe_link_info_stats_asic_instance {
    container stats {
      container data {
        uses sfe_link_info_asic_instance;
      }
      container ctrl {
        uses sfe_link_info_asic_instance;
      }
      container all {
        uses sfe_link_info_asic_instance;
      }
    }
  }

  grouping sfe_statistics_asic_instance {
    list instance {
      key "instance-id";
      leaf instance-id {
        type fabric-types:sfe_instance_type_ncs5500;
      }
      leaf stats_output {
        type string;
      }
    }
  }

  grouping sfe_trace {
    container sfe_driver {
      uses show-trace:traceable;
    }
  }

  grouping sfe_parse_link_instance {
    list instance {
      key "instance-id";
      leaf instance-id {
        type fabric-types:sfe_instance_type_ncs5500;
      }
      leaf is_show {
        type boolean;
      }
      list link_idx_list {
        key "link_idx";
        leaf link_idx {
          type int64;
        }
        leaf rack_id_str {
          type string;
        }
        leaf slot_id_str {
          type string;
        }
        leaf asic_inst_id {
          type uint32;
        }
        leaf link_num_id {
          type uint32;
        }
        leaf log_slot {
          type uint32;
        }
        leaf phy_slot {
          type uint32;
        }
        leaf fap_id {
          type uint32;
        }
        leaf unit {
          type uint32;
        }
        leaf sfi_id {
          type uint32;
        }
        leaf ip_addr {
          type string;
        }
        leaf driver_run {
          type string;
        }
      }
    }
  }

  grouping sfe {
    container sfe {
      description
        "Fabric SFE driver commands";
      container driver {
        list location {
          key "loc_str";
          leaf loc_str {
            type fabric-types:sfe_location_type_ncs5500;
          }
          leaf description {
            type string;
            default "location (R/S).";
          }
          uses sfe_drvr_info;
        }
      }
      container statistics {
        list location {
          key "loc_str";
          leaf loc_str {
            type fabric-types:sfe_location_type_ncs5500;
          }
          leaf description {
            type string;
            default "location (R/S).";
          }
          list asic_types {
            key "asicname";
            leaf asicname {
              type string;
            }
            list block {
              key "blockname";
              leaf blockname {
                type string;
              }
              uses sfe_statistics_asic_instance;
            }
          }
        }
      }
      container link-info {
        list location {
          key "loc_str";
          leaf loc_str {
            type fabric-types:sfe_location_type_ncs5500;
          }
          leaf description {
            type string;
            default "location (R/S)";
          }
          list rx {
            key "start end";
            leaf start {
              type fabric-types:sfe_link_type;
            }
            leaf end {
              type fabric-types:sfe_link_type;
            }
            container detail {
              container topo {
                uses sfe_link_info_asic_instance;
              }
              container flap {
                uses sfe_link_info_asic_instance;
              }
            }
            container topo {
              uses sfe_link_info_asic_instance;
            }
            container flap {
              uses sfe_link_info_asic_instance;
            }
            uses sfe_link_info_stats_asic_instance;
          }
          list tx {
            key "start end";
            leaf start {
              type fabric-types:sfe_link_type;
            }
            leaf end {
              type fabric-types:sfe_link_type;
            }
            container detail {
              uses sfe_link_info_asic_instance;
            }
            uses sfe_link_info_asic_instance;
            uses sfe_link_info_stats_asic_instance;
          }
        }
      }
      container diagshell {
        list location {
          key "loc_str";
          leaf loc_str {
            type fabric-types:sfe_location_type_ncs5500;
          }
          leaf description {
            type string;
            default "location (R/S)";
          }
          list instance {
            key "instance_num";
            leaf instance_num {
              type fabric-types:fabric_diag_shell_instance_num_type;
            }
            list diag_cmd {
              key "cmd_str";
              leaf cmd_str {
                type fabric-types:fabric_diag_shell_cmd_type;
              }
              list bytes {
                key "byte_idx";
                leaf byte_idx {
                  type int64;
                }
                leaf data {
                  type string;
                }
              }
            }
          }
        }
      }
      container register {
        list location {
          key "loc_str";
          leaf loc_str {
            type fabric-types:sfe_location_type_ncs5500;
          }
          leaf description {
            type string;
            default "location (R/S)";
          }
          list instance {
            key "instance_num";
            leaf instance_num {
              type fabric-types:fabric_diag_shell_instance_num_type;
            }
            list bytes {
              key "byte_idx";
              leaf byte_idx {
                type int64;
              }
              leaf data {
                type string;
              }
            }
          }
        }
      }
      container dump-file {
        list location {
          key "loc_str";
          leaf loc_str {
            type fabric-types:sfe_location_type_ncs5500;
          }
          leaf description {
            type string;
            default "location (R/S)";
          }
          list file {
            key "file_name";
            leaf file_name {
              type string;
            }
            list bytes {
              key "byte_idx";
              leaf byte_idx {
                type int64;
              }
              leaf data {
                type string;
              }
            }
          }
        }
      }
      container parse {
        list location {
          key "loc_str";
          leaf loc_str {
            type fabric-types:sfe_location_type_ncs5500;
          }
          leaf description {
            type string;
            default "location (R/S)";
          }
          list link {
            key "start end";
            leaf start {
              type fabric-types:sfe_link_type;
            }
            leaf end {
              type fabric-types:sfe_link_type;
            }
            uses sfe_parse_link_instance;
          }
        }
      }
    }
    container sfe_trace {
      uses sfe_trace;
    }
  }
}

module Cisco-IOS-XR-ethernet-loopback-cfg {
  // Generated by yanger -t ncs
  tailf:mount-id "cisco-iosxr-nc-7.3:cisco-iosxr-nc-7.3";
  tailf:ncs-device-type "netconf";

  namespace "http://cisco.com/ns/yang/Cisco-IOS-XR-ethernet-loopback-cfg";
  prefix ethernet-loopback-cfg;

  import cisco-semver {
    prefix semver;
  }
  import Cisco-IOS-XR-ifmgr-cfg {
    prefix a1;
  }
  import Cisco-IOS-XR-l2-eth-infra-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-loopback package configuration.

     This YANG module augments the
       Cisco-IOS-XR-ifmgr-cfg,
       Cisco-IOS-XR-l2-eth-infra-cfg
     modules with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:template/ncs:ned-id/ncs:config/a1:interface-configurations/a1:interface-configuration/a2:ethernet-features" {
    description
      "This augment extends the configuration data of
       'Cisco-IOS-XR-l2-eth-infra-cfg'";
    container ethernet-loopback {
      description
        "Ethernet Loopback configuration data";
      container remote {
        description
          "This object acts as a container for the
           permission of remote-initiated external and
           internal loopback on a local interface.";
        leaf internal {
          type empty;
          description
            "Allow remote controllers to initiate latching
             loopback operations (internal loopback) on
             this interface.";
        }
        leaf external {
          type empty;
          description
            "Allow remote controllers to initiate latching
             loopback operations (external loopback) on
             this interface.";
        }
        leaf log-changes {
          type empty;
          description
            "Triggers a syslog on latching loopback
             activation and deactivation.";
        }
      }
      container permit {
        description
          "This object acts as a container for the
           permission of external and internal loopback on
           an interface.";
        leaf internal {
          type empty;
          description
            "Allow internal loopback to be enabled on this
             interface.";
        }
        leaf external {
          type empty;
          description
            "Allow external loopback to be enabled on this
             interface.";
        }
      }
      leaf latching-loopback-controller {
        type empty;
        description
          "Allow latching loopback sessions on remote
           devices to be managed from this interface.";
      }
    }
  }
  augment "/ncs:devices/ncs:device/ncs:live-status/a1:interface-configurations/a1:interface-configuration/a2:ethernet-features" {
    description
      "This augment extends the configuration data of
       'Cisco-IOS-XR-l2-eth-infra-cfg'";
    container ethernet-loopback {
      tailf:ncs-device-type "netconf";
      tailf:display-when "not(../../../../../ncs:module) or ../../../../../ncs:module[ncs:name='Cisco-IOS-XR-ethernet-loopback-cfg'] or (../../../../../ncs:live-status-protocol[not(ncs:capability)]) or (../../../../../ncs:live-status-protocol/ncs:capability/ncs:module[.='Cisco-IOS-XR-ethernet-loopback-cfg'])";
      description
        "Ethernet Loopback configuration data";
      container remote {
        description
          "This object acts as a container for the
           permission of remote-initiated external and
           internal loopback on a local interface.";
        leaf internal {
          type empty;
          description
            "Allow remote controllers to initiate latching
             loopback operations (internal loopback) on
             this interface.";
        }
        leaf external {
          type empty;
          description
            "Allow remote controllers to initiate latching
             loopback operations (external loopback) on
             this interface.";
        }
        leaf log-changes {
          type empty;
          description
            "Triggers a syslog on latching loopback
             activation and deactivation.";
        }
      }
      container permit {
        description
          "This object acts as a container for the
           permission of external and internal loopback on
           an interface.";
        leaf internal {
          type empty;
          description
            "Allow internal loopback to be enabled on this
             interface.";
        }
        leaf external {
          type empty;
          description
            "Allow external loopback to be enabled on this
             interface.";
        }
      }
      leaf latching-loopback-controller {
        type empty;
        description
          "Allow latching loopback sessions on remote
           devices to be managed from this interface.";
      }
    }
  }
  augment "/ncs:devices/ncs:device/ncs:config/a1:interface-configurations/a1:interface-configuration/a2:ethernet-features" {
    description
      "This augment extends the configuration data of
       'Cisco-IOS-XR-l2-eth-infra-cfg'";
    container ethernet-loopback {
      tailf:ncs-device-type "netconf";
      tailf:display-when "not(../../../../../ncs:module) or ../../../../../ncs:module[ncs:name='Cisco-IOS-XR-ethernet-loopback-cfg']";
      description
        "Ethernet Loopback configuration data";
      container remote {
        description
          "This object acts as a container for the
           permission of remote-initiated external and
           internal loopback on a local interface.";
        leaf internal {
          type empty;
          description
            "Allow remote controllers to initiate latching
             loopback operations (internal loopback) on
             this interface.";
        }
        leaf external {
          type empty;
          description
            "Allow remote controllers to initiate latching
             loopback operations (external loopback) on
             this interface.";
        }
        leaf log-changes {
          type empty;
          description
            "Triggers a syslog on latching loopback
             activation and deactivation.";
        }
      }
      container permit {
        description
          "This object acts as a container for the
           permission of external and internal loopback on
           an interface.";
        leaf internal {
          type empty;
          description
            "Allow internal loopback to be enabled on this
             interface.";
        }
        leaf external {
          type empty;
          description
            "Allow external loopback to be enabled on this
             interface.";
        }
      }
      leaf latching-loopback-controller {
        type empty;
        description
          "Allow latching loopback sessions on remote
           devices to be managed from this interface.";
      }
    }
  }
}

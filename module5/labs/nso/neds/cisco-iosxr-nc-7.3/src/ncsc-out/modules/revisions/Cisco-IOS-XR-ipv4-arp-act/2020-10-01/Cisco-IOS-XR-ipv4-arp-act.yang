module Cisco-IOS-XR-ipv4-arp-act {
  // Generated by yanger -t ncs
  tailf:mount-id "cisco-iosxr-nc-7.3:cisco-iosxr-nc-7.3";
  tailf:ncs-device-type "netconf";

  namespace "http://cisco.com/ns/yang/Cisco-IOS-XR-ipv4-arp-act";
  prefix arp-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2020 by Cisco Systems, Inc.
     All rights reserved.";

  revision 2020-10-01 {
    description
      "Changing task to cef as commonly used in arp ref cdets : CSCtq86525";
    semver:module-version "1.2.0";
  }
  revision 2019-10-01 {
    description
      "Made changes to be RFC6087 compliant";
    semver:module-version "1.1.0";
  }
  revision 2019-04-05 {
    description
      "Establish semantic version baseline.";
    semver:module-version "1.0.0";
  }
  revision 2018-10-08 {
    description
      "IOS XR 6.1.1 revision.";
  }

  augment "/ncs:devices/ncs:device/ncs:rpc" {
    container rpc-clear-arp-cache-interface-ip-address-location {
      tailf:ncs-device-type "netconf";
      tailf:display-when "not(../../ncs:module) or ../../ncs:module[ncs:name='Cisco-IOS-XR-ipv4-arp-act']";
      tailf:action clear-arp-cache-interface-ip-address-location {
        tailf:actionpoint ncsproxy {
          tailf:internal;
        }
        description
          "Interface for which to clear ARP entries";
        input {
          leaf interface-name {
            type string;
            mandatory true;
            description
              "Interface name";
          }
          leaf ip-address {
            type string;
            mandatory true;
            description
              "IP address";
          }
          leaf node-location {
            type string;
            mandatory true;
            description
              "Node location";
          }
        }
      }
    }
  }
  augment "/ncs:devices/ncs:device-group/ncs:ned-id/ncs:rpc" {
    container rpc-clear-arp-cache-interface-ip-address-location {
      tailf:ncs-device-type "netconf";
      tailf:display-when "/ncs:devices/ncs:device[ncs:name=current()/../../../ncs:member]/ncs:module[ncs:name='Cisco-IOS-XR-ipv4-arp-act']";
      tailf:action clear-arp-cache-interface-ip-address-location {
        tailf:actionpoint ncsproxy {
          tailf:internal;
        }
        description
          "Interface for which to clear ARP entries";
        input {
          leaf interface-name {
            type string;
            mandatory true;
            description
              "Interface name";
          }
          leaf ip-address {
            type string;
            mandatory true;
            description
              "IP address";
          }
          leaf node-location {
            type string;
            mandatory true;
            description
              "Node location";
          }
        }
      }
    }
  }
  augment "/ncs:devices/ncs:device/ncs:rpc" {
    container rpc-clear-arp-cache-interface-location {
      tailf:ncs-device-type "netconf";
      tailf:display-when "not(../../ncs:module) or ../../ncs:module[ncs:name='Cisco-IOS-XR-ipv4-arp-act']";
      tailf:action clear-arp-cache-interface-location {
        tailf:actionpoint ncsproxy {
          tailf:internal;
        }
        description
          "Clear ARP cache entries for given interface";
        input {
          leaf interface-name {
            type string;
            mandatory true;
            description
              "Interface";
          }
          leaf node-location {
            type string;
            mandatory true;
            description
              "node location";
          }
        }
      }
    }
  }
  augment "/ncs:devices/ncs:device-group/ncs:ned-id/ncs:rpc" {
    container rpc-clear-arp-cache-interface-location {
      tailf:ncs-device-type "netconf";
      tailf:display-when "/ncs:devices/ncs:device[ncs:name=current()/../../../ncs:member]/ncs:module[ncs:name='Cisco-IOS-XR-ipv4-arp-act']";
      tailf:action clear-arp-cache-interface-location {
        tailf:actionpoint ncsproxy {
          tailf:internal;
        }
        description
          "Clear ARP cache entries for given interface";
        input {
          leaf interface-name {
            type string;
            mandatory true;
            description
              "Interface";
          }
          leaf node-location {
            type string;
            mandatory true;
            description
              "node location";
          }
        }
      }
    }
  }
  augment "/ncs:devices/ncs:device/ncs:rpc" {
    container rpc-clear-arp-cache-drop-adjacency-interface-ip-address-location {
      tailf:ncs-device-type "netconf";
      tailf:display-when "not(../../ncs:module) or ../../ncs:module[ncs:name='Cisco-IOS-XR-ipv4-arp-act']";
      tailf:action clear-arp-cache-drop-adjacency-interface-ip-address-location {
        tailf:actionpoint ncsproxy {
          tailf:internal;
        }
        description
          "Clear ARP drop adjancency entries";
        input {
          leaf interface-name {
            type string;
            mandatory true;
            description
              "Interface name";
          }
          leaf ip-address {
            type string;
            mandatory true;
            description
              "IP address";
          }
          leaf node-location {
            type string;
            mandatory true;
            description
              "Node location";
          }
        }
      }
    }
  }
  augment "/ncs:devices/ncs:device-group/ncs:ned-id/ncs:rpc" {
    container rpc-clear-arp-cache-drop-adjacency-interface-ip-address-location {
      tailf:ncs-device-type "netconf";
      tailf:display-when "/ncs:devices/ncs:device[ncs:name=current()/../../../ncs:member]/ncs:module[ncs:name='Cisco-IOS-XR-ipv4-arp-act']";
      tailf:action clear-arp-cache-drop-adjacency-interface-ip-address-location {
        tailf:actionpoint ncsproxy {
          tailf:internal;
        }
        description
          "Clear ARP drop adjancency entries";
        input {
          leaf interface-name {
            type string;
            mandatory true;
            description
              "Interface name";
          }
          leaf ip-address {
            type string;
            mandatory true;
            description
              "IP address";
          }
          leaf node-location {
            type string;
            mandatory true;
            description
              "Node location";
          }
        }
      }
    }
  }
  augment "/ncs:devices/ncs:device/ncs:rpc" {
    container rpc-clear-arp-cache-drop-adjacency-location {
      tailf:ncs-device-type "netconf";
      tailf:display-when "not(../../ncs:module) or ../../ncs:module[ncs:name='Cisco-IOS-XR-ipv4-arp-act']";
      tailf:action clear-arp-cache-drop-adjacency-location {
        tailf:actionpoint ncsproxy {
          tailf:internal;
        }
        description
          "Clear ARP drop adjancency entries";
        input {
          leaf node-location {
            type string;
            mandatory true;
            description
              "Node location";
          }
        }
      }
    }
  }
  augment "/ncs:devices/ncs:device-group/ncs:ned-id/ncs:rpc" {
    container rpc-clear-arp-cache-drop-adjacency-location {
      tailf:ncs-device-type "netconf";
      tailf:display-when "/ncs:devices/ncs:device[ncs:name=current()/../../../ncs:member]/ncs:module[ncs:name='Cisco-IOS-XR-ipv4-arp-act']";
      tailf:action clear-arp-cache-drop-adjacency-location {
        tailf:actionpoint ncsproxy {
          tailf:internal;
        }
        description
          "Clear ARP drop adjancency entries";
        input {
          leaf node-location {
            type string;
            mandatory true;
            description
              "Node location";
          }
        }
      }
    }
  }
  augment "/ncs:devices/ncs:device/ncs:rpc" {
    container rpc-clear-arp-cache-traffic-interface-location {
      tailf:ncs-device-type "netconf";
      tailf:display-when "not(../../ncs:module) or ../../ncs:module[ncs:name='Cisco-IOS-XR-ipv4-arp-act']";
      tailf:action clear-arp-cache-traffic-interface-location {
        tailf:actionpoint ncsproxy {
          tailf:internal;
        }
        description
          "Clear ARP cache traffic statistics for interface location";
        input {
          leaf interface-name {
            type string;
            mandatory true;
            description
              "Interface name";
          }
          leaf node-location {
            type string;
            mandatory true;
            description
              "Node location";
          }
        }
      }
    }
  }
  augment "/ncs:devices/ncs:device-group/ncs:ned-id/ncs:rpc" {
    container rpc-clear-arp-cache-traffic-interface-location {
      tailf:ncs-device-type "netconf";
      tailf:display-when "/ncs:devices/ncs:device[ncs:name=current()/../../../ncs:member]/ncs:module[ncs:name='Cisco-IOS-XR-ipv4-arp-act']";
      tailf:action clear-arp-cache-traffic-interface-location {
        tailf:actionpoint ncsproxy {
          tailf:internal;
        }
        description
          "Clear ARP cache traffic statistics for interface location";
        input {
          leaf interface-name {
            type string;
            mandatory true;
            description
              "Interface name";
          }
          leaf node-location {
            type string;
            mandatory true;
            description
              "Node location";
          }
        }
      }
    }
  }
  augment "/ncs:devices/ncs:device/ncs:rpc" {
    container rpc-clear-arp-cache-traffic-location {
      tailf:ncs-device-type "netconf";
      tailf:display-when "not(../../ncs:module) or ../../ncs:module[ncs:name='Cisco-IOS-XR-ipv4-arp-act']";
      tailf:action clear-arp-cache-traffic-location {
        tailf:actionpoint ncsproxy {
          tailf:internal;
        }
        description
          "Clear ARP cache traffic statistics";
        input {
          leaf node-location {
            type string;
            mandatory true;
            description
              "Node location";
          }
        }
      }
    }
  }
  augment "/ncs:devices/ncs:device-group/ncs:ned-id/ncs:rpc" {
    container rpc-clear-arp-cache-traffic-location {
      tailf:ncs-device-type "netconf";
      tailf:display-when "/ncs:devices/ncs:device[ncs:name=current()/../../../ncs:member]/ncs:module[ncs:name='Cisco-IOS-XR-ipv4-arp-act']";
      tailf:action clear-arp-cache-traffic-location {
        tailf:actionpoint ncsproxy {
          tailf:internal;
        }
        description
          "Clear ARP cache traffic statistics";
        input {
          leaf node-location {
            type string;
            mandatory true;
            description
              "Node location";
          }
        }
      }
    }
  }
  augment "/ncs:devices/ncs:device/ncs:rpc" {
    container rpc-clear-arp-cache-location {
      tailf:ncs-device-type "netconf";
      tailf:display-when "not(../../ncs:module) or ../../ncs:module[ncs:name='Cisco-IOS-XR-ipv4-arp-act']";
      tailf:action clear-arp-cache-location {
        tailf:actionpoint ncsproxy {
          tailf:internal;
        }
        description
          "clear ARP cache for given node";
        input {
          leaf node-location {
            type string;
            mandatory true;
            description
              "Node location";
          }
        }
      }
    }
  }
  augment "/ncs:devices/ncs:device-group/ncs:ned-id/ncs:rpc" {
    container rpc-clear-arp-cache-location {
      tailf:ncs-device-type "netconf";
      tailf:display-when "/ncs:devices/ncs:device[ncs:name=current()/../../../ncs:member]/ncs:module[ncs:name='Cisco-IOS-XR-ipv4-arp-act']";
      tailf:action clear-arp-cache-location {
        tailf:actionpoint ncsproxy {
          tailf:internal;
        }
        description
          "clear ARP cache for given node";
        input {
          leaf node-location {
            type string;
            mandatory true;
            description
              "Node location";
          }
        }
      }
    }
  }
  augment "/ncs:devices/ncs:device/ncs:rpc" {
    container rpc-clear-arp-api-stats-location {
      tailf:ncs-device-type "netconf";
      tailf:display-when "not(../../ncs:module) or ../../ncs:module[ncs:name='Cisco-IOS-XR-ipv4-arp-act']";
      tailf:action clear-arp-api-stats-location {
        tailf:actionpoint ncsproxy {
          tailf:internal;
        }
        description
          "Clear ARP API stats location";
        input {
          leaf node-location {
            type string;
            mandatory true;
            description
              "Node location";
          }
        }
      }
    }
  }
  augment "/ncs:devices/ncs:device-group/ncs:ned-id/ncs:rpc" {
    container rpc-clear-arp-api-stats-location {
      tailf:ncs-device-type "netconf";
      tailf:display-when "/ncs:devices/ncs:device[ncs:name=current()/../../../ncs:member]/ncs:module[ncs:name='Cisco-IOS-XR-ipv4-arp-act']";
      tailf:action clear-arp-api-stats-location {
        tailf:actionpoint ncsproxy {
          tailf:internal;
        }
        description
          "Clear ARP API stats location";
        input {
          leaf node-location {
            type string;
            mandatory true;
            description
              "Node location";
          }
        }
      }
    }
  }
  augment "/ncs:devices/ncs:device/ncs:rpc" {
    container rpc-clear-arp-api-stats-api {
      tailf:ncs-device-type "netconf";
      tailf:display-when "not(../../ncs:module) or ../../ncs:module[ncs:name='Cisco-IOS-XR-ipv4-arp-act']";
      tailf:action clear-arp-api-stats-api {
        tailf:actionpoint ncsproxy {
          tailf:internal;
        }
        description
          "Clear ARP API stats API";
        input {
          leaf name {
            type string;
            mandatory true;
            description
              "Name of api";
          }
        }
      }
    }
  }
  augment "/ncs:devices/ncs:device-group/ncs:ned-id/ncs:rpc" {
    container rpc-clear-arp-api-stats-api {
      tailf:ncs-device-type "netconf";
      tailf:display-when "/ncs:devices/ncs:device[ncs:name=current()/../../../ncs:member]/ncs:module[ncs:name='Cisco-IOS-XR-ipv4-arp-act']";
      tailf:action clear-arp-api-stats-api {
        tailf:actionpoint ncsproxy {
          tailf:internal;
        }
        description
          "Clear ARP API stats API";
        input {
          leaf name {
            type string;
            mandatory true;
            description
              "Name of api";
          }
        }
      }
    }
  }
}

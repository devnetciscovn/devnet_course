module Cisco-IOS-XR-lpts-pa-act {
  // Generated by yanger -t ncs
  tailf:mount-id "cisco-iosxr-nc-7.3:cisco-iosxr-nc-7.3";
  tailf:ncs-device-type "netconf";

  namespace "http://cisco.com/ns/yang/Cisco-IOS-XR-lpts-pa-act";
  prefix lpts-pa-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

        Copyright (c) 2016-2020 by Cisco Systems, Inc.
            All rights reserved.";

  revision 2020-09-20 {
    description
      "Initial revision";
    semver:module-version "1.0.0";
  }

  augment "/ncs:devices/ncs:device/ncs:rpc" {
    container rpc-clear-lpts-client-times {
      tailf:ncs-device-type "netconf";
      tailf:display-when "not(../../ncs:module) or ../../ncs:module[ncs:name='Cisco-IOS-XR-lpts-pa-act']";
      tailf:action clear-lpts-client-times {
        tailf:actionpoint ncsproxy {
          tailf:internal;
        }
        description
          "Clear lpts client times ";
      }
    }
  }
  augment "/ncs:devices/ncs:device-group/ncs:ned-id/ncs:rpc" {
    container rpc-clear-lpts-client-times {
      tailf:ncs-device-type "netconf";
      tailf:display-when "/ncs:devices/ncs:device[ncs:name=current()/../../../ncs:member]/ncs:module[ncs:name='Cisco-IOS-XR-lpts-pa-act']";
      tailf:action clear-lpts-client-times {
        tailf:actionpoint ncsproxy {
          tailf:internal;
        }
        description
          "Clear lpts client times ";
      }
    }
  }
  augment "/ncs:devices/ncs:device/ncs:rpc" {
    container rpc-clear-lpts-internal-queue-pa-statistics {
      tailf:ncs-device-type "netconf";
      tailf:display-when "not(../../ncs:module) or ../../ncs:module[ncs:name='Cisco-IOS-XR-lpts-pa-act']";
      tailf:action clear-lpts-internal-queue-pa-statistics {
        tailf:actionpoint ncsproxy {
          tailf:internal;
        }
        description
          "Clear lpts internal stats ";
      }
    }
  }
  augment "/ncs:devices/ncs:device-group/ncs:ned-id/ncs:rpc" {
    container rpc-clear-lpts-internal-queue-pa-statistics {
      tailf:ncs-device-type "netconf";
      tailf:display-when "/ncs:devices/ncs:device[ncs:name=current()/../../../ncs:member]/ncs:module[ncs:name='Cisco-IOS-XR-lpts-pa-act']";
      tailf:action clear-lpts-internal-queue-pa-statistics {
        tailf:actionpoint ncsproxy {
          tailf:internal;
        }
        description
          "Clear lpts internal stats ";
      }
    }
  }
}

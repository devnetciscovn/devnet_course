module Cisco-IOS-XR-infra-rt-check-cfg {
  // Generated by yanger -t ncs
  tailf:mount-id "cisco-iosxr-nc-7.3:cisco-iosxr-nc-7.3";
  tailf:ncs-device-type "netconf";

  namespace "http://cisco.com/ns/yang/Cisco-IOS-XR-infra-rt-check-cfg";
  prefix infra-rt-check-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-rt-check package configuration.

     This module contains definitions
     for the following management objects:
       rcc: RCC (Route Consistency Checker) configuration

     Copyright (c) 2013-2020 by Cisco Systems, Inc.
     All rights reserved.";

  revision 2020-07-21 {
    description
      "Removed Mulicast SAFI from RCC/LCC config which has never been supported.";
    semver:module-version "2.0.0";
  }
  revision 2019-04-05 {
    description
      "Establish semantic version baseline.";
    semver:module-version "1.0.1";
  }
  revision 2015-11-09 {
    description
      "IOS XR 6.0 revision.";
  }

  grouping ncs_template_UNICAST {
    description
      "Common node of ipv4, ipv6";
    container unicast {
      description
        "RCC configuration for unicast";
      uses ncs_template_PERIOD;
      uses ncs_template_ENABLE;
    }
  }

  grouping ncs_template_PERIOD {
    description
      "Common node of unicast, lcc";
    leaf period {
      type string;
      units "millisecond";
      description
        "Period of check in milliseconds";
    }
  }

  grouping ncs_template_ENABLE {
    description
      "Common node of unicast, lcc";
    leaf enable {
      type empty;
      description
        "Enable RCC/LCC";
    }
  }

  grouping ncs_template_LCC {
    description
      "Common node of ipv4, ipv6";
    container lcc {
      description
        "IPv4/IPv6 LCC (Label Consistency Checker)
         configuration";
      uses ncs_template_PERIOD;
      uses ncs_template_ENABLE;
    }
  }

  grouping ncs_rpc_notif_UNICAST {
    description
      "Common node of ipv4, ipv6";
    container unicast {
      description
        "RCC configuration for unicast";
      uses ncs_rpc_notif_PERIOD;
      uses ncs_rpc_notif_ENABLE;
    }
  }

  grouping ncs_rpc_notif_PERIOD {
    description
      "Common node of unicast, lcc";
    leaf period {
      type uint32 {
        range "100..600000";
      }
      units "millisecond";
      description
        "Period of check in milliseconds";
    }
  }

  grouping ncs_rpc_notif_ENABLE {
    description
      "Common node of unicast, lcc";
    leaf enable {
      type empty;
      description
        "Enable RCC/LCC";
    }
  }

  grouping ncs_rpc_notif_LCC {
    description
      "Common node of ipv4, ipv6";
    container lcc {
      description
        "IPv4/IPv6 LCC (Label Consistency Checker)
         configuration";
      uses ncs_rpc_notif_PERIOD;
      uses ncs_rpc_notif_ENABLE;
    }
  }

  grouping live_ncs_UNICAST {
    description
      "Common node of ipv4, ipv6";
    container unicast {
      description
        "RCC configuration for unicast";
      uses live_ncs_PERIOD;
      uses live_ncs_ENABLE;
    }
  }

  grouping live_ncs_PERIOD {
    description
      "Common node of unicast, lcc";
    leaf period {
      type uint32 {
        range "100..600000";
      }
      units "millisecond";
      description
        "Period of check in milliseconds";
    }
  }

  grouping live_ncs_ENABLE {
    description
      "Common node of unicast, lcc";
    leaf enable {
      type empty;
      description
        "Enable RCC/LCC";
    }
  }

  grouping live_ncs_LCC {
    description
      "Common node of ipv4, ipv6";
    container lcc {
      description
        "IPv4/IPv6 LCC (Label Consistency Checker)
         configuration";
      uses live_ncs_PERIOD;
      uses live_ncs_ENABLE;
    }
  }

  grouping UNICAST {
    description
      "Common node of ipv4, ipv6";
    container unicast {
      description
        "RCC configuration for unicast";
      uses PERIOD;
      uses ENABLE;
    }
  }

  grouping PERIOD {
    description
      "Common node of unicast, lcc";
    leaf period {
      type uint32 {
        range "100..600000";
      }
      units "millisecond";
      description
        "Period of check in milliseconds";
    }
  }

  grouping ENABLE {
    description
      "Common node of unicast, lcc";
    leaf enable {
      type empty;
      description
        "Enable RCC/LCC";
    }
  }

  grouping LCC {
    description
      "Common node of ipv4, ipv6";
    container lcc {
      description
        "IPv4/IPv6 LCC (Label Consistency Checker)
         configuration";
      uses PERIOD;
      uses ENABLE;
    }
  }

  augment "/ncs:devices/ncs:device/ncs:config" {
    container rcc {
      tailf:ncs-device-type "netconf";
      tailf:display-when "not(../../ncs:module) or ../../ncs:module[ncs:name='Cisco-IOS-XR-infra-rt-check-cfg']";
      description
        "RCC (Route Consistency Checker) configuration";
      container ipv6 {
        description
          "RCC/LCC configuration for IPv6";
        uses LCC;
        uses UNICAST;
      }
      container ipv4 {
        description
          "RCC/LCC configuration for IPv4";
        uses LCC;
        uses UNICAST;
      }
    }
  }
  augment "/ncs:devices/ncs:device/ncs:live-status" {
    container rcc {
      tailf:ncs-device-type "netconf";
      tailf:display-when "not(../../ncs:module) or ../../ncs:module[ncs:name='Cisco-IOS-XR-infra-rt-check-cfg'] or (../../ncs:live-status-protocol[not(ncs:capability)]) or (../../ncs:live-status-protocol/ncs:capability/ncs:module[.='Cisco-IOS-XR-infra-rt-check-cfg'])";
      description
        "RCC (Route Consistency Checker) configuration";
      container ipv6 {
        description
          "RCC/LCC configuration for IPv6";
        uses live_ncs_LCC;
        uses live_ncs_UNICAST;
      }
      container ipv4 {
        description
          "RCC/LCC configuration for IPv4";
        uses live_ncs_LCC;
        uses live_ncs_UNICAST;
      }
    }
  }
  augment "/ncs:devices/ncs:template/ncs:ned-id/ncs:config" {
    container rcc {
      description
        "RCC (Route Consistency Checker) configuration";
      container ipv6 {
        description
          "RCC/LCC configuration for IPv6";
        uses ncs_template_LCC;
        uses ncs_template_UNICAST;
      }
      container ipv4 {
        description
          "RCC/LCC configuration for IPv4";
        uses ncs_template_LCC;
        uses ncs_template_UNICAST;
      }
    }
  }
}

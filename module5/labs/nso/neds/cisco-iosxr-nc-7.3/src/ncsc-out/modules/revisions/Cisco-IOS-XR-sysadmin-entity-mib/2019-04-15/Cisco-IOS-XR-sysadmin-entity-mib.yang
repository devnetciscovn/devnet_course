module Cisco-IOS-XR-sysadmin-entity-mib {
  // Generated by yanger -t ncs
  tailf:mount-id "cisco-iosxr-nc-7.3:cisco-iosxr-nc-7.3";
  tailf:ncs-device-type "netconf";

  namespace "http://www.cisco.com/ns/yang/Cisco-IOS-XR-sysadmin-entity-mib";
  prefix ENTITY_MIB;

  import ietf-yang-types {
    prefix yang;
  }
  import tailf-common {
    prefix tailf;
  }
  import SNMPv2-TC {
    prefix SNMPv2-TC;
  }
  import SNMP-FRAMEWORK-MIB {
    prefix SNMP-FRAMEWORK-MIB;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright (c) 2015-2020 by Cisco Systems, Inc.
     All rights reserved.";

  revision 2019-04-15 {
    description
      "Establish semantic version baseline.";
    semver:module-version "1.0.0";
  }
  revision 2017-04-12 {
    description
      "Changed namespace and module name";
  }
  revision 1999-12-07 {
    description
      "";
  }

  typedef ncs_template_PhysicalIndex {
    type string;
  }

  typedef ncs_template_PhysicalClass {
    type string;
  }

  typedef ncs_template_SnmpEngineIdOrNone {
    type string;
  }

  typedef ncs_template_entPhysicalContainedInType {
    type string;
  }

  typedef ncs_template_entPhysicalParentRelPosType {
    type string;
  }

  typedef ncs_template_entPhysicalSerialNumType {
    type string;
  }

  typedef ncs_template_entPhysicalAliasType {
    type string;
  }

  typedef ncs_template_entPhysicalAssetIDType {
    type string;
  }

  typedef ncs_template_entLogicalIndexType {
    type string;
  }

  typedef ncs_template_entLogicalCommunityType {
    type string;
  }

  typedef ncs_template_entAliasLogicalIndexOrZeroType {
    type string;
  }

  typedef ncs_rpc_notif_PhysicalIndex {
    type int32 {
      range "1 .. 2147483647";
    }
  }

  typedef ncs_rpc_notif_PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef ncs_rpc_notif_SnmpEngineIdOrNone {
    type tailf:hex-list;
  }

  typedef ncs_rpc_notif_entPhysicalContainedInType {
    type int32 {
      range "0 .. 2147483647";
    }
  }

  typedef ncs_rpc_notif_entPhysicalParentRelPosType {
    type int32 {
      range "-1 .. 2147483647";
    }
  }

  typedef ncs_rpc_notif_entPhysicalSerialNumType {
    type string {
      length "min .. 32";
    }
  }

  typedef ncs_rpc_notif_entPhysicalAliasType {
    type string {
      length "min .. 32";
    }
  }

  typedef ncs_rpc_notif_entPhysicalAssetIDType {
    type string {
      length "min .. 32";
    }
  }

  typedef ncs_rpc_notif_entLogicalIndexType {
    type int32 {
      range "1 .. 2147483647";
    }
  }

  typedef ncs_rpc_notif_entLogicalCommunityType {
    type tailf:hex-list;
  }

  typedef ncs_rpc_notif_entAliasLogicalIndexOrZeroType {
    type int32 {
      range "0 .. 2147483647";
    }
  }

  typedef live_ncs_PhysicalIndex {
    type int32 {
      range "1 .. 2147483647";
    }
  }

  typedef live_ncs_PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef live_ncs_SnmpEngineIdOrNone {
    type tailf:hex-list;
  }

  typedef live_ncs_entPhysicalContainedInType {
    type int32 {
      range "0 .. 2147483647";
    }
  }

  typedef live_ncs_entPhysicalParentRelPosType {
    type int32 {
      range "-1 .. 2147483647";
    }
  }

  typedef live_ncs_entPhysicalSerialNumType {
    type string {
      length "min .. 32";
    }
  }

  typedef live_ncs_entPhysicalAliasType {
    type string {
      length "min .. 32";
    }
  }

  typedef live_ncs_entPhysicalAssetIDType {
    type string {
      length "min .. 32";
    }
  }

  typedef live_ncs_entLogicalIndexType {
    type int32 {
      range "1 .. 2147483647";
    }
  }

  typedef live_ncs_entLogicalCommunityType {
    type tailf:hex-list;
  }

  typedef live_ncs_entAliasLogicalIndexOrZeroType {
    type int32 {
      range "0 .. 2147483647";
    }
  }

  typedef PhysicalIndex {
    type int32 {
      range "1 .. 2147483647";
    }
  }

  typedef PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef SnmpEngineIdOrNone {
    type tailf:hex-list;
  }

  typedef entPhysicalContainedInType {
    type int32 {
      range "0 .. 2147483647";
    }
  }

  typedef entPhysicalParentRelPosType {
    type int32 {
      range "-1 .. 2147483647";
    }
  }

  typedef entPhysicalSerialNumType {
    type string {
      length "min .. 32";
    }
  }

  typedef entPhysicalAliasType {
    type string {
      length "min .. 32";
    }
  }

  typedef entPhysicalAssetIDType {
    type string {
      length "min .. 32";
    }
  }

  typedef entLogicalIndexType {
    type int32 {
      range "1 .. 2147483647";
    }
  }

  typedef entLogicalCommunityType {
    type tailf:hex-list;
  }

  typedef entAliasLogicalIndexOrZeroType {
    type int32 {
      range "0 .. 2147483647";
    }
  }

  augment "/ncs:devices/ncs:device/ncs:config" {
    container ENTITY-MIB {
      tailf:ncs-device-type "netconf";
      tailf:display-when "not(../../ncs:module) or ../../ncs:module[ncs:name='Cisco-IOS-XR-sysadmin-entity-mib']";
      // NCS drop config false container entityGeneral
      // NCS drop config false container entPhysicalTable
      // NCS drop config false container entLogicalTable
      // NCS drop config false container entLPMappingTable
      // NCS drop config false container entAliasMappingTable
      // NCS drop config false container entPhysicalContainsTable
    }
  }
  augment "/ncs:devices/ncs:device/ncs:live-status" {
    container ENTITY-MIB {
      tailf:ncs-device-type "netconf";
      tailf:display-when "not(../../ncs:module) or ../../ncs:module[ncs:name='Cisco-IOS-XR-sysadmin-entity-mib'] or (../../ncs:live-status-protocol[not(ncs:capability)]) or (../../ncs:live-status-protocol/ncs:capability/ncs:module[.='Cisco-IOS-XR-sysadmin-entity-mib'])";
      container entityGeneral {
        leaf entLastChangeTime {
          type yang:timestamp;
        }
      }
      container entPhysicalTable {
        list entPhysicalEntry {
          key "entPhysicalIndex";
          leaf entPhysicalIndex {
            type live_ncs_PhysicalIndex;
          }
          leaf entPhysicalDescr {
            type SNMP-FRAMEWORK-MIB:live_ncs_SnmpAdminString;
          }
          leaf entPhysicalVendorType {
            type SNMPv2-TC:live_ncs_AutonomousType;
          }
          leaf entPhysicalContainedIn {
            type live_ncs_entPhysicalContainedInType;
          }
          leaf entPhysicalClass {
            type live_ncs_PhysicalClass;
          }
          leaf entPhysicalParentRelPos {
            type live_ncs_entPhysicalParentRelPosType;
          }
          leaf entPhysicalName {
            type SNMP-FRAMEWORK-MIB:live_ncs_SnmpAdminString;
          }
          leaf entPhysicalHardwareRev {
            type SNMP-FRAMEWORK-MIB:live_ncs_SnmpAdminString;
          }
          leaf entPhysicalFirmwareRev {
            type SNMP-FRAMEWORK-MIB:live_ncs_SnmpAdminString;
          }
          leaf entPhysicalSoftwareRev {
            type SNMP-FRAMEWORK-MIB:live_ncs_SnmpAdminString;
          }
          leaf entPhysicalSerialNum {
            type live_ncs_entPhysicalSerialNumType;
          }
          leaf entPhysicalMfgName {
            type SNMP-FRAMEWORK-MIB:live_ncs_SnmpAdminString;
          }
          leaf entPhysicalModelName {
            type SNMP-FRAMEWORK-MIB:live_ncs_SnmpAdminString;
          }
          leaf entPhysicalAlias {
            type live_ncs_entPhysicalAliasType;
          }
          leaf entPhysicalAssetID {
            type live_ncs_entPhysicalAssetIDType;
          }
          leaf entPhysicalIsFRU {
            type SNMPv2-TC:live_ncs_TruthValue;
          }
        }
      }
      container entLogicalTable {
        list entLogicalEntry {
          key "entLogicalIndex";
          leaf entLogicalIndex {
            type live_ncs_entLogicalIndexType;
          }
          leaf entLogicalDescr {
            type SNMP-FRAMEWORK-MIB:live_ncs_SnmpAdminString;
          }
          leaf entLogicalType {
            type SNMPv2-TC:live_ncs_AutonomousType;
          }
          leaf entLogicalCommunity {
            type live_ncs_entLogicalCommunityType;
          }
          leaf entLogicalTAddress {
            type SNMPv2-TC:live_ncs_TAddress;
          }
          leaf entLogicalTDomain {
            type SNMPv2-TC:live_ncs_TDomain;
          }
          leaf entLogicalContextEngineID {
            type live_ncs_SnmpEngineIdOrNone;
          }
          leaf entLogicalContextName {
            type SNMP-FRAMEWORK-MIB:live_ncs_SnmpAdminString;
          }
        }
      }
      container entLPMappingTable {
        list entLPMappingEntry {
          key "entLogicalIndex entLPPhysicalIndex";
          leaf entLogicalIndex {
            type live_ncs_entLogicalIndexType;
          }
          leaf entLPPhysicalIndex {
            type live_ncs_PhysicalIndex;
          }
        }
      }
      container entAliasMappingTable {
        list entAliasMappingEntry {
          key "entPhysicalIndex entAliasLogicalIndexOrZero";
          leaf entPhysicalIndex {
            type live_ncs_PhysicalIndex;
          }
          leaf entAliasLogicalIndexOrZero {
            type live_ncs_entAliasLogicalIndexOrZeroType;
          }
          leaf entAliasMappingIdentifier {
            type SNMPv2-TC:live_ncs_RowPointer;
          }
        }
      }
      container entPhysicalContainsTable {
        list entPhysicalContainsEntry {
          key "entPhysicalIndex entPhysicalChildIndex";
          leaf entPhysicalIndex {
            type live_ncs_PhysicalIndex;
          }
          leaf entPhysicalChildIndex {
            type live_ncs_PhysicalIndex;
          }
        }
      }
    }
  }
  augment "/ncs:devices/ncs:template/ncs:ned-id/ncs:config" {
    container ENTITY-MIB {
      // NCS drop config false container entityGeneral
      // NCS drop config false container entPhysicalTable
      // NCS drop config false container entLogicalTable
      // NCS drop config false container entLPMappingTable
      // NCS drop config false container entAliasMappingTable
      // NCS drop config false container entPhysicalContainsTable
    }
  }
}

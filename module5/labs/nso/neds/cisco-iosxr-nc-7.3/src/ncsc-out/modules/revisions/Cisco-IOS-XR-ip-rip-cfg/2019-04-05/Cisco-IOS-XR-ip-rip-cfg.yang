module Cisco-IOS-XR-ip-rip-cfg {
  // Generated by yanger -t ncs
  tailf:mount-id "cisco-iosxr-nc-7.3:cisco-iosxr-nc-7.3";
  tailf:ncs-device-type "netconf";

  namespace "http://cisco.com/ns/yang/Cisco-IOS-XR-ip-rip-cfg";
  prefix ip-rip-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-rip package configuration.

     This module contains definitions
     for the following management objects:
       rip: RIP configuration

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Rip-ext-community {
    type string;
    description
      "Rip ext community";
  }

  typedef ncs_template_Default-redist-route {
    type string;
    description
      "Default redist route";
  }

  typedef ncs_template_Default-information-option {
    type string;
    description
      "Default information option";
  }

  typedef ncs_template_Isis-redist-route {
    type string;
    description
      "Isis redist route";
  }

  typedef ncs_template_Bgp-redist-route {
    type string;
    description
      "Bgp redist route";
  }

  typedef ncs_template_Rip-auth-mode {
    type string;
    description
      "Rip auth mode";
  }

  typedef ncs_rpc_notif_Rip-ext-community {
    type enumeration {
      enum "as" {
        value 0;
        description
          "AS:nn format";
      }
      enum "ipv4-address" {
        value 1;
        description
          "IPV4Address:nn format";
      }
      enum "four-byte-as" {
        value 2;
        description
          "4-byte ASN format";
      }
    }
    description
      "Rip ext community";
  }

  typedef ncs_rpc_notif_Default-redist-route {
    type enumeration {
      enum "all" {
        value 0;
        description
          "All routes";
      }
    }
    description
      "Default redist route";
  }

  typedef ncs_rpc_notif_Default-information-option {
    type enumeration {
      enum "always" {
        value 0;
        description
          "Always";
      }
      enum "policy" {
        value 1;
        description
          "Use route-policy";
      }
    }
    description
      "Default information option";
  }

  typedef ncs_rpc_notif_Isis-redist-route {
    type enumeration {
      enum "level1" {
        value 1;
        description
          "Level-1 routes only";
      }
      enum "level2" {
        value 2;
        description
          "Level-1 routes only";
      }
      enum "level1-and2" {
        value 3;
        description
          "Level-1 and level-2 routes";
      }
    }
    description
      "Isis redist route";
  }

  typedef ncs_rpc_notif_Bgp-redist-route {
    type enumeration {
      enum "all" {
        value 0;
        description
          "All routes";
      }
      enum "internal" {
        value 512;
        description
          "Internal routes only";
      }
      enum "external" {
        value 1024;
        description
          "External routes only";
      }
      enum "local" {
        value 2048;
        description
          "Local routes only";
      }
    }
    description
      "Bgp redist route";
  }

  typedef ncs_rpc_notif_Rip-auth-mode {
    type enumeration {
      enum "text" {
        value 2;
        description
          "Text mode";
      }
      enum "md5" {
        value 3;
        description
          "MD5 mode";
      }
    }
    description
      "Rip auth mode";
  }

  typedef live_ncs_Rip-ext-community {
    type enumeration {
      enum "as" {
        value 0;
        description
          "AS:nn format";
      }
      enum "ipv4-address" {
        value 1;
        description
          "IPV4Address:nn format";
      }
      enum "four-byte-as" {
        value 2;
        description
          "4-byte ASN format";
      }
    }
    description
      "Rip ext community";
  }

  typedef live_ncs_Default-redist-route {
    type enumeration {
      enum "all" {
        value 0;
        description
          "All routes";
      }
    }
    description
      "Default redist route";
  }

  typedef live_ncs_Default-information-option {
    type enumeration {
      enum "always" {
        value 0;
        description
          "Always";
      }
      enum "policy" {
        value 1;
        description
          "Use route-policy";
      }
    }
    description
      "Default information option";
  }

  typedef live_ncs_Isis-redist-route {
    type enumeration {
      enum "level1" {
        value 1;
        description
          "Level-1 routes only";
      }
      enum "level2" {
        value 2;
        description
          "Level-1 routes only";
      }
      enum "level1-and2" {
        value 3;
        description
          "Level-1 and level-2 routes";
      }
    }
    description
      "Isis redist route";
  }

  typedef live_ncs_Bgp-redist-route {
    type enumeration {
      enum "all" {
        value 0;
        description
          "All routes";
      }
      enum "internal" {
        value 512;
        description
          "Internal routes only";
      }
      enum "external" {
        value 1024;
        description
          "External routes only";
      }
      enum "local" {
        value 2048;
        description
          "Local routes only";
      }
    }
    description
      "Bgp redist route";
  }

  typedef live_ncs_Rip-auth-mode {
    type enumeration {
      enum "text" {
        value 2;
        description
          "Text mode";
      }
      enum "md5" {
        value 3;
        description
          "MD5 mode";
      }
    }
    description
      "Rip auth mode";
  }

  typedef Rip-ext-community {
    type enumeration {
      enum "as" {
        value 0;
        description
          "AS:nn format";
      }
      enum "ipv4-address" {
        value 1;
        description
          "IPV4Address:nn format";
      }
      enum "four-byte-as" {
        value 2;
        description
          "4-byte ASN format";
      }
    }
    description
      "Rip ext community";
  }

  typedef Default-redist-route {
    type enumeration {
      enum "all" {
        value 0;
        description
          "All routes";
      }
    }
    description
      "Default redist route";
  }

  typedef Default-information-option {
    type enumeration {
      enum "always" {
        value 0;
        description
          "Always";
      }
      enum "policy" {
        value 1;
        description
          "Use route-policy";
      }
    }
    description
      "Default information option";
  }

  typedef Isis-redist-route {
    type enumeration {
      enum "level1" {
        value 1;
        description
          "Level-1 routes only";
      }
      enum "level2" {
        value 2;
        description
          "Level-1 routes only";
      }
      enum "level1-and2" {
        value 3;
        description
          "Level-1 and level-2 routes";
      }
    }
    description
      "Isis redist route";
  }

  typedef Bgp-redist-route {
    type enumeration {
      enum "all" {
        value 0;
        description
          "All routes";
      }
      enum "internal" {
        value 512;
        description
          "Internal routes only";
      }
      enum "external" {
        value 1024;
        description
          "External routes only";
      }
      enum "local" {
        value 2048;
        description
          "Local routes only";
      }
    }
    description
      "Bgp redist route";
  }

  typedef Rip-auth-mode {
    type enumeration {
      enum "text" {
        value 2;
        description
          "Text mode";
      }
      enum "md5" {
        value 3;
        description
          "MD5 mode";
      }
    }
    description
      "Rip auth mode";
  }

  grouping ncs_template_DISTANCE {
    description
      "Common node of default-vrf, vrf";
    leaf distance {
      type string;
      // NCS drop default statement
      description
        "Administrative distance";
    }
  }

  grouping ncs_template_VALIDATE-SOURCE-DISABLE {
    description
      "Common node of default-vrf, vrf";
    leaf validate-source-disable {
      type empty;
      description
        "Disable validation of source address of routing
         updates";
    }
  }

  grouping ncs_template_AUTO-SUMMARY {
    description
      "Common node of default-vrf, vrf";
    leaf auto-summary {
      type empty;
      description
        "Enable automatic network number summarization";
    }
  }

  grouping ncs_template_TIMERS {
    description
      "Common node of default-vrf, vrf";
    container timers {
      presence "Indicates a timers node is configured.";
      description
        "Various routing timers";
      leaf update-timer {
        type string;
        // NCS drop mandatory statement
        description
          "Interval between updates";
      }
      leaf invalid-timer {
        type string;
        // NCS drop mandatory statement
        description
          "Invalid";
      }
      leaf holddown-timer {
        type string;
        // NCS drop mandatory statement
        description
          "Holddown";
      }
      leaf flush-timer {
        type string;
        // NCS drop mandatory statement
        description
          "Flush";
      }
    }
  }

  grouping ncs_template_REDISTRIBUTION {
    description
      "Common node of default-vrf, vrf";
    container redistribution {
      description
        "Redistribute information from another routing
         protocol";
      container connected {
        presence "enable connected";
        description
          "Redistribute connected routes";
        leaf route-policy-name {
          type string;
          description
            "Route Policy name";
        }
        leaf route-type {
          type ncs_template_Default-redist-route;
          description
            "Route type";
        }
      }
      container bgps {
        description
          "Redistribute BGP routes";
        list bgp {
          // NCS patched for predictable order
          ordered-by user;
          key "asnxx asnyy";
          description
            "Autonomous system number";
          leaf asnxx {
            type string;
            description
              "Higher 16 bits of 4-byte BGP AS number";
          }
          leaf asnyy {
            type string;
            description
              "2-byte or 4-byte BGP AS number";
          }
          leaf policy {
            type string;
            description
              "Route Policy name";
          }
          leaf type {
            type ncs_template_Bgp-redist-route;
            description
              "Route type";
          }
        }
      }
      container isises {
        description
          "Redistribute IS-IS routes";
        list isis {
          // NCS patched for predictable order
          ordered-by user;
          key "isis-name";
          description
            "Redistribute IS-IS routes";
          leaf isis-name {
            type xr:ncs_template_Cisco-ios-xr-string;
            description
              "IS-IS instance name";
          }
          leaf route-policy-name {
            type string;
            description
              "Route Policy name";
          }
          leaf route-type {
            type ncs_template_Isis-redist-route;
            description
              "Route type";
          }
        }
      }
      container eigrp-s {
        description
          "Redistribute EIGRP routes";
        list eigrp {
          // NCS patched for predictable order
          ordered-by user;
          key "as";
          description
            "Redistribute EIGRP routes";
          leaf as {
            type string;
            description
              "Autonomous system number";
          }
          leaf route-policy-name {
            type string;
            description
              "Route Policy name";
          }
          leaf route-type {
            type ncs_template_Default-redist-route;
            description
              "Route type";
          }
        }
      }
      container static {
        presence "enable static";
        description
          "Redistribute static routes";
        leaf route-policy-name {
          type string;
          description
            "Route Policy name";
        }
        leaf route-type {
          type ncs_template_Default-redist-route;
          description
            "Route type";
        }
      }
      container ospfs {
        description
          "Redistribute OSPF routes";
        list ospf {
          // NCS patched for predictable order
          ordered-by user;
          key "ospf-name";
          description
            "Redistribute OSPF routes";
          leaf ospf-name {
            type xr:ncs_template_Cisco-ios-xr-string;
            description
              "Process ID for the OSPF instance";
          }
          leaf route-policy-name {
            type string;
            description
              "Route Policy name";
          }
          leaf internal {
            type string;
            description
              "Internal routes";
          }
          leaf external {
            type string;
            description
              "External routes";
          }
          leaf external-type {
            type string;
            description
              "External route type";
          }
          leaf nssa-external {
            type string;
            description
              "NSSA External routes";
          }
          leaf nssa-external-type {
            type string;
            description
              "NSSA External route type";
          }
        }
      }
    }
  }

  grouping ncs_template_DEFAULT-INFORMATION {
    description
      "Common node of default-vrf, vrf";
    container default-information {
      presence "Indicates a default-information node is configured.";
      description
        "Controls default information origination";
      leaf route-policy-name {
        type string;
        description
          "Route policy name";
      }
      leaf option {
        type ncs_template_Default-information-option;
        // NCS drop mandatory statement
        description
          "Origination option";
      }
    }
  }

  grouping ncs_template_IP-DISTANCE-TABLE {
    description
      "Common node of default-vrf, vrf";
    container ip-distances {
      description
        "Table of IP specific administrative distances";
      list ip-distance {
        // NCS patched for predictable order
        ordered-by user;
        key "address netmask";
        description
          "IP specific administrative distance";
        leaf address {
          type string;
          description
            "IP Source address";
        }
        leaf netmask {
          type string;
          description
            "IP address mask";
        }
        leaf distance {
          type string;
          // NCS drop mandatory statement
          description
            "Administrative distance";
        }
      }
    }
  }

  grouping ncs_template_MAXIMUM-PATHS {
    description
      "Common node of default-vrf, vrf";
    leaf maximum-paths {
      type string;
      // NCS drop default statement
      description
        "Maximum number of paths allowed per route";
    }
  }

  grouping ncs_template_POLICY-IN {
    description
      "Common node of default-vrf, vrf";
    leaf policy-in {
      type string;
      description
        "Route Policy for inbbound routing updates";
    }
  }

  grouping ncs_template_POLICY-OUT {
    description
      "Common node of default-vrf, vrf";
    leaf policy-out {
      type string;
      description
        "Route Policy for outbound routing updates";
    }
  }

  grouping ncs_template_INTERFACE-TABLE {
    description
      "Common node of default-vrf, vrf";
    container interfaces {
      description
        "Table of RIP interfaces";
      list interface {
        // NCS patched for predictable order
        ordered-by user;
        key "interface-name";
        description
          "RIP interface name";
        container authentication {
          presence "Indicates a authentication node is configured.";
          description
            "Authentication keychain and mode";
          leaf keychain {
            type string;
            // NCS drop mandatory statement
            description
              "Name of keychain";
          }
          leaf mode {
            type ncs_template_Rip-auth-mode;
            // NCS drop mandatory statement
            description
              "Authentication mode";
          }
        }
        container site-of-origin {
          description
            "SOO community for prefixes learned over this
             interface";
          leaf type {
            type ncs_template_Rip-ext-community;
            description
              "Extended community type";
          }
          leaf as-xx {
            // NCS drop when statement
            type string;
            description
              "AS Number for AS:nn format";
          }
          leaf as-yy {
            // NCS drop when statement
            type string;
            description
              "32 bit value for AS:nn format";
          }
          leaf as-index {
            // NCS drop when statement
            type string;
            description
              "AS Number Index";
          }
          leaf address {
            // NCS drop when statement
            type string;
            description
              "IPV4 address for IPV4Address:nn format";
          }
          leaf address-index {
            // NCS drop when statement
            type string;
            description
              "16bit value for IPV4Address:nn format";
          }
        }
        container receive-version {
          description
            "RIP versions supported for receiving
             advertisements";
          leaf version1 {
            type string;
            description
              "Support RIP version 1";
          }
          leaf version2 {
            type string;
            // NCS drop default statement
            description
              "Support RIP version 2";
          }
        }
        container send-version {
          description
            "RIP versions supported for sending
             advertisements";
          leaf version1 {
            type string;
            description
              "Support RIP version 1";
          }
          leaf version2 {
            type string;
            // NCS drop default statement
            description
              "Support RIP version 2";
          }
        }
        leaf broadcast-for-v2 {
          type empty;
          description
            "Send RIP v2 output packets to broadcast
             address";
        }
        leaf poison-reverse {
          type empty;
          description
            "Enable poison reverse";
        }
        leaf passive {
          type empty;
          description
            "Suppress routing updates on this interface";
        }
        leaf enable {
          type empty;
          description
            "Starts RIP interface configuration";
        }
        leaf policy-out {
          type string;
          description
            "Route Policy for outbound routing updates";
        }
        leaf accept-metric-zero {
          type empty;
          description
            "Accept RIP updates with metric 0";
        }
        leaf policy-in {
          type string;
          description
            "Route Policy for inbound routing updates";
        }
        leaf split-horizon-disable {
          type empty;
          description
            "Disable split horizon";
        }
        leaf interface-name {
          type xr:ncs_template_Interface-name;
          description
            "Interface name";
        }
      }
    }
  }

  grouping ncs_template_BROADCAST-FOR-V2 {
    description
      "Common node of default-vrf, vrf";
    leaf broadcast-for-v2 {
      type empty;
      description
        "Send RIP v2 output packets to broadcast address";
    }
  }

  grouping ncs_template_NSF {
    description
      "Common node of default-vrf, vrf";
    leaf nsf {
      type empty;
      description
        "Enable Cisco Non Stop Forwarding";
    }
  }

  grouping ncs_template_NEIGHBOR-TABLE {
    description
      "Common node of default-vrf, vrf";
    container neighbors {
      description
        "Configure RIP Neighbors";
      list neighbor {
        // NCS patched for predictable order
        ordered-by user;
        key "neighbor-address";
        description
          "Neighbor address";
        leaf neighbor-address {
          type string;
          description
            "IPv4 address";
        }
      }
    }
  }

  grouping ncs_template_OUTPUT-DELAY {
    description
      "Common node of default-vrf, vrf";
    leaf output-delay {
      type string;
      units "millisecond";
      description
        "Inter-packet delay for RIP updates";
    }
  }

  grouping ncs_template_DEFAULT-METRIC {
    description
      "Common node of default-vrf, vrf";
    leaf default-metric {
      type string;
      description
        "Default metric of redistributed routes";
    }
  }

  grouping ncs_rpc_notif_DISTANCE {
    description
      "Common node of default-vrf, vrf";
    leaf distance {
      type uint32 {
        range "0..255";
      }
      default "120";
      description
        "Administrative distance";
    }
  }

  grouping ncs_rpc_notif_VALIDATE-SOURCE-DISABLE {
    description
      "Common node of default-vrf, vrf";
    leaf validate-source-disable {
      type empty;
      description
        "Disable validation of source address of routing
         updates";
    }
  }

  grouping ncs_rpc_notif_AUTO-SUMMARY {
    description
      "Common node of default-vrf, vrf";
    leaf auto-summary {
      type empty;
      description
        "Enable automatic network number summarization";
    }
  }

  grouping ncs_rpc_notif_TIMERS {
    description
      "Common node of default-vrf, vrf";
    container timers {
      presence "Indicates a timers node is configured.";
      description
        "Various routing timers";
      leaf update-timer {
        type uint32 {
          range "5..50000";
        }
        mandatory true;
        description
          "Interval between updates";
      }
      leaf invalid-timer {
        type uint32 {
          range "15..200000";
        }
        mandatory true;
        description
          "Invalid";
      }
      leaf holddown-timer {
        type uint32 {
          range "15..200000";
        }
        mandatory true;
        description
          "Holddown";
      }
      leaf flush-timer {
        type uint32 {
          range "16..250000";
        }
        mandatory true;
        description
          "Flush";
      }
    }
  }

  grouping ncs_rpc_notif_REDISTRIBUTION {
    description
      "Common node of default-vrf, vrf";
    container redistribution {
      description
        "Redistribute information from another routing
         protocol";
      container connected {
        presence "enable connected";
        description
          "Redistribute connected routes";
        leaf route-policy-name {
          type string;
          description
            "Route Policy name";
        }
        leaf route-type {
          type ncs_rpc_notif_Default-redist-route;
          description
            "Route type";
        }
      }
      container bgps {
        description
          "Redistribute BGP routes";
        list bgp {
          key "asnxx asnyy";
          description
            "Autonomous system number";
          leaf asnxx {
            type uint32 {
              range "0..65535";
            }
            description
              "Higher 16 bits of 4-byte BGP AS number";
          }
          leaf asnyy {
            type uint32 {
              range "0..4294967295";
            }
            description
              "2-byte or 4-byte BGP AS number";
          }
          leaf policy {
            type string;
            description
              "Route Policy name";
          }
          leaf type {
            type ncs_rpc_notif_Bgp-redist-route;
            description
              "Route type";
          }
        }
      }
      container isises {
        description
          "Redistribute IS-IS routes";
        list isis {
          key "isis-name";
          description
            "Redistribute IS-IS routes";
          leaf isis-name {
            type xr:ncs_rpc_notif_Cisco-ios-xr-string;
            description
              "IS-IS instance name";
          }
          leaf route-policy-name {
            type string;
            description
              "Route Policy name";
          }
          leaf route-type {
            type ncs_rpc_notif_Isis-redist-route;
            description
              "Route type";
          }
        }
      }
      container eigrp-s {
        description
          "Redistribute EIGRP routes";
        list eigrp {
          key "as";
          description
            "Redistribute EIGRP routes";
          leaf as {
            type uint32 {
              range "1..65535";
            }
            description
              "Autonomous system number";
          }
          leaf route-policy-name {
            type string;
            description
              "Route Policy name";
          }
          leaf route-type {
            type ncs_rpc_notif_Default-redist-route;
            description
              "Route type";
          }
        }
      }
      container static {
        presence "enable static";
        description
          "Redistribute static routes";
        leaf route-policy-name {
          type string;
          description
            "Route Policy name";
        }
        leaf route-type {
          type ncs_rpc_notif_Default-redist-route;
          description
            "Route type";
        }
      }
      container ospfs {
        description
          "Redistribute OSPF routes";
        list ospf {
          key "ospf-name";
          description
            "Redistribute OSPF routes";
          leaf ospf-name {
            type xr:ncs_rpc_notif_Cisco-ios-xr-string;
            description
              "Process ID for the OSPF instance";
          }
          leaf route-policy-name {
            type string;
            description
              "Route Policy name";
          }
          leaf internal {
            type boolean;
            description
              "Internal routes";
          }
          leaf external {
            type boolean;
            description
              "External routes";
          }
          leaf external-type {
            type uint32 {
              range "0..2";
            }
            description
              "External route type";
          }
          leaf nssa-external {
            type boolean;
            description
              "NSSA External routes";
          }
          leaf nssa-external-type {
            type uint32 {
              range "0..2";
            }
            description
              "NSSA External route type";
          }
        }
      }
    }
  }

  grouping ncs_rpc_notif_DEFAULT-INFORMATION {
    description
      "Common node of default-vrf, vrf";
    container default-information {
      presence "Indicates a default-information node is configured.";
      description
        "Controls default information origination";
      leaf route-policy-name {
        type string;
        description
          "Route policy name";
      }
      leaf option {
        type ncs_rpc_notif_Default-information-option;
        mandatory true;
        description
          "Origination option";
      }
    }
  }

  grouping ncs_rpc_notif_IP-DISTANCE-TABLE {
    description
      "Common node of default-vrf, vrf";
    container ip-distances {
      description
        "Table of IP specific administrative distances";
      list ip-distance {
        key "address netmask";
        description
          "IP specific administrative distance";
        leaf address {
          type inet:ipv4-address-no-zone;
          description
            "IP Source address";
        }
        leaf netmask {
          type inet:ipv4-address-no-zone;
          description
            "IP address mask";
        }
        leaf distance {
          type uint32 {
            range "0..255";
          }
          mandatory true;
          description
            "Administrative distance";
        }
      }
    }
  }

  grouping ncs_rpc_notif_MAXIMUM-PATHS {
    description
      "Common node of default-vrf, vrf";
    leaf maximum-paths {
      type uint32 {
        range "1..128";
      }
      default "4";
      description
        "Maximum number of paths allowed per route";
    }
  }

  grouping ncs_rpc_notif_POLICY-IN {
    description
      "Common node of default-vrf, vrf";
    leaf policy-in {
      type string;
      description
        "Route Policy for inbbound routing updates";
    }
  }

  grouping ncs_rpc_notif_POLICY-OUT {
    description
      "Common node of default-vrf, vrf";
    leaf policy-out {
      type string;
      description
        "Route Policy for outbound routing updates";
    }
  }

  grouping ncs_rpc_notif_INTERFACE-TABLE {
    description
      "Common node of default-vrf, vrf";
    container interfaces {
      description
        "Table of RIP interfaces";
      list interface {
        key "interface-name";
        description
          "RIP interface name";
        container authentication {
          presence "Indicates a authentication node is configured.";
          description
            "Authentication keychain and mode";
          leaf keychain {
            type string;
            mandatory true;
            description
              "Name of keychain";
          }
          leaf mode {
            type ncs_rpc_notif_Rip-auth-mode;
            mandatory true;
            description
              "Authentication mode";
          }
        }
        container site-of-origin {
          description
            "SOO community for prefixes learned over this
             interface";
          leaf type {
            type ncs_rpc_notif_Rip-ext-community;
            description
              "Extended community type";
          }
          leaf as-xx {
            when "../type != 'as' and ../type != 'ipv4-address'" {
              tailf:xpath-root 3;
              description
                "../Type != AS and ../Type != IPV4Address";
            }
            type uint32 {
              range "0..65535";
            }
            description
              "AS Number for AS:nn format";
          }
          leaf as-yy {
            when "../type != 'ipv4-address'" {
              tailf:xpath-root 3;
              description
                "../Type != IPV4Address";
            }
            type uint32 {
              range "0..4294967295";
            }
            description
              "32 bit value for AS:nn format";
          }
          leaf as-index {
            when "../type != 'ipv4-address'" {
              tailf:xpath-root 3;
              description
                "../Type != IPV4Address";
            }
            type uint32 {
              range "0..4294967295";
            }
            description
              "AS Number Index";
          }
          leaf address {
            when "../type = 'ipv4-address'" {
              tailf:xpath-root 3;
              description
                "../Type = IPV4Address";
            }
            type inet:ipv4-address-no-zone;
            description
              "IPV4 address for IPV4Address:nn format";
          }
          leaf address-index {
            when "../type = 'ipv4-address'" {
              tailf:xpath-root 3;
              description
                "../Type = IPV4Address";
            }
            type uint32 {
              range "0..65535";
            }
            description
              "16bit value for IPV4Address:nn format";
          }
        }
        container receive-version {
          description
            "RIP versions supported for receiving
             advertisements";
          leaf version1 {
            type boolean;
            description
              "Support RIP version 1";
          }
          leaf version2 {
            type boolean;
            default "true";
            description
              "Support RIP version 2";
          }
        }
        container send-version {
          description
            "RIP versions supported for sending
             advertisements";
          leaf version1 {
            type boolean;
            description
              "Support RIP version 1";
          }
          leaf version2 {
            type boolean;
            default "true";
            description
              "Support RIP version 2";
          }
        }
        leaf broadcast-for-v2 {
          type empty;
          description
            "Send RIP v2 output packets to broadcast
             address";
        }
        leaf poison-reverse {
          type empty;
          description
            "Enable poison reverse";
        }
        leaf passive {
          type empty;
          description
            "Suppress routing updates on this interface";
        }
        leaf enable {
          type empty;
          description
            "Starts RIP interface configuration";
        }
        leaf policy-out {
          type string;
          description
            "Route Policy for outbound routing updates";
        }
        leaf accept-metric-zero {
          type empty;
          description
            "Accept RIP updates with metric 0";
        }
        leaf policy-in {
          type string;
          description
            "Route Policy for inbound routing updates";
        }
        leaf split-horizon-disable {
          type empty;
          description
            "Disable split horizon";
        }
        leaf interface-name {
          type xr:ncs_rpc_notif_Interface-name;
          description
            "Interface name";
        }
      }
    }
  }

  grouping ncs_rpc_notif_BROADCAST-FOR-V2 {
    description
      "Common node of default-vrf, vrf";
    leaf broadcast-for-v2 {
      type empty;
      description
        "Send RIP v2 output packets to broadcast address";
    }
  }

  grouping ncs_rpc_notif_NSF {
    description
      "Common node of default-vrf, vrf";
    leaf nsf {
      type empty;
      description
        "Enable Cisco Non Stop Forwarding";
    }
  }

  grouping ncs_rpc_notif_NEIGHBOR-TABLE {
    description
      "Common node of default-vrf, vrf";
    container neighbors {
      description
        "Configure RIP Neighbors";
      list neighbor {
        key "neighbor-address";
        description
          "Neighbor address";
        leaf neighbor-address {
          type inet:ipv4-address-no-zone;
          description
            "IPv4 address";
        }
      }
    }
  }

  grouping ncs_rpc_notif_OUTPUT-DELAY {
    description
      "Common node of default-vrf, vrf";
    leaf output-delay {
      type uint32 {
        range "8..50";
      }
      units "millisecond";
      description
        "Inter-packet delay for RIP updates";
    }
  }

  grouping ncs_rpc_notif_DEFAULT-METRIC {
    description
      "Common node of default-vrf, vrf";
    leaf default-metric {
      type uint32 {
        range "0..16";
      }
      description
        "Default metric of redistributed routes";
    }
  }

  grouping live_ncs_DISTANCE {
    description
      "Common node of default-vrf, vrf";
    leaf distance {
      type uint32 {
        range "0..255";
      }
      // NCS drop default statement
      description
        "Administrative distance";
    }
  }

  grouping live_ncs_VALIDATE-SOURCE-DISABLE {
    description
      "Common node of default-vrf, vrf";
    leaf validate-source-disable {
      type empty;
      description
        "Disable validation of source address of routing
         updates";
    }
  }

  grouping live_ncs_AUTO-SUMMARY {
    description
      "Common node of default-vrf, vrf";
    leaf auto-summary {
      type empty;
      description
        "Enable automatic network number summarization";
    }
  }

  grouping live_ncs_TIMERS {
    description
      "Common node of default-vrf, vrf";
    container timers {
      presence "Indicates a timers node is configured.";
      description
        "Various routing timers";
      leaf update-timer {
        type uint32 {
          range "5..50000";
        }
        // NCS drop mandatory statement
        description
          "Interval between updates";
      }
      leaf invalid-timer {
        type uint32 {
          range "15..200000";
        }
        // NCS drop mandatory statement
        description
          "Invalid";
      }
      leaf holddown-timer {
        type uint32 {
          range "15..200000";
        }
        // NCS drop mandatory statement
        description
          "Holddown";
      }
      leaf flush-timer {
        type uint32 {
          range "16..250000";
        }
        // NCS drop mandatory statement
        description
          "Flush";
      }
    }
  }

  grouping live_ncs_REDISTRIBUTION {
    description
      "Common node of default-vrf, vrf";
    container redistribution {
      description
        "Redistribute information from another routing
         protocol";
      container connected {
        presence "enable connected";
        description
          "Redistribute connected routes";
        leaf route-policy-name {
          type string;
          description
            "Route Policy name";
        }
        leaf route-type {
          type live_ncs_Default-redist-route;
          description
            "Route type";
        }
      }
      container bgps {
        description
          "Redistribute BGP routes";
        list bgp {
          key "asnxx asnyy";
          description
            "Autonomous system number";
          leaf asnxx {
            type uint32 {
              range "0..65535";
            }
            description
              "Higher 16 bits of 4-byte BGP AS number";
          }
          leaf asnyy {
            type uint32 {
              range "0..4294967295";
            }
            description
              "2-byte or 4-byte BGP AS number";
          }
          leaf policy {
            type string;
            description
              "Route Policy name";
          }
          leaf type {
            type live_ncs_Bgp-redist-route;
            description
              "Route type";
          }
        }
      }
      container isises {
        description
          "Redistribute IS-IS routes";
        list isis {
          key "isis-name";
          description
            "Redistribute IS-IS routes";
          leaf isis-name {
            type xr:live_ncs_Cisco-ios-xr-string;
            description
              "IS-IS instance name";
          }
          leaf route-policy-name {
            type string;
            description
              "Route Policy name";
          }
          leaf route-type {
            type live_ncs_Isis-redist-route;
            description
              "Route type";
          }
        }
      }
      container eigrp-s {
        description
          "Redistribute EIGRP routes";
        list eigrp {
          key "as";
          description
            "Redistribute EIGRP routes";
          leaf as {
            type uint32 {
              range "1..65535";
            }
            description
              "Autonomous system number";
          }
          leaf route-policy-name {
            type string;
            description
              "Route Policy name";
          }
          leaf route-type {
            type live_ncs_Default-redist-route;
            description
              "Route type";
          }
        }
      }
      container static {
        presence "enable static";
        description
          "Redistribute static routes";
        leaf route-policy-name {
          type string;
          description
            "Route Policy name";
        }
        leaf route-type {
          type live_ncs_Default-redist-route;
          description
            "Route type";
        }
      }
      container ospfs {
        description
          "Redistribute OSPF routes";
        list ospf {
          key "ospf-name";
          description
            "Redistribute OSPF routes";
          leaf ospf-name {
            type xr:live_ncs_Cisco-ios-xr-string;
            description
              "Process ID for the OSPF instance";
          }
          leaf route-policy-name {
            type string;
            description
              "Route Policy name";
          }
          leaf internal {
            type boolean;
            description
              "Internal routes";
          }
          leaf external {
            type boolean;
            description
              "External routes";
          }
          leaf external-type {
            type uint32 {
              range "0..2";
            }
            description
              "External route type";
          }
          leaf nssa-external {
            type boolean;
            description
              "NSSA External routes";
          }
          leaf nssa-external-type {
            type uint32 {
              range "0..2";
            }
            description
              "NSSA External route type";
          }
        }
      }
    }
  }

  grouping live_ncs_DEFAULT-INFORMATION {
    description
      "Common node of default-vrf, vrf";
    container default-information {
      presence "Indicates a default-information node is configured.";
      description
        "Controls default information origination";
      leaf route-policy-name {
        type string;
        description
          "Route policy name";
      }
      leaf option {
        type live_ncs_Default-information-option;
        // NCS drop mandatory statement
        description
          "Origination option";
      }
    }
  }

  grouping live_ncs_IP-DISTANCE-TABLE {
    description
      "Common node of default-vrf, vrf";
    container ip-distances {
      description
        "Table of IP specific administrative distances";
      list ip-distance {
        key "address netmask";
        description
          "IP specific administrative distance";
        leaf address {
          type inet:ipv4-address-no-zone;
          description
            "IP Source address";
        }
        leaf netmask {
          type inet:ipv4-address-no-zone;
          description
            "IP address mask";
        }
        leaf distance {
          type uint32 {
            range "0..255";
          }
          // NCS drop mandatory statement
          description
            "Administrative distance";
        }
      }
    }
  }

  grouping live_ncs_MAXIMUM-PATHS {
    description
      "Common node of default-vrf, vrf";
    leaf maximum-paths {
      type uint32 {
        range "1..128";
      }
      // NCS drop default statement
      description
        "Maximum number of paths allowed per route";
    }
  }

  grouping live_ncs_POLICY-IN {
    description
      "Common node of default-vrf, vrf";
    leaf policy-in {
      type string;
      description
        "Route Policy for inbbound routing updates";
    }
  }

  grouping live_ncs_POLICY-OUT {
    description
      "Common node of default-vrf, vrf";
    leaf policy-out {
      type string;
      description
        "Route Policy for outbound routing updates";
    }
  }

  grouping live_ncs_INTERFACE-TABLE {
    description
      "Common node of default-vrf, vrf";
    container interfaces {
      description
        "Table of RIP interfaces";
      list interface {
        key "interface-name";
        description
          "RIP interface name";
        container authentication {
          presence "Indicates a authentication node is configured.";
          description
            "Authentication keychain and mode";
          leaf keychain {
            type string;
            // NCS drop mandatory statement
            description
              "Name of keychain";
          }
          leaf mode {
            type live_ncs_Rip-auth-mode;
            // NCS drop mandatory statement
            description
              "Authentication mode";
          }
        }
        container site-of-origin {
          description
            "SOO community for prefixes learned over this
             interface";
          leaf type {
            type live_ncs_Rip-ext-community;
            description
              "Extended community type";
          }
          leaf as-xx {
            // NCS drop when statement
            type uint32 {
              range "0..65535";
            }
            description
              "AS Number for AS:nn format";
          }
          leaf as-yy {
            // NCS drop when statement
            type uint32 {
              range "0..4294967295";
            }
            description
              "32 bit value for AS:nn format";
          }
          leaf as-index {
            // NCS drop when statement
            type uint32 {
              range "0..4294967295";
            }
            description
              "AS Number Index";
          }
          leaf address {
            // NCS drop when statement
            type inet:ipv4-address-no-zone;
            description
              "IPV4 address for IPV4Address:nn format";
          }
          leaf address-index {
            // NCS drop when statement
            type uint32 {
              range "0..65535";
            }
            description
              "16bit value for IPV4Address:nn format";
          }
        }
        container receive-version {
          description
            "RIP versions supported for receiving
             advertisements";
          leaf version1 {
            type boolean;
            description
              "Support RIP version 1";
          }
          leaf version2 {
            type boolean;
            // NCS drop default statement
            description
              "Support RIP version 2";
          }
        }
        container send-version {
          description
            "RIP versions supported for sending
             advertisements";
          leaf version1 {
            type boolean;
            description
              "Support RIP version 1";
          }
          leaf version2 {
            type boolean;
            // NCS drop default statement
            description
              "Support RIP version 2";
          }
        }
        leaf broadcast-for-v2 {
          type empty;
          description
            "Send RIP v2 output packets to broadcast
             address";
        }
        leaf poison-reverse {
          type empty;
          description
            "Enable poison reverse";
        }
        leaf passive {
          type empty;
          description
            "Suppress routing updates on this interface";
        }
        leaf enable {
          type empty;
          description
            "Starts RIP interface configuration";
        }
        leaf policy-out {
          type string;
          description
            "Route Policy for outbound routing updates";
        }
        leaf accept-metric-zero {
          type empty;
          description
            "Accept RIP updates with metric 0";
        }
        leaf policy-in {
          type string;
          description
            "Route Policy for inbound routing updates";
        }
        leaf split-horizon-disable {
          type empty;
          description
            "Disable split horizon";
        }
        leaf interface-name {
          type xr:live_ncs_Interface-name;
          description
            "Interface name";
        }
      }
    }
  }

  grouping live_ncs_BROADCAST-FOR-V2 {
    description
      "Common node of default-vrf, vrf";
    leaf broadcast-for-v2 {
      type empty;
      description
        "Send RIP v2 output packets to broadcast address";
    }
  }

  grouping live_ncs_NSF {
    description
      "Common node of default-vrf, vrf";
    leaf nsf {
      type empty;
      description
        "Enable Cisco Non Stop Forwarding";
    }
  }

  grouping live_ncs_NEIGHBOR-TABLE {
    description
      "Common node of default-vrf, vrf";
    container neighbors {
      description
        "Configure RIP Neighbors";
      list neighbor {
        key "neighbor-address";
        description
          "Neighbor address";
        leaf neighbor-address {
          type inet:ipv4-address-no-zone;
          description
            "IPv4 address";
        }
      }
    }
  }

  grouping live_ncs_OUTPUT-DELAY {
    description
      "Common node of default-vrf, vrf";
    leaf output-delay {
      type uint32 {
        range "8..50";
      }
      units "millisecond";
      description
        "Inter-packet delay for RIP updates";
    }
  }

  grouping live_ncs_DEFAULT-METRIC {
    description
      "Common node of default-vrf, vrf";
    leaf default-metric {
      type uint32 {
        range "0..16";
      }
      description
        "Default metric of redistributed routes";
    }
  }

  grouping DISTANCE {
    description
      "Common node of default-vrf, vrf";
    leaf distance {
      type uint32 {
        range "0..255";
      }
      default "120";
      description
        "Administrative distance";
    }
  }

  grouping VALIDATE-SOURCE-DISABLE {
    description
      "Common node of default-vrf, vrf";
    leaf validate-source-disable {
      type empty;
      description
        "Disable validation of source address of routing
         updates";
    }
  }

  grouping AUTO-SUMMARY {
    description
      "Common node of default-vrf, vrf";
    leaf auto-summary {
      type empty;
      description
        "Enable automatic network number summarization";
    }
  }

  grouping TIMERS {
    description
      "Common node of default-vrf, vrf";
    container timers {
      presence "Indicates a timers node is configured.";
      description
        "Various routing timers";
      leaf update-timer {
        type uint32 {
          range "5..50000";
        }
        mandatory true;
        description
          "Interval between updates";
      }
      leaf invalid-timer {
        type uint32 {
          range "15..200000";
        }
        mandatory true;
        description
          "Invalid";
      }
      leaf holddown-timer {
        type uint32 {
          range "15..200000";
        }
        mandatory true;
        description
          "Holddown";
      }
      leaf flush-timer {
        type uint32 {
          range "16..250000";
        }
        mandatory true;
        description
          "Flush";
      }
    }
  }

  grouping REDISTRIBUTION {
    description
      "Common node of default-vrf, vrf";
    container redistribution {
      description
        "Redistribute information from another routing
         protocol";
      container connected {
        presence "enable connected";
        description
          "Redistribute connected routes";
        leaf route-policy-name {
          type string;
          description
            "Route Policy name";
        }
        leaf route-type {
          type Default-redist-route;
          description
            "Route type";
        }
      }
      container bgps {
        description
          "Redistribute BGP routes";
        list bgp {
          key "asnxx asnyy";
          description
            "Autonomous system number";
          leaf asnxx {
            type uint32 {
              range "0..65535";
            }
            description
              "Higher 16 bits of 4-byte BGP AS number";
          }
          leaf asnyy {
            type uint32 {
              range "0..4294967295";
            }
            description
              "2-byte or 4-byte BGP AS number";
          }
          leaf policy {
            type string;
            description
              "Route Policy name";
          }
          leaf type {
            type Bgp-redist-route;
            description
              "Route type";
          }
        }
      }
      container isises {
        description
          "Redistribute IS-IS routes";
        list isis {
          key "isis-name";
          description
            "Redistribute IS-IS routes";
          leaf isis-name {
            type xr:Cisco-ios-xr-string;
            description
              "IS-IS instance name";
          }
          leaf route-policy-name {
            type string;
            description
              "Route Policy name";
          }
          leaf route-type {
            type Isis-redist-route;
            description
              "Route type";
          }
        }
      }
      container eigrp-s {
        description
          "Redistribute EIGRP routes";
        list eigrp {
          key "as";
          description
            "Redistribute EIGRP routes";
          leaf as {
            type uint32 {
              range "1..65535";
            }
            description
              "Autonomous system number";
          }
          leaf route-policy-name {
            type string;
            description
              "Route Policy name";
          }
          leaf route-type {
            type Default-redist-route;
            description
              "Route type";
          }
        }
      }
      container static {
        presence "enable static";
        description
          "Redistribute static routes";
        leaf route-policy-name {
          type string;
          description
            "Route Policy name";
        }
        leaf route-type {
          type Default-redist-route;
          description
            "Route type";
        }
      }
      container ospfs {
        description
          "Redistribute OSPF routes";
        list ospf {
          key "ospf-name";
          description
            "Redistribute OSPF routes";
          leaf ospf-name {
            type xr:Cisco-ios-xr-string;
            description
              "Process ID for the OSPF instance";
          }
          leaf route-policy-name {
            type string;
            description
              "Route Policy name";
          }
          leaf internal {
            type boolean;
            description
              "Internal routes";
          }
          leaf external {
            type boolean;
            description
              "External routes";
          }
          leaf external-type {
            type uint32 {
              range "0..2";
            }
            description
              "External route type";
          }
          leaf nssa-external {
            type boolean;
            description
              "NSSA External routes";
          }
          leaf nssa-external-type {
            type uint32 {
              range "0..2";
            }
            description
              "NSSA External route type";
          }
        }
      }
    }
  }

  grouping DEFAULT-INFORMATION {
    description
      "Common node of default-vrf, vrf";
    container default-information {
      presence "Indicates a default-information node is configured.";
      description
        "Controls default information origination";
      leaf route-policy-name {
        type string;
        description
          "Route policy name";
      }
      leaf option {
        type Default-information-option;
        mandatory true;
        description
          "Origination option";
      }
    }
  }

  grouping IP-DISTANCE-TABLE {
    description
      "Common node of default-vrf, vrf";
    container ip-distances {
      description
        "Table of IP specific administrative distances";
      list ip-distance {
        key "address netmask";
        description
          "IP specific administrative distance";
        leaf address {
          type inet:ipv4-address-no-zone;
          description
            "IP Source address";
        }
        leaf netmask {
          type inet:ipv4-address-no-zone;
          description
            "IP address mask";
        }
        leaf distance {
          type uint32 {
            range "0..255";
          }
          mandatory true;
          description
            "Administrative distance";
        }
      }
    }
  }

  grouping MAXIMUM-PATHS {
    description
      "Common node of default-vrf, vrf";
    leaf maximum-paths {
      type uint32 {
        range "1..128";
      }
      default "4";
      description
        "Maximum number of paths allowed per route";
    }
  }

  grouping POLICY-IN {
    description
      "Common node of default-vrf, vrf";
    leaf policy-in {
      type string;
      description
        "Route Policy for inbbound routing updates";
    }
  }

  grouping POLICY-OUT {
    description
      "Common node of default-vrf, vrf";
    leaf policy-out {
      type string;
      description
        "Route Policy for outbound routing updates";
    }
  }

  grouping INTERFACE-TABLE {
    description
      "Common node of default-vrf, vrf";
    container interfaces {
      description
        "Table of RIP interfaces";
      list interface {
        key "interface-name";
        description
          "RIP interface name";
        container authentication {
          presence "Indicates a authentication node is configured.";
          description
            "Authentication keychain and mode";
          leaf keychain {
            type string;
            mandatory true;
            description
              "Name of keychain";
          }
          leaf mode {
            type Rip-auth-mode;
            mandatory true;
            description
              "Authentication mode";
          }
        }
        container site-of-origin {
          description
            "SOO community for prefixes learned over this
             interface";
          leaf type {
            type Rip-ext-community;
            description
              "Extended community type";
          }
          leaf as-xx {
            when "../type != 'as' and ../type != 'ipv4-address'" {
              tailf:xpath-root 3;
              description
                "../Type != AS and ../Type != IPV4Address";
            }
            type uint32 {
              range "0..65535";
            }
            description
              "AS Number for AS:nn format";
          }
          leaf as-yy {
            when "../type != 'ipv4-address'" {
              tailf:xpath-root 3;
              description
                "../Type != IPV4Address";
            }
            type uint32 {
              range "0..4294967295";
            }
            description
              "32 bit value for AS:nn format";
          }
          leaf as-index {
            when "../type != 'ipv4-address'" {
              tailf:xpath-root 3;
              description
                "../Type != IPV4Address";
            }
            type uint32 {
              range "0..4294967295";
            }
            description
              "AS Number Index";
          }
          leaf address {
            when "../type = 'ipv4-address'" {
              tailf:xpath-root 3;
              description
                "../Type = IPV4Address";
            }
            type inet:ipv4-address-no-zone;
            description
              "IPV4 address for IPV4Address:nn format";
          }
          leaf address-index {
            when "../type = 'ipv4-address'" {
              tailf:xpath-root 3;
              description
                "../Type = IPV4Address";
            }
            type uint32 {
              range "0..65535";
            }
            description
              "16bit value for IPV4Address:nn format";
          }
        }
        container receive-version {
          description
            "RIP versions supported for receiving
             advertisements";
          leaf version1 {
            type boolean;
            description
              "Support RIP version 1";
          }
          leaf version2 {
            type boolean;
            default "true";
            description
              "Support RIP version 2";
          }
        }
        container send-version {
          description
            "RIP versions supported for sending
             advertisements";
          leaf version1 {
            type boolean;
            description
              "Support RIP version 1";
          }
          leaf version2 {
            type boolean;
            default "true";
            description
              "Support RIP version 2";
          }
        }
        leaf broadcast-for-v2 {
          type empty;
          description
            "Send RIP v2 output packets to broadcast
             address";
        }
        leaf poison-reverse {
          type empty;
          description
            "Enable poison reverse";
        }
        leaf passive {
          type empty;
          description
            "Suppress routing updates on this interface";
        }
        leaf enable {
          type empty;
          description
            "Starts RIP interface configuration";
        }
        leaf policy-out {
          type string;
          description
            "Route Policy for outbound routing updates";
        }
        leaf accept-metric-zero {
          type empty;
          description
            "Accept RIP updates with metric 0";
        }
        leaf policy-in {
          type string;
          description
            "Route Policy for inbound routing updates";
        }
        leaf split-horizon-disable {
          type empty;
          description
            "Disable split horizon";
        }
        leaf interface-name {
          type xr:Interface-name;
          description
            "Interface name";
        }
      }
    }
  }

  grouping BROADCAST-FOR-V2 {
    description
      "Common node of default-vrf, vrf";
    leaf broadcast-for-v2 {
      type empty;
      description
        "Send RIP v2 output packets to broadcast address";
    }
  }

  grouping NSF {
    description
      "Common node of default-vrf, vrf";
    leaf nsf {
      type empty;
      description
        "Enable Cisco Non Stop Forwarding";
    }
  }

  grouping NEIGHBOR-TABLE {
    description
      "Common node of default-vrf, vrf";
    container neighbors {
      description
        "Configure RIP Neighbors";
      list neighbor {
        key "neighbor-address";
        description
          "Neighbor address";
        leaf neighbor-address {
          type inet:ipv4-address-no-zone;
          description
            "IPv4 address";
        }
      }
    }
  }

  grouping OUTPUT-DELAY {
    description
      "Common node of default-vrf, vrf";
    leaf output-delay {
      type uint32 {
        range "8..50";
      }
      units "millisecond";
      description
        "Inter-packet delay for RIP updates";
    }
  }

  grouping DEFAULT-METRIC {
    description
      "Common node of default-vrf, vrf";
    leaf default-metric {
      type uint32 {
        range "0..16";
      }
      description
        "Default metric of redistributed routes";
    }
  }

  augment "/ncs:devices/ncs:device/ncs:config" {
    container rip {
      tailf:ncs-device-type "netconf";
      tailf:display-when "not(../../ncs:module) or ../../ncs:module[ncs:name='Cisco-IOS-XR-ip-rip-cfg']";
      description
        "RIP configuration";
      container default-vrf {
        description
          "RIP configuration for Default VRF";
        leaf enable {
          type empty;
          description
            "Starts RIP configuration for Default VRF";
        }
        uses BROADCAST-FOR-V2;
        uses DISTANCE;
        uses DEFAULT-INFORMATION;
        uses DEFAULT-METRIC;
        uses OUTPUT-DELAY;
        uses AUTO-SUMMARY;
        uses REDISTRIBUTION;
        uses IP-DISTANCE-TABLE;
        uses POLICY-OUT;
        uses INTERFACE-TABLE;
        uses NEIGHBOR-TABLE;
        uses VALIDATE-SOURCE-DISABLE;
        uses MAXIMUM-PATHS;
        uses NSF;
        uses POLICY-IN;
        uses TIMERS;
      }
      container vrfs {
        description
          "VRF related RIP configuration";
        list vrf {
          key "vrf-name";
          description
            "RIP configuration for a particular VRF";
          leaf enable {
            type empty;
            description
              "Starts RIP configuration for a particular VRF";
          }
          leaf vrf-name {
            type xr:Cisco-ios-xr-string;
            description
              "VRF Name";
          }
          uses BROADCAST-FOR-V2;
          uses DISTANCE;
          uses DEFAULT-INFORMATION;
          uses DEFAULT-METRIC;
          uses OUTPUT-DELAY;
          uses AUTO-SUMMARY;
          uses REDISTRIBUTION;
          uses IP-DISTANCE-TABLE;
          uses POLICY-OUT;
          uses INTERFACE-TABLE;
          uses NEIGHBOR-TABLE;
          uses VALIDATE-SOURCE-DISABLE;
          uses MAXIMUM-PATHS;
          uses NSF;
          uses POLICY-IN;
          uses TIMERS;
        }
      }
    }
  }
  augment "/ncs:devices/ncs:device/ncs:live-status" {
    container rip {
      tailf:ncs-device-type "netconf";
      tailf:display-when "not(../../ncs:module) or ../../ncs:module[ncs:name='Cisco-IOS-XR-ip-rip-cfg'] or (../../ncs:live-status-protocol[not(ncs:capability)]) or (../../ncs:live-status-protocol/ncs:capability/ncs:module[.='Cisco-IOS-XR-ip-rip-cfg'])";
      description
        "RIP configuration";
      container default-vrf {
        description
          "RIP configuration for Default VRF";
        leaf enable {
          type empty;
          description
            "Starts RIP configuration for Default VRF";
        }
        uses live_ncs_BROADCAST-FOR-V2;
        uses live_ncs_DISTANCE;
        uses live_ncs_DEFAULT-INFORMATION;
        uses live_ncs_DEFAULT-METRIC;
        uses live_ncs_OUTPUT-DELAY;
        uses live_ncs_AUTO-SUMMARY;
        uses live_ncs_REDISTRIBUTION;
        uses live_ncs_IP-DISTANCE-TABLE;
        uses live_ncs_POLICY-OUT;
        uses live_ncs_INTERFACE-TABLE;
        uses live_ncs_NEIGHBOR-TABLE;
        uses live_ncs_VALIDATE-SOURCE-DISABLE;
        uses live_ncs_MAXIMUM-PATHS;
        uses live_ncs_NSF;
        uses live_ncs_POLICY-IN;
        uses live_ncs_TIMERS;
      }
      container vrfs {
        description
          "VRF related RIP configuration";
        list vrf {
          key "vrf-name";
          description
            "RIP configuration for a particular VRF";
          leaf enable {
            type empty;
            description
              "Starts RIP configuration for a particular VRF";
          }
          leaf vrf-name {
            type xr:live_ncs_Cisco-ios-xr-string;
            description
              "VRF Name";
          }
          uses live_ncs_BROADCAST-FOR-V2;
          uses live_ncs_DISTANCE;
          uses live_ncs_DEFAULT-INFORMATION;
          uses live_ncs_DEFAULT-METRIC;
          uses live_ncs_OUTPUT-DELAY;
          uses live_ncs_AUTO-SUMMARY;
          uses live_ncs_REDISTRIBUTION;
          uses live_ncs_IP-DISTANCE-TABLE;
          uses live_ncs_POLICY-OUT;
          uses live_ncs_INTERFACE-TABLE;
          uses live_ncs_NEIGHBOR-TABLE;
          uses live_ncs_VALIDATE-SOURCE-DISABLE;
          uses live_ncs_MAXIMUM-PATHS;
          uses live_ncs_NSF;
          uses live_ncs_POLICY-IN;
          uses live_ncs_TIMERS;
        }
      }
    }
  }
  augment "/ncs:devices/ncs:template/ncs:ned-id/ncs:config" {
    container rip {
      description
        "RIP configuration";
      container default-vrf {
        description
          "RIP configuration for Default VRF";
        leaf enable {
          type empty;
          description
            "Starts RIP configuration for Default VRF";
        }
        uses ncs_template_BROADCAST-FOR-V2;
        uses ncs_template_DISTANCE;
        uses ncs_template_DEFAULT-INFORMATION;
        uses ncs_template_DEFAULT-METRIC;
        uses ncs_template_OUTPUT-DELAY;
        uses ncs_template_AUTO-SUMMARY;
        uses ncs_template_REDISTRIBUTION;
        uses ncs_template_IP-DISTANCE-TABLE;
        uses ncs_template_POLICY-OUT;
        uses ncs_template_INTERFACE-TABLE;
        uses ncs_template_NEIGHBOR-TABLE;
        uses ncs_template_VALIDATE-SOURCE-DISABLE;
        uses ncs_template_MAXIMUM-PATHS;
        uses ncs_template_NSF;
        uses ncs_template_POLICY-IN;
        uses ncs_template_TIMERS;
      }
      container vrfs {
        description
          "VRF related RIP configuration";
        list vrf {
          // NCS patched for predictable order
          ordered-by user;
          key "vrf-name";
          description
            "RIP configuration for a particular VRF";
          leaf enable {
            type empty;
            description
              "Starts RIP configuration for a particular VRF";
          }
          leaf vrf-name {
            type xr:ncs_template_Cisco-ios-xr-string;
            description
              "VRF Name";
          }
          uses ncs_template_BROADCAST-FOR-V2;
          uses ncs_template_DISTANCE;
          uses ncs_template_DEFAULT-INFORMATION;
          uses ncs_template_DEFAULT-METRIC;
          uses ncs_template_OUTPUT-DELAY;
          uses ncs_template_AUTO-SUMMARY;
          uses ncs_template_REDISTRIBUTION;
          uses ncs_template_IP-DISTANCE-TABLE;
          uses ncs_template_POLICY-OUT;
          uses ncs_template_INTERFACE-TABLE;
          uses ncs_template_NEIGHBOR-TABLE;
          uses ncs_template_VALIDATE-SOURCE-DISABLE;
          uses ncs_template_MAXIMUM-PATHS;
          uses ncs_template_NSF;
          uses ncs_template_POLICY-IN;
          uses ncs_template_TIMERS;
        }
      }
    }
  }
}

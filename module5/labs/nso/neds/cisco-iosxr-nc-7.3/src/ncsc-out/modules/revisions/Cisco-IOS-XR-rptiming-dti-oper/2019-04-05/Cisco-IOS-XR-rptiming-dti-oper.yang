module Cisco-IOS-XR-rptiming-dti-oper {
  // Generated by yanger -t ncs
  tailf:mount-id "cisco-iosxr-nc-7.3:cisco-iosxr-nc-7.3";
  tailf:ncs-device-type "netconf";

  namespace "http://cisco.com/ns/yang/Cisco-IOS-XR-rptiming-dti-oper";
  prefix rptiming-dti-oper;

  import Cisco-IOS-XR-types {
    prefix xr;
  }
  import cisco-semver {
    prefix semver;
  }
  include Cisco-IOS-XR-rptiming-dti-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR rptiming-dti package operational data.

     This module contains definitions
     for the following management objects:
       dti-controller: DTI interface controller status and
         configuration

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'dti-controller'
  }
  augment "/ncs:devices/ncs:device/ncs:live-status" {
    container dti-controller {
      tailf:ncs-device-type "netconf";
      tailf:display-when "not(../../ncs:module) or ../../ncs:module[ncs:name='Cisco-IOS-XR-rptiming-dti-oper'] or (../../ncs:live-status-protocol[not(ncs:capability)]) or (../../ncs:live-status-protocol/ncs:capability/ncs:module[.='Cisco-IOS-XR-rptiming-dti-oper'])";
      description
        "DTI interface controller status and configuration";
      container nodes {
        description
          "List of nodes applicable to DTI controller";
        list node {
          key "node-name";
          description
            "DTI operational data for a single node";
          container client {
            description
              "Display DTI client status";
            uses live_ncs_DTI-CLIENT-INFO;
          }
          container port {
            description
              "Display DTI input port status";
            uses live_ncs_DTI-PORT-INFO;
          }
          container time-of-day {
            description
              "Display DTI time-of-day status";
            uses live_ncs_DTI-TOD-INFO;
          }
          leaf node-name {
            type xr:live_ncs_Node-id;
            description
              "Node Name";
          }
        }
      }
    }
  }
  augment "/ncs:devices/ncs:template/ncs:ned-id/ncs:config" {
    // NCS drop config false container 'dti-controller'
  }
}

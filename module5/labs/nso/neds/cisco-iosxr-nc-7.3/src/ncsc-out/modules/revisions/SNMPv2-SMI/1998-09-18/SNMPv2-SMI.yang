module SNMPv2-SMI {
  // Generated by yanger -t ncs
  tailf:mount-id "cisco-iosxr-nc-7.3:cisco-iosxr-nc-7.3";
  tailf:ncs-device-type "netconf";

  namespace "http://tail-f.com/ns/mibs/SNMPv2-SMI/1.0";
  prefix SNMPv2_SMI;

  import ietf-yang-types {
    prefix yang;
  }
  import tailf-common {
    prefix tailf;
  }
  import tailf-ncs {
    prefix ncs;
  }

  revision 1998-09-18 {
    description
      "Initial revision";
  }

  typedef ncs_template_ExtUTCTime {
    type string;
  }

  typedef ncs_template_ObjectName {
    type string;
  }

  typedef ncs_template_NotificationName {
    type string;
  }

  typedef ncs_template_Integer32 {
    type string;
  }

  typedef ncs_template_IpAddress {
    type string;
  }

  typedef ncs_template_Counter32 {
    type string;
  }

  typedef ncs_template_Gauge32 {
    type string;
  }

  typedef ncs_template_Unsigned32 {
    type string;
  }

  typedef ncs_template_TimeTicks {
    type string;
  }

  typedef ncs_template_Opaque {
    type string;
  }

  typedef ncs_template_Counter64 {
    type string;
  }

  typedef ncs_rpc_notif_ExtUTCTime {
    type tailf:hex-list {
      tailf:value-length "11 .. 13";
    }
  }

  typedef ncs_rpc_notif_ObjectName {
    type yang:object-identifier;
  }

  typedef ncs_rpc_notif_NotificationName {
    type yang:object-identifier;
  }

  typedef ncs_rpc_notif_Integer32 {
    type int32 {
      range "-2147483648 .. 2147483647";
    }
  }

  typedef ncs_rpc_notif_IpAddress {
    type string {
      pattern '(0|[1-9](([0-9]){0,2})).(0|[1-9](([0-9]){0,2})).(0|[1-9](([0-9]){0,2})).(0|[1-9](([0-9]){0,2}))';
    }
  }

  typedef ncs_rpc_notif_Counter32 {
    type uint32 {
      range "0 .. 4294967295";
    }
  }

  typedef ncs_rpc_notif_Gauge32 {
    type uint32 {
      range "0 .. 4294967295";
    }
  }

  typedef ncs_rpc_notif_Unsigned32 {
    type uint32 {
      range "0 .. 4294967295";
    }
  }

  typedef ncs_rpc_notif_TimeTicks {
    type uint32 {
      range "0 .. 4294967295";
    }
  }

  typedef ncs_rpc_notif_Opaque {
    type tailf:hex-list;
  }

  typedef ncs_rpc_notif_Counter64 {
    type yang:counter64 {
      range "0 .. 18446744073709551615";
    }
  }

  typedef live_ncs_ExtUTCTime {
    type tailf:hex-list {
      tailf:value-length "11 .. 13";
    }
  }

  typedef live_ncs_ObjectName {
    type yang:object-identifier;
  }

  typedef live_ncs_NotificationName {
    type yang:object-identifier;
  }

  typedef live_ncs_Integer32 {
    type int32 {
      range "-2147483648 .. 2147483647";
    }
  }

  typedef live_ncs_IpAddress {
    type string {
      pattern '(0|[1-9](([0-9]){0,2})).(0|[1-9](([0-9]){0,2})).(0|[1-9](([0-9]){0,2})).(0|[1-9](([0-9]){0,2}))';
    }
  }

  typedef live_ncs_Counter32 {
    type uint32 {
      range "0 .. 4294967295";
    }
  }

  typedef live_ncs_Gauge32 {
    type uint32 {
      range "0 .. 4294967295";
    }
  }

  typedef live_ncs_Unsigned32 {
    type uint32 {
      range "0 .. 4294967295";
    }
  }

  typedef live_ncs_TimeTicks {
    type uint32 {
      range "0 .. 4294967295";
    }
  }

  typedef live_ncs_Opaque {
    type tailf:hex-list;
  }

  typedef live_ncs_Counter64 {
    type yang:counter64 {
      range "0 .. 18446744073709551615";
    }
  }

  typedef ExtUTCTime {
    type tailf:hex-list {
      tailf:value-length "11 .. 13";
    }
  }

  typedef ObjectName {
    type yang:object-identifier;
  }

  typedef NotificationName {
    type yang:object-identifier;
  }

  typedef Integer32 {
    type int32 {
      range "-2147483648 .. 2147483647";
    }
  }

  typedef IpAddress {
    type string {
      pattern '(0|[1-9](([0-9]){0,2})).(0|[1-9](([0-9]){0,2})).(0|[1-9](([0-9]){0,2})).(0|[1-9](([0-9]){0,2}))';
    }
  }

  typedef Counter32 {
    type uint32 {
      range "0 .. 4294967295";
    }
  }

  typedef Gauge32 {
    type uint32 {
      range "0 .. 4294967295";
    }
  }

  typedef Unsigned32 {
    type uint32 {
      range "0 .. 4294967295";
    }
  }

  typedef TimeTicks {
    type uint32 {
      range "0 .. 4294967295";
    }
  }

  typedef Opaque {
    type tailf:hex-list;
  }

  typedef Counter64 {
    type yang:counter64 {
      range "0 .. 18446744073709551615";
    }
  }
}

module Cisco-IOS-XR-tunnel-gre-datatypes {
  // Generated by yanger -t ncs
  tailf:mount-id "cisco-iosxr-nc-7.3:cisco-iosxr-nc-7.3";
  tailf:ncs-device-type "netconf";

  namespace "http://cisco.com/ns/yang/Cisco-IOS-XR-tunnel-gre-datatypes";
  prefix tunnel-gre-datatypes;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Tunl-addr-family-enum {
    type string;
    description
      "Tunl addr family enum";
  }

  typedef ncs_template_Tunl-id-range {
    type string;
    description
      "Tunl id range";
  }

  typedef ncs_template_Tunl-addr-family-list {
    type string;
    description
      "ipv4: Tunnel Transport Protocol Address Family
       IPv4, ipv6: Tunnel Transport Protocol Address
       Family IPv6, all: Tunnel Transport Protocol
       Address Families all";
  }

  typedef ncs_template_Tunl-addr-length-range {
    type string;
    description
      "Tunl addr length range";
  }

  typedef ncs_template_Tunl-mode-enum {
    type string;
    description
      "Tunl mode enum";
  }

  typedef ncs_rpc_notif_Tunl-addr-family-enum {
    type enumeration {
      enum "inet" {
        value 2;
        description
          "IPv4 address Family";
      }
      enum "inet6" {
        value 10;
        description
          "IPv6 address Family";
      }
    }
    description
      "Tunl addr family enum";
  }

  typedef ncs_rpc_notif_Tunl-id-range {
    type uint32 {
      range "0..131070";
    }
    description
      "Tunl id range";
  }

  typedef ncs_rpc_notif_Tunl-addr-family-list {
    type string {
      pattern '(ipv4)|(ipv6)|(all)';
    }
    description
      "ipv4: Tunnel Transport Protocol Address Family
       IPv4, ipv6: Tunnel Transport Protocol Address
       Family IPv6, all: Tunnel Transport Protocol
       Address Families all";
  }

  typedef ncs_rpc_notif_Tunl-addr-length-range {
    type uint32 {
      range "1..128";
    }
    description
      "Tunl addr length range";
  }

  typedef ncs_rpc_notif_Tunl-mode-enum {
    type enumeration {
      enum "gre-ipv4" {
        value 1;
        description
          "GRE over IPv4 encapsulation";
      }
      enum "gre-ipv6" {
        value 2;
        description
          "GRE over IPv6 encapsulation";
      }
      enum "mgre-ipv4" {
        value 3;
        description
          "Multipoint GRE over IPv4 encapsulation";
      }
      enum "mgre-ipv6" {
        value 4;
        description
          "Multipoint GRE over IPv6 encapsulation";
      }
      enum "ipv4" {
        value 5;
        description
          "Generic packet tunneling over IPv4
           encapsulation";
      }
      enum "ipv6" {
        value 6;
        description
          "Generic packet tunneling over IPv6
           encapsulation";
      }
    }
    description
      "Tunl mode enum";
  }

  typedef live_ncs_Tunl-addr-family-enum {
    type enumeration {
      enum "inet" {
        value 2;
        description
          "IPv4 address Family";
      }
      enum "inet6" {
        value 10;
        description
          "IPv6 address Family";
      }
    }
    description
      "Tunl addr family enum";
  }

  typedef live_ncs_Tunl-id-range {
    type uint32 {
      range "0..131070";
    }
    description
      "Tunl id range";
  }

  typedef live_ncs_Tunl-addr-family-list {
    type string {
      pattern '(ipv4)|(ipv6)|(all)';
    }
    description
      "ipv4: Tunnel Transport Protocol Address Family
       IPv4, ipv6: Tunnel Transport Protocol Address
       Family IPv6, all: Tunnel Transport Protocol
       Address Families all";
  }

  typedef live_ncs_Tunl-addr-length-range {
    type uint32 {
      range "1..128";
    }
    description
      "Tunl addr length range";
  }

  typedef live_ncs_Tunl-mode-enum {
    type enumeration {
      enum "gre-ipv4" {
        value 1;
        description
          "GRE over IPv4 encapsulation";
      }
      enum "gre-ipv6" {
        value 2;
        description
          "GRE over IPv6 encapsulation";
      }
      enum "mgre-ipv4" {
        value 3;
        description
          "Multipoint GRE over IPv4 encapsulation";
      }
      enum "mgre-ipv6" {
        value 4;
        description
          "Multipoint GRE over IPv6 encapsulation";
      }
      enum "ipv4" {
        value 5;
        description
          "Generic packet tunneling over IPv4
           encapsulation";
      }
      enum "ipv6" {
        value 6;
        description
          "Generic packet tunneling over IPv6
           encapsulation";
      }
    }
    description
      "Tunl mode enum";
  }

  typedef Tunl-addr-family-enum {
    type enumeration {
      enum "inet" {
        value 2;
        description
          "IPv4 address Family";
      }
      enum "inet6" {
        value 10;
        description
          "IPv6 address Family";
      }
    }
    description
      "Tunl addr family enum";
  }

  typedef Tunl-id-range {
    type uint32 {
      range "0..131070";
    }
    description
      "Tunl id range";
  }

  typedef Tunl-addr-family-list {
    type string {
      pattern '(ipv4)|(ipv6)|(all)';
    }
    description
      "ipv4: Tunnel Transport Protocol Address Family
       IPv4, ipv6: Tunnel Transport Protocol Address
       Family IPv6, all: Tunnel Transport Protocol
       Address Families all";
  }

  typedef Tunl-addr-length-range {
    type uint32 {
      range "1..128";
    }
    description
      "Tunl addr length range";
  }

  typedef Tunl-mode-enum {
    type enumeration {
      enum "gre-ipv4" {
        value 1;
        description
          "GRE over IPv4 encapsulation";
      }
      enum "gre-ipv6" {
        value 2;
        description
          "GRE over IPv6 encapsulation";
      }
      enum "mgre-ipv4" {
        value 3;
        description
          "Multipoint GRE over IPv4 encapsulation";
      }
      enum "mgre-ipv6" {
        value 4;
        description
          "Multipoint GRE over IPv6 encapsulation";
      }
      enum "ipv4" {
        value 5;
        description
          "Generic packet tunneling over IPv4
           encapsulation";
      }
      enum "ipv6" {
        value 6;
        description
          "Generic packet tunneling over IPv6
           encapsulation";
      }
    }
    description
      "Tunl mode enum";
  }
}

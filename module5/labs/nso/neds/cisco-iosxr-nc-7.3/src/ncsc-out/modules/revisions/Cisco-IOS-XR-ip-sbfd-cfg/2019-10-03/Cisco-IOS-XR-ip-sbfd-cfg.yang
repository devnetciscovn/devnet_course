module Cisco-IOS-XR-ip-sbfd-cfg {
  // Generated by yanger -t ncs
  tailf:mount-id "cisco-iosxr-nc-7.3:cisco-iosxr-nc-7.3";
  tailf:ncs-device-type "netconf";

  namespace "http://cisco.com/ns/yang/Cisco-IOS-XR-ip-sbfd-cfg";
  prefix ip-sbfd-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-sbfd package configuration.

     This module contains definitions
     for the following management objects:
       sbfd: SBFD Configuration ,Seamless-BFD is method for detecting
         faultsbetween two different nodes in a network

     Copyright (c) 2013-2019 by Cisco Systems, Inc.
     All rights reserved.";

  revision 2019-10-03 {
    description
      "SBFD configuration objects.";
    semver:module-version "1.0.1";
  }
  revision 2019-04-05 {
    description
      "Establish semantic version baseline.";
    semver:module-version "1.0.0";
  }
  revision 2015-11-09 {
    description
      "IOS XR 6.0 revision.";
  }

  grouping ncs_template_REMOTE-DISCRIMINATOR {
    description
      "Common node of ipv4-address, ipv6-address";
    list remote-discriminator {
      // NCS patched for predictable order
      ordered-by user;
      key "remote-discriminator";
      description
        "Remote Discriminator value";
      leaf remote-discriminator {
        type string;
        description
          "Remote Discriminator Value";
      }
    }
  }

  grouping ncs_rpc_notif_REMOTE-DISCRIMINATOR {
    description
      "Common node of ipv4-address, ipv6-address";
    list remote-discriminator {
      key "remote-discriminator";
      description
        "Remote Discriminator value";
      leaf remote-discriminator {
        type uint32 {
          range "1..4294967295";
        }
        description
          "Remote Discriminator Value";
      }
    }
  }

  grouping live_ncs_REMOTE-DISCRIMINATOR {
    description
      "Common node of ipv4-address, ipv6-address";
    list remote-discriminator {
      key "remote-discriminator";
      description
        "Remote Discriminator value";
      leaf remote-discriminator {
        type uint32 {
          range "1..4294967295";
        }
        description
          "Remote Discriminator Value";
      }
    }
  }

  grouping REMOTE-DISCRIMINATOR {
    description
      "Common node of ipv4-address, ipv6-address";
    list remote-discriminator {
      key "remote-discriminator";
      description
        "Remote Discriminator value";
      leaf remote-discriminator {
        type uint32 {
          range "1..4294967295";
        }
        description
          "Remote Discriminator Value";
      }
    }
  }

  augment "/ncs:devices/ncs:device/ncs:config" {
    container sbfd {
      tailf:ncs-device-type "netconf";
      tailf:display-when "not(../../ncs:module) or ../../ncs:module[ncs:name='Cisco-IOS-XR-ip-sbfd-cfg']";
      description
        "SBFD Configuration ,Seamless-BFD is method for
         detecting faultsbetween two different nodes in a
         network";
      container remote-target {
        description
          "configure remote target";
        container ipv4-addresses {
          description
            "ipv4 address as target";
          list ipv4-address {
            key "address";
            description
              "IP Address Value for RemoteDiscriminatorTable";
            leaf address {
              type inet:ipv4-address-no-zone;
              description
                " IPv4 address";
            }
            uses REMOTE-DISCRIMINATOR;
          }
        }
        container ipv6-addresses {
          description
            "ipv6 address as target";
          list ipv6-address {
            key "address";
            description
              "IP Address Value for RemoteDiscriminatorTable";
            leaf address {
              type inet:ipv6-address-no-zone;
              description
                " IPv6 adddress";
            }
            uses REMOTE-DISCRIMINATOR;
          }
        }
      }
      container local-discriminator {
        description
          "Configure local discriminator";
        container intf-discriminators {
          description
            "Configure local discriminator from interface
             address";
          list intf-discriminator {
            key "interface-name";
            description
              "interface address as discriminator";
            leaf interface-name {
              type xr:Interface-name;
              description
                "Interface Name";
            }
          }
        }
        container dynamic-discriminators {
          description
            "Configure local discriminator dynamically";
          list dynamic-discriminator {
            key "discriminator";
            description
              "Local discriminator value";
            leaf discriminator {
              type uint32 {
                range "0..1";
              }
              description
                "Dynamic discriminator value";
            }
          }
        }
        container ipv4-discriminators {
          description
            "Configure local discriminator as an ipv4
             address";
          list ipv4-discriminator {
            key "address";
            description
              "ipv4 address as discriminator";
            leaf address {
              type inet:ip-address-no-zone;
              description
                " IPv4 address";
            }
          }
        }
        container val32-discriminators {
          description
            "Configure local discriminator as an integer";
          list val32-discriminator {
            key "discriminator";
            description
              "Local discriminator value";
            leaf discriminator {
              type uint32 {
                range "1..4294967295";
              }
              description
                "Local discriminator value";
            }
          }
        }
      }
    }
  }
  augment "/ncs:devices/ncs:device/ncs:live-status" {
    container sbfd {
      tailf:ncs-device-type "netconf";
      tailf:display-when "not(../../ncs:module) or ../../ncs:module[ncs:name='Cisco-IOS-XR-ip-sbfd-cfg'] or (../../ncs:live-status-protocol[not(ncs:capability)]) or (../../ncs:live-status-protocol/ncs:capability/ncs:module[.='Cisco-IOS-XR-ip-sbfd-cfg'])";
      description
        "SBFD Configuration ,Seamless-BFD is method for
         detecting faultsbetween two different nodes in a
         network";
      container remote-target {
        description
          "configure remote target";
        container ipv4-addresses {
          description
            "ipv4 address as target";
          list ipv4-address {
            key "address";
            description
              "IP Address Value for RemoteDiscriminatorTable";
            leaf address {
              type inet:ipv4-address-no-zone;
              description
                " IPv4 address";
            }
            uses live_ncs_REMOTE-DISCRIMINATOR;
          }
        }
        container ipv6-addresses {
          description
            "ipv6 address as target";
          list ipv6-address {
            key "address";
            description
              "IP Address Value for RemoteDiscriminatorTable";
            leaf address {
              type inet:ipv6-address-no-zone;
              description
                " IPv6 adddress";
            }
            uses live_ncs_REMOTE-DISCRIMINATOR;
          }
        }
      }
      container local-discriminator {
        description
          "Configure local discriminator";
        container intf-discriminators {
          description
            "Configure local discriminator from interface
             address";
          list intf-discriminator {
            key "interface-name";
            description
              "interface address as discriminator";
            leaf interface-name {
              type xr:live_ncs_Interface-name;
              description
                "Interface Name";
            }
          }
        }
        container dynamic-discriminators {
          description
            "Configure local discriminator dynamically";
          list dynamic-discriminator {
            key "discriminator";
            description
              "Local discriminator value";
            leaf discriminator {
              type uint32 {
                range "0..1";
              }
              description
                "Dynamic discriminator value";
            }
          }
        }
        container ipv4-discriminators {
          description
            "Configure local discriminator as an ipv4
             address";
          list ipv4-discriminator {
            key "address";
            description
              "ipv4 address as discriminator";
            leaf address {
              type inet:ip-address-no-zone;
              description
                " IPv4 address";
            }
          }
        }
        container val32-discriminators {
          description
            "Configure local discriminator as an integer";
          list val32-discriminator {
            key "discriminator";
            description
              "Local discriminator value";
            leaf discriminator {
              type uint32 {
                range "1..4294967295";
              }
              description
                "Local discriminator value";
            }
          }
        }
      }
    }
  }
  augment "/ncs:devices/ncs:template/ncs:ned-id/ncs:config" {
    container sbfd {
      description
        "SBFD Configuration ,Seamless-BFD is method for
         detecting faultsbetween two different nodes in a
         network";
      container remote-target {
        description
          "configure remote target";
        container ipv4-addresses {
          description
            "ipv4 address as target";
          list ipv4-address {
            // NCS patched for predictable order
            ordered-by user;
            key "address";
            description
              "IP Address Value for RemoteDiscriminatorTable";
            leaf address {
              type string;
              description
                " IPv4 address";
            }
            uses ncs_template_REMOTE-DISCRIMINATOR;
          }
        }
        container ipv6-addresses {
          description
            "ipv6 address as target";
          list ipv6-address {
            // NCS patched for predictable order
            ordered-by user;
            key "address";
            description
              "IP Address Value for RemoteDiscriminatorTable";
            leaf address {
              type string;
              description
                " IPv6 adddress";
            }
            uses ncs_template_REMOTE-DISCRIMINATOR;
          }
        }
      }
      container local-discriminator {
        description
          "Configure local discriminator";
        container intf-discriminators {
          description
            "Configure local discriminator from interface
             address";
          list intf-discriminator {
            // NCS patched for predictable order
            ordered-by user;
            key "interface-name";
            description
              "interface address as discriminator";
            leaf interface-name {
              type xr:ncs_template_Interface-name;
              description
                "Interface Name";
            }
          }
        }
        container dynamic-discriminators {
          description
            "Configure local discriminator dynamically";
          list dynamic-discriminator {
            // NCS patched for predictable order
            ordered-by user;
            key "discriminator";
            description
              "Local discriminator value";
            leaf discriminator {
              type string;
              description
                "Dynamic discriminator value";
            }
          }
        }
        container ipv4-discriminators {
          description
            "Configure local discriminator as an ipv4
             address";
          list ipv4-discriminator {
            // NCS patched for predictable order
            ordered-by user;
            key "address";
            description
              "ipv4 address as discriminator";
            leaf address {
              type string;
              description
                " IPv4 address";
            }
          }
        }
        container val32-discriminators {
          description
            "Configure local discriminator as an integer";
          list val32-discriminator {
            // NCS patched for predictable order
            ordered-by user;
            key "discriminator";
            description
              "Local discriminator value";
            leaf discriminator {
              type string;
              description
                "Local discriminator value";
            }
          }
        }
      }
    }
  }
}

module Cisco-IOS-XR-patch-panel-cfg {
  // Generated by yanger -t ncs
  tailf:mount-id "cisco-iosxr-nc-7.3:cisco-iosxr-nc-7.3";
  tailf:ncs-device-type "netconf";

  namespace "http://cisco.com/ns/yang/Cisco-IOS-XR-patch-panel-cfg";
  prefix patch-panel-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR patch-panel package configuration.

     This module contains definitions
     for the following management objects:
       patch-panel: patch-panel service submode

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    container patch-panel {
      tailf:ncs-device-type "netconf";
      tailf:display-when "not(../../ncs:module) or ../../ncs:module[ncs:name='Cisco-IOS-XR-patch-panel-cfg']";
      presence "Indicates a patch-panel node is configured.";
      description
        "patch-panel service submode";
      leaf enable {
        type empty;
        mandatory true;
        description
          "Enable patch-panel service";
      }
      leaf user-name {
        type string;
        description
          "User name to be used for Authentication with
           Patch-Panel";
      }
      leaf password {
        type xr:Proprietary-password;
        description
          "Password name to be used for Authentication with
           Patch-Panel";
      }
      leaf ipv4 {
        type inet:ipv4-address-no-zone;
        description
          "IP address for patch-panel";
      }
    }
  }
  augment "/ncs:devices/ncs:device/ncs:live-status" {
    container patch-panel {
      tailf:ncs-device-type "netconf";
      tailf:display-when "not(../../ncs:module) or ../../ncs:module[ncs:name='Cisco-IOS-XR-patch-panel-cfg'] or (../../ncs:live-status-protocol[not(ncs:capability)]) or (../../ncs:live-status-protocol/ncs:capability/ncs:module[.='Cisco-IOS-XR-patch-panel-cfg'])";
      presence "Indicates a patch-panel node is configured.";
      description
        "patch-panel service submode";
      leaf enable {
        type empty;
        // NCS drop mandatory statement
        description
          "Enable patch-panel service";
      }
      leaf user-name {
        type string;
        description
          "User name to be used for Authentication with
           Patch-Panel";
      }
      leaf password {
        type xr:live_ncs_Proprietary-password;
        description
          "Password name to be used for Authentication with
           Patch-Panel";
      }
      leaf ipv4 {
        type inet:ipv4-address-no-zone;
        description
          "IP address for patch-panel";
      }
    }
  }
  augment "/ncs:devices/ncs:template/ncs:ned-id/ncs:config" {
    container patch-panel {
      presence "Indicates a patch-panel node is configured.";
      description
        "patch-panel service submode";
      leaf enable {
        type empty;
        // NCS drop mandatory statement
        description
          "Enable patch-panel service";
      }
      leaf user-name {
        type string;
        description
          "User name to be used for Authentication with
           Patch-Panel";
      }
      leaf password {
        type xr:ncs_template_Proprietary-password;
        description
          "Password name to be used for Authentication with
           Patch-Panel";
      }
      leaf ipv4 {
        type string;
        description
          "IP address for patch-panel";
      }
    }
  }
}

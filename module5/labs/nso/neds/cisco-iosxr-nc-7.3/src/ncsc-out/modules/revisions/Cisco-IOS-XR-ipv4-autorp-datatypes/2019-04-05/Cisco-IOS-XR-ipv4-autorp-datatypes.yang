module Cisco-IOS-XR-ipv4-autorp-datatypes {
  // Generated by yanger -t ncs
  tailf:mount-id "cisco-iosxr-nc-7.3:cisco-iosxr-nc-7.3";
  tailf:ncs-device-type "netconf";

  namespace "http://cisco.com/ns/yang/Cisco-IOS-XR-ipv4-autorp-datatypes";
  prefix ipv4-autorp-datatypes;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Auto-rp-protocol-mode {
    type string;
    description
      "Auto rp protocol mode";
  }

  typedef ncs_rpc_notif_Auto-rp-protocol-mode {
    type enumeration {
      enum "sparse" {
        value 0;
        description
          "Sparse Mode";
      }
      enum "bidirectional" {
        value 1;
        description
          "Bidirectional Mode";
      }
    }
    description
      "Auto rp protocol mode";
  }

  typedef live_ncs_Auto-rp-protocol-mode {
    type enumeration {
      enum "sparse" {
        value 0;
        description
          "Sparse Mode";
      }
      enum "bidirectional" {
        value 1;
        description
          "Bidirectional Mode";
      }
    }
    description
      "Auto rp protocol mode";
  }

  typedef Auto-rp-protocol-mode {
    type enumeration {
      enum "sparse" {
        value 0;
        description
          "Sparse Mode";
      }
      enum "bidirectional" {
        value 1;
        description
          "Bidirectional Mode";
      }
    }
    description
      "Auto rp protocol mode";
  }
}

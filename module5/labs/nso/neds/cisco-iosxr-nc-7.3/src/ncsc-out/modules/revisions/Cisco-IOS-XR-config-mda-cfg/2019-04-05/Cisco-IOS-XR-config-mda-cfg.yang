module Cisco-IOS-XR-config-mda-cfg {
  // Generated by yanger -t ncs
  tailf:mount-id "cisco-iosxr-nc-7.3:cisco-iosxr-nc-7.3";
  tailf:ncs-device-type "netconf";

  namespace "http://cisco.com/ns/yang/Cisco-IOS-XR-config-mda-cfg";
  prefix config-mda-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-mda package configuration.

     This module contains definitions
     for the following management objects:
       active-nodes: Per-node configuration for active nodes
       preconfigured-nodes: Per-node configuration for non-active
         nodes

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    container active-nodes {
      tailf:ncs-device-type "netconf";
      tailf:display-when "not(../../ncs:module) or ../../ncs:module[ncs:name='Cisco-IOS-XR-config-mda-cfg']";
      description
        "Per-node configuration for active nodes";
      list active-node {
        key "node-name";
        description
          "The configuration for an active node";
        leaf node-name {
          type xr:Node-id;
          description
            "The identifier for this node";
        }
      }
    }
    container preconfigured-nodes {
      tailf:ncs-device-type "netconf";
      tailf:display-when "not(../../ncs:module) or ../../ncs:module[ncs:name='Cisco-IOS-XR-config-mda-cfg']";
      description
        "Per-node configuration for non-active nodes";
      list preconfigured-node {
        key "node-name";
        description
          "The configuration for a non-active node";
        leaf node-name {
          type xr:Node-id;
          description
            "The identifier for this node";
        }
      }
    }
  }
  augment "/ncs:devices/ncs:device/ncs:live-status" {
    container active-nodes {
      tailf:ncs-device-type "netconf";
      tailf:display-when "not(../../ncs:module) or ../../ncs:module[ncs:name='Cisco-IOS-XR-config-mda-cfg'] or (../../ncs:live-status-protocol[not(ncs:capability)]) or (../../ncs:live-status-protocol/ncs:capability/ncs:module[.='Cisco-IOS-XR-config-mda-cfg'])";
      description
        "Per-node configuration for active nodes";
      list active-node {
        key "node-name";
        description
          "The configuration for an active node";
        leaf node-name {
          type xr:live_ncs_Node-id;
          description
            "The identifier for this node";
        }
      }
    }
    container preconfigured-nodes {
      tailf:ncs-device-type "netconf";
      tailf:display-when "not(../../ncs:module) or ../../ncs:module[ncs:name='Cisco-IOS-XR-config-mda-cfg'] or (../../ncs:live-status-protocol[not(ncs:capability)]) or (../../ncs:live-status-protocol/ncs:capability/ncs:module[.='Cisco-IOS-XR-config-mda-cfg'])";
      description
        "Per-node configuration for non-active nodes";
      list preconfigured-node {
        key "node-name";
        description
          "The configuration for a non-active node";
        leaf node-name {
          type xr:live_ncs_Node-id;
          description
            "The identifier for this node";
        }
      }
    }
  }
  augment "/ncs:devices/ncs:template/ncs:ned-id/ncs:config" {
    container active-nodes {
      description
        "Per-node configuration for active nodes";
      list active-node {
        // NCS patched for predictable order
        ordered-by user;
        key "node-name";
        description
          "The configuration for an active node";
        leaf node-name {
          type xr:ncs_template_Node-id;
          description
            "The identifier for this node";
        }
      }
    }
    container preconfigured-nodes {
      description
        "Per-node configuration for non-active nodes";
      list preconfigured-node {
        // NCS patched for predictable order
        ordered-by user;
        key "node-name";
        description
          "The configuration for a non-active node";
        leaf node-name {
          type xr:ncs_template_Node-id;
          description
            "The identifier for this node";
        }
      }
    }
  }
}

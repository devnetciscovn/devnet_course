module Cisco-IOS-XR-pmengine-clear-act {
  // Generated by yanger -t ncs
  tailf:mount-id "cisco-iosxr-nc-7.3:cisco-iosxr-nc-7.3";
  tailf:ncs-device-type "netconf";

  namespace "http://cisco.com/ns/yang/Cisco-IOS-XR-pmengine-clear-act";
  prefix pmengine-clear-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR clear statistics for pm-engine module.

     Copyright (c) 2018-2020 by Cisco Systems, Inc.
     All rights reserved.";

  revision 2020-09-13 {
    description
      "Clear per layer support for otu controllers";
    semver:module-version "1.2.0";
  }
  revision 2019-10-15 {
    description
      "Added support for flexible interval";
    semver:module-version "1.1.0";
  }
  revision 2019-10-01 {
    description
      "Made changes to be RFC6087 compliant";
    semver:module-version "1.0.1";
  }
  revision 2019-04-05 {
    description
      "Establish semantic version baseline.";
    semver:module-version "1.0.0";
  }
  revision 2018-01-09 {
    description
      "IOS XR 6.5.1 revision.";
  }

  augment "/ncs:devices/ncs:device/ncs:rpc" {
    container rpc-clear-controller-pm {
      tailf:ncs-device-type "netconf";
      tailf:display-when "not(../../ncs:module) or ../../ncs:module[ncs:name='Cisco-IOS-XR-pmengine-clear-act']";
      tailf:action clear-controller-pm {
        tailf:actionpoint ncsproxy {
          tailf:internal;
        }
        description
          "Clear pm-engine statistics";
        input {
          leaf controller {
            type string;
            description
              "Controller name in R/S/I/P format";
          }
          leaf pm {
            type empty;
            description
              "clear pm counters";
          }
          leaf interval {
            type uint8 {
              range "0..4";
            }
            description
              "Clear 24-hour(0)/15-min(1)/30-sec(2)/Flexible-Interval(3)/all(4) pm statistics";
          }
          leaf layer {
            type string;
            description
              "Layer name to clear PM counter for specific layer";
          }
        }
      }
    }
  }
  augment "/ncs:devices/ncs:device-group/ncs:ned-id/ncs:rpc" {
    container rpc-clear-controller-pm {
      tailf:ncs-device-type "netconf";
      tailf:display-when "/ncs:devices/ncs:device[ncs:name=current()/../../../ncs:member]/ncs:module[ncs:name='Cisco-IOS-XR-pmengine-clear-act']";
      tailf:action clear-controller-pm {
        tailf:actionpoint ncsproxy {
          tailf:internal;
        }
        description
          "Clear pm-engine statistics";
        input {
          leaf controller {
            type string;
            description
              "Controller name in R/S/I/P format";
          }
          leaf pm {
            type empty;
            description
              "clear pm counters";
          }
          leaf interval {
            type uint8 {
              range "0..4";
            }
            description
              "Clear 24-hour(0)/15-min(1)/30-sec(2)/Flexible-Interval(3)/all(4) pm statistics";
          }
          leaf layer {
            type string;
            description
              "Layer name to clear PM counter for specific layer";
          }
        }
      }
    }
  }
}

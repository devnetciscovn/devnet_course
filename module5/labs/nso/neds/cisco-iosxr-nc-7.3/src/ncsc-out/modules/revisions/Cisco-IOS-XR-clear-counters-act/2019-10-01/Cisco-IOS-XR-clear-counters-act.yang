module Cisco-IOS-XR-clear-counters-act {
  // Generated by yanger -t ncs
  tailf:mount-id "cisco-iosxr-nc-7.3:cisco-iosxr-nc-7.3";
  tailf:ncs-device-type "netconf";

  namespace "http://cisco.com/ns/yang/Cisco-IOS-XR-clear-counters-act";
  prefix clear-counters-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Controller to clear alarm counters.

     Copyright (c) 2018-2019 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2018-02-14 {
    description
      "IOS XR 6.5.1 revision.";
  }

  augment "/ncs:devices/ncs:device/ncs:rpc" {
    container rpc-clear-counters {
      tailf:ncs-device-type "netconf";
      tailf:display-when "not(../../ncs:module) or ../../ncs:module[ncs:name='Cisco-IOS-XR-clear-counters-act']";
      tailf:action clear-counters {
        tailf:actionpoint ncsproxy {
          tailf:internal;
        }
        description
          "Execute clear counters operations";
        input {
          leaf controller {
            type string;
            description
              "Controller name in R/S/I/P format";
          }
        }
      }
    }
  }
  augment "/ncs:devices/ncs:device-group/ncs:ned-id/ncs:rpc" {
    container rpc-clear-counters {
      tailf:ncs-device-type "netconf";
      tailf:display-when "/ncs:devices/ncs:device[ncs:name=current()/../../../ncs:member]/ncs:module[ncs:name='Cisco-IOS-XR-clear-counters-act']";
      tailf:action clear-counters {
        tailf:actionpoint ncsproxy {
          tailf:internal;
        }
        description
          "Execute clear counters operations";
        input {
          leaf controller {
            type string;
            description
              "Controller name in R/S/I/P format";
          }
        }
      }
    }
  }
}

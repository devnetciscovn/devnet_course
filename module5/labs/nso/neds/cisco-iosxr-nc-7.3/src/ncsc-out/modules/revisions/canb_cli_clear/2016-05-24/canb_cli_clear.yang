module canb_cli_clear {
  // Generated by yanger -t ncs
  tailf:mount-id "cisco-iosxr-nc-7.3:cisco-iosxr-nc-7.3";
  tailf:ncs-device-type "netconf";

  namespace "http://cisco.com/calvados/canb_cli_clear";
  prefix canb_clear;

  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module is for clearing OIR counters.

     Copyright (c) 2012-2020 by Cisco Systems, Inc.
     All rights reserved.";

  revision 2016-05-24 {
    description
      "Initial revision.";
  }

  grouping ncs_template_canb-clear-grp {
    // NCS drop config false container plugin
  }

  grouping ncs_rpc_notif_canb-clear-grp {
    container plugin {
      config false;
      container slot {
        config false;
        list location {
          key "location";
          config false;
          leaf location {
            type string;
          }
        }
      }
    }
  }

  grouping live_ncs_canb-clear-grp {
    container plugin {
      container slot {
        list location {
          key "location";
          leaf location {
            type string;
          }
        }
      }
    }
  }

  grouping canb-clear-grp {
    // NCS drop config false container plugin
  }
}

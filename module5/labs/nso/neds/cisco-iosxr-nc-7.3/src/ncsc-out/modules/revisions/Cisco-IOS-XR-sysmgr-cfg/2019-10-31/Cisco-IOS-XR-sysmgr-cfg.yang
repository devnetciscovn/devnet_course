module Cisco-IOS-XR-sysmgr-cfg {
  // Generated by yanger -t ncs
  tailf:mount-id "cisco-iosxr-nc-7.3:cisco-iosxr-nc-7.3";
  tailf:ncs-device-type "netconf";

  namespace "http://cisco.com/ns/yang/Cisco-IOS-XR-sysmgr-cfg";
  prefix sysmgr-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sysmgr package configuration.

     This module contains definitions
     for the following management objects:
       process-mandatory: Process mandatory configuration
       process-single-crash: Reboot condition for single mandatory
         process that crashes

     Copyright (c) 2013-2019 by Cisco Systems, Inc.
     All rights reserved.";

  revision 2019-10-31 {
    description
      "Added mandatory nodes.";
    semver:module-version "2.0.0";
  }
  revision 2019-04-05 {
    description
      "Establish semantic version baseline.";
    semver:module-version "1.0.0";
  }
  revision 2015-11-09 {
    description
      "IOS XR 6.0 revision.";
  }

  grouping ncs_template_PROCESS-TABLE {
    description
      "Common node of all, node";
    container processes {
      description
        "Table of processes";
      list process {
        // NCS patched for predictable order
        ordered-by user;
        key "process-name";
        description
          "Name of the executable process";
        leaf process-name {
          type xr:ncs_template_Cisco-ios-xr-string;
          description
            "Process name";
        }
      }
    }
  }

  grouping ncs_rpc_notif_PROCESS-TABLE {
    description
      "Common node of all, node";
    container processes {
      description
        "Table of processes";
      list process {
        key "process-name";
        description
          "Name of the executable process";
        leaf process-name {
          type xr:ncs_rpc_notif_Cisco-ios-xr-string;
          description
            "Process name";
        }
      }
    }
  }

  grouping live_ncs_PROCESS-TABLE {
    description
      "Common node of all, node";
    container processes {
      description
        "Table of processes";
      list process {
        key "process-name";
        description
          "Name of the executable process";
        leaf process-name {
          type xr:live_ncs_Cisco-ios-xr-string;
          description
            "Process name";
        }
      }
    }
  }

  grouping PROCESS-TABLE {
    description
      "Common node of all, node";
    container processes {
      description
        "Table of processes";
      list process {
        key "process-name";
        description
          "Name of the executable process";
        leaf process-name {
          type xr:Cisco-ios-xr-string;
          description
            "Process name";
        }
      }
    }
  }

  augment "/ncs:devices/ncs:device/ncs:config" {
    container process-mandatory {
      tailf:ncs-device-type "netconf";
      tailf:display-when "not(../../ncs:module) or ../../ncs:module[ncs:name='Cisco-IOS-XR-sysmgr-cfg']";
      description
        "Process mandatory configuration";
      container nodes {
        description
          "Table of mandatory nodes";
        list node {
          key "node-name";
          description
            "Mandatory node";
          leaf node-name {
            type xr:Node-id;
            description
              "Node name";
          }
          uses PROCESS-TABLE;
        }
      }
      container all {
        description
          "Mandatory for all nodes";
        uses PROCESS-TABLE;
      }
    }
    container process-single-crash {
      tailf:ncs-device-type "netconf";
      tailf:display-when "not(../../ncs:module) or ../../ncs:module[ncs:name='Cisco-IOS-XR-sysmgr-cfg']";
      presence "Indicates a process-single-crash node is configured.";
      description
        "Reboot condition for single mandatory process
         that crashes";
      leaf crashes {
        type uint32 {
          range "1..500";
        }
        mandatory true;
        description
          "Number of crashes for a process to trigger
           reboot";
      }
      leaf minimum-up-time {
        type uint32 {
          range "0..4294967295";
        }
        units "second";
        mandatory true;
        description
          "Minimum process up time (in seconds) to reset
           crash count";
      }
    }
  }
  augment "/ncs:devices/ncs:device/ncs:live-status" {
    container process-mandatory {
      tailf:ncs-device-type "netconf";
      tailf:display-when "not(../../ncs:module) or ../../ncs:module[ncs:name='Cisco-IOS-XR-sysmgr-cfg'] or (../../ncs:live-status-protocol[not(ncs:capability)]) or (../../ncs:live-status-protocol/ncs:capability/ncs:module[.='Cisco-IOS-XR-sysmgr-cfg'])";
      description
        "Process mandatory configuration";
      container nodes {
        description
          "Table of mandatory nodes";
        list node {
          key "node-name";
          description
            "Mandatory node";
          leaf node-name {
            type xr:live_ncs_Node-id;
            description
              "Node name";
          }
          uses live_ncs_PROCESS-TABLE;
        }
      }
      container all {
        description
          "Mandatory for all nodes";
        uses live_ncs_PROCESS-TABLE;
      }
    }
    container process-single-crash {
      tailf:ncs-device-type "netconf";
      tailf:display-when "not(../../ncs:module) or ../../ncs:module[ncs:name='Cisco-IOS-XR-sysmgr-cfg'] or (../../ncs:live-status-protocol[not(ncs:capability)]) or (../../ncs:live-status-protocol/ncs:capability/ncs:module[.='Cisco-IOS-XR-sysmgr-cfg'])";
      presence "Indicates a process-single-crash node is configured.";
      description
        "Reboot condition for single mandatory process
         that crashes";
      leaf crashes {
        type uint32 {
          range "1..500";
        }
        // NCS drop mandatory statement
        description
          "Number of crashes for a process to trigger
           reboot";
      }
      leaf minimum-up-time {
        type uint32 {
          range "0..4294967295";
        }
        units "second";
        // NCS drop mandatory statement
        description
          "Minimum process up time (in seconds) to reset
           crash count";
      }
    }
  }
  augment "/ncs:devices/ncs:template/ncs:ned-id/ncs:config" {
    container process-mandatory {
      description
        "Process mandatory configuration";
      container nodes {
        description
          "Table of mandatory nodes";
        list node {
          // NCS patched for predictable order
          ordered-by user;
          key "node-name";
          description
            "Mandatory node";
          leaf node-name {
            type xr:ncs_template_Node-id;
            description
              "Node name";
          }
          uses ncs_template_PROCESS-TABLE;
        }
      }
      container all {
        description
          "Mandatory for all nodes";
        uses ncs_template_PROCESS-TABLE;
      }
    }
    container process-single-crash {
      presence "Indicates a process-single-crash node is configured.";
      description
        "Reboot condition for single mandatory process
         that crashes";
      leaf crashes {
        type string;
        // NCS drop mandatory statement
        description
          "Number of crashes for a process to trigger
           reboot";
      }
      leaf minimum-up-time {
        type string;
        units "second";
        // NCS drop mandatory statement
        description
          "Minimum process up time (in seconds) to reset
           crash count";
      }
    }
  }
}

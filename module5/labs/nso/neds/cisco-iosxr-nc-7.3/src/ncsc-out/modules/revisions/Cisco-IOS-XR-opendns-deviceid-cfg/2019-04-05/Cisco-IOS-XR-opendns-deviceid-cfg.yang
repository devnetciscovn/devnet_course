module Cisco-IOS-XR-opendns-deviceid-cfg {
  // Generated by yanger -t ncs
  tailf:mount-id "cisco-iosxr-nc-7.3:cisco-iosxr-nc-7.3";
  tailf:ncs-device-type "netconf";

  namespace "http://cisco.com/ns/yang/Cisco-IOS-XR-opendns-deviceid-cfg";
  prefix opendns-deviceid-cfg;

  import cisco-semver {
    prefix semver;
  }
  import Cisco-IOS-XR-subscriber-infra-tmplmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR opendns-deviceid package configuration.

     This YANG module augments the
       Cisco-IOS-XR-subscriber-infra-tmplmgr-cfg
     module with configuration data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:template/ncs:ned-id/ncs:config/a1:dynamic-template/a1:subscriber-services/a1:subscriber-service" {
    description
      "This augment extends the configuration data of
       'Cisco-IOS-XR-subscriber-infra-tmplmgr-cfg'";
    container subscriber-attribute {
      description
        "Subscriber attribute configuration data";
      container open-dns {
        description
          "OpenDNS configuration data";
        leaf device-id {
          type string;
          description
            "Specify deviceID to be used for applying
             OpenDNS policies";
        }
      }
    }
  }
  augment "/ncs:devices/ncs:device/ncs:live-status/a1:dynamic-template/a1:subscriber-services/a1:subscriber-service" {
    description
      "This augment extends the configuration data of
       'Cisco-IOS-XR-subscriber-infra-tmplmgr-cfg'";
    container subscriber-attribute {
      tailf:ncs-device-type "netconf";
      tailf:display-when "not(../../../../../ncs:module) or ../../../../../ncs:module[ncs:name='Cisco-IOS-XR-opendns-deviceid-cfg'] or (../../../../../ncs:live-status-protocol[not(ncs:capability)]) or (../../../../../ncs:live-status-protocol/ncs:capability/ncs:module[.='Cisco-IOS-XR-opendns-deviceid-cfg'])";
      description
        "Subscriber attribute configuration data";
      container open-dns {
        description
          "OpenDNS configuration data";
        leaf device-id {
          type string;
          description
            "Specify deviceID to be used for applying
             OpenDNS policies";
        }
      }
    }
  }
  augment "/ncs:devices/ncs:device/ncs:config/a1:dynamic-template/a1:subscriber-services/a1:subscriber-service" {
    description
      "This augment extends the configuration data of
       'Cisco-IOS-XR-subscriber-infra-tmplmgr-cfg'";
    container subscriber-attribute {
      tailf:ncs-device-type "netconf";
      tailf:display-when "not(../../../../../ncs:module) or ../../../../../ncs:module[ncs:name='Cisco-IOS-XR-opendns-deviceid-cfg']";
      description
        "Subscriber attribute configuration data";
      container open-dns {
        description
          "OpenDNS configuration data";
        leaf device-id {
          type string;
          description
            "Specify deviceID to be used for applying
             OpenDNS policies";
        }
      }
    }
  }
}

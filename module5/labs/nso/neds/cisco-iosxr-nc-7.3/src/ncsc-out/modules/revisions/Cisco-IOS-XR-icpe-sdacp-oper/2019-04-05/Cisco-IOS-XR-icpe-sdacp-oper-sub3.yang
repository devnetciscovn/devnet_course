submodule Cisco-IOS-XR-icpe-sdacp-oper-sub3 {
  // Generated by yanger -t ncs
  tailf:mount-id "cisco-iosxr-nc-7.3:cisco-iosxr-nc-7.3";

  belongs-to Cisco-IOS-XR-icpe-sdacp-oper {
    prefix Cisco-IOS-XR-icpe-sdacp-oper;
  }

  import ietf-inet-types {
    prefix inet;
  }
  import ietf-yang-types {
    prefix yang;
  }
  import Cisco-IOS-XR-types {
    prefix xr;
  }
  import cisco-semver {
    prefix semver;
  }
  include Cisco-IOS-XR-icpe-sdacp-oper-sub2 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR icpe-sdacp package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_ICPE-SDACP-DISC-SAT-LINK-TYPE {
    description
      "ICPE SDACP DISC SAT LINK TYPE";
    leaf interface-handle {
      type xr:ncs_template_Interface-name;
      description
        "Interface handle";
    }
    leaf satellite-status {
      type ncs_template_Dpm-proto-state;
      description
        "Satellite status";
    }
    leaf conflict-reason {
      type string;
      description
        "Conflict reason";
    }
    leaf satellite-chassis-vendor {
      type ncs_template_Xr-yang-string;
      description
        "Satellite chassis vendor";
    }
    leaf satellite-interface-id {
      type string;
      description
        "Satellite interface ID";
    }
    leaf satellite-interface-mac {
      type string;
      description
        "Satellite interface MAC";
    }
    leaf satellite-chassis-mac {
      type string;
      description
        "Satellite chassis MAC";
    }
    leaf satellite-serial-id {
      type ncs_template_Xr-yang-string;
      description
        "Satellite serial id";
    }
    leaf satellite-module-vendor {
      type ncs_template_Xr-yang-string;
      description
        "Satellite module vendor";
    }
  }

  grouping ncs_template_ICPE-SDACP-SAT-TYPE {
    description
      "ICPE SDACP SAT TYPE";
    leaf satellite-id {
      type string;
      description
        "Satellite ID";
    }
    leaf satellite-status {
      type ncs_template_Dpm-proto-state;
      description
        "Satellite status";
    }
    leaf conflict-reason {
      type string;
      description
        "Conflict reason";
    }
    leaf satellite-ip-address {
      type string;
      description
        "Satellite IP address";
    }
    leaf host-ip-address {
      type string;
      description
        "Host IP address";
    }
    list interface {
      // NCS patched for predictable order
      ordered-by user;
      description
        "ICPE Discovered satellite state information
         table";
      uses ncs_template_ICPE-SDACP-DISC-SAT-LINK-TYPE;
    }
  }

  grouping ncs_template_ICPE-SDACP-DISC-SFL-TYPE {
    description
      "ICPE SDACP DISC SFL TYPE";
    leaf interface-name {
      type ncs_template_Xr-yang-string;
      description
        "Interface name";
    }
    leaf interface-status {
      type ncs_template_Dpm-proto-state;
      description
        "Interface status";
    }
  }

  grouping ncs_template_ICPE-SDACP-CFG-SFL {
    description
      "ICPE Configured interface state information";
    leaf interface-name-xr {
      type ncs_template_Xr-yang-string;
      description
        "Interface name";
    }
    list interface {
      // NCS patched for predictable order
      ordered-by user;
      description
        "ICPE Discovery interface state information table";
      uses ncs_template_ICPE-SDACP-DISC-SFL-TYPE;
    }
    list satellite {
      // NCS patched for predictable order
      ordered-by user;
      description
        "ICPE Satellite state information table";
      uses ncs_template_ICPE-SDACP-SAT-TYPE;
    }
  }

  grouping ncs_rpc_notif_ICPE-SDACP-DISC-SAT-LINK-TYPE {
    description
      "ICPE SDACP DISC SAT LINK TYPE";
    leaf interface-handle {
      type xr:ncs_rpc_notif_Interface-name;
      description
        "Interface handle";
    }
    leaf satellite-status {
      type ncs_rpc_notif_Dpm-proto-state;
      description
        "Satellite status";
    }
    leaf conflict-reason {
      type uint32;
      description
        "Conflict reason";
    }
    leaf satellite-chassis-vendor {
      type ncs_rpc_notif_Xr-yang-string;
      description
        "Satellite chassis vendor";
    }
    leaf satellite-interface-id {
      type uint32;
      description
        "Satellite interface ID";
    }
    leaf satellite-interface-mac {
      type yang:mac-address;
      description
        "Satellite interface MAC";
    }
    leaf satellite-chassis-mac {
      type yang:mac-address;
      description
        "Satellite chassis MAC";
    }
    leaf satellite-serial-id {
      type ncs_rpc_notif_Xr-yang-string;
      description
        "Satellite serial id";
    }
    leaf satellite-module-vendor {
      type ncs_rpc_notif_Xr-yang-string;
      description
        "Satellite module vendor";
    }
  }

  grouping ncs_rpc_notif_ICPE-SDACP-SAT-TYPE {
    description
      "ICPE SDACP SAT TYPE";
    leaf satellite-id {
      type uint16;
      description
        "Satellite ID";
    }
    leaf satellite-status {
      type ncs_rpc_notif_Dpm-proto-state;
      description
        "Satellite status";
    }
    leaf conflict-reason {
      type uint32;
      description
        "Conflict reason";
    }
    leaf satellite-ip-address {
      type inet:ipv4-address;
      description
        "Satellite IP address";
    }
    leaf host-ip-address {
      type inet:ipv4-address;
      description
        "Host IP address";
    }
    list interface {
      description
        "ICPE Discovered satellite state information
         table";
      uses ncs_rpc_notif_ICPE-SDACP-DISC-SAT-LINK-TYPE;
    }
  }

  grouping ncs_rpc_notif_ICPE-SDACP-DISC-SFL-TYPE {
    description
      "ICPE SDACP DISC SFL TYPE";
    leaf interface-name {
      type ncs_rpc_notif_Xr-yang-string;
      description
        "Interface name";
    }
    leaf interface-status {
      type ncs_rpc_notif_Dpm-proto-state;
      description
        "Interface status";
    }
  }

  grouping ncs_rpc_notif_ICPE-SDACP-CFG-SFL {
    description
      "ICPE Configured interface state information";
    leaf interface-name-xr {
      type ncs_rpc_notif_Xr-yang-string;
      description
        "Interface name";
    }
    list interface {
      description
        "ICPE Discovery interface state information table";
      uses ncs_rpc_notif_ICPE-SDACP-DISC-SFL-TYPE;
    }
    list satellite {
      description
        "ICPE Satellite state information table";
      uses ncs_rpc_notif_ICPE-SDACP-SAT-TYPE;
    }
  }

  grouping live_ncs_ICPE-SDACP-DISC-SAT-LINK-TYPE {
    description
      "ICPE SDACP DISC SAT LINK TYPE";
    leaf interface-handle {
      type xr:live_ncs_Interface-name;
      description
        "Interface handle";
    }
    leaf satellite-status {
      type live_ncs_Dpm-proto-state;
      description
        "Satellite status";
    }
    leaf conflict-reason {
      type uint32;
      description
        "Conflict reason";
    }
    leaf satellite-chassis-vendor {
      type live_ncs_Xr-yang-string;
      description
        "Satellite chassis vendor";
    }
    leaf satellite-interface-id {
      type uint32;
      description
        "Satellite interface ID";
    }
    leaf satellite-interface-mac {
      type yang:mac-address;
      description
        "Satellite interface MAC";
    }
    leaf satellite-chassis-mac {
      type yang:mac-address;
      description
        "Satellite chassis MAC";
    }
    leaf satellite-serial-id {
      type live_ncs_Xr-yang-string;
      description
        "Satellite serial id";
    }
    leaf satellite-module-vendor {
      type live_ncs_Xr-yang-string;
      description
        "Satellite module vendor";
    }
  }

  grouping live_ncs_ICPE-SDACP-SAT-TYPE {
    description
      "ICPE SDACP SAT TYPE";
    leaf satellite-id {
      type uint16;
      description
        "Satellite ID";
    }
    leaf satellite-status {
      type live_ncs_Dpm-proto-state;
      description
        "Satellite status";
    }
    leaf conflict-reason {
      type uint32;
      description
        "Conflict reason";
    }
    leaf satellite-ip-address {
      type inet:ipv4-address;
      description
        "Satellite IP address";
    }
    leaf host-ip-address {
      type inet:ipv4-address;
      description
        "Host IP address";
    }
    list interface {
      description
        "ICPE Discovered satellite state information
         table";
      uses live_ncs_ICPE-SDACP-DISC-SAT-LINK-TYPE;
    }
  }

  grouping live_ncs_ICPE-SDACP-DISC-SFL-TYPE {
    description
      "ICPE SDACP DISC SFL TYPE";
    leaf interface-name {
      type live_ncs_Xr-yang-string;
      description
        "Interface name";
    }
    leaf interface-status {
      type live_ncs_Dpm-proto-state;
      description
        "Interface status";
    }
  }

  grouping live_ncs_ICPE-SDACP-CFG-SFL {
    description
      "ICPE Configured interface state information";
    leaf interface-name-xr {
      type live_ncs_Xr-yang-string;
      description
        "Interface name";
    }
    list interface {
      description
        "ICPE Discovery interface state information table";
      uses live_ncs_ICPE-SDACP-DISC-SFL-TYPE;
    }
    list satellite {
      description
        "ICPE Satellite state information table";
      uses live_ncs_ICPE-SDACP-SAT-TYPE;
    }
  }

  grouping ICPE-SDACP-DISC-SAT-LINK-TYPE {
    description
      "ICPE SDACP DISC SAT LINK TYPE";
    leaf interface-handle {
      type xr:Interface-name;
      description
        "Interface handle";
    }
    leaf satellite-status {
      type Dpm-proto-state;
      description
        "Satellite status";
    }
    leaf conflict-reason {
      type uint32;
      description
        "Conflict reason";
    }
    leaf satellite-chassis-vendor {
      type Xr-yang-string;
      description
        "Satellite chassis vendor";
    }
    leaf satellite-interface-id {
      type uint32;
      description
        "Satellite interface ID";
    }
    leaf satellite-interface-mac {
      type yang:mac-address;
      description
        "Satellite interface MAC";
    }
    leaf satellite-chassis-mac {
      type yang:mac-address;
      description
        "Satellite chassis MAC";
    }
    leaf satellite-serial-id {
      type Xr-yang-string;
      description
        "Satellite serial id";
    }
    leaf satellite-module-vendor {
      type Xr-yang-string;
      description
        "Satellite module vendor";
    }
  }

  grouping ICPE-SDACP-SAT-TYPE {
    description
      "ICPE SDACP SAT TYPE";
    leaf satellite-id {
      type uint16;
      description
        "Satellite ID";
    }
    leaf satellite-status {
      type Dpm-proto-state;
      description
        "Satellite status";
    }
    leaf conflict-reason {
      type uint32;
      description
        "Conflict reason";
    }
    leaf satellite-ip-address {
      type inet:ipv4-address;
      description
        "Satellite IP address";
    }
    leaf host-ip-address {
      type inet:ipv4-address;
      description
        "Host IP address";
    }
    list interface {
      description
        "ICPE Discovered satellite state information
         table";
      uses ICPE-SDACP-DISC-SAT-LINK-TYPE;
    }
  }

  grouping ICPE-SDACP-DISC-SFL-TYPE {
    description
      "ICPE SDACP DISC SFL TYPE";
    leaf interface-name {
      type Xr-yang-string;
      description
        "Interface name";
    }
    leaf interface-status {
      type Dpm-proto-state;
      description
        "Interface status";
    }
  }

  grouping ICPE-SDACP-CFG-SFL {
    description
      "ICPE Configured interface state information";
    leaf interface-name-xr {
      type Xr-yang-string;
      description
        "Interface name";
    }
    list interface {
      description
        "ICPE Discovery interface state information table";
      uses ICPE-SDACP-DISC-SFL-TYPE;
    }
    list satellite {
      description
        "ICPE Satellite state information table";
      uses ICPE-SDACP-SAT-TYPE;
    }
  }
}

module Cisco-IOS-XR-lmp-oper {
  // Generated by yanger -t ncs
  tailf:mount-id "cisco-iosxr-nc-7.3:cisco-iosxr-nc-7.3";
  tailf:ncs-device-type "netconf";

  namespace "http://cisco.com/ns/yang/Cisco-IOS-XR-lmp-oper";
  prefix lmp-oper;

  import Cisco-IOS-XR-types {
    prefix xr;
  }
  import cisco-semver {
    prefix semver;
  }
  include Cisco-IOS-XR-lmp-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lmp package operational data.

     This module contains definitions
     for the following management objects:
       lmp: Main common UCP/OLM operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container lmp
  }
  augment "/ncs:devices/ncs:device/ncs:live-status" {
    container lmp {
      tailf:ncs-device-type "netconf";
      tailf:display-when "not(../../ncs:module) or ../../ncs:module[ncs:name='Cisco-IOS-XR-lmp-oper'] or (../../ncs:live-status-protocol[not(ncs:capability)]) or (../../ncs:live-status-protocol/ncs:capability/ncs:module[.='Cisco-IOS-XR-lmp-oper'])";
      description
        "Main common UCP/OLM operational data";
      container global-status {
        description
          "Global OLM process information";
        uses live_ncs_OLM-GLOBAL-INFO;
      }
      container clients {
        description
          "UCP OLM clients container class";
        list client {
          key "client-name";
          description
            "Information on a particular OLM API client";
          leaf client-name {
            type xr:live_ncs_Cisco-ios-xr-string;
            description
              "Client name";
          }
          uses live_ncs_OLM-CLIENT-INFO;
        }
      }
      container gmpls-uni {
        description
          "GMPLS UNI specific OLM/LMP configuration";
        container te-links {
          description
            "UCP OLM TE Links container class";
          list te-link {
            key "controller-name";
            description
              "Information on a particular OLM TE Link";
            leaf controller-name {
              type xr:live_ncs_Interface-name;
              description
                "Controller name";
            }
            uses live_ncs_OLM-TE-LINK-INFO;
          }
        }
        container neighbors {
          description
            "UCP OLM neighbors container class";
          list neighbor {
            key "neighbor-name";
            description
              "Information on a particular OLM neighbor";
            leaf neighbor-name {
              type xr:live_ncs_Cisco-ios-xr-string;
              description
                "Neighbor name";
            }
            uses live_ncs_OLM-NEIGHBOR-INFO;
          }
        }
      }
      container component-link-ids {
        description
          "UCP OLM component link ID container class";
        list component-link-id {
          key "controller-name";
          description
            "Retrieve the LMP component link ID for a given
             controller";
          leaf controller-name {
            type xr:live_ncs_Interface-name;
            description
              "Controller name";
          }
          uses live_ncs_OLM-COMPONENT-LINK-ID-INFO;
        }
      }
    }
  }
  augment "/ncs:devices/ncs:template/ncs:ned-id/ncs:config" {
    // NCS drop config false container lmp
  }
}

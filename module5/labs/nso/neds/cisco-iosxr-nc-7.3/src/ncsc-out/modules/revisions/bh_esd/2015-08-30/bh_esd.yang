module bh_esd {
  // Generated by yanger -t ncs
  tailf:mount-id "cisco-iosxr-nc-7.3:cisco-iosxr-nc-7.3";
  tailf:ncs-device-type "netconf";

  namespace "http://cisco.com/calvados/bh_esd";
  prefix bh_esd;

  import Cisco-IOS-XR-sysadmin-show-trace {
    prefix show_trace;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2015-08-30 {
    description
      "Initial version.";
  }

  augment "/ncs:devices/ncs:device/ncs:config" {
    // NCS drop config false container bh_esd
  }
  augment "/ncs:devices/ncs:device/ncs:live-status" {
    container bh_esd {
      tailf:ncs-device-type "netconf";
      tailf:display-when "not(../../ncs:module) or ../../ncs:module[ncs:name='bh_esd'] or (../../ncs:live-status-protocol[not(ncs:capability)]) or (../../ncs:live-status-protocol/ncs:capability/ncs:module[.='bh_esd'])";
      uses show_trace:live_ncs_traceable;
    }
  }
  augment "/ncs:devices/ncs:template/ncs:ned-id/ncs:config" {
    // NCS drop config false container bh_esd
  }
}

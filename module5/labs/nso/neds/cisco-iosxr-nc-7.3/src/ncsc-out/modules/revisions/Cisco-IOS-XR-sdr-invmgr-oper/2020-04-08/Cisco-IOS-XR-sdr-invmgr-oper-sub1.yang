submodule Cisco-IOS-XR-sdr-invmgr-oper-sub1 {
  // Generated by yanger -t ncs
  tailf:mount-id "cisco-iosxr-nc-7.3:cisco-iosxr-nc-7.3";

  belongs-to Cisco-IOS-XR-sdr-invmgr-oper {
    prefix Cisco-IOS-XR-sdr-invmgr-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR sdr-invmgr package operational data.

     Copyright (c) 2013-2020 by Cisco Systems, Inc.
     All rights reserved.";

  revision 2020-04-08 {
    description
      "Deprecated Memory container.";
    semver:module-version "2.0.0";
  }
  revision 2019-04-05 {
    description
      "Establish semantic version baseline.";
    semver:module-version "1.0.1";
  }
  revision 2019-03-07 {
    description
      "Improved description for certain fields.";
  }
  revision 2015-11-09 {
    description
      "IOS XR 6.0 revision.";
  }

  grouping ncs_template_INV-ADMIN-MEMPOOL-DATA {
    description
      "Inv Admin Mempool Data";
    leaf total-memory {
      type string;
      description
        "Total Memory of the inventory admin Memory Pool";
    }
    leaf available-memory {
      type string;
      description
        "Avaialble Memory of the inventory admin Memory
         Pool";
    }
  }

  grouping ncs_rpc_notif_INV-ADMIN-MEMPOOL-DATA {
    description
      "Inv Admin Mempool Data";
    leaf total-memory {
      type uint32;
      description
        "Total Memory of the inventory admin Memory Pool";
    }
    leaf available-memory {
      type uint32;
      description
        "Avaialble Memory of the inventory admin Memory
         Pool";
    }
  }

  grouping live_ncs_INV-ADMIN-MEMPOOL-DATA {
    description
      "Inv Admin Mempool Data";
    leaf total-memory {
      type uint32;
      description
        "Total Memory of the inventory admin Memory Pool";
    }
    leaf available-memory {
      type uint32;
      description
        "Avaialble Memory of the inventory admin Memory
         Pool";
    }
  }

  grouping INV-ADMIN-MEMPOOL-DATA {
    description
      "Inv Admin Mempool Data";
    leaf total-memory {
      type uint32;
      description
        "Total Memory of the inventory admin Memory Pool";
    }
    leaf available-memory {
      type uint32;
      description
        "Avaialble Memory of the inventory admin Memory
         Pool";
    }
  }
}

module Cisco-IOS-XR-icpe-sdacp-oper {
  // Generated by yanger -t ncs
  tailf:mount-id "cisco-iosxr-nc-7.3:cisco-iosxr-nc-7.3";
  tailf:ncs-device-type "netconf";

  namespace "http://cisco.com/ns/yang/Cisco-IOS-XR-icpe-sdacp-oper";
  prefix icpe-sdacp-oper;

  import Cisco-IOS-XR-types {
    prefix xr;
  }
  import cisco-semver {
    prefix semver;
  }
  import Cisco-IOS-XR-icpe-infra-oper {
    prefix a1;
  }
  include Cisco-IOS-XR-icpe-sdacp-oper-sub3 {
    revision-date 2019-04-05;
  }
  include Cisco-IOS-XR-icpe-sdacp-oper-sub2 {
    revision-date 2019-04-05;
  }
  include Cisco-IOS-XR-icpe-sdacp-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR icpe-sdacp package operational data.

     This YANG module augments the
       Cisco-IOS-XR-icpe-infra-oper
     module with state data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Icpe-sat-id {
    type string;
    description
      "Icpe sat id";
  }

  typedef ncs_rpc_notif_Icpe-sat-id {
    type uint32 {
      range "100..65534";
    }
    description
      "Icpe sat id";
  }

  typedef live_ncs_Icpe-sat-id {
    type uint32 {
      range "100..65534";
    }
    description
      "Icpe sat id";
  }

  typedef Icpe-sat-id {
    type uint32 {
      range "100..65534";
    }
    description
      "Icpe sat id";
  }

  augment "/ncs:devices/ncs:device/ncs:live-status/a1:nv-satellite" {
    description
      "This augment extends the operational data of
       'Cisco-IOS-XR-icpe-infra-oper'";
    container sdacp-discovery2s {
      tailf:ncs-device-type "netconf";
      tailf:display-when "not(../../../ncs:module) or ../../../ncs:module[ncs:name='Cisco-IOS-XR-icpe-sdacp-oper'] or (../../../ncs:live-status-protocol[not(ncs:capability)]) or (../../../ncs:live-status-protocol/ncs:capability/ncs:module[.='Cisco-IOS-XR-icpe-sdacp-oper'])";
      description
        "ICPE Configured interface state information
         table";
      list sdacp-discovery2 {
        key "interface-name";
        description
          "ICPE Configured interface state information";
        leaf interface-name {
          type xr:live_ncs_Interface-name;
          description
            "Interface name";
        }
        uses live_ncs_ICPE-SDACP-CFG-SFL;
      }
    }
  }
  augment "/ncs:devices/ncs:device/ncs:live-status/a1:nv-satellite" {
    description
      "This augment extends the operational data of
       'Cisco-IOS-XR-icpe-infra-oper'";
    container icpe-dpms {
      tailf:ncs-device-type "netconf";
      tailf:display-when "not(../../../ncs:module) or ../../../ncs:module[ncs:name='Cisco-IOS-XR-icpe-sdacp-oper'] or (../../../ncs:live-status-protocol[not(ncs:capability)]) or (../../../ncs:live-status-protocol/ncs:capability/ncs:module[.='Cisco-IOS-XR-icpe-sdacp-oper'])";
      description
        "ICPE DPM operational information table";
      list icpe-dpm {
        key "discovery-interface";
        description
          "ICPE DPM operational information";
        leaf discovery-interface {
          type xr:live_ncs_Interface-name;
          description
            "Discovery interface";
        }
        uses live_ncs_DPM-OPER-IF;
      }
    }
  }
  augment "/ncs:devices/ncs:device/ncs:live-status/a1:nv-satellite" {
    description
      "This augment extends the operational data of
       'Cisco-IOS-XR-icpe-infra-oper'";
    container sdacp-controls {
      tailf:ncs-device-type "netconf";
      tailf:display-when "not(../../../ncs:module) or ../../../ncs:module[ncs:name='Cisco-IOS-XR-icpe-sdacp-oper'] or (../../../ncs:live-status-protocol[not(ncs:capability)]) or (../../../ncs:live-status-protocol/ncs:capability/ncs:module[.='Cisco-IOS-XR-icpe-sdacp-oper'])";
      description
        "SDAC Protocol Discovery information table";
      list sdacp-control {
        key "satellite-id";
        description
          "SDAC Protocol Discovery information";
        leaf satellite-id {
          type live_ncs_Icpe-sat-id;
          description
            "Satellite ID";
        }
        uses live_ncs_ICPE-CPM-OPER-SAT;
      }
    }
  }
}

module Cisco-IOS-XR-envmon-cfg {
  // Generated by yanger -t ncs
  tailf:mount-id "cisco-iosxr-nc-7.3:cisco-iosxr-nc-7.3";
  tailf:ncs-device-type "netconf";

  namespace "http://cisco.com/ns/yang/Cisco-IOS-XR-envmon-cfg";
  prefix envmon-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR envmon package configuration.

     This module contains definitions
     for the following management objects:
       environmental-monitoring: Environmental Monitoring Operational
         data space

     Copyright (c) 2013-2020 by Cisco Systems, Inc.
     All rights reserved.";

  revision 2020-09-08 {
    description
      "IOS XR 7.3.1 revision. Added Alarm port config.";
    semver:module-version "1.1.0";
  }
  revision 2019-10-15 {
    description
      "IOS XR 7.0.12 revision. Added chassis door alarm.";
    semver:module-version "1.1.0";
  }
  revision 2019-04-05 {
    description
      "Establish semantic version baseline.";
    semver:module-version "1.0.0";
  }
  revision 2015-11-09 {
    description
      "IOS XR 6.0 revision.";
  }

  augment "/ncs:devices/ncs:device/ncs:config" {
    container environmental-monitoring {
      tailf:ncs-device-type "netconf";
      tailf:display-when "not(../../ncs:module) or ../../ncs:module[ncs:name='Cisco-IOS-XR-envmon-cfg']";
      description
        "Environmental Monitoring Operational data space";
      container fan-ctrl-optics {
        description
          "Control chassis fan status";
        leaf enable {
          type boolean;
          default "false";
          description
            "Enable or disable higher fan speed";
        }
      }
      container air-filter {
        description
          "Chassis air-filter status";
        container replaced {
          description
            "air-filter replaced date";
          leaf date {
            type string;
            description
              "CCYY-MM-DD format";
          }
        }
      }
      container chassis-door-alarm {
        description
          "Control chassis door alarm";
        leaf enable {
          type boolean;
          default "false";
          description
            "Enable or disable chassis door alarm";
        }
      }
      leaf min-fan-speed {
        type uint32 {
          range "0..100";
        }
        description
          "Min default fan speed in PWM";
      }
    }
  }
  augment "/ncs:devices/ncs:device/ncs:live-status" {
    container environmental-monitoring {
      tailf:ncs-device-type "netconf";
      tailf:display-when "not(../../ncs:module) or ../../ncs:module[ncs:name='Cisco-IOS-XR-envmon-cfg'] or (../../ncs:live-status-protocol[not(ncs:capability)]) or (../../ncs:live-status-protocol/ncs:capability/ncs:module[.='Cisco-IOS-XR-envmon-cfg'])";
      description
        "Environmental Monitoring Operational data space";
      container fan-ctrl-optics {
        description
          "Control chassis fan status";
        leaf enable {
          type boolean;
          // NCS drop default statement
          description
            "Enable or disable higher fan speed";
        }
      }
      container air-filter {
        description
          "Chassis air-filter status";
        container replaced {
          description
            "air-filter replaced date";
          leaf date {
            type string;
            description
              "CCYY-MM-DD format";
          }
        }
      }
      container chassis-door-alarm {
        description
          "Control chassis door alarm";
        leaf enable {
          type boolean;
          // NCS drop default statement
          description
            "Enable or disable chassis door alarm";
        }
      }
      leaf min-fan-speed {
        type uint32 {
          range "0..100";
        }
        description
          "Min default fan speed in PWM";
      }
    }
  }
  augment "/ncs:devices/ncs:template/ncs:ned-id/ncs:config" {
    container environmental-monitoring {
      description
        "Environmental Monitoring Operational data space";
      container fan-ctrl-optics {
        description
          "Control chassis fan status";
        leaf enable {
          type string;
          // NCS drop default statement
          description
            "Enable or disable higher fan speed";
        }
      }
      container air-filter {
        description
          "Chassis air-filter status";
        container replaced {
          description
            "air-filter replaced date";
          leaf date {
            type string;
            description
              "CCYY-MM-DD format";
          }
        }
      }
      container chassis-door-alarm {
        description
          "Control chassis door alarm";
        leaf enable {
          type string;
          // NCS drop default statement
          description
            "Enable or disable chassis door alarm";
        }
      }
      leaf min-fan-speed {
        type string;
        description
          "Min default fan speed in PWM";
      }
    }
  }
}

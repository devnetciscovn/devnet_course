module Cisco-IOS-XR-sysadmin-fpd-infra-cli-fpd {
  // Generated by yanger -t ncs
  tailf:mount-id "cisco-iosxr-nc-7.3:cisco-iosxr-nc-7.3";
  tailf:ncs-device-type "netconf";

  namespace "http://www.cisco.com/ns/yang/Cisco-IOS-XR-sysadmin-fpd-infra-cli-fpd";
  prefix fpd;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "FPD CLI support for both oper and config

     Copyright (c) 2012-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2011-12-03 {
    description
      "Initial revision.";
  }

  grouping ncs_template_fpd {
    container config {
      description
        "fpd config mode";
      uses ncs_template_global-fpd-config-group;
    }
  }

  grouping ncs_template_global-fpd-config-group {
    leaf auto-upgrade {
      type string;
      // NCS drop default statement
      // NCS dropped explicit config true
    }
  }

  grouping ncs_rpc_notif_fpd {
    container config {
      description
        "fpd config mode";
      uses ncs_rpc_notif_global-fpd-config-group;
    }
  }

  grouping ncs_rpc_notif_global-fpd-config-group {
    leaf auto-upgrade {
      type enumeration {
        enum "enable";
        enum "disable";
      }
      default "disable";
      // NCS dropped explicit config true
    }
  }

  grouping live_ncs_fpd {
    container config {
      description
        "fpd config mode";
      uses live_ncs_global-fpd-config-group;
    }
  }

  grouping live_ncs_global-fpd-config-group {
    leaf auto-upgrade {
      type enumeration {
        enum "enable";
        enum "disable";
      }
      // NCS drop default statement
    }
  }

  grouping fpd {
    container config {
      description
        "fpd config mode";
      uses global-fpd-config-group;
    }
  }

  grouping global-fpd-config-group {
    leaf auto-upgrade {
      type enumeration {
        enum "enable";
        enum "disable";
      }
      default "disable";
      // NCS dropped explicit config true
    }
  }

  augment "/ncs:devices/ncs:device/ncs:config" {
    container fpd {
      tailf:ncs-device-type "netconf";
      tailf:display-when "not(../../ncs:module) or ../../ncs:module[ncs:name='Cisco-IOS-XR-sysadmin-fpd-infra-cli-fpd']";
      uses fpd;
    }
  }
  augment "/ncs:devices/ncs:device/ncs:live-status" {
    container fpd {
      tailf:ncs-device-type "netconf";
      tailf:display-when "not(../../ncs:module) or ../../ncs:module[ncs:name='Cisco-IOS-XR-sysadmin-fpd-infra-cli-fpd'] or (../../ncs:live-status-protocol[not(ncs:capability)]) or (../../ncs:live-status-protocol/ncs:capability/ncs:module[.='Cisco-IOS-XR-sysadmin-fpd-infra-cli-fpd'])";
      uses live_ncs_fpd;
    }
  }
  augment "/ncs:devices/ncs:template/ncs:ned-id/ncs:config" {
    container fpd {
      uses ncs_template_fpd;
    }
  }
}

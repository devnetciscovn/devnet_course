module Cisco-IOS-XR-rptiming-tmg-oper {
  // Generated by yanger -t ncs
  tailf:mount-id "cisco-iosxr-nc-7.3:cisco-iosxr-nc-7.3";
  tailf:ncs-device-type "netconf";

  namespace "http://cisco.com/ns/yang/Cisco-IOS-XR-rptiming-tmg-oper";
  prefix rptiming-tmg-oper;

  import Cisco-IOS-XR-types {
    prefix xr;
  }
  import cisco-semver {
    prefix semver;
  }
  include Cisco-IOS-XR-rptiming-tmg-oper-sub1 {
    revision-date 2019-11-24;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR rptiming-tmg package operational data.

     This module contains definitions
     for the following management objects:
       timing-card: Timing PLL status and configuration

     Copyright (c) 2013-2019 by Cisco Systems, Inc.
     All rights reserved.";

  revision 2019-11-24 {
    description
      "Added Yang support for LED Information.";
    semver:module-version "1.0.0";
  }
  revision 2019-04-05 {
    description
      "Establish semantic version baseline.";
  }
  revision 2015-11-09 {
    description
      "IOS XR 6.0 revision.";
  }

  augment "/ncs:devices/ncs:device/ncs:config" {
    // NCS drop config false container 'timing-card'
  }
  augment "/ncs:devices/ncs:device/ncs:live-status" {
    container timing-card {
      tailf:ncs-device-type "netconf";
      tailf:display-when "not(../../ncs:module) or ../../ncs:module[ncs:name='Cisco-IOS-XR-rptiming-tmg-oper'] or (../../ncs:live-status-protocol[not(ncs:capability)]) or (../../ncs:live-status-protocol/ncs:capability/ncs:module[.='Cisco-IOS-XR-rptiming-tmg-oper'])";
      description
        "Timing PLL status and configuration";
      container nodes {
        description
          "List of nodes applicable to timing";
        list node {
          key "node-name";
          description
            "Timing operational data for a single node";
          container pll1 {
            description
              "Display the timing card SPLL1 status
               information";
            uses live_ncs_TMG-PLL-INFO;
          }
          container pll0 {
            description
              "Display the timing card SPLL0 status
               information";
            uses live_ncs_TMG-PLL-INFO;
          }
          container input-clock2 {
            description
              "Display the timing card input clock status
               information";
            uses live_ncs_TMG-CLKIN-INFO;
          }
          container input-clock1 {
            description
              "Display the timing card input clock status
               information";
            uses live_ncs_TMG-CLKIN-INFO;
          }
          container input-clock0 {
            description
              "Display the timing card input clock status
               information";
            uses live_ncs_TMG-CLKIN-INFO;
          }
          container pll-dump {
            description
              "Display the timing card PLL dump information";
            uses live_ncs_TMG-PLL-DUMP;
          }
          container led {
            description
              "Display the timing card LED information";
            uses live_ncs_TMG-LED-INFO;
          }
          container tod {
            description
              "Display the timing card ToD information";
            uses live_ncs_TMG-TOD-INFO;
          }
          container pll2 {
            description
              "Display the timing card SPLL2 status
               information";
            uses live_ncs_TMG-PLL-INFO;
          }
          leaf node-name {
            type xr:live_ncs_Node-id;
            description
              "Node Name";
          }
        }
      }
    }
  }
  augment "/ncs:devices/ncs:template/ncs:ned-id/ncs:config" {
    // NCS drop config false container 'timing-card'
  }
}

module SNMP-NOTIFICATION-MIB {
  // Generated by yanger -t ncs
  tailf:mount-id "cisco-iosxr-nc-7.3:cisco-iosxr-nc-7.3";
  tailf:ncs-device-type "netconf";

  namespace "http://tail-f.com/ns/mibs/SNMP-NOTIFICATION-MIB/200210140000Z";
  prefix SNMP_NOTIFICATION_MIB;

  import ietf-yang-types {
    prefix yang;
  }
  import tailf-common {
    prefix tailf;
  }
  import SNMPv2-TC {
    prefix SNMPv2_TC;
  }
  import SNMP-TARGET-MIB {
    prefix SNMP_TARGET_MIB;
  }
  import tailf-ncs {
    prefix ncs;
  }

  revision 2021-03-15 {
    description
      "Add textual description for presence statements";
  }
  revision 2002-10-14 {
    description
      "";
  }

  typedef ncs_template_snmpNotifyNameType {
    type string;
  }

  typedef ncs_template_snmpNotifyTypeType {
    type string;
  }

  typedef ncs_template_snmpTargetParamsNameType {
    type string;
  }

  typedef ncs_template_snmpNotifyFilterProfileNameType {
    type string;
  }

  typedef ncs_template_snmpNotifyFilterMaskType {
    type string;
  }

  typedef ncs_template_snmpNotifyFilterTypeType {
    type string;
  }

  typedef ncs_rpc_notif_snmpNotifyNameType {
    type string {
      length "1 .. 32";
    }
  }

  typedef ncs_rpc_notif_snmpNotifyTypeType {
    type enumeration {
      enum "trap" {
        value 1;
      }
      enum "inform" {
        value 2;
      }
    }
  }

  typedef ncs_rpc_notif_snmpTargetParamsNameType {
    type string {
      length "1 .. 32";
    }
  }

  typedef ncs_rpc_notif_snmpNotifyFilterProfileNameType {
    type string {
      length "1 .. 32";
    }
  }

  typedef ncs_rpc_notif_snmpNotifyFilterMaskType {
    type tailf:hex-list {
      pattern '(((([0-9A-Fa-f]{2}):){0,15}([0-9A-Fa-f]{2}))){0,1}';
      tailf:value-length "min .. 16";
    }
  }

  typedef ncs_rpc_notif_snmpNotifyFilterTypeType {
    type enumeration {
      enum "included" {
        value 1;
      }
      enum "excluded" {
        value 2;
      }
    }
  }

  typedef live_ncs_snmpNotifyNameType {
    type string {
      length "1 .. 32";
    }
  }

  typedef live_ncs_snmpNotifyTypeType {
    type enumeration {
      enum "trap" {
        value 1;
      }
      enum "inform" {
        value 2;
      }
    }
  }

  typedef live_ncs_snmpTargetParamsNameType {
    type string {
      length "1 .. 32";
    }
  }

  typedef live_ncs_snmpNotifyFilterProfileNameType {
    type string {
      length "1 .. 32";
    }
  }

  typedef live_ncs_snmpNotifyFilterMaskType {
    type tailf:hex-list {
      pattern '(((([0-9A-Fa-f]{2}):){0,15}([0-9A-Fa-f]{2}))){0,1}';
      tailf:value-length "min .. 16";
    }
  }

  typedef live_ncs_snmpNotifyFilterTypeType {
    type enumeration {
      enum "included" {
        value 1;
      }
      enum "excluded" {
        value 2;
      }
    }
  }

  typedef snmpNotifyNameType {
    type string {
      length "1 .. 32";
    }
  }

  typedef snmpNotifyTypeType {
    type enumeration {
      enum "trap" {
        value 1;
      }
      enum "inform" {
        value 2;
      }
    }
  }

  typedef snmpTargetParamsNameType {
    type string {
      length "1 .. 32";
    }
  }

  typedef snmpNotifyFilterProfileNameType {
    type string {
      length "1 .. 32";
    }
  }

  typedef snmpNotifyFilterMaskType {
    type tailf:hex-list {
      pattern '(((([0-9A-Fa-f]{2}):){0,15}([0-9A-Fa-f]{2}))){0,1}';
      tailf:value-length "min .. 16";
    }
  }

  typedef snmpNotifyFilterTypeType {
    type enumeration {
      enum "included" {
        value 1;
      }
      enum "excluded" {
        value 2;
      }
    }
  }

  augment "/ncs:devices/ncs:device/ncs:config" {
    container SNMP-NOTIFICATION-MIB {
      tailf:ncs-device-type "netconf";
      tailf:display-when "not(../../ncs:module) or ../../ncs:module[ncs:name='SNMP-NOTIFICATION-MIB']";
      container snmpNotifyTable {
        list snmpNotifyEntry {
          key "snmpNotifyName";
          leaf snmpNotifyName {
            type snmpNotifyNameType;
          }
          leaf snmpNotifyTag {
            type SNMP_TARGET_MIB:SnmpTagValue;
          }
          leaf snmpNotifyType {
            type snmpNotifyTypeType;
            default "trap";
          }
          leaf snmpNotifyStorageType {
            type SNMPv2_TC:StorageType;
            default "nonVolatile";
          }
        }
      }
      container snmpNotifyFilterProfileTable {
        presence "SNMP Notify Filter Profile Table";
        list snmpNotifyFilterProfileEntry {
          key "snmpTargetParamsName";
          leaf snmpTargetParamsName {
            type snmpTargetParamsNameType;
          }
          leaf snmpNotifyFilterProfileName {
            type snmpNotifyFilterProfileNameType;
          }
          leaf snmpNotifyFilterProfileStorType {
            type SNMPv2_TC:StorageType;
            default "nonVolatile";
          }
        }
      }
      container snmpNotifyFilterTable {
        presence "SNMP Notify Filter Table";
        list snmpNotifyFilterEntry {
          key "snmpNotifyFilterProfileName snmpNotifyFilterSubtree";
          leaf snmpNotifyFilterProfileName {
            type snmpNotifyFilterProfileNameType;
          }
          leaf snmpNotifyFilterSubtree {
            type yang:object-identifier;
          }
          leaf snmpNotifyFilterMask {
            type snmpNotifyFilterMaskType;
          }
          leaf snmpNotifyFilterType {
            type snmpNotifyFilterTypeType;
            default "included";
          }
          leaf snmpNotifyFilterStorageType {
            type SNMPv2_TC:StorageType;
            default "nonVolatile";
          }
        }
      }
    }
  }
  augment "/ncs:devices/ncs:device/ncs:live-status" {
    container SNMP-NOTIFICATION-MIB {
      tailf:ncs-device-type "netconf";
      tailf:display-when "not(../../ncs:module) or ../../ncs:module[ncs:name='SNMP-NOTIFICATION-MIB'] or (../../ncs:live-status-protocol[not(ncs:capability)]) or (../../ncs:live-status-protocol/ncs:capability/ncs:module[.='SNMP-NOTIFICATION-MIB'])";
      container snmpNotifyTable {
        list snmpNotifyEntry {
          key "snmpNotifyName";
          leaf snmpNotifyName {
            type live_ncs_snmpNotifyNameType;
          }
          leaf snmpNotifyTag {
            type SNMP_TARGET_MIB:live_ncs_SnmpTagValue;
          }
          leaf snmpNotifyType {
            type live_ncs_snmpNotifyTypeType;
            // NCS drop default statement
          }
          leaf snmpNotifyStorageType {
            type SNMPv2_TC:live_ncs_StorageType;
            // NCS drop default statement
          }
        }
      }
      container snmpNotifyFilterProfileTable {
        presence "SNMP Notify Filter Profile Table";
        list snmpNotifyFilterProfileEntry {
          key "snmpTargetParamsName";
          leaf snmpTargetParamsName {
            type live_ncs_snmpTargetParamsNameType;
          }
          leaf snmpNotifyFilterProfileName {
            type live_ncs_snmpNotifyFilterProfileNameType;
          }
          leaf snmpNotifyFilterProfileStorType {
            type SNMPv2_TC:live_ncs_StorageType;
            // NCS drop default statement
          }
        }
      }
      container snmpNotifyFilterTable {
        presence "SNMP Notify Filter Table";
        list snmpNotifyFilterEntry {
          key "snmpNotifyFilterProfileName snmpNotifyFilterSubtree";
          leaf snmpNotifyFilterProfileName {
            type live_ncs_snmpNotifyFilterProfileNameType;
          }
          leaf snmpNotifyFilterSubtree {
            type yang:object-identifier;
          }
          leaf snmpNotifyFilterMask {
            type live_ncs_snmpNotifyFilterMaskType;
          }
          leaf snmpNotifyFilterType {
            type live_ncs_snmpNotifyFilterTypeType;
            // NCS drop default statement
          }
          leaf snmpNotifyFilterStorageType {
            type SNMPv2_TC:live_ncs_StorageType;
            // NCS drop default statement
          }
        }
      }
    }
  }
  augment "/ncs:devices/ncs:template/ncs:ned-id/ncs:config" {
    container SNMP-NOTIFICATION-MIB {
      container snmpNotifyTable {
        list snmpNotifyEntry {
          // NCS patched for predictable order
          ordered-by user;
          key "snmpNotifyName";
          leaf snmpNotifyName {
            type ncs_template_snmpNotifyNameType;
          }
          leaf snmpNotifyTag {
            type SNMP_TARGET_MIB:ncs_template_SnmpTagValue;
          }
          leaf snmpNotifyType {
            type ncs_template_snmpNotifyTypeType;
            // NCS drop default statement
          }
          leaf snmpNotifyStorageType {
            type SNMPv2_TC:ncs_template_StorageType;
            // NCS drop default statement
          }
        }
      }
      container snmpNotifyFilterProfileTable {
        presence "SNMP Notify Filter Profile Table";
        list snmpNotifyFilterProfileEntry {
          // NCS patched for predictable order
          ordered-by user;
          key "snmpTargetParamsName";
          leaf snmpTargetParamsName {
            type ncs_template_snmpTargetParamsNameType;
          }
          leaf snmpNotifyFilterProfileName {
            type ncs_template_snmpNotifyFilterProfileNameType;
          }
          leaf snmpNotifyFilterProfileStorType {
            type SNMPv2_TC:ncs_template_StorageType;
            // NCS drop default statement
          }
        }
      }
      container snmpNotifyFilterTable {
        presence "SNMP Notify Filter Table";
        list snmpNotifyFilterEntry {
          // NCS patched for predictable order
          ordered-by user;
          key "snmpNotifyFilterProfileName snmpNotifyFilterSubtree";
          leaf snmpNotifyFilterProfileName {
            type ncs_template_snmpNotifyFilterProfileNameType;
          }
          leaf snmpNotifyFilterSubtree {
            type string;
          }
          leaf snmpNotifyFilterMask {
            type ncs_template_snmpNotifyFilterMaskType;
          }
          leaf snmpNotifyFilterType {
            type ncs_template_snmpNotifyFilterTypeType;
            // NCS drop default statement
          }
          leaf snmpNotifyFilterStorageType {
            type SNMPv2_TC:ncs_template_StorageType;
            // NCS drop default statement
          }
        }
      }
    }
  }
}

submodule Cisco-IOS-XR-ethernet-cfm-oper-sub4 {
  // Generated by yanger -t ncs
  tailf:mount-id "cisco-iosxr-nc-7.3:cisco-iosxr-nc-7.3";

  belongs-to Cisco-IOS-XR-ethernet-cfm-oper {
    prefix Cisco-IOS-XR-ethernet-cfm-oper;
  }

  import cisco-semver {
    prefix semver;
  }
  include Cisco-IOS-XR-ethernet-cfm-oper-sub3 {
    revision-date 2020-07-07;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ethernet-cfm package operational data.

     Copyright (c) 2013-2020 by Cisco Systems, Inc.
     All rights reserved.";

  revision 2020-07-07 {
    description
      "Added SLA summary information.";
    semver:module-version "1.3.0";
  }
  revision 2019-10-02 {
    description
      "Bandwidth notification addition";
    semver:module-version "1.1.0";
  }
  revision 2019-04-05 {
    description
      "Establish semantic version baseline.";
    semver:module-version "1.0.0";
  }
  revision 2018-12-20 {
    description
      "Bandwidth notification class and type name update.";
  }
  revision 2017-10-06 {
    description
      "Traceroute transaction ID changed from int to uint.";
  }
  revision 2015-11-09 {
    description
      "IOS XR 6.0 revision.";
  }

  grouping ncs_template_CGM-CFG-ERRORS {
    description
      "CFM Global Manager Service Error Information";
    container bridge-domain-id {
      description
        "BD/XC ID, or Service name if the Service is
         'down-only'";
      uses ncs_template_CFM-BAG-BDID;
    }
    leaf domain-name {
      type string;
      description
        "Domain name";
    }
    leaf level {
      type ncs_template_Cfm-bag-md-level;
      description
        "Level";
    }
    leaf service-name {
      type string;
      description
        "Service name";
    }
    leaf bridge-domain-is-configured {
      type string;
      description
        "The BD/XC is configured globally";
    }
    leaf l2-fib-download-error {
      type string;
      description
        "The BD/XC could not be downloaded to L2FIB";
    }
  }

  grouping ncs_rpc_notif_CGM-CFG-ERRORS {
    description
      "CFM Global Manager Service Error Information";
    container bridge-domain-id {
      description
        "BD/XC ID, or Service name if the Service is
         'down-only'";
      uses ncs_rpc_notif_CFM-BAG-BDID;
    }
    leaf domain-name {
      type string;
      description
        "Domain name";
    }
    leaf level {
      type ncs_rpc_notif_Cfm-bag-md-level;
      description
        "Level";
    }
    leaf service-name {
      type string;
      description
        "Service name";
    }
    leaf bridge-domain-is-configured {
      type boolean;
      description
        "The BD/XC is configured globally";
    }
    leaf l2-fib-download-error {
      type boolean;
      description
        "The BD/XC could not be downloaded to L2FIB";
    }
  }

  grouping live_ncs_CGM-CFG-ERRORS {
    description
      "CFM Global Manager Service Error Information";
    container bridge-domain-id {
      description
        "BD/XC ID, or Service name if the Service is
         'down-only'";
      uses live_ncs_CFM-BAG-BDID;
    }
    leaf domain-name {
      type string;
      description
        "Domain name";
    }
    leaf level {
      type live_ncs_Cfm-bag-md-level;
      description
        "Level";
    }
    leaf service-name {
      type string;
      description
        "Service name";
    }
    leaf bridge-domain-is-configured {
      type boolean;
      description
        "The BD/XC is configured globally";
    }
    leaf l2-fib-download-error {
      type boolean;
      description
        "The BD/XC could not be downloaded to L2FIB";
    }
  }

  grouping CGM-CFG-ERRORS {
    description
      "CFM Global Manager Service Error Information";
    container bridge-domain-id {
      description
        "BD/XC ID, or Service name if the Service is
         'down-only'";
      uses CFM-BAG-BDID;
    }
    leaf domain-name {
      type string;
      description
        "Domain name";
    }
    leaf level {
      type Cfm-bag-md-level;
      description
        "Level";
    }
    leaf service-name {
      type string;
      description
        "Service name";
    }
    leaf bridge-domain-is-configured {
      type boolean;
      description
        "The BD/XC is configured globally";
    }
    leaf l2-fib-download-error {
      type boolean;
      description
        "The BD/XC could not be downloaded to L2FIB";
    }
  }
}

module Cisco-IOS-XR-fretta-bcm-dpa-npu-stats-oper {
  // Generated by yanger -t ncs
  tailf:mount-id "cisco-iosxr-nc-7.3:cisco-iosxr-nc-7.3";
  tailf:ncs-device-type "netconf";

  namespace "http://cisco.com/ns/yang/Cisco-IOS-XR-fretta-bcm-dpa-npu-stats-oper";
  prefix fretta-bcm-dpa-npu-stats-oper;

  import Cisco-IOS-XR-types {
    prefix xr;
  }
  import cisco-semver {
    prefix semver;
  }
  include Cisco-IOS-XR-fretta-bcm-dpa-npu-stats-oper-sub2 {
    revision-date 2020-10-09;
  }
  include Cisco-IOS-XR-fretta-bcm-dpa-npu-stats-oper-sub1 {
    revision-date 2020-10-09;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fretta-bcm-dpa-npu-stats package operational data.

     This module contains definitions
     for the following management objects:
       dpa: Stats Data

     Copyright (c) 2013-2020 by Cisco Systems, Inc.
     All rights reserved.";

  revision 2020-10-09 {
    description
      "Added task-id";
    semver:module-version "2.0.0";
  }
  revision 2019-04-05 {
    description
      "Establish semantic version baseline.";
    semver:module-version "1.2.0";
  }
  revision 2015-11-09 {
    description
      "IOS XR 6.0 revision.";
  }

  typedef ncs_template_Max-trap-s {
    type string;
    description
      "Max trap s";
  }

  typedef ncs_template_Max-lc-intf-hand-les {
    type string;
    description
      "Max lc intf hand les";
  }

  typedef ncs_rpc_notif_Max-trap-s {
    type uint32 {
      range "0..4294967295";
    }
    description
      "Max trap s";
  }

  typedef ncs_rpc_notif_Max-lc-intf-hand-les {
    type uint32 {
      range "0..4294967295";
    }
    description
      "Max lc intf hand les";
  }

  typedef live_ncs_Max-trap-s {
    type uint32 {
      range "0..4294967295";
    }
    description
      "Max trap s";
  }

  typedef live_ncs_Max-lc-intf-hand-les {
    type uint32 {
      range "0..4294967295";
    }
    description
      "Max lc intf hand les";
  }

  typedef Max-trap-s {
    type uint32 {
      range "0..4294967295";
    }
    description
      "Max trap s";
  }

  typedef Max-lc-intf-hand-les {
    type uint32 {
      range "0..4294967295";
    }
    description
      "Max lc intf hand les";
  }

  augment "/ncs:devices/ncs:device/ncs:config" {
    // NCS drop config false container dpa
  }
  augment "/ncs:devices/ncs:device/ncs:live-status" {
    container dpa {
      tailf:ncs-device-type "netconf";
      tailf:display-when "not(../../ncs:module) or ../../ncs:module[ncs:name='Cisco-IOS-XR-fretta-bcm-dpa-npu-stats-oper'] or (../../ncs:live-status-protocol[not(ncs:capability)]) or (../../ncs:live-status-protocol/ncs:capability/ncs:module[.='Cisco-IOS-XR-fretta-bcm-dpa-npu-stats-oper'])";
      status deprecated;
      description
        "Stats Data. This model is being deprecated and is being
         replaced by Cisco-IOS-XR-ofa-npu-stats-oper.yang, which will retain the
         functionality of this model.";
      container stats {
        description
          "Voq or Trap Data";
        container nodes {
          description
            "DPA data for available nodes";
          list node {
            key "node-name";
            description
              "DPA operational data for a particular node";
            container asic-statistics {
              description
                "ASIC statistics table";
              container asic-statistics-detail-for-npu-ids {
                description
                  "Detailed ASIC statistics";
                list asic-statistics-detail-for-npu-id {
                  key "npu-id";
                  description
                    "Detailed ASIC statistics for a particular
                     NPU";
                  leaf npu-id {
                    type uint32;
                    description
                      "NPU number";
                  }
                  uses live_ncs_FIA-EDM-STATS-INFO;
                }
              }
              container asic-statistics-for-npu-ids {
                description
                  "ASIC statistics";
                list asic-statistics-for-npu-id {
                  key "npu-id";
                  description
                    "ASIC statistics for a particular NPU";
                  leaf npu-id {
                    type uint32;
                    description
                      "NPU number";
                  }
                  uses live_ncs_FIA-EDM-STATS-BRIEF-INFO;
                }
              }
            }
            container npu-numbers {
              description
                "Ingress Stats";
              list npu-number {
                key "npu-id";
                description
                  "Stats for a particular npu";
                container display {
                  description
                    "show npu specific voq or trap stats";
                  container trap-ids {
                    description
                      "Trap stats for a particular npu";
                    list trap-id {
                      key "trap-id";
                      description
                        "Filter by specific trap id";
                      leaf trap-id {
                        type live_ncs_Max-trap-s;
                        description
                          "Trap ID";
                      }
                      uses live_ncs_DPA-TRAP-STATS;
                    }
                  }
                  container interface-handles {
                    description
                      "Voq stats grouped by interface handle";
                    list interface-handle {
                      key "interface-handle";
                      description
                        "Voq stats for a particular interface
                         handle";
                      leaf interface-handle {
                        type live_ncs_Max-lc-intf-hand-les;
                        description
                          "Interface Handle";
                      }
                      uses live_ncs_DPA-VOQ-INTF-PORT;
                    }
                  }
                  container base-numbers {
                    description
                      "Voq stats grouped by voq base numbers";
                    list base-number {
                      key "base-number";
                      description
                        "Voq Base Number for a particular voq";
                      leaf base-number {
                        type live_ncs_Max-lc-intf-hand-les;
                        description
                          "Interface handle";
                      }
                      uses live_ncs_DPA-VOQ-INTF-PORT;
                    }
                  }
                }
                leaf npu-id {
                  type uint32;
                  description
                    "Npu number";
                }
              }
            }
            leaf node-name {
              type xr:live_ncs_Node-id;
              description
                "Node ID";
            }
          }
        }
      }
    }
  }
  augment "/ncs:devices/ncs:template/ncs:ned-id/ncs:config" {
    // NCS drop config false container dpa
  }
}

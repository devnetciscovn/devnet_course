module CISCO-ENTITY-FRU-CONTROL-MIB {
  // Generated by yanger -t ncs
  tailf:mount-id "cisco-iosxr-nc-7.3:cisco-iosxr-nc-7.3";
  tailf:ncs-device-type "netconf";

  namespace "http://tail-f.com/ns/mibs/CISCO-ENTITY-FRU-CONTROL-MIB/200311240000Z";
  prefix CISCO_ENTITY_FRU_CONTROL_MIB;

  import ietf-yang-types {
    prefix yang;
  }
  import tailf-common {
    prefix tailf;
  }
  import SNMPv2-TC {
    prefix SNMPv2-TC;
  }
  import INET-ADDRESS-MIB {
    prefix INET-ADDRESS-MIB;
  }
  import Cisco-IOS-XR-sysadmin-entity-mib {
    prefix ENTITY-MIB;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2003-11-24;

  typedef ncs_template_PowerRedundancyType {
    type string;
  }

  typedef ncs_template_PowerAdminType {
    type string;
  }

  typedef ncs_template_PowerOperType {
    type string;
  }

  typedef ncs_template_FRUCurrentType {
    type string;
  }

  typedef ncs_template_ModuleAdminType {
    type string;
  }

  typedef ncs_template_ModuleOperType {
    type string;
  }

  typedef ncs_template_ModuleResetReasonType {
    type string;
  }

  typedef ncs_template_FRUTimeSeconds {
    type string;
  }

  typedef ncs_template_cefcMaxDefaultInLinePowerType {
    type string;
  }

  typedef ncs_template_cefcFanTrayOperStatusType {
    type string;
  }

  typedef ncs_template_cefcPhysicalStatusType {
    type string;
  }

  typedef ncs_rpc_notif_PowerRedundancyType {
    type enumeration {
      enum "notsupported" {
        value 1;
      }
      enum "redundant" {
        value 2;
      }
      enum "combined" {
        value 3;
      }
    }
  }

  typedef ncs_rpc_notif_PowerAdminType {
    type enumeration {
      enum "on" {
        value 1;
      }
      enum "off" {
        value 2;
      }
      enum "inlineAuto" {
        value 3;
      }
      enum "inlineOn" {
        value 4;
      }
    }
  }

  typedef ncs_rpc_notif_PowerOperType {
    type enumeration {
      enum "offEnvOther" {
        value 1;
      }
      enum "on" {
        value 2;
      }
      enum "offAdmin" {
        value 3;
      }
      enum "offDenied" {
        value 4;
      }
      enum "offEnvPower" {
        value 5;
      }
      enum "offEnvTemp" {
        value 6;
      }
      enum "offEnvFan" {
        value 7;
      }
      enum "failed" {
        value 8;
      }
      enum "onButFanFail" {
        value 9;
      }
    }
  }

  typedef ncs_rpc_notif_FRUCurrentType {
    type int32 {
      range "-1000000000 .. 1000000000";
    }
  }

  typedef ncs_rpc_notif_ModuleAdminType {
    type enumeration {
      enum "enabled" {
        value 1;
      }
      enum "disabled" {
        value 2;
      }
      enum "reset" {
        value 3;
      }
      enum "outOfServiceAdmin" {
        value 4;
      }
    }
  }

  typedef ncs_rpc_notif_ModuleOperType {
    type enumeration {
      enum "unknown" {
        value 1;
      }
      enum "ok" {
        value 2;
      }
      enum "disabled" {
        value 3;
      }
      enum "okButDiagFailed" {
        value 4;
      }
      enum "boot" {
        value 5;
      }
      enum "selfTest" {
        value 6;
      }
      enum "failed" {
        value 7;
      }
      enum "missing" {
        value 8;
      }
      enum "mismatchWithParent" {
        value 9;
      }
      enum "mismatchConfig" {
        value 10;
      }
      enum "diagFailed" {
        value 11;
      }
      enum "dormant" {
        value 12;
      }
      enum "outOfServiceAdmin" {
        value 13;
      }
      enum "outOfServiceEnvTemp" {
        value 14;
      }
      enum "poweredDown" {
        value 15;
      }
      enum "poweredUp" {
        value 16;
      }
      enum "powerDenied" {
        value 17;
      }
      enum "powerCycled" {
        value 18;
      }
      enum "okButPowerOverWarning" {
        value 19;
      }
      enum "okButPowerOverCritical" {
        value 20;
      }
      enum "updatingFPD" {
        value 21;
      }
    }
  }

  typedef ncs_rpc_notif_ModuleResetReasonType {
    type enumeration {
      enum "unknown" {
        value 1;
      }
      enum "powerUp" {
        value 2;
      }
      enum "parityError" {
        value 3;
      }
      enum "clearConfigReset" {
        value 4;
      }
      enum "manualReset" {
        value 5;
      }
      enum "watchDogTimeoutReset" {
        value 6;
      }
      enum "resourceOverflowReset" {
        value 7;
      }
      enum "missingTaskReset" {
        value 8;
      }
      enum "lowVoltageReset" {
        value 9;
      }
      enum "controllerReset" {
        value 10;
      }
      enum "systemReset" {
        value 11;
      }
      enum "switchoverReset" {
        value 12;
      }
      enum "upgradeReset" {
        value 13;
      }
      enum "downgradeReset" {
        value 14;
      }
      enum "cacheErrorReset" {
        value 15;
      }
      enum "deviceDriverReset" {
        value 16;
      }
      enum "softwareExceptionReset" {
        value 17;
      }
      enum "restoreConfigReset" {
        value 18;
      }
      enum "abortRevReset" {
        value 19;
      }
      enum "burnBootReset" {
        value 20;
      }
      enum "standbyCdHealthierReset" {
        value 21;
      }
      enum "nonNativeConfigClearReset" {
        value 22;
      }
      enum "memoryProtectionErrorReset" {
        value 23;
      }
    }
  }

  typedef ncs_rpc_notif_FRUTimeSeconds {
    type uint32 {
      range "0 .. 4294967295";
    }
  }

  typedef ncs_rpc_notif_cefcMaxDefaultInLinePowerType {
    type int32 {
      range "0 .. 12500";
    }
  }

  typedef ncs_rpc_notif_cefcFanTrayOperStatusType {
    type enumeration {
      enum "unknown" {
        value 1;
      }
      enum "up" {
        value 2;
      }
      enum "down" {
        value 3;
      }
      enum "warning" {
        value 4;
      }
    }
  }

  typedef ncs_rpc_notif_cefcPhysicalStatusType {
    type enumeration {
      enum "other" {
        value 1;
      }
      enum "supported" {
        value 2;
      }
      enum "unsupported" {
        value 3;
      }
      enum "incompatible" {
        value 4;
      }
    }
  }

  typedef live_ncs_PowerRedundancyType {
    type enumeration {
      enum "notsupported" {
        value 1;
      }
      enum "redundant" {
        value 2;
      }
      enum "combined" {
        value 3;
      }
    }
  }

  typedef live_ncs_PowerAdminType {
    type enumeration {
      enum "on" {
        value 1;
      }
      enum "off" {
        value 2;
      }
      enum "inlineAuto" {
        value 3;
      }
      enum "inlineOn" {
        value 4;
      }
    }
  }

  typedef live_ncs_PowerOperType {
    type enumeration {
      enum "offEnvOther" {
        value 1;
      }
      enum "on" {
        value 2;
      }
      enum "offAdmin" {
        value 3;
      }
      enum "offDenied" {
        value 4;
      }
      enum "offEnvPower" {
        value 5;
      }
      enum "offEnvTemp" {
        value 6;
      }
      enum "offEnvFan" {
        value 7;
      }
      enum "failed" {
        value 8;
      }
      enum "onButFanFail" {
        value 9;
      }
    }
  }

  typedef live_ncs_FRUCurrentType {
    type int32 {
      range "-1000000000 .. 1000000000";
    }
  }

  typedef live_ncs_ModuleAdminType {
    type enumeration {
      enum "enabled" {
        value 1;
      }
      enum "disabled" {
        value 2;
      }
      enum "reset" {
        value 3;
      }
      enum "outOfServiceAdmin" {
        value 4;
      }
    }
  }

  typedef live_ncs_ModuleOperType {
    type enumeration {
      enum "unknown" {
        value 1;
      }
      enum "ok" {
        value 2;
      }
      enum "disabled" {
        value 3;
      }
      enum "okButDiagFailed" {
        value 4;
      }
      enum "boot" {
        value 5;
      }
      enum "selfTest" {
        value 6;
      }
      enum "failed" {
        value 7;
      }
      enum "missing" {
        value 8;
      }
      enum "mismatchWithParent" {
        value 9;
      }
      enum "mismatchConfig" {
        value 10;
      }
      enum "diagFailed" {
        value 11;
      }
      enum "dormant" {
        value 12;
      }
      enum "outOfServiceAdmin" {
        value 13;
      }
      enum "outOfServiceEnvTemp" {
        value 14;
      }
      enum "poweredDown" {
        value 15;
      }
      enum "poweredUp" {
        value 16;
      }
      enum "powerDenied" {
        value 17;
      }
      enum "powerCycled" {
        value 18;
      }
      enum "okButPowerOverWarning" {
        value 19;
      }
      enum "okButPowerOverCritical" {
        value 20;
      }
      enum "updatingFPD" {
        value 21;
      }
    }
  }

  typedef live_ncs_ModuleResetReasonType {
    type enumeration {
      enum "unknown" {
        value 1;
      }
      enum "powerUp" {
        value 2;
      }
      enum "parityError" {
        value 3;
      }
      enum "clearConfigReset" {
        value 4;
      }
      enum "manualReset" {
        value 5;
      }
      enum "watchDogTimeoutReset" {
        value 6;
      }
      enum "resourceOverflowReset" {
        value 7;
      }
      enum "missingTaskReset" {
        value 8;
      }
      enum "lowVoltageReset" {
        value 9;
      }
      enum "controllerReset" {
        value 10;
      }
      enum "systemReset" {
        value 11;
      }
      enum "switchoverReset" {
        value 12;
      }
      enum "upgradeReset" {
        value 13;
      }
      enum "downgradeReset" {
        value 14;
      }
      enum "cacheErrorReset" {
        value 15;
      }
      enum "deviceDriverReset" {
        value 16;
      }
      enum "softwareExceptionReset" {
        value 17;
      }
      enum "restoreConfigReset" {
        value 18;
      }
      enum "abortRevReset" {
        value 19;
      }
      enum "burnBootReset" {
        value 20;
      }
      enum "standbyCdHealthierReset" {
        value 21;
      }
      enum "nonNativeConfigClearReset" {
        value 22;
      }
      enum "memoryProtectionErrorReset" {
        value 23;
      }
    }
  }

  typedef live_ncs_FRUTimeSeconds {
    type uint32 {
      range "0 .. 4294967295";
    }
  }

  typedef live_ncs_cefcMaxDefaultInLinePowerType {
    type int32 {
      range "0 .. 12500";
    }
  }

  typedef live_ncs_cefcFanTrayOperStatusType {
    type enumeration {
      enum "unknown" {
        value 1;
      }
      enum "up" {
        value 2;
      }
      enum "down" {
        value 3;
      }
      enum "warning" {
        value 4;
      }
    }
  }

  typedef live_ncs_cefcPhysicalStatusType {
    type enumeration {
      enum "other" {
        value 1;
      }
      enum "supported" {
        value 2;
      }
      enum "unsupported" {
        value 3;
      }
      enum "incompatible" {
        value 4;
      }
    }
  }

  typedef PowerRedundancyType {
    type enumeration {
      enum "notsupported" {
        value 1;
      }
      enum "redundant" {
        value 2;
      }
      enum "combined" {
        value 3;
      }
    }
  }

  typedef PowerAdminType {
    type enumeration {
      enum "on" {
        value 1;
      }
      enum "off" {
        value 2;
      }
      enum "inlineAuto" {
        value 3;
      }
      enum "inlineOn" {
        value 4;
      }
    }
  }

  typedef PowerOperType {
    type enumeration {
      enum "offEnvOther" {
        value 1;
      }
      enum "on" {
        value 2;
      }
      enum "offAdmin" {
        value 3;
      }
      enum "offDenied" {
        value 4;
      }
      enum "offEnvPower" {
        value 5;
      }
      enum "offEnvTemp" {
        value 6;
      }
      enum "offEnvFan" {
        value 7;
      }
      enum "failed" {
        value 8;
      }
      enum "onButFanFail" {
        value 9;
      }
    }
  }

  typedef FRUCurrentType {
    type int32 {
      range "-1000000000 .. 1000000000";
    }
  }

  typedef ModuleAdminType {
    type enumeration {
      enum "enabled" {
        value 1;
      }
      enum "disabled" {
        value 2;
      }
      enum "reset" {
        value 3;
      }
      enum "outOfServiceAdmin" {
        value 4;
      }
    }
  }

  typedef ModuleOperType {
    type enumeration {
      enum "unknown" {
        value 1;
      }
      enum "ok" {
        value 2;
      }
      enum "disabled" {
        value 3;
      }
      enum "okButDiagFailed" {
        value 4;
      }
      enum "boot" {
        value 5;
      }
      enum "selfTest" {
        value 6;
      }
      enum "failed" {
        value 7;
      }
      enum "missing" {
        value 8;
      }
      enum "mismatchWithParent" {
        value 9;
      }
      enum "mismatchConfig" {
        value 10;
      }
      enum "diagFailed" {
        value 11;
      }
      enum "dormant" {
        value 12;
      }
      enum "outOfServiceAdmin" {
        value 13;
      }
      enum "outOfServiceEnvTemp" {
        value 14;
      }
      enum "poweredDown" {
        value 15;
      }
      enum "poweredUp" {
        value 16;
      }
      enum "powerDenied" {
        value 17;
      }
      enum "powerCycled" {
        value 18;
      }
      enum "okButPowerOverWarning" {
        value 19;
      }
      enum "okButPowerOverCritical" {
        value 20;
      }
      enum "updatingFPD" {
        value 21;
      }
    }
  }

  typedef ModuleResetReasonType {
    type enumeration {
      enum "unknown" {
        value 1;
      }
      enum "powerUp" {
        value 2;
      }
      enum "parityError" {
        value 3;
      }
      enum "clearConfigReset" {
        value 4;
      }
      enum "manualReset" {
        value 5;
      }
      enum "watchDogTimeoutReset" {
        value 6;
      }
      enum "resourceOverflowReset" {
        value 7;
      }
      enum "missingTaskReset" {
        value 8;
      }
      enum "lowVoltageReset" {
        value 9;
      }
      enum "controllerReset" {
        value 10;
      }
      enum "systemReset" {
        value 11;
      }
      enum "switchoverReset" {
        value 12;
      }
      enum "upgradeReset" {
        value 13;
      }
      enum "downgradeReset" {
        value 14;
      }
      enum "cacheErrorReset" {
        value 15;
      }
      enum "deviceDriverReset" {
        value 16;
      }
      enum "softwareExceptionReset" {
        value 17;
      }
      enum "restoreConfigReset" {
        value 18;
      }
      enum "abortRevReset" {
        value 19;
      }
      enum "burnBootReset" {
        value 20;
      }
      enum "standbyCdHealthierReset" {
        value 21;
      }
      enum "nonNativeConfigClearReset" {
        value 22;
      }
      enum "memoryProtectionErrorReset" {
        value 23;
      }
    }
  }

  typedef FRUTimeSeconds {
    type uint32 {
      range "0 .. 4294967295";
    }
  }

  typedef cefcMaxDefaultInLinePowerType {
    type int32 {
      range "0 .. 12500";
    }
  }

  typedef cefcFanTrayOperStatusType {
    type enumeration {
      enum "unknown" {
        value 1;
      }
      enum "up" {
        value 2;
      }
      enum "down" {
        value 3;
      }
      enum "warning" {
        value 4;
      }
    }
  }

  typedef cefcPhysicalStatusType {
    type enumeration {
      enum "other" {
        value 1;
      }
      enum "supported" {
        value 2;
      }
      enum "unsupported" {
        value 3;
      }
      enum "incompatible" {
        value 4;
      }
    }
  }

  augment "/ncs:devices/ncs:device/ncs:config" {
    container CISCO-ENTITY-FRU-CONTROL-MIB {
      tailf:ncs-device-type "netconf";
      tailf:display-when "not(../../ncs:module) or ../../ncs:module[ncs:name='CISCO-ENTITY-FRU-CONTROL-MIB']";
      // NCS drop config false container cefcFRUPower
      // NCS drop config false container cefcMIBNotificationEnables
      // NCS drop config false container cefcFRUPowerSupplyGroupTable
      // NCS drop config false container cefcFRUPowerStatusTable
      // NCS drop config false container cefcFRUPowerSupplyValueTable
      // NCS drop config false container cefcModuleTable
      // NCS drop config false container cefcIntelliModuleTable
      // NCS drop config false container cefcFanTrayStatusTable
      // NCS drop config false container cefcPhysicalTable
    }
  }
  augment "/ncs:devices/ncs:device/ncs:live-status" {
    container CISCO-ENTITY-FRU-CONTROL-MIB {
      tailf:ncs-device-type "netconf";
      tailf:display-when "not(../../ncs:module) or ../../ncs:module[ncs:name='CISCO-ENTITY-FRU-CONTROL-MIB'] or (../../ncs:live-status-protocol[not(ncs:capability)]) or (../../ncs:live-status-protocol/ncs:capability/ncs:module[.='CISCO-ENTITY-FRU-CONTROL-MIB'])";
      container cefcFRUPower {
        leaf cefcMaxDefaultInLinePower {
          type live_ncs_cefcMaxDefaultInLinePowerType;
          // NCS drop default statement
        }
        leaf cefcMaxDefaultHighInLinePower {
          type uint32;
        }
      }
      container cefcMIBNotificationEnables {
        leaf cefcMIBEnableStatusNotification {
          type SNMPv2-TC:live_ncs_TruthValue;
          // NCS drop default statement
        }
      }
      container cefcFRUPowerSupplyGroupTable {
        list cefcFRUPowerSupplyGroupEntry {
          key "entPhysicalIndex";
          leaf entPhysicalIndex {
            type ENTITY-MIB:live_ncs_PhysicalIndex;
          }
          leaf cefcPowerRedundancyMode {
            type live_ncs_PowerRedundancyType;
          }
          leaf cefcPowerUnits {
            type string {
              length "0 .. 255";
            }
          }
          leaf cefcTotalAvailableCurrent {
            type live_ncs_FRUCurrentType;
          }
          leaf cefcTotalDrawnCurrent {
            type live_ncs_FRUCurrentType;
          }
          leaf cefcPowerRedundancyOperMode {
            type live_ncs_PowerRedundancyType;
          }
        }
      }
      container cefcFRUPowerStatusTable {
        list cefcFRUPowerStatusEntry {
          key "entPhysicalIndex";
          leaf entPhysicalIndex {
            type ENTITY-MIB:live_ncs_PhysicalIndex;
          }
          leaf cefcFRUPowerAdminStatus {
            type live_ncs_PowerAdminType;
          }
          leaf cefcFRUPowerOperStatus {
            type live_ncs_PowerOperType;
          }
          leaf cefcFRUCurrent {
            type live_ncs_FRUCurrentType;
          }
        }
      }
      container cefcFRUPowerSupplyValueTable {
        list cefcFRUPowerSupplyValueEntry {
          key "entPhysicalIndex";
          leaf entPhysicalIndex {
            type ENTITY-MIB:live_ncs_PhysicalIndex;
          }
          leaf cefcFRUTotalSystemCurrent {
            type live_ncs_FRUCurrentType;
          }
          leaf cefcFRUDrawnSystemCurrent {
            type live_ncs_FRUCurrentType;
          }
          leaf cefcFRUTotalInlineCurrent {
            type live_ncs_FRUCurrentType;
          }
          leaf cefcFRUDrawnInlineCurrent {
            type live_ncs_FRUCurrentType;
          }
        }
      }
      container cefcModuleTable {
        list cefcModuleEntry {
          key "entPhysicalIndex";
          leaf entPhysicalIndex {
            type ENTITY-MIB:live_ncs_PhysicalIndex;
          }
          leaf cefcModuleAdminStatus {
            type live_ncs_ModuleAdminType;
          }
          leaf cefcModuleOperStatus {
            type live_ncs_ModuleOperType;
          }
          leaf cefcModuleResetReason {
            type live_ncs_ModuleResetReasonType;
          }
          leaf cefcModuleStatusLastChangeTime {
            type yang:timestamp;
          }
          leaf cefcModuleLastClearConfigTime {
            type yang:timestamp;
          }
          leaf cefcModuleResetReasonDescription {
            type string {
              length "0 .. 255";
            }
          }
          leaf cefcModuleStateChangeReasonDescr {
            type string {
              length "0 .. 255";
            }
          }
          leaf cefcModuleUpTime {
            type live_ncs_FRUTimeSeconds;
          }
        }
      }
      container cefcIntelliModuleTable {
        list cefcIntelliModuleEntry {
          key "entPhysicalIndex";
          leaf entPhysicalIndex {
            type ENTITY-MIB:live_ncs_PhysicalIndex;
          }
          leaf cefcIntelliModuleIPAddrType {
            type INET-ADDRESS-MIB:live_ncs_InetAddressType;
          }
          leaf cefcIntelliModuleIPAddr {
            type INET-ADDRESS-MIB:live_ncs_InetAddress;
          }
        }
      }
      container cefcFanTrayStatusTable {
        list cefcFanTrayStatusEntry {
          key "entPhysicalIndex";
          leaf entPhysicalIndex {
            type ENTITY-MIB:live_ncs_PhysicalIndex;
          }
          leaf cefcFanTrayOperStatus {
            type live_ncs_cefcFanTrayOperStatusType;
          }
        }
      }
      container cefcPhysicalTable {
        list cefcPhysicalEntry {
          key "entPhysicalIndex";
          leaf entPhysicalIndex {
            type ENTITY-MIB:live_ncs_PhysicalIndex;
          }
          leaf cefcPhysicalStatus {
            type live_ncs_cefcPhysicalStatusType;
          }
        }
      }
    }
  }
  augment "/ncs:devices/ncs:template/ncs:ned-id/ncs:config" {
    container CISCO-ENTITY-FRU-CONTROL-MIB {
      // NCS drop config false container cefcFRUPower
      // NCS drop config false container cefcMIBNotificationEnables
      // NCS drop config false container cefcFRUPowerSupplyGroupTable
      // NCS drop config false container cefcFRUPowerStatusTable
      // NCS drop config false container cefcFRUPowerSupplyValueTable
      // NCS drop config false container cefcModuleTable
      // NCS drop config false container cefcIntelliModuleTable
      // NCS drop config false container cefcFanTrayStatusTable
      // NCS drop config false container cefcPhysicalTable
    }
  }
}

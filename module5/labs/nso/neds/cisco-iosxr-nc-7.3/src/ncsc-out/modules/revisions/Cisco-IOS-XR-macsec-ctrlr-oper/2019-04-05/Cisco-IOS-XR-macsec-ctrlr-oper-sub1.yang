submodule Cisco-IOS-XR-macsec-ctrlr-oper-sub1 {
  // Generated by yanger -t ncs
  tailf:mount-id "cisco-iosxr-nc-7.3:cisco-iosxr-nc-7.3";

  belongs-to Cisco-IOS-XR-macsec-ctrlr-oper {
    prefix Cisco-IOS-XR-macsec-ctrlr-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR macsec-ctrlr package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Macsec-ctrlr-ciphersuit {
    type string;
    description
      "Macsec ctrlr ciphersuit";
  }

  typedef ncs_template_Macsec-ctrlr-state {
    type string;
    description
      "Macsec ctrlr state";
  }

  typedef ncs_rpc_notif_Macsec-ctrlr-ciphersuit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Macsec ctrlr ciphersuit";
  }

  typedef ncs_rpc_notif_Macsec-ctrlr-state {
    type enumeration {
      enum "macsec-ctrlr-state-up" {
        value 0;
        description
          "Up";
      }
      enum "macsec-ctrlr-state-down" {
        value 1;
        description
          "Down";
      }
      enum "macsec-ctrlr-state-admin-down" {
        value 2;
        description
          "Administratively Down";
      }
    }
    description
      "Macsec ctrlr state";
  }

  typedef live_ncs_Macsec-ctrlr-ciphersuit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Macsec ctrlr ciphersuit";
  }

  typedef live_ncs_Macsec-ctrlr-state {
    type enumeration {
      enum "macsec-ctrlr-state-up" {
        value 0;
        description
          "Up";
      }
      enum "macsec-ctrlr-state-down" {
        value 1;
        description
          "Down";
      }
      enum "macsec-ctrlr-state-admin-down" {
        value 2;
        description
          "Administratively Down";
      }
    }
    description
      "Macsec ctrlr state";
  }

  typedef Macsec-ctrlr-ciphersuit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Macsec ctrlr ciphersuit";
  }

  typedef Macsec-ctrlr-state {
    type enumeration {
      enum "macsec-ctrlr-state-up" {
        value 0;
        description
          "Up";
      }
      enum "macsec-ctrlr-state-down" {
        value 1;
        description
          "Down";
      }
      enum "macsec-ctrlr-state-admin-down" {
        value 2;
        description
          "Administratively Down";
      }
    }
    description
      "Macsec ctrlr state";
  }

  grouping ncs_template_MACSEC-CTRLR-AN-STATUS {
    description
      "AN status";
    leaf association-number {
      type string;
      description
        "Association Number";
    }
    leaf short-secure-channel-id {
      type string;
      description
        "Short secure channel id";
    }
  }

  grouping ncs_template_MACSEC-CTRLR-SC-STATUS {
    description
      "Secure Channel status";
    leaf protection-enabled {
      type string;
      description
        "Protection Enabled";
    }
    leaf secure-channel-id {
      type string;
      description
        "Secure Channel Id";
    }
    leaf confidentiality-offset {
      type string;
      description
        "Confidentiality offset";
    }
    leaf cipher-suite {
      type ncs_template_Macsec-ctrlr-ciphersuit;
      description
        "Cipher Suite";
    }
    leaf max-packet-number {
      type string;
      description
        "Max packet Number";
    }
    leaf recent-packet-number {
      type string;
      description
        "Recent Packet Number";
    }
    list active-association {
      // NCS patched for predictable order
      ordered-by user;
      description
        "Active Associations";
      uses ncs_template_MACSEC-CTRLR-AN-STATUS;
    }
  }

  grouping ncs_template_MACSEC-CTRLR-IF-STATUS {
    description
      "Interface Status details";
    container encrypt-sc-status {
      description
        "Encrypt Secure Channel Status";
      uses ncs_template_MACSEC-CTRLR-SC-STATUS;
    }
    container decrypt-sc-status {
      description
        "Decrypt Secure Channel Status";
      uses ncs_template_MACSEC-CTRLR-SC-STATUS;
    }
    leaf state {
      type ncs_template_Macsec-ctrlr-state;
      description
        "State";
    }
    leaf replay-window-size {
      type string;
      description
        "Replay Window Size";
    }
    leaf must-secure {
      type string;
      description
        "Must Secure";
    }
    leaf secure-mode {
      type string;
      description
        "Secure Mode";
    }
  }

  grouping ncs_rpc_notif_MACSEC-CTRLR-AN-STATUS {
    description
      "AN status";
    leaf association-number {
      type uint8;
      description
        "Association Number";
    }
    leaf short-secure-channel-id {
      type uint32;
      description
        "Short secure channel id";
    }
  }

  grouping ncs_rpc_notif_MACSEC-CTRLR-SC-STATUS {
    description
      "Secure Channel status";
    leaf protection-enabled {
      type boolean;
      description
        "Protection Enabled";
    }
    leaf secure-channel-id {
      type string;
      description
        "Secure Channel Id";
    }
    leaf confidentiality-offset {
      type uint32;
      description
        "Confidentiality offset";
    }
    leaf cipher-suite {
      type ncs_rpc_notif_Macsec-ctrlr-ciphersuit;
      description
        "Cipher Suite";
    }
    leaf max-packet-number {
      type uint64;
      description
        "Max packet Number";
    }
    leaf recent-packet-number {
      type uint64;
      description
        "Recent Packet Number";
    }
    list active-association {
      description
        "Active Associations";
      uses ncs_rpc_notif_MACSEC-CTRLR-AN-STATUS;
    }
  }

  grouping ncs_rpc_notif_MACSEC-CTRLR-IF-STATUS {
    description
      "Interface Status details";
    container encrypt-sc-status {
      description
        "Encrypt Secure Channel Status";
      uses ncs_rpc_notif_MACSEC-CTRLR-SC-STATUS;
    }
    container decrypt-sc-status {
      description
        "Decrypt Secure Channel Status";
      uses ncs_rpc_notif_MACSEC-CTRLR-SC-STATUS;
    }
    leaf state {
      type ncs_rpc_notif_Macsec-ctrlr-state;
      description
        "State";
    }
    leaf replay-window-size {
      type uint32;
      description
        "Replay Window Size";
    }
    leaf must-secure {
      type boolean;
      description
        "Must Secure";
    }
    leaf secure-mode {
      type uint32;
      description
        "Secure Mode";
    }
  }

  grouping live_ncs_MACSEC-CTRLR-AN-STATUS {
    description
      "AN status";
    leaf association-number {
      type uint8;
      description
        "Association Number";
    }
    leaf short-secure-channel-id {
      type uint32;
      description
        "Short secure channel id";
    }
  }

  grouping live_ncs_MACSEC-CTRLR-SC-STATUS {
    description
      "Secure Channel status";
    leaf protection-enabled {
      type boolean;
      description
        "Protection Enabled";
    }
    leaf secure-channel-id {
      type string;
      description
        "Secure Channel Id";
    }
    leaf confidentiality-offset {
      type uint32;
      description
        "Confidentiality offset";
    }
    leaf cipher-suite {
      type live_ncs_Macsec-ctrlr-ciphersuit;
      description
        "Cipher Suite";
    }
    leaf max-packet-number {
      type uint64;
      description
        "Max packet Number";
    }
    leaf recent-packet-number {
      type uint64;
      description
        "Recent Packet Number";
    }
    list active-association {
      description
        "Active Associations";
      uses live_ncs_MACSEC-CTRLR-AN-STATUS;
    }
  }

  grouping live_ncs_MACSEC-CTRLR-IF-STATUS {
    description
      "Interface Status details";
    container encrypt-sc-status {
      description
        "Encrypt Secure Channel Status";
      uses live_ncs_MACSEC-CTRLR-SC-STATUS;
    }
    container decrypt-sc-status {
      description
        "Decrypt Secure Channel Status";
      uses live_ncs_MACSEC-CTRLR-SC-STATUS;
    }
    leaf state {
      type live_ncs_Macsec-ctrlr-state;
      description
        "State";
    }
    leaf replay-window-size {
      type uint32;
      description
        "Replay Window Size";
    }
    leaf must-secure {
      type boolean;
      description
        "Must Secure";
    }
    leaf secure-mode {
      type uint32;
      description
        "Secure Mode";
    }
  }

  grouping MACSEC-CTRLR-AN-STATUS {
    description
      "AN status";
    leaf association-number {
      type uint8;
      description
        "Association Number";
    }
    leaf short-secure-channel-id {
      type uint32;
      description
        "Short secure channel id";
    }
  }

  grouping MACSEC-CTRLR-SC-STATUS {
    description
      "Secure Channel status";
    leaf protection-enabled {
      type boolean;
      description
        "Protection Enabled";
    }
    leaf secure-channel-id {
      type string;
      description
        "Secure Channel Id";
    }
    leaf confidentiality-offset {
      type uint32;
      description
        "Confidentiality offset";
    }
    leaf cipher-suite {
      type Macsec-ctrlr-ciphersuit;
      description
        "Cipher Suite";
    }
    leaf max-packet-number {
      type uint64;
      description
        "Max packet Number";
    }
    leaf recent-packet-number {
      type uint64;
      description
        "Recent Packet Number";
    }
    list active-association {
      description
        "Active Associations";
      uses MACSEC-CTRLR-AN-STATUS;
    }
  }

  grouping MACSEC-CTRLR-IF-STATUS {
    description
      "Interface Status details";
    container encrypt-sc-status {
      description
        "Encrypt Secure Channel Status";
      uses MACSEC-CTRLR-SC-STATUS;
    }
    container decrypt-sc-status {
      description
        "Decrypt Secure Channel Status";
      uses MACSEC-CTRLR-SC-STATUS;
    }
    leaf state {
      type Macsec-ctrlr-state;
      description
        "State";
    }
    leaf replay-window-size {
      type uint32;
      description
        "Replay Window Size";
    }
    leaf must-secure {
      type boolean;
      description
        "Must Secure";
    }
    leaf secure-mode {
      type uint32;
      description
        "Secure Mode";
    }
  }
}

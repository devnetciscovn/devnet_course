module Cisco-IOS-XR-tunnel-nve-oper {
  // Generated by yanger -t ncs
  tailf:mount-id "cisco-iosxr-nc-7.3:cisco-iosxr-nc-7.3";
  tailf:ncs-device-type "netconf";

  namespace "http://cisco.com/ns/yang/Cisco-IOS-XR-tunnel-nve-oper";
  prefix tunnel-nve-oper;

  import Cisco-IOS-XR-types {
    prefix xr;
  }
  import cisco-semver {
    prefix semver;
  }
  include Cisco-IOS-XR-tunnel-nve-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-nve package operational data.

     This module contains definitions
     for the following management objects:
       nve: NVE operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container nve
  }
  augment "/ncs:devices/ncs:device/ncs:live-status" {
    container nve {
      tailf:ncs-device-type "netconf";
      tailf:display-when "not(../../ncs:module) or ../../ncs:module[ncs:name='Cisco-IOS-XR-tunnel-nve-oper'] or (../../ncs:live-status-protocol[not(ncs:capability)]) or (../../ncs:live-status-protocol/ncs:capability/ncs:module[.='Cisco-IOS-XR-tunnel-nve-oper'])";
      description
        "NVE operational data";
      container vnis {
        description
          "Table for VNIs";
        list vni {
          key "vni";
          description
            "The attributes for a particular VNI";
          leaf vni {
            type xr:live_ncs_Cisco-ios-xr-string;
            description
              "VNI ID";
          }
          uses live_ncs_NVE-SHOW-VNI-BD;
        }
      }
      container interfaces {
        description
          "Table for NVE interface attributes";
        list interface {
          key "interface-name";
          description
            "The attributes for a particular interface";
          leaf interface-name {
            type xr:live_ncs_Interface-name;
            description
              "Interface Name";
          }
          uses live_ncs_NVE-SHOW-NVE-INTF-BD;
        }
      }
    }
  }
  augment "/ncs:devices/ncs:template/ncs:ned-id/ncs:config" {
    // NCS drop config false container nve
  }
}

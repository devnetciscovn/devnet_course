module Cisco-IOS-XR-Ethernet-SPAN-act {
  // Generated by yanger -t ncs
  tailf:mount-id "cisco-iosxr-nc-7.3:cisco-iosxr-nc-7.3";
  tailf:ncs-device-type "netconf";

  namespace "http://cisco.com/ns/yang/Cisco-IOS-XR-Ethernet-SPAN-act";
  prefix ethernet-span-act;

  import Cisco-IOS-XR-types {
    prefix xr;
  }
  import Cisco-IOS-XR-Ethernet-SPAN-datatypes {
    prefix dt1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN action commands.

     Copyright (c) 2020 by Cisco Systems, Inc.
     All rights reserved.";

  revision 2020-11-09 {
    description
      "First implementation of action yang for File destinations";
  }

  augment "/ncs:devices/ncs:device/ncs:rpc" {
    container rpc-packet-collection-stop-write {
      tailf:ncs-device-type "netconf";
      tailf:display-when "not(../../ncs:module) or ../../ncs:module[ncs:name='Cisco-IOS-XR-Ethernet-SPAN-act']";
      tailf:action packet-collection-stop-write {
        tailf:actionpoint ncsproxy {
          tailf:internal;
        }
        description
          "Stop packet collection on this session and write contents to file";
        input {
          leaf session {
            type string {
              length "1..63";
            }
            mandatory true;
            description
              "Session name";
          }
          leaf dirname {
            type string {
              length "1..63";
            }
            mandatory true;
            description
              "Directory name";
          }
          leaf filename {
            type string {
              length "1..63";
            }
            mandatory true;
            description
              "File name";
          }
        }
        xr:xr-task "ethernet-services";
        xr:cli-command "monitor-session <session> packet-collection stop write directory <dirname> filename <filename>";
      }
    }
  }
  augment "/ncs:devices/ncs:device-group/ncs:ned-id/ncs:rpc" {
    container rpc-packet-collection-stop-write {
      tailf:ncs-device-type "netconf";
      tailf:display-when "/ncs:devices/ncs:device[ncs:name=current()/../../../ncs:member]/ncs:module[ncs:name='Cisco-IOS-XR-Ethernet-SPAN-act']";
      tailf:action packet-collection-stop-write {
        tailf:actionpoint ncsproxy {
          tailf:internal;
        }
        description
          "Stop packet collection on this session and write contents to file";
        input {
          leaf session {
            type string {
              length "1..63";
            }
            mandatory true;
            description
              "Session name";
          }
          leaf dirname {
            type string {
              length "1..63";
            }
            mandatory true;
            description
              "Directory name";
          }
          leaf filename {
            type string {
              length "1..63";
            }
            mandatory true;
            description
              "File name";
          }
        }
        xr:xr-task "ethernet-services";
        xr:cli-command "monitor-session <session> packet-collection stop write directory <dirname> filename <filename>";
      }
    }
  }
  augment "/ncs:devices/ncs:device/ncs:rpc" {
    container rpc-packet-collection-stop-discard {
      tailf:ncs-device-type "netconf";
      tailf:display-when "not(../../ncs:module) or ../../ncs:module[ncs:name='Cisco-IOS-XR-Ethernet-SPAN-act']";
      tailf:action packet-collection-stop-discard {
        tailf:actionpoint ncsproxy {
          tailf:internal;
        }
        description
          "Stop packet collection on this session and discard data in buffer";
        input {
          leaf session {
            type string {
              length "1..63";
            }
            mandatory true;
            description
              "Session name";
          }
        }
        xr:xr-task "ethernet-services";
        xr:cli-command "monitor-session <session> packet-collection stop discard-data";
      }
    }
  }
  augment "/ncs:devices/ncs:device-group/ncs:ned-id/ncs:rpc" {
    container rpc-packet-collection-stop-discard {
      tailf:ncs-device-type "netconf";
      tailf:display-when "/ncs:devices/ncs:device[ncs:name=current()/../../../ncs:member]/ncs:module[ncs:name='Cisco-IOS-XR-Ethernet-SPAN-act']";
      tailf:action packet-collection-stop-discard {
        tailf:actionpoint ncsproxy {
          tailf:internal;
        }
        description
          "Stop packet collection on this session and discard data in buffer";
        input {
          leaf session {
            type string {
              length "1..63";
            }
            mandatory true;
            description
              "Session name";
          }
        }
        xr:xr-task "ethernet-services";
        xr:cli-command "monitor-session <session> packet-collection stop discard-data";
      }
    }
  }
  augment "/ncs:devices/ncs:device/ncs:rpc" {
    container rpc-packet-collection-start {
      tailf:ncs-device-type "netconf";
      tailf:display-when "not(../../ncs:module) or ../../ncs:module[ncs:name='Cisco-IOS-XR-Ethernet-SPAN-act']";
      tailf:action packet-collection-start {
        tailf:actionpoint ncsproxy {
          tailf:internal;
        }
        description
          "Start packet collection on this session";
        input {
          leaf session {
            type string {
              length "1..63";
            }
            mandatory true;
            description
              "Session name";
          }
        }
        xr:xr-task "ethernet-services";
        xr:cli-command "monitor-session <session> packet-collection start";
      }
    }
  }
  augment "/ncs:devices/ncs:device-group/ncs:ned-id/ncs:rpc" {
    container rpc-packet-collection-start {
      tailf:ncs-device-type "netconf";
      tailf:display-when "/ncs:devices/ncs:device[ncs:name=current()/../../../ncs:member]/ncs:module[ncs:name='Cisco-IOS-XR-Ethernet-SPAN-act']";
      tailf:action packet-collection-start {
        tailf:actionpoint ncsproxy {
          tailf:internal;
        }
        description
          "Start packet collection on this session";
        input {
          leaf session {
            type string {
              length "1..63";
            }
            mandatory true;
            description
              "Session name";
          }
        }
        xr:xr-task "ethernet-services";
        xr:cli-command "monitor-session <session> packet-collection start";
      }
    }
  }
}

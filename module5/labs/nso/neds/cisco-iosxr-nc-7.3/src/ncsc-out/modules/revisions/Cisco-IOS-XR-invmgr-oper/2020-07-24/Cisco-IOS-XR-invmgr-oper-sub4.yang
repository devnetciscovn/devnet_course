submodule Cisco-IOS-XR-invmgr-oper-sub4 {
  // Generated by yanger -t ncs
  tailf:mount-id "cisco-iosxr-nc-7.3:cisco-iosxr-nc-7.3";

  belongs-to Cisco-IOS-XR-invmgr-oper {
    prefix Cisco-IOS-XR-invmgr-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR invmgr package operational data.

     Copyright (c) 2013-2020 by Cisco Systems, Inc.
     All rights reserved.";

  revision 2020-07-24 {
    description
      "IOS XR 7.0.14 revision. Modified eeprom_bag to match eXR
       2020-07-24
         Addition of revision to match LNT.";
    semver:module-version "3.0.0";
  }
  revision 2020-05-08 {
    description
      "Deprecated Inventory:Rack container.
       2020-03-30
       Changed threshold-value type to int32.
       2019-10-07
       Added pluggable-info bag.
       2019-10-04
       Removed slot-info, vm-done bags.";
    semver:module-version "2.0.0";
  }
  revision 2019-04-05 {
    description
      "Establish semantic version baseline.";
    semver:module-version "1.0.0";
  }
  revision 2019-03-21 {
    description
      "Resolved string constraints issue.";
  }
  revision 2018-08-03 {
    description
      "Added slot-info and parent-info bags.";
  }
  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  grouping ncs_template_ENVMON-SENSOR-INFO {
    description
      "ENVMON sensor Info";
    leaf field-validity-bitmap {
      type string;
      description
        "Sensor valid bitmap";
    }
    leaf device-description {
      type string;
      description
        "Device Name";
    }
    leaf units {
      type string;
      description
        "Units of variable being read";
    }
    leaf device-id {
      type string;
      description
        "Identifier for this device";
    }
    leaf value {
      type string;
      description
        "Current reading of sensor";
    }
    leaf alarm-type {
      type string;
      description
        "Indicates threshold violation";
    }
    leaf data-type {
      type string;
      description
        "Sensor data type enums";
    }
    leaf scale {
      type string;
      description
        "Sensor scale enums";
    }
    leaf precision {
      type string;
      description
        "Sensor precision range";
    }
    leaf status {
      type string;
      description
        "Sensor operation state enums";
    }
    leaf age-time-stamp {
      type string;
      description
        "Age of the sensor value; set to the current time
         if directly access the value from sensor";
    }
    leaf update-rate {
      type string;
      description
        "Sensor value update rate;set to 0 if sensor
         value is updated and evaluated immediately";
    }
    leaf average {
      type string;
      description
        "Average sensor value over time interval";
    }
    leaf minimum {
      type string;
      description
        "Minimum Sensor value over time interval";
    }
    leaf maximum {
      type string;
      description
        "Maximum Sensor value over time interval";
    }
    leaf interval {
      type string;
      description
        "Time Interval over which sensor value is
         monitored";
    }
    leaf min-time {
      type string;
      description
        "Absolute time when maximum sensor value occured";
    }
    leaf max-time {
      type string;
      description
        "Absolute time when minimum sensor value occured";
    }
  }

  grouping ncs_template_ENVMON-THRESHOLD-INFO {
    description
      "ENVMON threshold Info";
    leaf threshold-severity {
      type string;
      description
        "Indicates minor, major, critical severities";
    }
    leaf threshold-relation {
      type string;
      description
        "Indicates relation between sensor value and
         threshold";
    }
    leaf threshold-value {
      type string;
      description
        "Value of the configured threshold";
    }
    leaf threshold-evaluation {
      type string;
      description
        "Indicates the result of the most recent
         evaluation of the thresholD";
    }
    leaf threshold-notification-enabled {
      type string;
      description
        "Indicates whether or not a notification should
         result, in case of threshold violation";
    }
  }

  grouping ncs_rpc_notif_ENVMON-SENSOR-INFO {
    description
      "ENVMON sensor Info";
    leaf field-validity-bitmap {
      type uint32;
      description
        "Sensor valid bitmap";
    }
    leaf device-description {
      type string {
        length "0..50";
      }
      description
        "Device Name";
    }
    leaf units {
      type string {
        length "0..50";
      }
      description
        "Units of variable being read";
    }
    leaf device-id {
      type uint32;
      description
        "Identifier for this device";
    }
    leaf value {
      type uint32;
      description
        "Current reading of sensor";
    }
    leaf alarm-type {
      type uint32;
      description
        "Indicates threshold violation";
    }
    leaf data-type {
      type uint32;
      description
        "Sensor data type enums";
    }
    leaf scale {
      type uint32;
      description
        "Sensor scale enums";
    }
    leaf precision {
      type uint32;
      description
        "Sensor precision range";
    }
    leaf status {
      type uint32;
      description
        "Sensor operation state enums";
    }
    leaf age-time-stamp {
      type uint32;
      description
        "Age of the sensor value; set to the current time
         if directly access the value from sensor";
    }
    leaf update-rate {
      type uint32;
      description
        "Sensor value update rate;set to 0 if sensor
         value is updated and evaluated immediately";
    }
    leaf average {
      type int32;
      description
        "Average sensor value over time interval";
    }
    leaf minimum {
      type int32;
      description
        "Minimum Sensor value over time interval";
    }
    leaf maximum {
      type int32;
      description
        "Maximum Sensor value over time interval";
    }
    leaf interval {
      type int32;
      description
        "Time Interval over which sensor value is
         monitored";
    }
    leaf min-time {
      type uint64;
      description
        "Absolute time when maximum sensor value occured";
    }
    leaf max-time {
      type uint64;
      description
        "Absolute time when minimum sensor value occured";
    }
  }

  grouping ncs_rpc_notif_ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }

  grouping live_ncs_ENVMON-SENSOR-INFO {
    description
      "ENVMON sensor Info";
    leaf field-validity-bitmap {
      type uint32;
      description
        "Sensor valid bitmap";
    }
    leaf device-description {
      type string {
        length "0..50";
      }
      description
        "Device Name";
    }
    leaf units {
      type string {
        length "0..50";
      }
      description
        "Units of variable being read";
    }
    leaf device-id {
      type uint32;
      description
        "Identifier for this device";
    }
    leaf value {
      type uint32;
      description
        "Current reading of sensor";
    }
    leaf alarm-type {
      type uint32;
      description
        "Indicates threshold violation";
    }
    leaf data-type {
      type uint32;
      description
        "Sensor data type enums";
    }
    leaf scale {
      type uint32;
      description
        "Sensor scale enums";
    }
    leaf precision {
      type uint32;
      description
        "Sensor precision range";
    }
    leaf status {
      type uint32;
      description
        "Sensor operation state enums";
    }
    leaf age-time-stamp {
      type uint32;
      description
        "Age of the sensor value; set to the current time
         if directly access the value from sensor";
    }
    leaf update-rate {
      type uint32;
      description
        "Sensor value update rate;set to 0 if sensor
         value is updated and evaluated immediately";
    }
    leaf average {
      type int32;
      description
        "Average sensor value over time interval";
    }
    leaf minimum {
      type int32;
      description
        "Minimum Sensor value over time interval";
    }
    leaf maximum {
      type int32;
      description
        "Maximum Sensor value over time interval";
    }
    leaf interval {
      type int32;
      description
        "Time Interval over which sensor value is
         monitored";
    }
    leaf min-time {
      type uint64;
      description
        "Absolute time when maximum sensor value occured";
    }
    leaf max-time {
      type uint64;
      description
        "Absolute time when minimum sensor value occured";
    }
  }

  grouping live_ncs_ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }

  grouping ENVMON-SENSOR-INFO {
    description
      "ENVMON sensor Info";
    leaf field-validity-bitmap {
      type uint32;
      description
        "Sensor valid bitmap";
    }
    leaf device-description {
      type string {
        length "0..50";
      }
      description
        "Device Name";
    }
    leaf units {
      type string {
        length "0..50";
      }
      description
        "Units of variable being read";
    }
    leaf device-id {
      type uint32;
      description
        "Identifier for this device";
    }
    leaf value {
      type uint32;
      description
        "Current reading of sensor";
    }
    leaf alarm-type {
      type uint32;
      description
        "Indicates threshold violation";
    }
    leaf data-type {
      type uint32;
      description
        "Sensor data type enums";
    }
    leaf scale {
      type uint32;
      description
        "Sensor scale enums";
    }
    leaf precision {
      type uint32;
      description
        "Sensor precision range";
    }
    leaf status {
      type uint32;
      description
        "Sensor operation state enums";
    }
    leaf age-time-stamp {
      type uint32;
      description
        "Age of the sensor value; set to the current time
         if directly access the value from sensor";
    }
    leaf update-rate {
      type uint32;
      description
        "Sensor value update rate;set to 0 if sensor
         value is updated and evaluated immediately";
    }
    leaf average {
      type int32;
      description
        "Average sensor value over time interval";
    }
    leaf minimum {
      type int32;
      description
        "Minimum Sensor value over time interval";
    }
    leaf maximum {
      type int32;
      description
        "Maximum Sensor value over time interval";
    }
    leaf interval {
      type int32;
      description
        "Time Interval over which sensor value is
         monitored";
    }
    leaf min-time {
      type uint64;
      description
        "Absolute time when maximum sensor value occured";
    }
    leaf max-time {
      type uint64;
      description
        "Absolute time when minimum sensor value occured";
    }
  }

  grouping ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }
}

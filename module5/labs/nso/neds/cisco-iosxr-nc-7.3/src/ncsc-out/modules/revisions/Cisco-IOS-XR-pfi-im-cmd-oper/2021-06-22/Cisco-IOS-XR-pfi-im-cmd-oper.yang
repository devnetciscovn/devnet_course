module Cisco-IOS-XR-pfi-im-cmd-oper {
  // Generated by yanger -t ncs
  tailf:mount-id "cisco-iosxr-nc-7.3:cisco-iosxr-nc-7.3";
  tailf:ncs-device-type "netconf";

  namespace "http://cisco.com/ns/yang/Cisco-IOS-XR-pfi-im-cmd-oper";
  prefix pfi-im-cmd-oper;

  import Cisco-IOS-XR-types {
    prefix xr;
  }
  import cisco-semver {
    prefix semver;
  }
  include Cisco-IOS-XR-pfi-im-cmd-oper-sub2 {
    revision-date 2021-06-22;
  }
  include Cisco-IOS-XR-pfi-im-cmd-oper-sub1 {
    revision-date 2021-06-22;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pfi-im-cmd package operational data.

     This module contains definitions
     for the following management objects:
       interfaces: Interface operational data

     Copyright (c) 2013-2021 by Cisco Systems, Inc.
     All rights reserved.";

  revision 2021-06-22 {
    description
      "Deprecated container for non-dynamic interfaces.
       2021-05-23
         Removed container for non-dynamic interfaces.";
    semver:module-version "3.2.0";
  }
  revision 2020-10-08 {
    description
      "Unit of last-data-time in milliseconds reverted to seconds for generic stats
       2020-09-03
       Removed event-telemetry annotation from leaf interface-name of grouping BM-MEMBER-DATA
       2020-04-14
       Unit of last-data-time changed from seconds to milliseconds for generic stats
       2020-04-14
       Support added for non-dynamic interfaces.
       2020-04-14
       Data type of last-data-time changed from uint32 to uint64 for generic and proto stats";
    semver:module-version "3.1.0";
  }
  revision 2019-12-03 {
    description
      "Updated description.";
    semver:module-version "3.0.0";
  }
  revision 2019-08-14 {
    description
      "Added last state transition time.
       2019-07-23
       Changes in IosApi version.
       2019-05-30
       64 bit bandwidth changes.";
    semver:module-version "2.0.0";
  }
  revision 2019-04-05 {
    description
      "Establish semantic version baseline.";
    semver:module-version "1.0.0";
  }
  revision 2017-06-26 {
    description
      "Change identifiers to be more readable.";
  }
  revision 2017-05-01 {
    description
      "Fixing backward compatibility error in module.";
  }
  revision 2016-12-18 {
    description
      "Description updated.";
  }
  revision 2015-11-09 {
    description
      "IOS XR 6.0 revision.";
  }

  typedef ncs_template_Interface-type-set {
    type string;
    description
      "Interface type set";
  }

  typedef ncs_rpc_notif_Interface-type-set {
    type enumeration {
      enum "hardware-interfaces" {
        value 0;
        description
          "Restrict the output to hardware interfaces only";
      }
    }
    description
      "Interface type set";
  }

  typedef live_ncs_Interface-type-set {
    type enumeration {
      enum "hardware-interfaces" {
        value 0;
        description
          "Restrict the output to hardware interfaces only";
      }
    }
    description
      "Interface type set";
  }

  typedef Interface-type-set {
    type enumeration {
      enum "hardware-interfaces" {
        value 0;
        description
          "Restrict the output to hardware interfaces only";
      }
    }
    description
      "Interface type set";
  }

  grouping ncs_template_INTERFACE-SUMMARY {
    description
      "Common node of node-type-set, interfaces";
    container interface-summary {
      description
        "Interface summary information";
      uses ncs_template_IM-IF-SUMMARY-INFO;
    }
  }

  grouping ncs_rpc_notif_INTERFACE-SUMMARY {
    description
      "Common node of node-type-set, interfaces";
    container interface-summary {
      description
        "Interface summary information";
      uses ncs_rpc_notif_IM-IF-SUMMARY-INFO;
    }
  }

  grouping live_ncs_INTERFACE-SUMMARY {
    description
      "Common node of node-type-set, interfaces";
    container interface-summary {
      description
        "Interface summary information";
      uses live_ncs_IM-IF-SUMMARY-INFO;
    }
  }

  grouping INTERFACE-SUMMARY {
    description
      "Common node of node-type-set, interfaces";
    container interface-summary {
      description
        "Interface summary information";
      uses IM-IF-SUMMARY-INFO;
    }
  }

  augment "/ncs:devices/ncs:device/ncs:config" {
    // NCS drop config false container interfaces
  }
  augment "/ncs:devices/ncs:device/ncs:live-status" {
    container interfaces {
      tailf:ncs-device-type "netconf";
      tailf:display-when "not(../../ncs:module) or ../../ncs:module[ncs:name='Cisco-IOS-XR-pfi-im-cmd-oper'] or (../../ncs:live-status-protocol[not(ncs:capability)]) or (../../ncs:live-status-protocol/ncs:capability/ncs:module[.='Cisco-IOS-XR-pfi-im-cmd-oper'])";
      description
        "Interface operational data";
      container interface-xr {
        description
          "Detailed operational data for interfaces and
           configured features";
        list interface {
          key "interface-name";
          description
            "Detailed operational data for a particular
             interface";
          leaf interface-name {
            type xr:live_ncs_Interface-name;
            description
              "The name of the interface";
          }
          uses live_ncs_IM-CMD-INFO;
        }
      }
      container node-type-sets {
        description
          "Node and/or interface type specific view of
           interface summary data";
        list node-type-set {
          description
            "Summary data for all interfaces on a particular
             node";
          leaf node-name {
            type xr:live_ncs_Node-id;
            description
              "The location to filter on";
          }
          leaf type-set-name {
            type live_ncs_Interface-type-set;
            description
              "The interface type to filter on";
          }
          uses live_ncs_INTERFACE-SUMMARY;
        }
      }
      container interface-briefs {
        description
          "Brief operational data for interfaces";
        list interface-brief {
          key "interface-name";
          description
            "Brief operational attributes for a particular
             interface";
          leaf interface-name {
            type xr:live_ncs_Interface-name;
            description
              "The name of the interface";
          }
          uses live_ncs_IMDS-IFATTR-BASE-INFO;
        }
      }
      container inventory-summary {
        description
          "Inventory summary information";
        uses live_ncs_IM-IF-SUMMARY-INFO;
      }
      container interfaces {
        description
          "Descriptions for interfaces";
        list interface {
          key "interface-name";
          description
            "Description for a particular interface";
          leaf interface-name {
            type xr:live_ncs_Interface-name;
            description
              "The name of the interface";
          }
          uses live_ncs_IM-DESC-INFO;
        }
      }
      container interface-non-dynamics {
        status deprecated;
        description
          "Selective operational data for non-dynamic
           interfaces";
        list interface-non-dynamic {
          key "interface-name";
          status deprecated;
          description
            "Selective operational data for a particular
             non-dynamic interface";
          leaf interface-name {
            type xr:live_ncs_Interface-name;
            description
              "The name of the interface";
          }
          uses live_ncs_IM-NON-DYNAMIC-INTF-INFO;
        }
      }
      uses live_ncs_INTERFACE-SUMMARY;
    }
  }
  augment "/ncs:devices/ncs:template/ncs:ned-id/ncs:config" {
    // NCS drop config false container interfaces
  }
}

submodule Cisco-IOS-XR-snmp-sensormib-oper-sub2 {
  // Generated by yanger -t ncs
  tailf:mount-id "cisco-iosxr-nc-7.3:cisco-iosxr-nc-7.3";

  belongs-to Cisco-IOS-XR-snmp-sensormib-oper {
    prefix Cisco-IOS-XR-snmp-sensormib-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR snmp-sensormib package operational data.

     Copyright (c) 2013-2020 by Cisco Systems, Inc.
     All rights reserved.";

  revision 2020-05-15 {
    description
      "Fixing backward compatibility error in module.";
    semver:module-version "2.0.0";
  }
  revision 2019-04-05 {
    description
      "Establish semantic version baseline.";
    semver:module-version "1.0.1";
  }
  revision 2015-11-09 {
    description
      "IOS XR 6.0 revision.";
  }

  grouping ncs_template_ENVMON-THRESHOLD-INFO {
    description
      "ENVMON threshold Info";
    leaf threshold-severity {
      type string;
      description
        "Indicates minor, major, critical severities";
    }
    leaf threshold-relation {
      type string;
      description
        "Indicates relation between sensor value and
         threshold";
    }
    leaf threshold-value {
      type string;
      description
        "Value of the configured threshold";
    }
    leaf threshold-evaluation {
      type string;
      description
        "Indicates the result of the most recent
         evaluation of the thresholD";
    }
    leaf threshold-notification-enabled {
      type string;
      description
        "Indicates whether or not a notification should
         result, in case of threshold violation";
    }
  }

  grouping ncs_rpc_notif_ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }

  grouping live_ncs_ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }

  grouping ENVMON-THRESHOLD-INFO {
    description
      "ENVMON threshold Info";
    leaf threshold-severity {
      type uint32;
      description
        "Indicates minor, major, critical severities";
    }
    leaf threshold-relation {
      type uint32;
      description
        "Indicates relation between sensor value and
         threshold";
    }
    leaf threshold-value {
      type int32;
      description
        "Value of the configured threshold";
    }
    leaf threshold-evaluation {
      type boolean;
      description
        "Indicates the result of the most recent
         evaluation of the thresholD";
    }
    leaf threshold-notification-enabled {
      type boolean;
      description
        "Indicates whether or not a notification should
         result, in case of threshold violation";
    }
  }
}

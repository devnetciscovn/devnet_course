module SNMP-VIEW-BASED-ACM-MIB {
  // Generated by yanger -t ncs
  tailf:mount-id "cisco-iosxr-nc-7.3:cisco-iosxr-nc-7.3";
  tailf:ncs-device-type "netconf";

  namespace "http://tail-f.com/ns/mibs/SNMP-VIEW-BASED-ACM-MIB/200210160000Z";
  prefix SNMP_VIEW_BASED_ACM_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }
  import tailf-ncs {
    prefix ncs;
  }

  revision 2002-10-16 {
    description
      "";
  }

  typedef ncs_template_vacmContextNameType {
    type string;
  }

  typedef ncs_template_vacmSecurityModelType {
    type string;
  }

  typedef ncs_template_vacmSecurityNameType {
    type string;
  }

  typedef ncs_template_vacmGroupNameType {
    type string;
  }

  typedef ncs_template_vacmAccessContextPrefixType {
    type string;
  }

  typedef ncs_template_vacmAccessContextMatchType {
    type string;
  }

  typedef ncs_template_vacmAccessReadViewNameType {
    type string;
  }

  typedef ncs_template_vacmAccessWriteViewNameType {
    type string;
  }

  typedef ncs_template_vacmAccessNotifyViewNameType {
    type string;
  }

  typedef ncs_template_vacmViewTreeFamilyViewNameType {
    type string;
  }

  typedef ncs_template_vacmViewTreeFamilyMaskType {
    type string;
  }

  typedef ncs_template_vacmViewTreeFamilyTypeType {
    type string;
  }

  typedef ncs_rpc_notif_vacmContextNameType {
    type string {
      length "min .. 32";
    }
  }

  typedef ncs_rpc_notif_vacmSecurityModelType {
    type int32 {
      range "1 .. 2147483647";
    }
  }

  typedef ncs_rpc_notif_vacmSecurityNameType {
    type string {
      length "1 .. 32";
    }
  }

  typedef ncs_rpc_notif_vacmGroupNameType {
    type string {
      length "1 .. 32";
    }
  }

  typedef ncs_rpc_notif_vacmAccessContextPrefixType {
    type string {
      length "min .. 32";
    }
  }

  typedef ncs_rpc_notif_vacmAccessContextMatchType {
    type enumeration {
      enum "exact" {
        value 1;
      }
      enum "prefix" {
        value 2;
      }
    }
  }

  typedef ncs_rpc_notif_vacmAccessReadViewNameType {
    type string {
      length "min .. 32";
    }
  }

  typedef ncs_rpc_notif_vacmAccessWriteViewNameType {
    type string {
      length "min .. 32";
    }
  }

  typedef ncs_rpc_notif_vacmAccessNotifyViewNameType {
    type string {
      length "min .. 32";
    }
  }

  typedef ncs_rpc_notif_vacmViewTreeFamilyViewNameType {
    type string {
      length "1 .. 32";
    }
  }

  typedef ncs_rpc_notif_vacmViewTreeFamilyMaskType {
    type tailf:hex-list {
      pattern '(((([0-9A-Fa-f]{2}):){0,15}([0-9A-Fa-f]{2}))){0,1}';
      tailf:value-length "0 .. 16";
    }
  }

  typedef ncs_rpc_notif_vacmViewTreeFamilyTypeType {
    type enumeration {
      enum "included" {
        value 1;
      }
      enum "excluded" {
        value 2;
      }
    }
  }

  typedef live_ncs_vacmContextNameType {
    type string {
      length "min .. 32";
    }
  }

  typedef live_ncs_vacmSecurityModelType {
    type int32 {
      range "1 .. 2147483647";
    }
  }

  typedef live_ncs_vacmSecurityNameType {
    type string {
      length "1 .. 32";
    }
  }

  typedef live_ncs_vacmGroupNameType {
    type string {
      length "1 .. 32";
    }
  }

  typedef live_ncs_vacmAccessContextPrefixType {
    type string {
      length "min .. 32";
    }
  }

  typedef live_ncs_vacmAccessContextMatchType {
    type enumeration {
      enum "exact" {
        value 1;
      }
      enum "prefix" {
        value 2;
      }
    }
  }

  typedef live_ncs_vacmAccessReadViewNameType {
    type string {
      length "min .. 32";
    }
  }

  typedef live_ncs_vacmAccessWriteViewNameType {
    type string {
      length "min .. 32";
    }
  }

  typedef live_ncs_vacmAccessNotifyViewNameType {
    type string {
      length "min .. 32";
    }
  }

  typedef live_ncs_vacmViewTreeFamilyViewNameType {
    type string {
      length "1 .. 32";
    }
  }

  typedef live_ncs_vacmViewTreeFamilyMaskType {
    type tailf:hex-list {
      pattern '(((([0-9A-Fa-f]{2}):){0,15}([0-9A-Fa-f]{2}))){0,1}';
      tailf:value-length "0 .. 16";
    }
  }

  typedef live_ncs_vacmViewTreeFamilyTypeType {
    type enumeration {
      enum "included" {
        value 1;
      }
      enum "excluded" {
        value 2;
      }
    }
  }

  typedef vacmContextNameType {
    type string {
      length "min .. 32";
    }
  }

  typedef vacmSecurityModelType {
    type int32 {
      range "1 .. 2147483647";
    }
  }

  typedef vacmSecurityNameType {
    type string {
      length "1 .. 32";
    }
  }

  typedef vacmGroupNameType {
    type string {
      length "1 .. 32";
    }
  }

  typedef vacmAccessContextPrefixType {
    type string {
      length "min .. 32";
    }
  }

  typedef vacmAccessContextMatchType {
    type enumeration {
      enum "exact" {
        value 1;
      }
      enum "prefix" {
        value 2;
      }
    }
  }

  typedef vacmAccessReadViewNameType {
    type string {
      length "min .. 32";
    }
  }

  typedef vacmAccessWriteViewNameType {
    type string {
      length "min .. 32";
    }
  }

  typedef vacmAccessNotifyViewNameType {
    type string {
      length "min .. 32";
    }
  }

  typedef vacmViewTreeFamilyViewNameType {
    type string {
      length "1 .. 32";
    }
  }

  typedef vacmViewTreeFamilyMaskType {
    type tailf:hex-list {
      pattern '(((([0-9A-Fa-f]{2}):){0,15}([0-9A-Fa-f]{2}))){0,1}';
      tailf:value-length "0 .. 16";
    }
  }

  typedef vacmViewTreeFamilyTypeType {
    type enumeration {
      enum "included" {
        value 1;
      }
      enum "excluded" {
        value 2;
      }
    }
  }

  augment "/ncs:devices/ncs:device/ncs:config" {
    container SNMP-VIEW-BASED-ACM-MIB {
      tailf:ncs-device-type "netconf";
      tailf:display-when "not(../../ncs:module) or ../../ncs:module[ncs:name='SNMP-VIEW-BASED-ACM-MIB']";
      container vacmSecurityToGroupTable {
        list vacmSecurityToGroupEntry {
          key "vacmSecurityModel vacmSecurityName";
          leaf vacmSecurityModel {
            type vacmSecurityModelType;
          }
          leaf vacmSecurityName {
            type vacmSecurityNameType;
          }
          leaf vacmGroupName {
            type vacmGroupNameType;
            mandatory true;
          }
          leaf vacmSecurityToGroupStorageType {
            type SNMPv2_TC:StorageType;
            default "nonVolatile";
          }
        }
      }
      container vacmAccessTable {
        list vacmAccessEntry {
          key "vacmGroupName vacmAccessContextPrefix vacmAccessSecurityModel vacmAccessSecurityLevel";
          leaf vacmGroupName {
            type vacmGroupNameType;
          }
          leaf vacmAccessContextPrefix {
            type vacmAccessContextPrefixType;
          }
          leaf vacmAccessSecurityModel {
            type SNMP_FRAMEWORK_MIB:SnmpSecurityModel;
          }
          leaf vacmAccessSecurityLevel {
            type SNMP_FRAMEWORK_MIB:SnmpSecurityLevel;
          }
          leaf vacmAccessContextMatch {
            type vacmAccessContextMatchType;
            default "exact";
          }
          leaf vacmAccessReadViewName {
            type vacmAccessReadViewNameType;
          }
          leaf vacmAccessWriteViewName {
            type vacmAccessWriteViewNameType;
          }
          leaf vacmAccessNotifyViewName {
            type vacmAccessNotifyViewNameType;
          }
          leaf vacmAccessStorageType {
            type SNMPv2_TC:StorageType;
            default "nonVolatile";
          }
        }
      }
      container vacmViewTreeFamilyTable {
        list vacmViewTreeFamilyEntry {
          key "vacmViewTreeFamilyViewName vacmViewTreeFamilySubtree";
          leaf vacmViewTreeFamilyViewName {
            type vacmViewTreeFamilyViewNameType;
          }
          leaf vacmViewTreeFamilySubtree {
            type yang:object-identifier;
          }
          leaf vacmViewTreeFamilyMask {
            type vacmViewTreeFamilyMaskType;
          }
          leaf vacmViewTreeFamilyType {
            type vacmViewTreeFamilyTypeType;
            default "included";
          }
          leaf vacmViewTreeFamilyStorageType {
            type SNMPv2_TC:StorageType;
            default "nonVolatile";
          }
        }
      }
    }
  }
  augment "/ncs:devices/ncs:device/ncs:live-status" {
    container SNMP-VIEW-BASED-ACM-MIB {
      tailf:ncs-device-type "netconf";
      tailf:display-when "not(../../ncs:module) or ../../ncs:module[ncs:name='SNMP-VIEW-BASED-ACM-MIB'] or (../../ncs:live-status-protocol[not(ncs:capability)]) or (../../ncs:live-status-protocol/ncs:capability/ncs:module[.='SNMP-VIEW-BASED-ACM-MIB'])";
      container vacmSecurityToGroupTable {
        list vacmSecurityToGroupEntry {
          key "vacmSecurityModel vacmSecurityName";
          leaf vacmSecurityModel {
            type live_ncs_vacmSecurityModelType;
          }
          leaf vacmSecurityName {
            type live_ncs_vacmSecurityNameType;
          }
          leaf vacmGroupName {
            type live_ncs_vacmGroupNameType;
            // NCS drop mandatory statement
          }
          leaf vacmSecurityToGroupStorageType {
            type SNMPv2_TC:live_ncs_StorageType;
            // NCS drop default statement
          }
        }
      }
      container vacmAccessTable {
        list vacmAccessEntry {
          key "vacmGroupName vacmAccessContextPrefix vacmAccessSecurityModel vacmAccessSecurityLevel";
          leaf vacmGroupName {
            type live_ncs_vacmGroupNameType;
          }
          leaf vacmAccessContextPrefix {
            type live_ncs_vacmAccessContextPrefixType;
          }
          leaf vacmAccessSecurityModel {
            type SNMP_FRAMEWORK_MIB:live_ncs_SnmpSecurityModel;
          }
          leaf vacmAccessSecurityLevel {
            type SNMP_FRAMEWORK_MIB:live_ncs_SnmpSecurityLevel;
          }
          leaf vacmAccessContextMatch {
            type live_ncs_vacmAccessContextMatchType;
            // NCS drop default statement
          }
          leaf vacmAccessReadViewName {
            type live_ncs_vacmAccessReadViewNameType;
          }
          leaf vacmAccessWriteViewName {
            type live_ncs_vacmAccessWriteViewNameType;
          }
          leaf vacmAccessNotifyViewName {
            type live_ncs_vacmAccessNotifyViewNameType;
          }
          leaf vacmAccessStorageType {
            type SNMPv2_TC:live_ncs_StorageType;
            // NCS drop default statement
          }
        }
      }
      container vacmViewTreeFamilyTable {
        list vacmViewTreeFamilyEntry {
          key "vacmViewTreeFamilyViewName vacmViewTreeFamilySubtree";
          leaf vacmViewTreeFamilyViewName {
            type live_ncs_vacmViewTreeFamilyViewNameType;
          }
          leaf vacmViewTreeFamilySubtree {
            type yang:object-identifier;
          }
          leaf vacmViewTreeFamilyMask {
            type live_ncs_vacmViewTreeFamilyMaskType;
          }
          leaf vacmViewTreeFamilyType {
            type live_ncs_vacmViewTreeFamilyTypeType;
            // NCS drop default statement
          }
          leaf vacmViewTreeFamilyStorageType {
            type SNMPv2_TC:live_ncs_StorageType;
            // NCS drop default statement
          }
        }
      }
    }
  }
  augment "/ncs:devices/ncs:template/ncs:ned-id/ncs:config" {
    container SNMP-VIEW-BASED-ACM-MIB {
      container vacmSecurityToGroupTable {
        list vacmSecurityToGroupEntry {
          // NCS patched for predictable order
          ordered-by user;
          key "vacmSecurityModel vacmSecurityName";
          leaf vacmSecurityModel {
            type ncs_template_vacmSecurityModelType;
          }
          leaf vacmSecurityName {
            type ncs_template_vacmSecurityNameType;
          }
          leaf vacmGroupName {
            type ncs_template_vacmGroupNameType;
            // NCS drop mandatory statement
          }
          leaf vacmSecurityToGroupStorageType {
            type SNMPv2_TC:ncs_template_StorageType;
            // NCS drop default statement
          }
        }
      }
      container vacmAccessTable {
        list vacmAccessEntry {
          // NCS patched for predictable order
          ordered-by user;
          key "vacmGroupName vacmAccessContextPrefix vacmAccessSecurityModel vacmAccessSecurityLevel";
          leaf vacmGroupName {
            type ncs_template_vacmGroupNameType;
          }
          leaf vacmAccessContextPrefix {
            type ncs_template_vacmAccessContextPrefixType;
          }
          leaf vacmAccessSecurityModel {
            type SNMP_FRAMEWORK_MIB:ncs_template_SnmpSecurityModel;
          }
          leaf vacmAccessSecurityLevel {
            type SNMP_FRAMEWORK_MIB:ncs_template_SnmpSecurityLevel;
          }
          leaf vacmAccessContextMatch {
            type ncs_template_vacmAccessContextMatchType;
            // NCS drop default statement
          }
          leaf vacmAccessReadViewName {
            type ncs_template_vacmAccessReadViewNameType;
          }
          leaf vacmAccessWriteViewName {
            type ncs_template_vacmAccessWriteViewNameType;
          }
          leaf vacmAccessNotifyViewName {
            type ncs_template_vacmAccessNotifyViewNameType;
          }
          leaf vacmAccessStorageType {
            type SNMPv2_TC:ncs_template_StorageType;
            // NCS drop default statement
          }
        }
      }
      container vacmViewTreeFamilyTable {
        list vacmViewTreeFamilyEntry {
          // NCS patched for predictable order
          ordered-by user;
          key "vacmViewTreeFamilyViewName vacmViewTreeFamilySubtree";
          leaf vacmViewTreeFamilyViewName {
            type ncs_template_vacmViewTreeFamilyViewNameType;
          }
          leaf vacmViewTreeFamilySubtree {
            type string;
          }
          leaf vacmViewTreeFamilyMask {
            type ncs_template_vacmViewTreeFamilyMaskType;
          }
          leaf vacmViewTreeFamilyType {
            type ncs_template_vacmViewTreeFamilyTypeType;
            // NCS drop default statement
          }
          leaf vacmViewTreeFamilyStorageType {
            type SNMPv2_TC:ncs_template_StorageType;
            // NCS drop default statement
          }
        }
      }
    }
  }
}

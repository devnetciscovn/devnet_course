module Cisco-IOS-XR-fabric-fgid-stats-8000-oper {
  // Generated by yanger -t ncs
  tailf:mount-id "cisco-iosxr-nc-7.3:cisco-iosxr-nc-7.3";
  tailf:ncs-device-type "netconf";

  namespace "http://cisco.com/ns/yang/Cisco-IOS-XR-fabric-fgid-stats-8000-oper";
  prefix fabric-fgid-stats-8000-oper;

  import Cisco-IOS-XR-types {
    prefix xr;
  }
  import cisco-semver {
    prefix semver;
  }
  include Cisco-IOS-XR-fabric-fgid-stats-8000-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fabric-fgid-stats-8000 package operational data.

     This module contains definitions
     for the following management objects:
       fabric-fgid: Fabric Fgid Data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Fgid-info-elem-max {
    type string;
    description
      "Fgid info elem max";
  }

  typedef ncs_template_Fgid-info-start-max {
    type string;
    description
      "Fgid info start max";
  }

  typedef ncs_rpc_notif_Fgid-info-elem-max {
    type uint32 {
      range "1..262144";
    }
    description
      "Fgid info elem max";
  }

  typedef ncs_rpc_notif_Fgid-info-start-max {
    type uint32 {
      range "0..262143";
    }
    description
      "Fgid info start max";
  }

  typedef live_ncs_Fgid-info-elem-max {
    type uint32 {
      range "1..262144";
    }
    description
      "Fgid info elem max";
  }

  typedef live_ncs_Fgid-info-start-max {
    type uint32 {
      range "0..262143";
    }
    description
      "Fgid info start max";
  }

  typedef Fgid-info-elem-max {
    type uint32 {
      range "1..262144";
    }
    description
      "Fgid info elem max";
  }

  typedef Fgid-info-start-max {
    type uint32 {
      range "0..262143";
    }
    description
      "Fgid info start max";
  }

  augment "/ncs:devices/ncs:device/ncs:config" {
    // NCS drop config false container 'fabric-fgid'
  }
  augment "/ncs:devices/ncs:device/ncs:live-status" {
    container fabric-fgid {
      tailf:ncs-device-type "netconf";
      tailf:display-when "not(../../ncs:module) or ../../ncs:module[ncs:name='Cisco-IOS-XR-fabric-fgid-stats-8000-oper'] or (../../ncs:live-status-protocol[not(ncs:capability)]) or (../../ncs:live-status-protocol/ncs:capability/ncs:module[.='Cisco-IOS-XR-fabric-fgid-stats-8000-oper'])";
      description
        "Fabric Fgid Data";
      container statistics {
        description
          "Fabric Fgid Statistics";
        container all {
          description
            "Statistics Data";
          uses live_ncs_FGID-ALL-STATS-INFO;
        }
        container system {
          description
            "Statistics Data";
          uses live_ncs_FGID-SYS-STATS-INFO;
        }
      }
      container display-opts {
        description
          "Fabric Fgid System";
        list display-opt {
          key "displayopt";
          description
            "Display Option";
          leaf displayopt {
            type xr:live_ncs_Cisco-ios-xr-string;
            description
              "brief/detail/diag";
          }
          list start-fgid-id {
            key "fgid-id";
            description
              "Start FGID Number";
            leaf fgid-id {
              type live_ncs_Fgid-info-start-max;
              description
                "Fabric FGID";
            }
            list element {
              key "num-fgids";
              description
                "Number of Fgids";
              leaf num-fgids {
                type live_ncs_Fgid-info-elem-max;
                description
                  "Number of Fabric FGIDs";
              }
              list fgid-id {
                key "fgid-id";
                description
                  "Single Fgid information";
                leaf fgid-id {
                  type live_ncs_Fgid-info-start-max;
                  description
                    "Single Fgid";
                }
                uses live_ncs_FGID-INFO;
              }
            }
          }
        }
      }
    }
  }
  augment "/ncs:devices/ncs:template/ncs:ned-id/ncs:config" {
    // NCS drop config false container 'fabric-fgid'
  }
}

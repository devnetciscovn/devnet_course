module Cisco-IOS-XR-sysadmin-fabric-mgr-fsdb-server-ncs5502 {
  // Generated by yanger -t ncs
  tailf:mount-id "cisco-iosxr-nc-7.3:cisco-iosxr-nc-7.3";
  tailf:ncs-device-type "netconf";

  namespace "http://www.cisco.com/ns/yang/Cisco-IOS-XR-sysadmin-fabric-mgr-fsdb-server-ncs5502";
  prefix fabric_fsdb;

  import Cisco-IOS-XR-sysadmin-fabric-types {
    prefix fabric-types;
  }
  import Cisco-IOS-XR-sysadmin-show-trace {
    prefix show-trace;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2020-10-06 {
    description
      "Added Plane ID info to FSDB PLA";
    semver:module-version "1.1.0";
  }
  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2017-04-07 {
    description
      "fsdb_server operational CLI support for non-modular NCS5500 platforms";
  }

  grouping ncs_template_link_port_show {
    list data_idx {
      // NCS patched for predictable order
      ordered-by user;
      key "port_data_idx";
      // NCS drop max-elements statement
      leaf port_data_idx {
        type string;
      }
      leaf sfe_port {
        type string;
      }
      leaf admin-state {
        type string;
      }
      leaf oper_state {
        type string;
      }
      leaf near_end_cdr_ln {
        type string;
      }
      leaf near_end_cxp_ch {
        type string;
      }
      leaf far_end_cxp_ch {
        type string;
      }
      leaf far_end_cdr_ln {
        type string;
      }
      leaf neighbor_link {
        type string;
      }
      list history {
        // NCS patched for predictable order
        ordered-by user;
        key "history_idx";
        leaf history_idx {
          type string;
        }
        leaf time_stamp {
          type string;
        }
        leaf admin-state {
          type string;
        }
        leaf oper_state {
          type string;
        }
        leaf error_state {
          type string;
        }
      }
    }
  }

  grouping ncs_template_link_port_stats_show {
    list data_idx {
      // NCS patched for predictable order
      ordered-by user;
      key "port_data_idx";
      // NCS drop max-elements statement
      leaf port_data_idx {
        type string;
      }
      leaf rack_num {
        type string;
      }
      leaf sfe_port {
        type string;
      }
      leaf TX_Control_cells_counter {
        type string;
      }
      leaf TX_Data_cell_counter {
        type string;
      }
      leaf TX_Data_byte_counter {
        type string;
      }
      leaf RX_CRC_errors_counter {
        type string;
      }
      leaf RX_LFEC_FEC_correctable_error {
        type string;
      }
      leaf RX_8b_10b_disparity_errors {
        type string;
      }
      leaf RX_Control_cells_counter {
        type string;
      }
      leaf RX_Data_cell_counter {
        type string;
      }
      leaf RX_Data_byte_counter {
        type string;
      }
      leaf RX_dropped_retransmitted_control {
        type string;
      }
      leaf TX_Asyn_fifo_rate {
        type string;
      }
      leaf RX_Asyn_fifo_rate {
        type string;
      }
      leaf RX_LFEC_FEC_uncorrectable_errors {
        type string;
      }
      leaf RX_8b_10b_code_errors {
        type string;
      }
      leaf is_link_error {
        type string;
        // NCS drop default statement
      }
      leaf link_crc_error {
        type string;
      }
      leaf link_size_error {
        type string;
      }
      leaf link_mis_align_error {
        type string;
      }
      leaf link_code_group_error {
        type string;
      }
      leaf link_no_sig_lock_error {
        type string;
      }
      leaf link_no_sig_accept_error {
        type string;
      }
      leaf link_tokens_error {
        type string;
      }
      leaf error_token_count {
        type string;
      }
    }
  }

  grouping ncs_template_fabric_link_port_show_with_option {
    uses ncs_template_link_port_show;
    container brief {
      uses ncs_template_link_port_show;
    }
    container detail {
      uses ncs_template_link_port_show;
    }
  }

  grouping ncs_template_fabric_link_port_states {
    container state {
      container up {
        uses ncs_template_fabric_link_port_show_with_option;
      }
      container down {
        uses ncs_template_fabric_link_port_show_with_option;
      }
      container mismatch {
        uses ncs_template_fabric_link_port_show_with_option;
      }
    }
  }

  grouping ncs_template_asic_status_show {
    list asic_list {
      // NCS patched for predictable order
      ordered-by user;
      key "asic_idx";
      leaf asic_idx {
        type string;
      }
      leaf asic_loc_str {
        type string;
      }
      leaf admin-state {
        type string;
      }
      leaf oper_state {
        type string;
      }
      leaf down_flags {
        type string;
      }
      leaf fab_group {
        type string;
      }
      list history {
        // NCS patched for predictable order
        ordered-by user;
        key "history_idx";
        leaf history_idx {
          type string;
        }
        leaf time_stamp {
          type string;
        }
        leaf admin-state {
          type string;
        }
        leaf oper_state {
          type string;
        }
        leaf error_state {
          type string;
        }
      }
    }
  }

  grouping ncs_template_fsdb_svr_trace {
    container fsdb_srvr {
      description
        "FSDB Server information";
      container fsdb_server {
        uses show-trace:ncs_template_traceable;
      }
    }
  }

  grouping ncs_template_fsdb_pla_reachability_show {
    list planes {
      // NCS patched for predictable order
      ordered-by user;
      key "plane_idx";
      leaf plane_idx {
        type string;
      }
      leaf plane_num {
        type string;
      }
      leaf fabid_name {
        type string;
      }
      leaf show_fabid {
        type string;
      }
      leaf asic_stage {
        type string;
      }
      list cards {
        // NCS patched for predictable order
        ordered-by user;
        key "card_idx";
        leaf card_idx {
          type string;
        }
        list asics {
          // NCS patched for predictable order
          ordered-by user;
          key "asic_idx";
          leaf asic_idx {
            type string;
          }
          leaf asic_RSA {
            type string;
          }
          leaf reachability_mask {
            type string;
          }
          leaf linkup_mask {
            type string;
          }
          leaf all_reach_mask {
            type string;
          }
          leaf total_links {
            type string;
          }
          leaf total_up_links {
            type string;
          }
          leaf total_all_reach_links {
            type string;
          }
          leaf asic_stage_name {
            type fabric-types:ncs_template_sfe_stage_type;
          }
        }
      }
    }
  }

  grouping ncs_template_fabric_link_state_and_statistics_show_w_loc {
    uses ncs_template_fabric_link_port_show_with_option;
    uses ncs_template_fabric_link_port_states;
    container statistics {
      uses ncs_template_link_port_stats_show;
      container brief {
        uses ncs_template_link_port_stats_show;
      }
      container detail {
        uses ncs_template_link_port_stats_show;
      }
    }
  }

  grouping ncs_template_fabric_link_state_and_statistics_show {
    uses ncs_template_fabric_link_port_show_with_option;
    uses ncs_template_fabric_link_port_states;
    container statistics {
      uses ncs_template_link_port_stats_show;
      container brief {
        uses ncs_template_link_port_stats_show;
      }
      container detail {
        uses ncs_template_link_port_stats_show;
      }
    }
  }

  grouping ncs_template_fabric_link_port_state_and_stats {
    list port {
      // NCS patched for predictable order
      ordered-by user;
      key "portname";
      leaf portname {
        type fabric-types:ncs_template_link_port_type;
      }
      leaf description {
        type string;
        // NCS drop default statement
      }
      list location {
        // NCS patched for predictable order
        ordered-by user;
        key "loc_str";
        leaf loc_str {
          type fabric-types:ncs_template_link_port_location_zermatt_type_for_yang;
        }
        container rx {
          description
            "Rx link option";
          uses ncs_template_fabric_link_state_and_statistics_show_w_loc;
        }
        container tx {
          description
            "Tx link option";
          uses ncs_template_fabric_link_state_and_statistics_show_w_loc;
        }
      }
      container rx {
        description
          "Rx link option";
        uses ncs_template_fabric_link_state_and_statistics_show;
      }
      container tx {
        description
          "Tx link option";
        uses ncs_template_fabric_link_state_and_statistics_show;
      }
    }
  }

  grouping ncs_template_fsdb_svr {
    container link {
      description
        "Fabric link option";
      list rack {
        // NCS patched for predictable order
        ordered-by user;
        key "rack_number";
        leaf rack_number {
          type string;
        }
        uses ncs_template_fabric_link_port_state_and_stats;
      }
      list node_location {
        // NCS patched for predictable order
        ordered-by user;
        key "node_str";
        leaf node_str {
          type string;
        }
        uses ncs_template_fabric_link_port_state_and_stats;
      }
    }
    container sfe {
      description
        "Switch Fabric Element option";
      list rack {
        // NCS patched for predictable order
        ordered-by user;
        key "rack_number";
        leaf rack_number {
          type string;
        }
        list asic_stages {
          // NCS patched for predictable order
          ordered-by user;
          key "asic_stage_name";
          leaf asic_stage_name {
            type fabric-types:ncs_template_asic_stage_type;
          }
          list location {
            // NCS patched for predictable order
            ordered-by user;
            key "loc_str";
            leaf loc_str {
              type fabric-types:ncs_template_asic_location_zermatt_type;
            }
            uses ncs_template_asic_status_show;
            container brief {
              uses ncs_template_asic_status_show;
            }
            container detail {
              uses ncs_template_asic_status_show;
            }
          }
          uses ncs_template_asic_status_show;
          container brief {
            uses ncs_template_asic_status_show;
          }
          container detail {
            uses ncs_template_asic_status_show;
          }
        }
      }
    }
    container fsdb_pla {
      description
        "plane availability status option";
      list rack {
        // NCS patched for predictable order
        ordered-by user;
        key "rack_number";
        description
          "Rack";
        leaf rack_number {
          type string;
        }
        list asic_stages {
          // NCS patched for predictable order
          ordered-by user;
          key "asic_stage_idx";
          leaf asic_stage_idx {
            type fabric-types:ncs_template_sfe_stage_type;
          }
          leaf asic_stage_name {
            type fabric-types:ncs_template_sfe_stage_type;
          }
          leaf rack_number {
            type string;
          }
          leaf plane_number {
            type string;
          }
          leaf plane_id {
            type string;
          }
          list fabids {
            // NCS patched for predictable order
            ordered-by user;
            key "idx";
            leaf idx {
              type string;
            }
            leaf fabid_address {
              type string;
            }
            leaf plane_num {
              type string;
            }
            leaf plane_0_mask {
              type string;
            }
            leaf plane_1_mask {
              type string;
            }
            leaf plane_2_mask {
              type string;
            }
            leaf plane_3_mask {
              type string;
            }
            leaf plane_4_mask {
              type string;
            }
            leaf plane_5_mask {
              type string;
            }
            leaf min_links_per_asic {
              type string;
            }
            leaf max_links_per_asic {
              type string;
            }
            leaf total_links {
              type string;
            }
            leaf min_up_links_per_asic {
              type string;
            }
            leaf max_up_links_per_asic {
              type string;
            }
            leaf total_up_links {
              type string;
            }
          }
          list down_fabids {
            // NCS patched for predictable order
            ordered-by user;
            key "idx";
            leaf idx {
              type string;
            }
            leaf fabid_address {
              type string;
            }
            leaf fabid_status {
              type string;
            }
          }
          list destination {
            // NCS patched for predictable order
            ordered-by user;
            key "amba_id";
            leaf amba_id {
              type fabric-types:ncs_template_fabric_fabid_type;
            }
            uses ncs_template_fsdb_pla_reachability_show;
          }
        }
      }
    }
    uses ncs_template_fsdb_svr_trace;
  }

  grouping ncs_rpc_notif_link_port_show {
    list data_idx {
      key "port_data_idx";
      max-elements 1024;
      leaf port_data_idx {
        type int64;
      }
      leaf sfe_port {
        type string;
      }
      leaf admin-state {
        type string;
      }
      leaf oper_state {
        type string;
      }
      leaf near_end_cdr_ln {
        type string;
      }
      leaf near_end_cxp_ch {
        type string;
      }
      leaf far_end_cxp_ch {
        type string;
      }
      leaf far_end_cdr_ln {
        type string;
      }
      leaf neighbor_link {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping ncs_rpc_notif_link_port_stats_show {
    list data_idx {
      key "port_data_idx";
      max-elements 1024;
      leaf port_data_idx {
        type int64;
      }
      leaf rack_num {
        type string;
      }
      leaf sfe_port {
        type string;
      }
      leaf TX_Control_cells_counter {
        type uint64;
      }
      leaf TX_Data_cell_counter {
        type uint64;
      }
      leaf TX_Data_byte_counter {
        type uint64;
      }
      leaf RX_CRC_errors_counter {
        type uint64;
      }
      leaf RX_LFEC_FEC_correctable_error {
        type uint64;
      }
      leaf RX_8b_10b_disparity_errors {
        type uint64;
      }
      leaf RX_Control_cells_counter {
        type uint64;
      }
      leaf RX_Data_cell_counter {
        type uint64;
      }
      leaf RX_Data_byte_counter {
        type uint64;
      }
      leaf RX_dropped_retransmitted_control {
        type uint64;
      }
      leaf TX_Asyn_fifo_rate {
        type uint64;
      }
      leaf RX_Asyn_fifo_rate {
        type uint64;
      }
      leaf RX_LFEC_FEC_uncorrectable_errors {
        type uint64;
      }
      leaf RX_8b_10b_code_errors {
        type uint64;
      }
      leaf is_link_error {
        type boolean;
        default "false";
      }
      leaf link_crc_error {
        type uint32;
      }
      leaf link_size_error {
        type uint32;
      }
      leaf link_mis_align_error {
        type uint32;
      }
      leaf link_code_group_error {
        type uint32;
      }
      leaf link_no_sig_lock_error {
        type uint32;
      }
      leaf link_no_sig_accept_error {
        type uint32;
      }
      leaf link_tokens_error {
        type uint32;
      }
      leaf error_token_count {
        type uint32;
      }
    }
  }

  grouping ncs_rpc_notif_fabric_link_port_show_with_option {
    uses ncs_rpc_notif_link_port_show;
    container brief {
      uses ncs_rpc_notif_link_port_show;
    }
    container detail {
      uses ncs_rpc_notif_link_port_show;
    }
  }

  grouping ncs_rpc_notif_fabric_link_port_states {
    container state {
      container up {
        uses ncs_rpc_notif_fabric_link_port_show_with_option;
      }
      container down {
        uses ncs_rpc_notif_fabric_link_port_show_with_option;
      }
      container mismatch {
        uses ncs_rpc_notif_fabric_link_port_show_with_option;
      }
    }
  }

  grouping ncs_rpc_notif_asic_status_show {
    list asic_list {
      key "asic_idx";
      leaf asic_idx {
        type int64;
      }
      leaf asic_loc_str {
        type string;
      }
      leaf admin-state {
        type string;
      }
      leaf oper_state {
        type string;
      }
      leaf down_flags {
        type string;
      }
      leaf fab_group {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping ncs_rpc_notif_fsdb_svr_trace {
    container fsdb_srvr {
      description
        "FSDB Server information";
      container fsdb_server {
        uses show-trace:ncs_rpc_notif_traceable;
      }
    }
  }

  grouping ncs_rpc_notif_fsdb_pla_reachability_show {
    list planes {
      key "plane_idx";
      leaf plane_idx {
        type int32;
      }
      leaf plane_num {
        type int32;
      }
      leaf fabid_name {
        type string;
      }
      leaf show_fabid {
        type boolean;
      }
      leaf asic_stage {
        type string;
      }
      list cards {
        key "card_idx";
        leaf card_idx {
          type int32;
        }
        list asics {
          key "asic_idx";
          leaf asic_idx {
            type int32;
          }
          leaf asic_RSA {
            type string;
          }
          leaf reachability_mask {
            type string;
          }
          leaf linkup_mask {
            type string;
          }
          leaf all_reach_mask {
            type string;
          }
          leaf total_links {
            type int32;
          }
          leaf total_up_links {
            type int32;
          }
          leaf total_all_reach_links {
            type int32;
          }
          leaf asic_stage_name {
            type fabric-types:ncs_rpc_notif_sfe_stage_type;
          }
        }
      }
    }
  }

  grouping ncs_rpc_notif_fabric_link_state_and_statistics_show_w_loc {
    uses ncs_rpc_notif_fabric_link_port_show_with_option;
    uses ncs_rpc_notif_fabric_link_port_states;
    container statistics {
      uses ncs_rpc_notif_link_port_stats_show;
      container brief {
        uses ncs_rpc_notif_link_port_stats_show;
      }
      container detail {
        uses ncs_rpc_notif_link_port_stats_show;
      }
    }
  }

  grouping ncs_rpc_notif_fabric_link_state_and_statistics_show {
    uses ncs_rpc_notif_fabric_link_port_show_with_option;
    uses ncs_rpc_notif_fabric_link_port_states;
    container statistics {
      uses ncs_rpc_notif_link_port_stats_show;
      container brief {
        uses ncs_rpc_notif_link_port_stats_show;
      }
      container detail {
        uses ncs_rpc_notif_link_port_stats_show;
      }
    }
  }

  grouping ncs_rpc_notif_fabric_link_port_state_and_stats {
    list port {
      key "portname";
      leaf portname {
        type fabric-types:ncs_rpc_notif_link_port_type;
      }
      leaf description {
        type string;
        default "port.";
      }
      list location {
        key "loc_str";
        leaf loc_str {
          type fabric-types:ncs_rpc_notif_link_port_location_zermatt_type_for_yang;
        }
        container rx {
          description
            "Rx link option";
          uses ncs_rpc_notif_fabric_link_state_and_statistics_show_w_loc;
        }
        container tx {
          description
            "Tx link option";
          uses ncs_rpc_notif_fabric_link_state_and_statistics_show_w_loc;
        }
      }
      container rx {
        description
          "Rx link option";
        uses ncs_rpc_notif_fabric_link_state_and_statistics_show;
      }
      container tx {
        description
          "Tx link option";
        uses ncs_rpc_notif_fabric_link_state_and_statistics_show;
      }
    }
  }

  grouping ncs_rpc_notif_fsdb_svr {
    container link {
      description
        "Fabric link option";
      list rack {
        key "rack_number";
        leaf rack_number {
          type int32;
        }
        uses ncs_rpc_notif_fabric_link_port_state_and_stats;
      }
      list node_location {
        key "node_str";
        leaf node_str {
          type string;
        }
        uses ncs_rpc_notif_fabric_link_port_state_and_stats;
      }
    }
    container sfe {
      description
        "Switch Fabric Element option";
      list rack {
        key "rack_number";
        leaf rack_number {
          type int32;
        }
        list asic_stages {
          key "asic_stage_name";
          leaf asic_stage_name {
            type fabric-types:ncs_rpc_notif_asic_stage_type;
          }
          list location {
            key "loc_str";
            leaf loc_str {
              type fabric-types:ncs_rpc_notif_asic_location_zermatt_type;
            }
            uses ncs_rpc_notif_asic_status_show;
            container brief {
              uses ncs_rpc_notif_asic_status_show;
            }
            container detail {
              uses ncs_rpc_notif_asic_status_show;
            }
          }
          uses ncs_rpc_notif_asic_status_show;
          container brief {
            uses ncs_rpc_notif_asic_status_show;
          }
          container detail {
            uses ncs_rpc_notif_asic_status_show;
          }
        }
      }
    }
    container fsdb_pla {
      description
        "plane availability status option";
      list rack {
        key "rack_number";
        description
          "Rack";
        leaf rack_number {
          type int32;
        }
        list asic_stages {
          key "asic_stage_idx";
          leaf asic_stage_idx {
            type fabric-types:ncs_rpc_notif_sfe_stage_type;
          }
          leaf asic_stage_name {
            type fabric-types:ncs_rpc_notif_sfe_stage_type;
          }
          leaf rack_number {
            type string;
          }
          leaf plane_number {
            type int32;
          }
          leaf plane_id {
            type int32;
          }
          list fabids {
            key "idx";
            leaf idx {
              type int32;
            }
            leaf fabid_address {
              type string;
            }
            leaf plane_num {
              type int32;
            }
            leaf plane_0_mask {
              type string;
            }
            leaf plane_1_mask {
              type string;
            }
            leaf plane_2_mask {
              type string;
            }
            leaf plane_3_mask {
              type string;
            }
            leaf plane_4_mask {
              type string;
            }
            leaf plane_5_mask {
              type string;
            }
            leaf min_links_per_asic {
              type int32;
            }
            leaf max_links_per_asic {
              type int32;
            }
            leaf total_links {
              type int32;
            }
            leaf min_up_links_per_asic {
              type int32;
            }
            leaf max_up_links_per_asic {
              type int32;
            }
            leaf total_up_links {
              type int32;
            }
          }
          list down_fabids {
            key "idx";
            leaf idx {
              type int32;
            }
            leaf fabid_address {
              type string;
            }
            leaf fabid_status {
              type string;
            }
          }
          list destination {
            key "amba_id";
            leaf amba_id {
              type fabric-types:ncs_rpc_notif_fabric_fabid_type;
            }
            uses ncs_rpc_notif_fsdb_pla_reachability_show;
          }
        }
      }
    }
    uses ncs_rpc_notif_fsdb_svr_trace;
  }

  grouping live_ncs_link_port_show {
    list data_idx {
      key "port_data_idx";
      // NCS drop max-elements statement
      leaf port_data_idx {
        type int64;
      }
      leaf sfe_port {
        type string;
      }
      leaf admin-state {
        type string;
      }
      leaf oper_state {
        type string;
      }
      leaf near_end_cdr_ln {
        type string;
      }
      leaf near_end_cxp_ch {
        type string;
      }
      leaf far_end_cxp_ch {
        type string;
      }
      leaf far_end_cdr_ln {
        type string;
      }
      leaf neighbor_link {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping live_ncs_link_port_stats_show {
    list data_idx {
      key "port_data_idx";
      // NCS drop max-elements statement
      leaf port_data_idx {
        type int64;
      }
      leaf rack_num {
        type string;
      }
      leaf sfe_port {
        type string;
      }
      leaf TX_Control_cells_counter {
        type uint64;
      }
      leaf TX_Data_cell_counter {
        type uint64;
      }
      leaf TX_Data_byte_counter {
        type uint64;
      }
      leaf RX_CRC_errors_counter {
        type uint64;
      }
      leaf RX_LFEC_FEC_correctable_error {
        type uint64;
      }
      leaf RX_8b_10b_disparity_errors {
        type uint64;
      }
      leaf RX_Control_cells_counter {
        type uint64;
      }
      leaf RX_Data_cell_counter {
        type uint64;
      }
      leaf RX_Data_byte_counter {
        type uint64;
      }
      leaf RX_dropped_retransmitted_control {
        type uint64;
      }
      leaf TX_Asyn_fifo_rate {
        type uint64;
      }
      leaf RX_Asyn_fifo_rate {
        type uint64;
      }
      leaf RX_LFEC_FEC_uncorrectable_errors {
        type uint64;
      }
      leaf RX_8b_10b_code_errors {
        type uint64;
      }
      leaf is_link_error {
        type boolean;
        // NCS drop default statement
      }
      leaf link_crc_error {
        type uint32;
      }
      leaf link_size_error {
        type uint32;
      }
      leaf link_mis_align_error {
        type uint32;
      }
      leaf link_code_group_error {
        type uint32;
      }
      leaf link_no_sig_lock_error {
        type uint32;
      }
      leaf link_no_sig_accept_error {
        type uint32;
      }
      leaf link_tokens_error {
        type uint32;
      }
      leaf error_token_count {
        type uint32;
      }
    }
  }

  grouping live_ncs_fabric_link_port_show_with_option {
    uses live_ncs_link_port_show;
    container brief {
      uses live_ncs_link_port_show;
    }
    container detail {
      uses live_ncs_link_port_show;
    }
  }

  grouping live_ncs_fabric_link_port_states {
    container state {
      container up {
        uses live_ncs_fabric_link_port_show_with_option;
      }
      container down {
        uses live_ncs_fabric_link_port_show_with_option;
      }
      container mismatch {
        uses live_ncs_fabric_link_port_show_with_option;
      }
    }
  }

  grouping live_ncs_asic_status_show {
    list asic_list {
      key "asic_idx";
      leaf asic_idx {
        type int64;
      }
      leaf asic_loc_str {
        type string;
      }
      leaf admin-state {
        type string;
      }
      leaf oper_state {
        type string;
      }
      leaf down_flags {
        type string;
      }
      leaf fab_group {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping live_ncs_fsdb_svr_trace {
    container fsdb_srvr {
      description
        "FSDB Server information";
      container fsdb_server {
        uses show-trace:live_ncs_traceable;
      }
    }
  }

  grouping live_ncs_fsdb_pla_reachability_show {
    list planes {
      key "plane_idx";
      leaf plane_idx {
        type int32;
      }
      leaf plane_num {
        type int32;
      }
      leaf fabid_name {
        type string;
      }
      leaf show_fabid {
        type boolean;
      }
      leaf asic_stage {
        type string;
      }
      list cards {
        key "card_idx";
        leaf card_idx {
          type int32;
        }
        list asics {
          key "asic_idx";
          leaf asic_idx {
            type int32;
          }
          leaf asic_RSA {
            type string;
          }
          leaf reachability_mask {
            type string;
          }
          leaf linkup_mask {
            type string;
          }
          leaf all_reach_mask {
            type string;
          }
          leaf total_links {
            type int32;
          }
          leaf total_up_links {
            type int32;
          }
          leaf total_all_reach_links {
            type int32;
          }
          leaf asic_stage_name {
            type fabric-types:live_ncs_sfe_stage_type;
          }
        }
      }
    }
  }

  grouping live_ncs_fabric_link_state_and_statistics_show_w_loc {
    uses live_ncs_fabric_link_port_show_with_option;
    uses live_ncs_fabric_link_port_states;
    container statistics {
      uses live_ncs_link_port_stats_show;
      container brief {
        uses live_ncs_link_port_stats_show;
      }
      container detail {
        uses live_ncs_link_port_stats_show;
      }
    }
  }

  grouping live_ncs_fabric_link_state_and_statistics_show {
    uses live_ncs_fabric_link_port_show_with_option;
    uses live_ncs_fabric_link_port_states;
    container statistics {
      uses live_ncs_link_port_stats_show;
      container brief {
        uses live_ncs_link_port_stats_show;
      }
      container detail {
        uses live_ncs_link_port_stats_show;
      }
    }
  }

  grouping live_ncs_fabric_link_port_state_and_stats {
    list port {
      key "portname";
      leaf portname {
        type fabric-types:live_ncs_link_port_type;
      }
      leaf description {
        type string;
        // NCS drop default statement
      }
      list location {
        key "loc_str";
        leaf loc_str {
          type fabric-types:live_ncs_link_port_location_zermatt_type_for_yang;
        }
        container rx {
          description
            "Rx link option";
          uses live_ncs_fabric_link_state_and_statistics_show_w_loc;
        }
        container tx {
          description
            "Tx link option";
          uses live_ncs_fabric_link_state_and_statistics_show_w_loc;
        }
      }
      container rx {
        description
          "Rx link option";
        uses live_ncs_fabric_link_state_and_statistics_show;
      }
      container tx {
        description
          "Tx link option";
        uses live_ncs_fabric_link_state_and_statistics_show;
      }
    }
  }

  grouping live_ncs_fsdb_svr {
    container link {
      description
        "Fabric link option";
      list rack {
        key "rack_number";
        leaf rack_number {
          type int32;
        }
        uses live_ncs_fabric_link_port_state_and_stats;
      }
      list node_location {
        key "node_str";
        leaf node_str {
          type string;
        }
        uses live_ncs_fabric_link_port_state_and_stats;
      }
    }
    container sfe {
      description
        "Switch Fabric Element option";
      list rack {
        key "rack_number";
        leaf rack_number {
          type int32;
        }
        list asic_stages {
          key "asic_stage_name";
          leaf asic_stage_name {
            type fabric-types:live_ncs_asic_stage_type;
          }
          list location {
            key "loc_str";
            leaf loc_str {
              type fabric-types:live_ncs_asic_location_zermatt_type;
            }
            uses live_ncs_asic_status_show;
            container brief {
              uses live_ncs_asic_status_show;
            }
            container detail {
              uses live_ncs_asic_status_show;
            }
          }
          uses live_ncs_asic_status_show;
          container brief {
            uses live_ncs_asic_status_show;
          }
          container detail {
            uses live_ncs_asic_status_show;
          }
        }
      }
    }
    container fsdb_pla {
      description
        "plane availability status option";
      list rack {
        key "rack_number";
        description
          "Rack";
        leaf rack_number {
          type int32;
        }
        list asic_stages {
          key "asic_stage_idx";
          leaf asic_stage_idx {
            type fabric-types:live_ncs_sfe_stage_type;
          }
          leaf asic_stage_name {
            type fabric-types:live_ncs_sfe_stage_type;
          }
          leaf rack_number {
            type string;
          }
          leaf plane_number {
            type int32;
          }
          leaf plane_id {
            type int32;
          }
          list fabids {
            key "idx";
            leaf idx {
              type int32;
            }
            leaf fabid_address {
              type string;
            }
            leaf plane_num {
              type int32;
            }
            leaf plane_0_mask {
              type string;
            }
            leaf plane_1_mask {
              type string;
            }
            leaf plane_2_mask {
              type string;
            }
            leaf plane_3_mask {
              type string;
            }
            leaf plane_4_mask {
              type string;
            }
            leaf plane_5_mask {
              type string;
            }
            leaf min_links_per_asic {
              type int32;
            }
            leaf max_links_per_asic {
              type int32;
            }
            leaf total_links {
              type int32;
            }
            leaf min_up_links_per_asic {
              type int32;
            }
            leaf max_up_links_per_asic {
              type int32;
            }
            leaf total_up_links {
              type int32;
            }
          }
          list down_fabids {
            key "idx";
            leaf idx {
              type int32;
            }
            leaf fabid_address {
              type string;
            }
            leaf fabid_status {
              type string;
            }
          }
          list destination {
            key "amba_id";
            leaf amba_id {
              type fabric-types:live_ncs_fabric_fabid_type;
            }
            uses live_ncs_fsdb_pla_reachability_show;
          }
        }
      }
    }
    uses live_ncs_fsdb_svr_trace;
  }

  grouping link_port_show {
    list data_idx {
      key "port_data_idx";
      max-elements 1024;
      leaf port_data_idx {
        type int64;
      }
      leaf sfe_port {
        type string;
      }
      leaf admin-state {
        type string;
      }
      leaf oper_state {
        type string;
      }
      leaf near_end_cdr_ln {
        type string;
      }
      leaf near_end_cxp_ch {
        type string;
      }
      leaf far_end_cxp_ch {
        type string;
      }
      leaf far_end_cdr_ln {
        type string;
      }
      leaf neighbor_link {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping link_port_stats_show {
    list data_idx {
      key "port_data_idx";
      max-elements 1024;
      leaf port_data_idx {
        type int64;
      }
      leaf rack_num {
        type string;
      }
      leaf sfe_port {
        type string;
      }
      leaf TX_Control_cells_counter {
        type uint64;
      }
      leaf TX_Data_cell_counter {
        type uint64;
      }
      leaf TX_Data_byte_counter {
        type uint64;
      }
      leaf RX_CRC_errors_counter {
        type uint64;
      }
      leaf RX_LFEC_FEC_correctable_error {
        type uint64;
      }
      leaf RX_8b_10b_disparity_errors {
        type uint64;
      }
      leaf RX_Control_cells_counter {
        type uint64;
      }
      leaf RX_Data_cell_counter {
        type uint64;
      }
      leaf RX_Data_byte_counter {
        type uint64;
      }
      leaf RX_dropped_retransmitted_control {
        type uint64;
      }
      leaf TX_Asyn_fifo_rate {
        type uint64;
      }
      leaf RX_Asyn_fifo_rate {
        type uint64;
      }
      leaf RX_LFEC_FEC_uncorrectable_errors {
        type uint64;
      }
      leaf RX_8b_10b_code_errors {
        type uint64;
      }
      leaf is_link_error {
        type boolean;
        default "false";
      }
      leaf link_crc_error {
        type uint32;
      }
      leaf link_size_error {
        type uint32;
      }
      leaf link_mis_align_error {
        type uint32;
      }
      leaf link_code_group_error {
        type uint32;
      }
      leaf link_no_sig_lock_error {
        type uint32;
      }
      leaf link_no_sig_accept_error {
        type uint32;
      }
      leaf link_tokens_error {
        type uint32;
      }
      leaf error_token_count {
        type uint32;
      }
    }
  }

  grouping fabric_link_port_show_with_option {
    uses link_port_show;
    container brief {
      uses link_port_show;
    }
    container detail {
      uses link_port_show;
    }
  }

  grouping fabric_link_port_states {
    container state {
      container up {
        uses fabric_link_port_show_with_option;
      }
      container down {
        uses fabric_link_port_show_with_option;
      }
      container mismatch {
        uses fabric_link_port_show_with_option;
      }
    }
  }

  grouping asic_status_show {
    list asic_list {
      key "asic_idx";
      leaf asic_idx {
        type int64;
      }
      leaf asic_loc_str {
        type string;
      }
      leaf admin-state {
        type string;
      }
      leaf oper_state {
        type string;
      }
      leaf down_flags {
        type string;
      }
      leaf fab_group {
        type string;
      }
      list history {
        key "history_idx";
        leaf history_idx {
          type int32;
        }
        leaf time_stamp {
          type string;
        }
        leaf admin-state {
          type string;
        }
        leaf oper_state {
          type string;
        }
        leaf error_state {
          type string;
        }
      }
    }
  }

  grouping fsdb_svr_trace {
    container fsdb_srvr {
      description
        "FSDB Server information";
      container fsdb_server {
        uses show-trace:traceable;
      }
    }
  }

  grouping fsdb_pla_reachability_show {
    list planes {
      key "plane_idx";
      leaf plane_idx {
        type int32;
      }
      leaf plane_num {
        type int32;
      }
      leaf fabid_name {
        type string;
      }
      leaf show_fabid {
        type boolean;
      }
      leaf asic_stage {
        type string;
      }
      list cards {
        key "card_idx";
        leaf card_idx {
          type int32;
        }
        list asics {
          key "asic_idx";
          leaf asic_idx {
            type int32;
          }
          leaf asic_RSA {
            type string;
          }
          leaf reachability_mask {
            type string;
          }
          leaf linkup_mask {
            type string;
          }
          leaf all_reach_mask {
            type string;
          }
          leaf total_links {
            type int32;
          }
          leaf total_up_links {
            type int32;
          }
          leaf total_all_reach_links {
            type int32;
          }
          leaf asic_stage_name {
            type fabric-types:sfe_stage_type;
          }
        }
      }
    }
  }

  grouping fabric_link_state_and_statistics_show_w_loc {
    uses fabric_link_port_show_with_option;
    uses fabric_link_port_states;
    container statistics {
      uses link_port_stats_show;
      container brief {
        uses link_port_stats_show;
      }
      container detail {
        uses link_port_stats_show;
      }
    }
  }

  grouping fabric_link_state_and_statistics_show {
    uses fabric_link_port_show_with_option;
    uses fabric_link_port_states;
    container statistics {
      uses link_port_stats_show;
      container brief {
        uses link_port_stats_show;
      }
      container detail {
        uses link_port_stats_show;
      }
    }
  }

  grouping fabric_link_port_state_and_stats {
    list port {
      key "portname";
      leaf portname {
        type fabric-types:link_port_type;
      }
      leaf description {
        type string;
        default "port.";
      }
      list location {
        key "loc_str";
        leaf loc_str {
          type fabric-types:link_port_location_zermatt_type_for_yang;
        }
        container rx {
          description
            "Rx link option";
          uses fabric_link_state_and_statistics_show_w_loc;
        }
        container tx {
          description
            "Tx link option";
          uses fabric_link_state_and_statistics_show_w_loc;
        }
      }
      container rx {
        description
          "Rx link option";
        uses fabric_link_state_and_statistics_show;
      }
      container tx {
        description
          "Tx link option";
        uses fabric_link_state_and_statistics_show;
      }
    }
  }

  grouping fsdb_svr {
    container link {
      description
        "Fabric link option";
      list rack {
        key "rack_number";
        leaf rack_number {
          type int32;
        }
        uses fabric_link_port_state_and_stats;
      }
      list node_location {
        key "node_str";
        leaf node_str {
          type string;
        }
        uses fabric_link_port_state_and_stats;
      }
    }
    container sfe {
      description
        "Switch Fabric Element option";
      list rack {
        key "rack_number";
        leaf rack_number {
          type int32;
        }
        list asic_stages {
          key "asic_stage_name";
          leaf asic_stage_name {
            type fabric-types:asic_stage_type;
          }
          list location {
            key "loc_str";
            leaf loc_str {
              type fabric-types:asic_location_zermatt_type;
            }
            uses asic_status_show;
            container brief {
              uses asic_status_show;
            }
            container detail {
              uses asic_status_show;
            }
          }
          uses asic_status_show;
          container brief {
            uses asic_status_show;
          }
          container detail {
            uses asic_status_show;
          }
        }
      }
    }
    container fsdb_pla {
      description
        "plane availability status option";
      list rack {
        key "rack_number";
        description
          "Rack";
        leaf rack_number {
          type int32;
        }
        list asic_stages {
          key "asic_stage_idx";
          leaf asic_stage_idx {
            type fabric-types:sfe_stage_type;
          }
          leaf asic_stage_name {
            type fabric-types:sfe_stage_type;
          }
          leaf rack_number {
            type string;
          }
          leaf plane_number {
            type int32;
          }
          leaf plane_id {
            type int32;
          }
          list fabids {
            key "idx";
            leaf idx {
              type int32;
            }
            leaf fabid_address {
              type string;
            }
            leaf plane_num {
              type int32;
            }
            leaf plane_0_mask {
              type string;
            }
            leaf plane_1_mask {
              type string;
            }
            leaf plane_2_mask {
              type string;
            }
            leaf plane_3_mask {
              type string;
            }
            leaf plane_4_mask {
              type string;
            }
            leaf plane_5_mask {
              type string;
            }
            leaf min_links_per_asic {
              type int32;
            }
            leaf max_links_per_asic {
              type int32;
            }
            leaf total_links {
              type int32;
            }
            leaf min_up_links_per_asic {
              type int32;
            }
            leaf max_up_links_per_asic {
              type int32;
            }
            leaf total_up_links {
              type int32;
            }
          }
          list down_fabids {
            key "idx";
            leaf idx {
              type int32;
            }
            leaf fabid_address {
              type string;
            }
            leaf fabid_status {
              type string;
            }
          }
          list destination {
            key "amba_id";
            leaf amba_id {
              type fabric-types:fabric_fabid_type;
            }
            uses fsdb_pla_reachability_show;
          }
        }
      }
    }
    uses fsdb_svr_trace;
  }
}

module Cisco-IOS-XR-install-act {
  // Generated by yanger -t ncs
  tailf:mount-id "cisco-iosxr-nc-7.3:cisco-iosxr-nc-7.3";
  tailf:ncs-device-type "netconf";

  namespace "http://cisco.com/ns/yang/Cisco-IOS-XR-install-act";
  prefix install-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR install actions.

     Copyright (c) 2018-2020 by Cisco Systems, Inc.
     All rights reserved.";

  revision 2019-12-10 {
    description
      "Addition of install-mode-type enum, deprecation of update-all leaf, and
       addition of tar to packages-source-type";
    semver:module-version "1.2.0";
  }
  revision 2019-11-05 {
    description
      "Addition of INST-SHARED-OP-ID-TYPE for the return type of action RPCs";
    semver:module-version "1.1.0";
  }
  revision 2019-10-03 {
    description
      "Addition of apply type enumeration and option for replace/source commands
       2019-10-01
       Made changes to be RFC6087 compliant";
    semver:module-version "1.1.0";
  }
  revision 2019-04-05 {
    description
      "Establish semantic version baseline.";
    semver:module-version "1.0.0";
  }
  revision 2018-10-05 {
    description
      "IOS XR 7.0.1 revision.";
  }

  typedef ncs_template_replace-source-type {
    type string;
    description
      "replace source type";
  }

  typedef ncs_template_packages-source-type {
    type string;
    description
      "packages source type";
  }

  typedef ncs_template_config-type {
    type string;
    description
      "config type";
  }

  typedef ncs_template_apply-type {
    type string;
    description
      "apply type";
  }

  typedef ncs_template_install-mode-type {
    type string;
  }

  typedef ncs_rpc_notif_replace-source-type {
    type enumeration {
      enum "local" {
        description
          "Install from a local file path";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
    }
    description
      "replace source type";
  }

  typedef ncs_rpc_notif_packages-source-type {
    type enumeration {
      enum "local" {
        description
          "Install from a local directory or repository containing RPMs and/or
           tar files";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
      enum "any-configured-repository" {
        description
          "Install from any configured repository";
      }
      enum "configured-repository" {
        description
          "Install from the given repository";
      }
      enum "tar" {
        description
          "Install from a local tar file";
      }
    }
    description
      "packages source type";
  }

  typedef ncs_rpc_notif_config-type {
    type enumeration {
      enum "ignore" {
        description
          "Ignore the configuration in the given ISO";
      }
      enum "merge" {
        description
          "Merge the configuration in the given ISO with existing
           configuration";
      }
      enum "replace" {
        description
          "Replace the existing configuration with the configuration
           in the given ISO";
      }
    }
    description
      "config type";
  }

  typedef ncs_rpc_notif_apply-type {
    type enumeration {
      enum "restart" {
        description
          "Apply atomic change by restarting processes - only valid
           for the augmented 'install-apply' operation";
      }
      enum "reload" {
        description
          "Apply atomic change by reloading";
      }
      enum "least-impactful" {
        description
          "Apply atomic change by least impactful method";
      }
    }
    description
      "apply type";
  }

  typedef ncs_rpc_notif_install-mode-type {
    type enumeration {
      enum "specified-packages" {
        description
          "Add the specified packages";
      }
      enum "upgrade-all" {
        description
          "Upgrade all packages that have a higher version available";
      }
      enum "install-all" {
        description
          "Install the highest compatible version of all packages
           from a specified source";
      }
    }
  }

  typedef live_ncs_replace-source-type {
    type enumeration {
      enum "local" {
        description
          "Install from a local file path";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
    }
    description
      "replace source type";
  }

  typedef live_ncs_packages-source-type {
    type enumeration {
      enum "local" {
        description
          "Install from a local directory or repository containing RPMs and/or
           tar files";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
      enum "any-configured-repository" {
        description
          "Install from any configured repository";
      }
      enum "configured-repository" {
        description
          "Install from the given repository";
      }
      enum "tar" {
        description
          "Install from a local tar file";
      }
    }
    description
      "packages source type";
  }

  typedef live_ncs_config-type {
    type enumeration {
      enum "ignore" {
        description
          "Ignore the configuration in the given ISO";
      }
      enum "merge" {
        description
          "Merge the configuration in the given ISO with existing
           configuration";
      }
      enum "replace" {
        description
          "Replace the existing configuration with the configuration
           in the given ISO";
      }
    }
    description
      "config type";
  }

  typedef live_ncs_apply-type {
    type enumeration {
      enum "restart" {
        description
          "Apply atomic change by restarting processes - only valid
           for the augmented 'install-apply' operation";
      }
      enum "reload" {
        description
          "Apply atomic change by reloading";
      }
      enum "least-impactful" {
        description
          "Apply atomic change by least impactful method";
      }
    }
    description
      "apply type";
  }

  typedef live_ncs_install-mode-type {
    type enumeration {
      enum "specified-packages" {
        description
          "Add the specified packages";
      }
      enum "upgrade-all" {
        description
          "Upgrade all packages that have a higher version available";
      }
      enum "install-all" {
        description
          "Install the highest compatible version of all packages
           from a specified source";
      }
    }
  }

  typedef replace-source-type {
    type enumeration {
      enum "local" {
        description
          "Install from a local file path";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
    }
    description
      "replace source type";
  }

  typedef packages-source-type {
    type enumeration {
      enum "local" {
        description
          "Install from a local directory or repository containing RPMs and/or
           tar files";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
      enum "any-configured-repository" {
        description
          "Install from any configured repository";
      }
      enum "configured-repository" {
        description
          "Install from the given repository";
      }
      enum "tar" {
        description
          "Install from a local tar file";
      }
    }
    description
      "packages source type";
  }

  typedef config-type {
    type enumeration {
      enum "ignore" {
        description
          "Ignore the configuration in the given ISO";
      }
      enum "merge" {
        description
          "Merge the configuration in the given ISO with existing
           configuration";
      }
      enum "replace" {
        description
          "Replace the existing configuration with the configuration
           in the given ISO";
      }
    }
    description
      "config type";
  }

  typedef apply-type {
    type enumeration {
      enum "restart" {
        description
          "Apply atomic change by restarting processes - only valid
           for the augmented 'install-apply' operation";
      }
      enum "reload" {
        description
          "Apply atomic change by reloading";
      }
      enum "least-impactful" {
        description
          "Apply atomic change by least impactful method";
      }
    }
    description
      "apply type";
  }

  typedef install-mode-type {
    type enumeration {
      enum "specified-packages" {
        description
          "Add the specified packages";
      }
      enum "upgrade-all" {
        description
          "Upgrade all packages that have a higher version available";
      }
      enum "install-all" {
        description
          "Install the highest compatible version of all packages
           from a specified source";
      }
    }
  }

  grouping ncs_template_INST-SHARED-OP-ID-TYPE {
    leaf op-id {
      type string;
      description
        "operation id of the triggered action";
    }
    leaf Error {
      type string;
      description
        "error information";
    }
  }

  grouping ncs_rpc_notif_INST-SHARED-OP-ID-TYPE {
    leaf op-id {
      type string;
      description
        "operation id of the triggered action";
    }
    leaf Error {
      type string;
      description
        "error information";
    }
  }

  grouping live_ncs_INST-SHARED-OP-ID-TYPE {
    leaf op-id {
      type string;
      description
        "operation id of the triggered action";
    }
    leaf Error {
      type string;
      description
        "error information";
    }
  }

  grouping INST-SHARED-OP-ID-TYPE {
    leaf op-id {
      type string;
      description
        "operation id of the triggered action";
    }
    leaf Error {
      type string;
      description
        "error information";
    }
  }

  augment "/ncs:devices/ncs:device/ncs:rpc" {
    container rpc-install-commit {
      tailf:ncs-device-type "netconf";
      tailf:display-when "not(../../ncs:module) or ../../ncs:module[ncs:name='Cisco-IOS-XR-install-act']";
      tailf:action install-commit {
        tailf:actionpoint ncsproxy {
          tailf:internal;
        }
        description
          "Commit the current software, such that it will persist over reload.";
        output {
          uses ncs_rpc_notif_INST-SHARED-OP-ID-TYPE;
        }
        csc:xr-task "pkg-mgmt";
      }
    }
  }
  augment "/ncs:devices/ncs:device-group/ncs:ned-id/ncs:rpc" {
    container rpc-install-commit {
      tailf:ncs-device-type "netconf";
      tailf:display-when "/ncs:devices/ncs:device[ncs:name=current()/../../../ncs:member]/ncs:module[ncs:name='Cisco-IOS-XR-install-act']";
      tailf:action install-commit {
        tailf:actionpoint ncsproxy {
          tailf:internal;
        }
        description
          "Commit the current software, such that it will persist over reload.";
        output {
          container "device" {
            leaf "name" {
              type string;
            }
            leaf "info" {
              type string;
            }
            container "result" {
              uses ncs_rpc_notif_INST-SHARED-OP-ID-TYPE;
            }
          }
        }
        csc:xr-task "pkg-mgmt";
      }
    }
  }
  augment "/ncs:devices/ncs:device/ncs:rpc" {
    container rpc-install {
      tailf:ncs-device-type "netconf";
      tailf:display-when "not(../../ncs:module) or ../../ncs:module[ncs:name='Cisco-IOS-XR-install-act']";
      tailf:action install {
        tailf:actionpoint ncsproxy {
          tailf:internal;
        }
        description
          "Install packages from a given source";
        input {
          container packages {
            description
              "Set of packages to install. Should be set only when 'install-mode'
               is 'specified-packages'";
            leaf-list packagename {
              type string;
              description
                "package name";
            }
          }
          leaf update-all {
            type boolean;
            default "false";
            status deprecated;
            description
              "True to update all packages using the given source, False
               to only install or update the specified packages";
          }
          leaf source-type {
            type ncs_rpc_notif_packages-source-type;
            default "local";
            description
              "Type of source used to obtain the packages";
          }
          leaf source {
            type string;
            description
              "Path to the location of the packages.  If source-type is
               'any-configured-repository' this field is unused, and if
               source-type is 'configured-repository' this should be the
               name of the repository to use.";
          }
          leaf activation-type {
            type ncs_rpc_notif_apply-type;
            default "least-impactful";
            description
              "Activate the software using the specified apply type";
          }
          leaf install-mode {
            type ncs_rpc_notif_install-mode-type;
            default "specified-packages";
            description
              "Mode of install operation";
          }
        }
        output {
          uses ncs_rpc_notif_INST-SHARED-OP-ID-TYPE;
        }
        csc:xr-task "pkg-mgmt";
      }
    }
  }
  augment "/ncs:devices/ncs:device-group/ncs:ned-id/ncs:rpc" {
    container rpc-install {
      tailf:ncs-device-type "netconf";
      tailf:display-when "/ncs:devices/ncs:device[ncs:name=current()/../../../ncs:member]/ncs:module[ncs:name='Cisco-IOS-XR-install-act']";
      tailf:action install {
        tailf:actionpoint ncsproxy {
          tailf:internal;
        }
        description
          "Install packages from a given source";
        input {
          container packages {
            description
              "Set of packages to install. Should be set only when 'install-mode'
               is 'specified-packages'";
            leaf-list packagename {
              type string;
              description
                "package name";
            }
          }
          leaf update-all {
            type boolean;
            default "false";
            status deprecated;
            description
              "True to update all packages using the given source, False
               to only install or update the specified packages";
          }
          leaf source-type {
            type ncs_rpc_notif_packages-source-type;
            default "local";
            description
              "Type of source used to obtain the packages";
          }
          leaf source {
            type string;
            description
              "Path to the location of the packages.  If source-type is
               'any-configured-repository' this field is unused, and if
               source-type is 'configured-repository' this should be the
               name of the repository to use.";
          }
          leaf activation-type {
            type ncs_rpc_notif_apply-type;
            default "least-impactful";
            description
              "Activate the software using the specified apply type";
          }
          leaf install-mode {
            type ncs_rpc_notif_install-mode-type;
            default "specified-packages";
            description
              "Mode of install operation";
          }
        }
        output {
          container "device" {
            leaf "name" {
              type string;
            }
            leaf "info" {
              type string;
            }
            container "result" {
              uses ncs_rpc_notif_INST-SHARED-OP-ID-TYPE;
            }
          }
        }
        csc:xr-task "pkg-mgmt";
      }
    }
  }
  augment "/ncs:devices/ncs:device/ncs:rpc" {
    container rpc-install-replace {
      tailf:ncs-device-type "netconf";
      tailf:display-when "not(../../ncs:module) or ../../ncs:module[ncs:name='Cisco-IOS-XR-install-act']";
      tailf:action install-replace {
        tailf:actionpoint ncsproxy {
          tailf:internal;
        }
        description
          "Replace the existing software with that from the given ISO";
        input {
          leaf source-type {
            type ncs_rpc_notif_replace-source-type;
            default "local";
            description
              "Type of source used to obtain the ISO";
          }
          leaf source {
            type string;
            mandatory true;
            description
              "Path to the location of the ISO";
          }
          leaf file {
            type string;
            mandatory true;
            description
              "Name of the ISO to install";
          }
          leaf commit {
            type boolean;
            default "false";
            description
              "Commit at the end of the replace operation, if the
               software is successfully applied";
          }
          leaf config {
            type ncs_rpc_notif_config-type;
            default "ignore";
            description
              "Action to take on any configuration present in the ISO";
          }
          leaf activation-type {
            type ncs_rpc_notif_apply-type;
            default "least-impactful";
            description
              "Activate the software using the specified apply type";
          }
        }
        output {
          uses ncs_rpc_notif_INST-SHARED-OP-ID-TYPE;
        }
        csc:xr-task "pkg-mgmt";
      }
    }
  }
  augment "/ncs:devices/ncs:device-group/ncs:ned-id/ncs:rpc" {
    container rpc-install-replace {
      tailf:ncs-device-type "netconf";
      tailf:display-when "/ncs:devices/ncs:device[ncs:name=current()/../../../ncs:member]/ncs:module[ncs:name='Cisco-IOS-XR-install-act']";
      tailf:action install-replace {
        tailf:actionpoint ncsproxy {
          tailf:internal;
        }
        description
          "Replace the existing software with that from the given ISO";
        input {
          leaf source-type {
            type ncs_rpc_notif_replace-source-type;
            default "local";
            description
              "Type of source used to obtain the ISO";
          }
          leaf source {
            type string;
            mandatory true;
            description
              "Path to the location of the ISO";
          }
          leaf file {
            type string;
            mandatory true;
            description
              "Name of the ISO to install";
          }
          leaf commit {
            type boolean;
            default "false";
            description
              "Commit at the end of the replace operation, if the
               software is successfully applied";
          }
          leaf config {
            type ncs_rpc_notif_config-type;
            default "ignore";
            description
              "Action to take on any configuration present in the ISO";
          }
          leaf activation-type {
            type ncs_rpc_notif_apply-type;
            default "least-impactful";
            description
              "Activate the software using the specified apply type";
          }
        }
        output {
          container "device" {
            leaf "name" {
              type string;
            }
            leaf "info" {
              type string;
            }
            container "result" {
              uses ncs_rpc_notif_INST-SHARED-OP-ID-TYPE;
            }
          }
        }
        csc:xr-task "pkg-mgmt";
      }
    }
  }
}

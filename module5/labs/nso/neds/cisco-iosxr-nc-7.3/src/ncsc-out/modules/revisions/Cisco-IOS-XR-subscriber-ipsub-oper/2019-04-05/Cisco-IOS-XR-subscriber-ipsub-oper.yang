module Cisco-IOS-XR-subscriber-ipsub-oper {
  // Generated by yanger -t ncs
  tailf:mount-id "cisco-iosxr-nc-7.3:cisco-iosxr-nc-7.3";
  tailf:ncs-device-type "netconf";

  namespace "http://cisco.com/ns/yang/Cisco-IOS-XR-subscriber-ipsub-oper";
  prefix subscriber-ipsub-oper;

  import Cisco-IOS-XR-types {
    prefix xr;
  }
  import cisco-semver {
    prefix semver;
  }
  include Cisco-IOS-XR-subscriber-ipsub-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-ipsub package operational data.

     This module contains definitions
     for the following management objects:
       ip-subscriber: IP subscriber operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container 'ip-subscriber'
  }
  augment "/ncs:devices/ncs:device/ncs:live-status" {
    container ip-subscriber {
      tailf:ncs-device-type "netconf";
      tailf:display-when "not(../../ncs:module) or ../../ncs:module[ncs:name='Cisco-IOS-XR-subscriber-ipsub-oper'] or (../../ncs:live-status-protocol[not(ncs:capability)]) or (../../ncs:live-status-protocol/ncs:capability/ncs:module[.='Cisco-IOS-XR-subscriber-ipsub-oper'])";
      description
        "IP subscriber operational data";
      container nodes {
        description
          "IP subscriber operational data for a particular
           location";
        list node {
          key "node-name";
          description
            "Location. For eg., 0/1/CPU0";
          container summary {
            description
              "IP subscriber interface summary";
            uses live_ncs_IPSUB-MA-INTF-SUMMARY-DATA;
          }
          container interfaces {
            description
              "IP subscriber interface table";
            list interface {
              key "interface-name";
              description
                "IP subscriber interface entry";
              leaf interface-name {
                type xr:live_ncs_Interface-name;
                description
                  "Interface name";
              }
              uses live_ncs_IPSUB-MA-INTF-DATA;
            }
          }
          container access-interfaces {
            description
              "IP subscriber access interface table";
            list access-interface {
              key "interface-name";
              description
                "IP subscriber access interface entry";
              leaf interface-name {
                type xr:live_ncs_Interface-name;
                description
                  "Interface name";
              }
              uses live_ncs_IPSUB-MA-PARENT-INTF-DATA;
            }
          }
          leaf node-name {
            type xr:live_ncs_Node-id;
            description
              "The node ID to filter on. For eg., 0/1/CPU0";
          }
        }
      }
    }
  }
  augment "/ncs:devices/ncs:template/ncs:ned-id/ncs:config" {
    // NCS drop config false container 'ip-subscriber'
  }
}

module Cisco-IOS-XR-ikev2-oper {
  // Generated by yanger -t ncs
  tailf:mount-id "cisco-iosxr-nc-7.3:cisco-iosxr-nc-7.3";
  tailf:ncs-device-type "netconf";

  namespace "http://cisco.com/ns/yang/Cisco-IOS-XR-ikev2-oper";
  prefix ikev2-oper;

  import ietf-inet-types {
    prefix inet;
  }
  import Cisco-IOS-XR-types {
    prefix xr;
  }
  import cisco-semver {
    prefix semver;
  }
  include Cisco-IOS-XR-ikev2-oper-sub1 {
    revision-date 2019-09-27;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ikev2 package operational data.

     This module contains definitions
     for the following management objects:
       ikev2: IKEv2 operational data

     Copyright (c) 2013-2019 by Cisco Systems, Inc.
     All rights reserved.";

  revision 2019-09-27 {
    description
      "Certificate Authentication Support";
    semver:module-version "1.1.0";
  }
  revision 2019-04-05 {
    description
      "Establish semantic version baseline.";
    semver:module-version "1.0.1";
  }
  revision 2018-12-20 {
    description
      "Operational Yang Support";
  }
  revision 2015-11-09 {
    description
      "IOS XR 6.0 revision.";
  }

  grouping ncs_template_IP {
    description
      "Common node of local-v4, remote-v4";
    list ip {
      // NCS patched for predictable order
      ordered-by user;
      key "address";
      description
        "IKEv2 SA data based on address";
      leaf address {
        type string;
        description
          "Address";
      }
      uses ncs_template_IKEV2-EDM-SA-DB;
    }
  }

  grouping ncs_rpc_notif_IP {
    description
      "Common node of local-v4, remote-v4";
    list ip {
      key "address";
      description
        "IKEv2 SA data based on address";
      leaf address {
        type inet:ipv4-address-no-zone;
        description
          "Address";
      }
      uses ncs_rpc_notif_IKEV2-EDM-SA-DB;
    }
  }

  grouping live_ncs_IP {
    description
      "Common node of local-v4, remote-v4";
    list ip {
      key "address";
      description
        "IKEv2 SA data based on address";
      leaf address {
        type inet:ipv4-address-no-zone;
        description
          "Address";
      }
      uses live_ncs_IKEV2-EDM-SA-DB;
    }
  }

  grouping IP {
    description
      "Common node of local-v4, remote-v4";
    list ip {
      key "address";
      description
        "IKEv2 SA data based on address";
      leaf address {
        type inet:ipv4-address-no-zone;
        description
          "Address";
      }
      uses IKEV2-EDM-SA-DB;
    }
  }

  augment "/ncs:devices/ncs:device/ncs:config" {
    // NCS drop config false container ikev2
  }
  augment "/ncs:devices/ncs:device/ncs:live-status" {
    container ikev2 {
      tailf:ncs-device-type "netconf";
      tailf:display-when "not(../../ncs:module) or ../../ncs:module[ncs:name='Cisco-IOS-XR-ikev2-oper'] or (../../ncs:live-status-protocol[not(ncs:capability)]) or (../../ncs:live-status-protocol/ncs:capability/ncs:module[.='Cisco-IOS-XR-ikev2-oper'])";
      description
        "IKEv2 operational data";
      container nodes {
        description
          "Per node IKEv2 operational data";
        list node {
          key "node-name";
          description
            "IKEv2 operational data for a particular node";
          container session-ids {
            description
              "IKEv2 Session data";
            list session-id {
              key "id";
              description
                "IKEv2 Session data";
              leaf id {
                type uint32 {
                  range "1..65535";
                }
                description
                  "Session Id";
              }
              uses live_ncs_IKEV2-EDM-SESSION;
            }
          }
          container stats {
            description
              "IKEv2 Stats data";
            uses live_ncs_IKEV2-EDM-STATS;
          }
          container sa {
            description
              "IKEv2 SA data";
            container local-v4 {
              description
                "IKEv2 SA lookup on local IP";
              uses live_ncs_IP;
            }
            container remote-v4 {
              description
                "IKEv2 SA lookup on remote IP";
              uses live_ncs_IP;
            }
            container all {
              description
                "IKEv2 SA all data";
              uses live_ncs_IKEV2-EDM-SA-DB;
            }
          }
          container summary {
            description
              "IKEv2 Summary data";
            uses live_ncs_IKEV2-EDM-SUMMARY;
          }
          container policies {
            description
              "IKEv2 policies on this node";
            list policy {
              key "name";
              description
                "IKEv2 policy data";
              leaf name {
                type xr:live_ncs_Cisco-ios-xr-string;
                description
                  "Name of the IKEv2 policy";
              }
              uses live_ncs_IKEV2-EDM-POLICY;
            }
          }
          container proposals {
            description
              "IKEv2 proposals on this node";
            list proposal {
              key "name";
              description
                "IKEv2 proposal data";
              leaf name {
                type xr:live_ncs_Cisco-ios-xr-string;
                description
                  "Name of the IKEv2 proposal";
              }
              uses live_ncs_IKEV2-EDM-PROPOSAL;
            }
          }
          container profiles {
            description
              "IKEv2 profiles on this node";
            list profile {
              key "name";
              description
                "IKEv2 profile data";
              leaf name {
                type xr:live_ncs_Cisco-ios-xr-string;
                description
                  "Name of the IKEv2 profile";
              }
              uses live_ncs_IKEV2-EDM-PROFILE;
            }
          }
          leaf node-name {
            type xr:live_ncs_Node-id;
            description
              "The identifier for the node";
          }
        }
      }
    }
  }
  augment "/ncs:devices/ncs:template/ncs:ned-id/ncs:config" {
    // NCS drop config false container ikev2
  }
}

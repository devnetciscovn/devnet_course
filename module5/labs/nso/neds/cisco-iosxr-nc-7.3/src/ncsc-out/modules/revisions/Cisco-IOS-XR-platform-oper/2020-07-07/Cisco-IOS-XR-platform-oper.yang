module Cisco-IOS-XR-platform-oper {
  // Generated by yanger -t ncs
  tailf:mount-id "cisco-iosxr-nc-7.3:cisco-iosxr-nc-7.3";
  tailf:ncs-device-type "netconf";

  namespace "http://cisco.com/ns/yang/Cisco-IOS-XR-platform-oper";
  prefix platform-oper;

  import Cisco-IOS-XR-types {
    prefix xr;
  }
  import cisco-semver {
    prefix semver;
  }
  include Cisco-IOS-XR-platform-oper-sub1 {
    revision-date 2020-07-07;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platform package operational data.

     This module contains definitions
     for the following management objects:
       platform: Platform information

     Copyright (c) 2013-2020 by Cisco Systems, Inc.
     All rights reserved.";

  revision 2020-07-07 {
    description
      "Added VM class for Thin XR model";
    semver:module-version "2.0.0";
  }
  revision 2020-05-14 {
    description
      "New model, replaces Cisco-IOS-XR-plat-chas-invmgr-ng-oper";
  }
  revision 2019-04-05 {
    description
      "Establish semantic version baseline.";
  }
  revision 2015-11-09 {
    description
      "IOS XR 6.0 revision.";
  }

  grouping ncs_template_STATE {
    description
      "Common node of instance, slot";
    container state {
      description
        "State information";
      uses ncs_template_PLATFORM-INFO;
    }
  }

  grouping ncs_template_SLOT-TABLE {
    description
      "Common node of rack, rack";
    container slots {
      description
        "Table of slots";
      list slot {
        // NCS patched for predictable order
        ordered-by user;
        key "slot-name";
        description
          "Slot name";
        container instances {
          description
            "Table of Instances";
          list instance {
            // NCS patched for predictable order
            ordered-by user;
            key "instance-name";
            description
              "Instance name";
            leaf instance-name {
              type string;
              description
                "Instance name";
            }
            uses ncs_template_STATE;
          }
        }
        container vm {
          description
            "VM information";
          uses ncs_template_VM-INFO;
        }
        leaf slot-name {
          type xr:ncs_template_Cisco-ios-xr-string;
          description
            "Slot name";
        }
        uses ncs_template_STATE;
      }
    }
  }

  grouping ncs_rpc_notif_STATE {
    description
      "Common node of instance, slot";
    container state {
      description
        "State information";
      uses ncs_rpc_notif_PLATFORM-INFO;
    }
  }

  grouping ncs_rpc_notif_SLOT-TABLE {
    description
      "Common node of rack, rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses ncs_rpc_notif_STATE;
          }
        }
        container vm {
          description
            "VM information";
          uses ncs_rpc_notif_VM-INFO;
        }
        leaf slot-name {
          type xr:ncs_rpc_notif_Cisco-ios-xr-string;
          description
            "Slot name";
        }
        uses ncs_rpc_notif_STATE;
      }
    }
  }

  grouping live_ncs_STATE {
    description
      "Common node of instance, slot";
    container state {
      description
        "State information";
      uses live_ncs_PLATFORM-INFO;
    }
  }

  grouping live_ncs_SLOT-TABLE {
    description
      "Common node of rack, rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses live_ncs_STATE;
          }
        }
        container vm {
          description
            "VM information";
          uses live_ncs_VM-INFO;
        }
        leaf slot-name {
          type xr:live_ncs_Cisco-ios-xr-string;
          description
            "Slot name";
        }
        uses live_ncs_STATE;
      }
    }
  }

  grouping STATE {
    description
      "Common node of instance, slot";
    container state {
      description
        "State information";
      uses PLATFORM-INFO;
    }
  }

  grouping SLOT-TABLE {
    description
      "Common node of rack, rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses STATE;
          }
        }
        container vm {
          description
            "VM information";
          uses VM-INFO;
        }
        leaf slot-name {
          type xr:Cisco-ios-xr-string;
          description
            "Slot name";
        }
        uses STATE;
      }
    }
  }

  augment "/ncs:devices/ncs:device/ncs:config" {
    // NCS drop config false container platform
  }
  augment "/ncs:devices/ncs:device/ncs:live-status" {
    container platform {
      tailf:ncs-device-type "netconf";
      tailf:display-when "not(../../ncs:module) or ../../ncs:module[ncs:name='Cisco-IOS-XR-platform-oper'] or (../../ncs:live-status-protocol[not(ncs:capability)]) or (../../ncs:live-status-protocol/ncs:capability/ncs:module[.='Cisco-IOS-XR-platform-oper'])";
      description
        "Platform information";
      container racks {
        description
          "Table of racks";
        list rack {
          key "rack-name";
          description
            "Rack name";
          leaf rack-name {
            type xr:live_ncs_Cisco-ios-xr-string;
            description
              "Rack name";
          }
          uses live_ncs_SLOT-TABLE;
        }
      }
    }
  }
  augment "/ncs:devices/ncs:template/ncs:ned-id/ncs:config" {
    // NCS drop config false container platform
  }
}

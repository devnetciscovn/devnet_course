module Cisco-IOS-XR-sysadmin-sm {
  // Generated by yanger -t ncs
  tailf:mount-id "cisco-iosxr-nc-7.3:cisco-iosxr-nc-7.3";
  tailf:ncs-device-type "netconf";

  namespace "http://www.cisco.com/ns/yang/Cisco-IOS-XR-sysadmin-sm";
  prefix shelf_sm;

  import tailf-common {
    prefix tailf;
  }
  import ietf-yang-types {
    prefix ietf;
  }
  import ietf-inet-types {
    prefix inet;
  }
  import Cisco-IOS-XR-sysadmin-types {
    prefix calvados;
  }
  import Cisco-IOS-XR-sysadmin-show-trace {
    prefix show_trace;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module holds Shelf Management configuration data.

     Copyright (c) 2011-2020 by Cisco Systems, Inc.
     All rights reserved.";

  revision 2020-09-01 {
    description
      "Moved cluster oper command to shared_pkg";
    semver:module-version "2.0.0";
  }
  revision 2019-04-15 {
    description
      "Establish semantic version baseline.";
    semver:module-version "1.0.0";
  }
  revision 2018-04-09 {
    description
      "Required changes for ConfD 6.4.5";
  }
  revision 2017-07-22 {
    description
      "Updated chassis rack number pattern to include Compute Racks";
  }
  revision 2017-04-12 {
    description
      "Changed namespace and module name";
  }
  revision 2016-10-12 {
    description
      "Unhide commands and configs. Moved to advanced-grp";
  }
  revision 2012-01-05 {
    description
      "show platform [detail] [location L] support";
  }
  revision 2011-11-08 {
    description
      "Initial revision";
  }

  grouping ncs_template_sm-oper-group {
    // NCS drop config false container oper
  }

  grouping ncs_template_ctrace-oper-group {
    container shelf_mgr {
      uses show_trace:ncs_template_traceable;
    }
  }

  grouping ncs_template_platform-oper-group {
    // NCS drop config false container platform
  }

  grouping ncs_template_chassis-oper-group {
    // NCS drop config false container chassis
  }

  grouping ncs_template_reload-rack-oper-group {
    // NCS drop config false container reload
  }

  grouping ncs_template_reload-vm-oper-group {
    // NCS drop config false container reload_vm
  }

  grouping ncs_template_reboot-history-events-oper-group {
    list events {
      // NCS patched for predictable order
      ordered-by user;
      key "event_idx";
      leaf event_idx {
        type string;
      }
      container event {
        leaf timestamp {
          type string;
        }
        leaf reason_code {
          type string;
        }
        leaf reason {
          type string;
        }
        leaf src_loc {
          type string;
        }
        leaf src_name {
          type string;
        }
      }
    }
  }

  grouping ncs_template_reboot-pending-events-oper-group {
    list delay_events {
      // NCS patched for predictable order
      ordered-by user;
      key "delay_event_idx";
      leaf delay_event_idx {
        type string;
      }
      container delay_event {
        leaf active {
          type string;
        }
        leaf wait {
          type string;
        }
        leaf when {
          type string;
        }
        leaf reason {
          type string;
        }
        leaf count {
          type string;
        }
      }
    }
  }

  grouping ncs_template_reboot-history-card-oper-group {
    container card {
      list location {
        // NCS patched for predictable order
        ordered-by user;
        key "location";
        leaf location {
          type calvados:ncs_template_location-id;
        }
        uses ncs_template_reboot-history-events-oper-group;
      }
    }
  }

  grouping ncs_template_reboot-history-admin-vm-oper-group {
    container admin-vm {
      list location {
        // NCS patched for predictable order
        ordered-by user;
        key "location";
        leaf location {
          type calvados:ncs_template_location-id;
        }
        uses ncs_template_reboot-history-events-oper-group;
      }
    }
  }

  grouping ncs_template_reboot-history-reverse-oper-group {
    container reverse {
      uses ncs_template_reboot-history-card-oper-group;
      uses ncs_template_reboot-history-admin-vm-oper-group;
    }
  }

  grouping ncs_template_reboot-pending-card-oper-group {
    container card {
      list location {
        // NCS patched for predictable order
        ordered-by user;
        key "location";
        leaf location {
          type calvados:ncs_template_location-id;
        }
        uses ncs_template_reboot-pending-events-oper-group;
      }
    }
  }

  grouping ncs_template_reboot-history-oper-group {
    // NCS drop config false container 'reboot-history'
  }

  grouping ncs_template_reboot-pending-oper-group {
    // NCS drop config false container 'reboot-pending'
  }

  grouping ncs_template_mgmt-interfaces-oper-group {
    list interface {
      // NCS patched for predictable order
      ordered-by user;
      key "ifname";
      leaf ifname {
        type string;
      }
      container interface-data {
        leaf mac {
          type string;
        }
        leaf ipv4 {
          type string;
        }
        leaf flagstr {
          type string;
        }
        leaf port_status {
          type string;
        }
        leaf mtu {
          type string;
        }
        leaf metric {
          type string;
        }
        leaf rx_pak {
          type string;
        }
        leaf rx_errors {
          type string;
        }
        leaf rx_dropped {
          type string;
        }
        leaf rx_overruns {
          type string;
        }
        leaf rx_frame {
          type string;
        }
        leaf tx_pak {
          type string;
        }
        leaf tx_errors {
          type string;
        }
        leaf tx_dropped {
          type string;
        }
        leaf tx_overruns {
          type string;
        }
        leaf tx_carrier {
          type string;
        }
        leaf collisions {
          type string;
        }
        leaf tx_queuelen {
          type string;
        }
        leaf rx_bytes {
          type string;
        }
        leaf tx_bytes {
          type string;
        }
        leaf intf_num {
          type string;
        }
      }
    }
  }

  grouping ncs_template_mac-pool-oper-group {
    // NCS drop config false container macpool
  }

  grouping ncs_template_platform-summary-oper-group {
    container summary {
      list location {
        // NCS patched for predictable order
        ordered-by user;
        key "location";
        leaf location {
          type calvados:ncs_template_location-id;
        }
        container summary-data {
          leaf card_type {
            type string;
          }
          leaf hw_state {
            type string;
          }
          leaf sw_state {
            type string;
          }
          leaf config_state {
            type string;
          }
        }
      }
    }
  }

  grouping ncs_template_platform-detail-oper-group {
    container detail {
      list location {
        // NCS patched for predictable order
        ordered-by user;
        key "location";
        leaf location {
          type calvados:ncs_template_location-id;
        }
        container detail-data {
          leaf pid {
            type string;
          }
          leaf description {
            type string;
          }
          leaf vid_sn {
            type string;
          }
          leaf hw_state {
            type string;
          }
          leaf sw_state {
            type string;
          }
          leaf config_wordy {
            type string;
          }
          leaf hw_ver {
            type string;
          }
          leaf last_event {
            type string;
          }
          leaf last_ev_reason_str {
            type string;
          }
        }
      }
    }
  }

  grouping ncs_template_platform-slices-oper-group {
    container slices {
      list location {
        // NCS patched for predictable order
        ordered-by user;
        key "location";
        leaf location {
          type calvados:ncs_template_location-id;
        }
        list slice_values {
          // NCS patched for predictable order
          ordered-by user;
          key "slice_idx";
          leaf slice_idx {
            type string;
          }
          container slice {
            leaf slice_num {
              type string;
            }
            leaf admin_state {
              type string;
            }
            leaf oper_state {
              type string;
            }
          }
        }
      }
    }
  }

  grouping ncs_template_chassis-brief-oper-group {
    container brief {
      list chassis_serial {
        // NCS patched for predictable order
        ordered-by user;
        key "serial_number";
        leaf serial_number {
          type string;
        }
        container brief-data {
          leaf racknum {
            type string;
          }
          leaf rack_type {
            type string;
          }
          leaf rack_state {
            type string;
          }
          leaf data_plane {
            type string;
          }
          leaf ctrl_plane {
            type string;
          }
        }
      }
    }
  }

  grouping ncs_template_mac-pool-brief-oper-group {
    container brief {
      list rack {
        // NCS patched for predictable order
        ordered-by user;
        key "serial_number";
        leaf serial_number {
          type string;
        }
        container brief-data {
          leaf racknum {
            type string;
          }
          leaf mac_base {
            type string;
          }
          leaf mac_count {
            type string;
          }
          leaf is_selected {
            type string;
          }
          leaf allocated_count {
            type string;
          }
        }
      }
    }
  }

  grouping ncs_template_sm-config-group {
    container config {
      // NCS dropped explicit config true
      uses ncs_template_chassis-config-group;
      uses ncs_template_mgmt-interfaces-config-group;
      uses ncs_template_virtual-macaddr-config-group;
    }
  }

  grouping ncs_template_chassis-config-group {
    container chassis {
      list serial {
        // NCS patched for predictable order
        ordered-by user;
        key "serial";
        unique "rack";
        leaf serial {
          type string;
          // NCS drop mandatory statement
        }
        leaf rack {
          type string;
          // NCS drop mandatory statement
        }
      }
    }
  }

  grouping ncs_template_mgmt-interfaces-config-group {
    container interface {
      container MgmtEth {
        list locport {
          // NCS patched for predictable order
          ordered-by user;
          key "rack slot intf port";
          leaf rack {
            type string;
          }
          leaf slot {
            type string;
          }
          leaf intf {
            type string;
          }
          leaf port {
            type string;
          }
          container ipv4 {
            leaf address {
              type string;
            }
          }
          leaf shutdown {
            type empty;
          }
          leaf mtu {
            type string;
          }
          leaf default-gw {
            type string;
          }
          container arp {
            list ip {
              // NCS patched for predictable order
              ordered-by user;
              key "ip";
              leaf ip {
                type string;
                // NCS drop mandatory statement
              }
              leaf mac {
                type string;
                // NCS drop mandatory statement
              }
            }
          }
        }
      }
    }
    container domain {
      list name {
        // NCS patched for predictable order
        ordered-by user;
        key "name";
        leaf name {
          type string;
        }
      }
      list name-server {
        // NCS patched for predictable order
        ordered-by user;
        key "name-server";
        leaf name-server {
          type string;
        }
      }
    }
  }

  grouping ncs_template_virtual-macaddr-config-group {
    container virtual-macaddr-range {
      leaf base {
        type string;
      }
      leaf count {
        type string;
      }
    }
  }

  grouping ncs_template_sm-action-group {
    // NCS drop config false container actions
  }

  grouping ncs_template_reload-action-group;

  grouping ncs_rpc_notif_sm-oper-group {
    container oper {
      config false;
      uses ncs_rpc_notif_ctrace-oper-group;
      uses ncs_rpc_notif_platform-oper-group;
      uses ncs_rpc_notif_chassis-oper-group;
      uses ncs_rpc_notif_reload-rack-oper-group;
      uses ncs_rpc_notif_reboot-history-oper-group;
      uses ncs_rpc_notif_mgmt-interfaces-oper-group;
      uses ncs_rpc_notif_reload-vm-oper-group;
      uses ncs_rpc_notif_mac-pool-oper-group;
      uses ncs_rpc_notif_reboot-pending-oper-group;
    }
  }

  grouping ncs_rpc_notif_ctrace-oper-group {
    container shelf_mgr {
      uses show_trace:ncs_rpc_notif_traceable;
    }
  }

  grouping ncs_rpc_notif_platform-oper-group {
    container platform {
      config false;
      uses ncs_rpc_notif_platform-summary-oper-group;
      uses ncs_rpc_notif_platform-detail-oper-group;
      uses ncs_rpc_notif_platform-slices-oper-group;
    }
  }

  grouping ncs_rpc_notif_chassis-oper-group {
    container chassis {
      config false;
      uses ncs_rpc_notif_chassis-brief-oper-group;
    }
  }

  grouping ncs_rpc_notif_reload-rack-oper-group {
    container reload {
      config false;
      container rack {
        list racks {
          key "rack";
          leaf rack {
            type string;
          }
        }
      }
    }
  }

  grouping ncs_rpc_notif_reload-vm-oper-group {
    container reload_vm {
      config false;
      list location {
        key "location";
        leaf location {
          type string;
        }
      }
    }
  }

  grouping ncs_rpc_notif_reboot-history-events-oper-group {
    list events {
      key "event_idx";
      leaf event_idx {
        type uint32;
      }
      container event {
        leaf timestamp {
          type string;
        }
        leaf reason_code {
          type uint32;
        }
        leaf reason {
          type string;
        }
        leaf src_loc {
          type string;
        }
        leaf src_name {
          type string;
        }
      }
    }
  }

  grouping ncs_rpc_notif_reboot-pending-events-oper-group {
    list delay_events {
      key "delay_event_idx";
      leaf delay_event_idx {
        type uint32;
      }
      container delay_event {
        leaf active {
          type boolean;
        }
        leaf wait {
          type uint64;
        }
        leaf when {
          type uint64;
        }
        leaf reason {
          type string;
        }
        leaf count {
          type uint32;
        }
      }
    }
  }

  grouping ncs_rpc_notif_reboot-history-card-oper-group {
    container card {
      list location {
        key "location";
        leaf location {
          type calvados:ncs_rpc_notif_location-id;
        }
        uses ncs_rpc_notif_reboot-history-events-oper-group;
      }
    }
  }

  grouping ncs_rpc_notif_reboot-history-admin-vm-oper-group {
    container admin-vm {
      list location {
        key "location";
        leaf location {
          type calvados:ncs_rpc_notif_location-id;
        }
        uses ncs_rpc_notif_reboot-history-events-oper-group;
      }
    }
  }

  grouping ncs_rpc_notif_reboot-history-reverse-oper-group {
    container reverse {
      uses ncs_rpc_notif_reboot-history-card-oper-group;
      uses ncs_rpc_notif_reboot-history-admin-vm-oper-group;
    }
  }

  grouping ncs_rpc_notif_reboot-pending-card-oper-group {
    container card {
      list location {
        key "location";
        leaf location {
          type calvados:ncs_rpc_notif_location-id;
        }
        uses ncs_rpc_notif_reboot-pending-events-oper-group;
      }
    }
  }

  grouping ncs_rpc_notif_reboot-history-oper-group {
    container reboot-history {
      config false;
      uses ncs_rpc_notif_reboot-history-card-oper-group;
      uses ncs_rpc_notif_reboot-history-admin-vm-oper-group;
      uses ncs_rpc_notif_reboot-history-reverse-oper-group;
    }
  }

  grouping ncs_rpc_notif_reboot-pending-oper-group {
    container reboot-pending {
      config false;
      uses ncs_rpc_notif_reboot-pending-card-oper-group;
    }
  }

  grouping ncs_rpc_notif_mgmt-interfaces-oper-group {
    list interface {
      key "ifname";
      leaf ifname {
        type string;
      }
      container interface-data {
        leaf mac {
          type ietf:mac-address;
        }
        leaf ipv4 {
          type inet:ipv4-address;
        }
        leaf flagstr {
          type string;
        }
        leaf port_status {
          type string;
        }
        leaf mtu {
          type uint32;
        }
        leaf metric {
          type uint32;
        }
        leaf rx_pak {
          type uint32;
        }
        leaf rx_errors {
          type uint32;
        }
        leaf rx_dropped {
          type uint32;
        }
        leaf rx_overruns {
          type uint32;
        }
        leaf rx_frame {
          type uint32;
        }
        leaf tx_pak {
          type uint32;
        }
        leaf tx_errors {
          type uint32;
        }
        leaf tx_dropped {
          type uint32;
        }
        leaf tx_overruns {
          type uint32;
        }
        leaf tx_carrier {
          type uint32;
        }
        leaf collisions {
          type uint32;
        }
        leaf tx_queuelen {
          type uint32;
        }
        leaf rx_bytes {
          type uint64;
        }
        leaf tx_bytes {
          type uint64;
        }
        leaf intf_num {
          type uint32;
        }
      }
    }
  }

  grouping ncs_rpc_notif_mac-pool-oper-group {
    container macpool {
      config false;
      uses ncs_rpc_notif_mac-pool-brief-oper-group;
    }
  }

  grouping ncs_rpc_notif_platform-summary-oper-group {
    container summary {
      list location {
        key "location";
        leaf location {
          type calvados:ncs_rpc_notif_location-id;
        }
        container summary-data {
          leaf card_type {
            type string;
          }
          leaf hw_state {
            type string;
          }
          leaf sw_state {
            type string;
          }
          leaf config_state {
            type string;
          }
        }
      }
    }
  }

  grouping ncs_rpc_notif_platform-detail-oper-group {
    container detail {
      list location {
        key "location";
        leaf location {
          type calvados:ncs_rpc_notif_location-id;
        }
        container detail-data {
          leaf pid {
            type string;
          }
          leaf description {
            type string;
          }
          leaf vid_sn {
            type string;
          }
          leaf hw_state {
            type string;
          }
          leaf sw_state {
            type string;
          }
          leaf config_wordy {
            type string;
          }
          leaf hw_ver {
            type string;
          }
          leaf last_event {
            type string;
          }
          leaf last_ev_reason_str {
            type string;
          }
        }
      }
    }
  }

  grouping ncs_rpc_notif_platform-slices-oper-group {
    container slices {
      list location {
        key "location";
        leaf location {
          type calvados:ncs_rpc_notif_location-id;
        }
        list slice_values {
          key "slice_idx";
          leaf slice_idx {
            type uint32;
          }
          container slice {
            leaf slice_num {
              type uint32;
            }
            leaf admin_state {
              type string;
            }
            leaf oper_state {
              type string;
            }
          }
        }
      }
    }
  }

  grouping ncs_rpc_notif_chassis-brief-oper-group {
    container brief {
      list chassis_serial {
        key "serial_number";
        leaf serial_number {
          type string;
        }
        container brief-data {
          leaf racknum {
            type string;
          }
          leaf rack_type {
            type string;
          }
          leaf rack_state {
            type string;
          }
          leaf data_plane {
            type string;
          }
          leaf ctrl_plane {
            type string;
          }
        }
      }
    }
  }

  grouping ncs_rpc_notif_mac-pool-brief-oper-group {
    container brief {
      list rack {
        key "serial_number";
        leaf serial_number {
          type string;
        }
        container brief-data {
          leaf racknum {
            type string;
          }
          leaf mac_base {
            type ietf:mac-address;
          }
          leaf mac_count {
            type uint32;
          }
          leaf is_selected {
            type boolean;
          }
          leaf allocated_count {
            type uint32;
          }
        }
      }
    }
  }

  grouping ncs_rpc_notif_sm-config-group {
    container config {
      // NCS dropped explicit config true
      uses ncs_rpc_notif_chassis-config-group;
      uses ncs_rpc_notif_mgmt-interfaces-config-group;
      uses ncs_rpc_notif_virtual-macaddr-config-group;
    }
  }

  grouping ncs_rpc_notif_chassis-config-group {
    container chassis {
      list serial {
        key "serial";
        unique "rack";
        leaf serial {
          type string;
          mandatory true;
        }
        leaf rack {
          type string {
            pattern '[eE][0-3]|[bB][0-9]|[dD][0-1]|[fF][0-7]|[0-9]|[1][0-9]|[2-5][0-9]|[6][0-3]|[2][4][0-7]';
          }
          mandatory true;
        }
      }
    }
  }

  grouping ncs_rpc_notif_mgmt-interfaces-config-group {
    container interface {
      container MgmtEth {
        list locport {
          key "rack slot intf port";
          leaf rack {
            type string {
              pattern '[fF][0-7]|[0-9]|[1][0-5]|[bB][0-9]|[eE][0-3]';
            }
          }
          leaf slot {
            type string {
              pattern '[Rr][Pp][0-1]|[Rr][Ss][Pp][0-1]|[Ss][Cc][0-1]|[cC][bB][0-9]|[cC][eE][0-3]';
            }
          }
          leaf intf {
            type uint32 {
              range "0";
            }
          }
          leaf port {
            type uint32 {
              range "0";
            }
          }
          container ipv4 {
            leaf address {
              type string {
                pattern '(([0-9]|[1-9][0-9]|1[0-9][0-9]|2[0-4][0-9]|25[0-5])\.){3}([0-9]|[1-9][0-9]|1[0-9][0-9]|2[0-4][0-9]|25[0-5])(( (([0-9]|[1-9][0-9]|1[0-9][0-9]|2[0-4][0-9]|25[0-5])\.){3}([0-9]|[1-9][0-9]|1[0-9][0-9]|2[0-4][0-9]|25[0-5]))|(/([0-9]+)))';
              }
            }
          }
          leaf shutdown {
            type empty;
          }
          leaf mtu {
            type uint32 {
              range "48..9000";
            }
          }
          leaf default-gw {
            type inet:ipv4-address;
          }
          container arp {
            list ip {
              key "ip";
              leaf ip {
                type inet:ipv4-address;
                mandatory true;
              }
              leaf mac {
                type ietf:mac-address;
                mandatory true;
              }
            }
          }
        }
      }
    }
    container domain {
      list name {
        key "name";
        leaf name {
          type string;
        }
      }
      list name-server {
        key "name-server";
        leaf name-server {
          type inet:ipv4-address;
        }
      }
    }
  }

  grouping ncs_rpc_notif_virtual-macaddr-config-group {
    container virtual-macaddr-range {
      leaf base {
        type ietf:mac-address;
      }
      leaf count {
        type uint32 {
          range "1..65535";
        }
      }
    }
  }

  grouping ncs_rpc_notif_sm-action-group {
    container actions {
      config false;
      uses ncs_rpc_notif_reload-action-group;
    }
  }

  grouping ncs_rpc_notif_reload-action-group;

  grouping live_ncs_sm-oper-group {
    container oper {
      uses live_ncs_ctrace-oper-group;
      uses live_ncs_platform-oper-group;
      uses live_ncs_chassis-oper-group;
      uses live_ncs_reload-rack-oper-group;
      uses live_ncs_reboot-history-oper-group;
      uses live_ncs_mgmt-interfaces-oper-group;
      uses live_ncs_reload-vm-oper-group;
      uses live_ncs_mac-pool-oper-group;
      uses live_ncs_reboot-pending-oper-group;
    }
  }

  grouping live_ncs_ctrace-oper-group {
    container shelf_mgr {
      uses show_trace:live_ncs_traceable;
    }
  }

  grouping live_ncs_platform-oper-group {
    container platform {
      uses live_ncs_platform-summary-oper-group;
      uses live_ncs_platform-detail-oper-group;
      uses live_ncs_platform-slices-oper-group;
    }
  }

  grouping live_ncs_chassis-oper-group {
    container chassis {
      uses live_ncs_chassis-brief-oper-group;
    }
  }

  grouping live_ncs_reload-rack-oper-group {
    container reload {
      container rack {
        list racks {
          key "rack";
          leaf rack {
            type string;
          }
        }
      }
    }
  }

  grouping live_ncs_reload-vm-oper-group {
    container reload_vm {
      list location {
        key "location";
        leaf location {
          type string;
        }
      }
    }
  }

  grouping live_ncs_reboot-history-events-oper-group {
    list events {
      key "event_idx";
      leaf event_idx {
        type uint32;
      }
      container event {
        leaf timestamp {
          type string;
        }
        leaf reason_code {
          type uint32;
        }
        leaf reason {
          type string;
        }
        leaf src_loc {
          type string;
        }
        leaf src_name {
          type string;
        }
      }
    }
  }

  grouping live_ncs_reboot-pending-events-oper-group {
    list delay_events {
      key "delay_event_idx";
      leaf delay_event_idx {
        type uint32;
      }
      container delay_event {
        leaf active {
          type boolean;
        }
        leaf wait {
          type uint64;
        }
        leaf when {
          type uint64;
        }
        leaf reason {
          type string;
        }
        leaf count {
          type uint32;
        }
      }
    }
  }

  grouping live_ncs_reboot-history-card-oper-group {
    container card {
      list location {
        key "location";
        leaf location {
          type calvados:live_ncs_location-id;
        }
        uses live_ncs_reboot-history-events-oper-group;
      }
    }
  }

  grouping live_ncs_reboot-history-admin-vm-oper-group {
    container admin-vm {
      list location {
        key "location";
        leaf location {
          type calvados:live_ncs_location-id;
        }
        uses live_ncs_reboot-history-events-oper-group;
      }
    }
  }

  grouping live_ncs_reboot-history-reverse-oper-group {
    container reverse {
      uses live_ncs_reboot-history-card-oper-group;
      uses live_ncs_reboot-history-admin-vm-oper-group;
    }
  }

  grouping live_ncs_reboot-pending-card-oper-group {
    container card {
      list location {
        key "location";
        leaf location {
          type calvados:live_ncs_location-id;
        }
        uses live_ncs_reboot-pending-events-oper-group;
      }
    }
  }

  grouping live_ncs_reboot-history-oper-group {
    container reboot-history {
      uses live_ncs_reboot-history-card-oper-group;
      uses live_ncs_reboot-history-admin-vm-oper-group;
      uses live_ncs_reboot-history-reverse-oper-group;
    }
  }

  grouping live_ncs_reboot-pending-oper-group {
    container reboot-pending {
      uses live_ncs_reboot-pending-card-oper-group;
    }
  }

  grouping live_ncs_mgmt-interfaces-oper-group {
    list interface {
      key "ifname";
      leaf ifname {
        type string;
      }
      container interface-data {
        leaf mac {
          type ietf:mac-address;
        }
        leaf ipv4 {
          type inet:ipv4-address;
        }
        leaf flagstr {
          type string;
        }
        leaf port_status {
          type string;
        }
        leaf mtu {
          type uint32;
        }
        leaf metric {
          type uint32;
        }
        leaf rx_pak {
          type uint32;
        }
        leaf rx_errors {
          type uint32;
        }
        leaf rx_dropped {
          type uint32;
        }
        leaf rx_overruns {
          type uint32;
        }
        leaf rx_frame {
          type uint32;
        }
        leaf tx_pak {
          type uint32;
        }
        leaf tx_errors {
          type uint32;
        }
        leaf tx_dropped {
          type uint32;
        }
        leaf tx_overruns {
          type uint32;
        }
        leaf tx_carrier {
          type uint32;
        }
        leaf collisions {
          type uint32;
        }
        leaf tx_queuelen {
          type uint32;
        }
        leaf rx_bytes {
          type uint64;
        }
        leaf tx_bytes {
          type uint64;
        }
        leaf intf_num {
          type uint32;
        }
      }
    }
  }

  grouping live_ncs_mac-pool-oper-group {
    container macpool {
      uses live_ncs_mac-pool-brief-oper-group;
    }
  }

  grouping live_ncs_platform-summary-oper-group {
    container summary {
      list location {
        key "location";
        leaf location {
          type calvados:live_ncs_location-id;
        }
        container summary-data {
          leaf card_type {
            type string;
          }
          leaf hw_state {
            type string;
          }
          leaf sw_state {
            type string;
          }
          leaf config_state {
            type string;
          }
        }
      }
    }
  }

  grouping live_ncs_platform-detail-oper-group {
    container detail {
      list location {
        key "location";
        leaf location {
          type calvados:live_ncs_location-id;
        }
        container detail-data {
          leaf pid {
            type string;
          }
          leaf description {
            type string;
          }
          leaf vid_sn {
            type string;
          }
          leaf hw_state {
            type string;
          }
          leaf sw_state {
            type string;
          }
          leaf config_wordy {
            type string;
          }
          leaf hw_ver {
            type string;
          }
          leaf last_event {
            type string;
          }
          leaf last_ev_reason_str {
            type string;
          }
        }
      }
    }
  }

  grouping live_ncs_platform-slices-oper-group {
    container slices {
      list location {
        key "location";
        leaf location {
          type calvados:live_ncs_location-id;
        }
        list slice_values {
          key "slice_idx";
          leaf slice_idx {
            type uint32;
          }
          container slice {
            leaf slice_num {
              type uint32;
            }
            leaf admin_state {
              type string;
            }
            leaf oper_state {
              type string;
            }
          }
        }
      }
    }
  }

  grouping live_ncs_chassis-brief-oper-group {
    container brief {
      list chassis_serial {
        key "serial_number";
        leaf serial_number {
          type string;
        }
        container brief-data {
          leaf racknum {
            type string;
          }
          leaf rack_type {
            type string;
          }
          leaf rack_state {
            type string;
          }
          leaf data_plane {
            type string;
          }
          leaf ctrl_plane {
            type string;
          }
        }
      }
    }
  }

  grouping live_ncs_mac-pool-brief-oper-group {
    container brief {
      list rack {
        key "serial_number";
        leaf serial_number {
          type string;
        }
        container brief-data {
          leaf racknum {
            type string;
          }
          leaf mac_base {
            type ietf:mac-address;
          }
          leaf mac_count {
            type uint32;
          }
          leaf is_selected {
            type boolean;
          }
          leaf allocated_count {
            type uint32;
          }
        }
      }
    }
  }

  grouping live_ncs_sm-config-group {
    container config {
      uses live_ncs_chassis-config-group;
      uses live_ncs_mgmt-interfaces-config-group;
      uses live_ncs_virtual-macaddr-config-group;
    }
  }

  grouping live_ncs_chassis-config-group {
    container chassis {
      list serial {
        key "serial";
        unique "rack";
        leaf serial {
          type string;
          // NCS drop mandatory statement
        }
        leaf rack {
          type string {
            pattern '[eE][0-3]|[bB][0-9]|[dD][0-1]|[fF][0-7]|[0-9]|[1][0-9]|[2-5][0-9]|[6][0-3]|[2][4][0-7]';
          }
          // NCS drop mandatory statement
        }
      }
    }
  }

  grouping live_ncs_mgmt-interfaces-config-group {
    container interface {
      container MgmtEth {
        list locport {
          key "rack slot intf port";
          leaf rack {
            type string {
              pattern '[fF][0-7]|[0-9]|[1][0-5]|[bB][0-9]|[eE][0-3]';
            }
          }
          leaf slot {
            type string {
              pattern '[Rr][Pp][0-1]|[Rr][Ss][Pp][0-1]|[Ss][Cc][0-1]|[cC][bB][0-9]|[cC][eE][0-3]';
            }
          }
          leaf intf {
            type uint32 {
              range "0";
            }
          }
          leaf port {
            type uint32 {
              range "0";
            }
          }
          container ipv4 {
            leaf address {
              type string {
                pattern '(([0-9]|[1-9][0-9]|1[0-9][0-9]|2[0-4][0-9]|25[0-5])\.){3}([0-9]|[1-9][0-9]|1[0-9][0-9]|2[0-4][0-9]|25[0-5])(( (([0-9]|[1-9][0-9]|1[0-9][0-9]|2[0-4][0-9]|25[0-5])\.){3}([0-9]|[1-9][0-9]|1[0-9][0-9]|2[0-4][0-9]|25[0-5]))|(/([0-9]+)))';
              }
            }
          }
          leaf shutdown {
            type empty;
          }
          leaf mtu {
            type uint32 {
              range "48..9000";
            }
          }
          leaf default-gw {
            type inet:ipv4-address;
          }
          container arp {
            list ip {
              key "ip";
              leaf ip {
                type inet:ipv4-address;
                // NCS drop mandatory statement
              }
              leaf mac {
                type ietf:mac-address;
                // NCS drop mandatory statement
              }
            }
          }
        }
      }
    }
    container domain {
      list name {
        key "name";
        leaf name {
          type string;
        }
      }
      list name-server {
        key "name-server";
        leaf name-server {
          type inet:ipv4-address;
        }
      }
    }
  }

  grouping live_ncs_virtual-macaddr-config-group {
    container virtual-macaddr-range {
      leaf base {
        type ietf:mac-address;
      }
      leaf count {
        type uint32 {
          range "1..65535";
        }
      }
    }
  }

  grouping live_ncs_sm-action-group {
    container actions {
      uses live_ncs_reload-action-group;
    }
  }

  grouping live_ncs_reload-action-group;

  grouping sm-oper-group {
    // NCS drop config false container oper
  }

  grouping ctrace-oper-group {
    container shelf_mgr {
      uses show_trace:traceable;
    }
  }

  grouping platform-oper-group {
    // NCS drop config false container platform
  }

  grouping chassis-oper-group {
    // NCS drop config false container chassis
  }

  grouping reload-rack-oper-group {
    // NCS drop config false container reload
  }

  grouping reload-vm-oper-group {
    // NCS drop config false container reload_vm
  }

  grouping reboot-history-events-oper-group {
    list events {
      key "event_idx";
      leaf event_idx {
        type uint32;
      }
      container event {
        leaf timestamp {
          type string;
        }
        leaf reason_code {
          type uint32;
        }
        leaf reason {
          type string;
        }
        leaf src_loc {
          type string;
        }
        leaf src_name {
          type string;
        }
      }
    }
  }

  grouping reboot-pending-events-oper-group {
    list delay_events {
      key "delay_event_idx";
      leaf delay_event_idx {
        type uint32;
      }
      container delay_event {
        leaf active {
          type boolean;
        }
        leaf wait {
          type uint64;
        }
        leaf when {
          type uint64;
        }
        leaf reason {
          type string;
        }
        leaf count {
          type uint32;
        }
      }
    }
  }

  grouping reboot-history-card-oper-group {
    container card {
      list location {
        key "location";
        leaf location {
          type calvados:location-id;
        }
        uses reboot-history-events-oper-group;
      }
    }
  }

  grouping reboot-history-admin-vm-oper-group {
    container admin-vm {
      list location {
        key "location";
        leaf location {
          type calvados:location-id;
        }
        uses reboot-history-events-oper-group;
      }
    }
  }

  grouping reboot-history-reverse-oper-group {
    container reverse {
      uses reboot-history-card-oper-group;
      uses reboot-history-admin-vm-oper-group;
    }
  }

  grouping reboot-pending-card-oper-group {
    container card {
      list location {
        key "location";
        leaf location {
          type calvados:location-id;
        }
        uses reboot-pending-events-oper-group;
      }
    }
  }

  grouping reboot-history-oper-group {
    // NCS drop config false container 'reboot-history'
  }

  grouping reboot-pending-oper-group {
    // NCS drop config false container 'reboot-pending'
  }

  grouping mgmt-interfaces-oper-group {
    list interface {
      key "ifname";
      leaf ifname {
        type string;
      }
      container interface-data {
        leaf mac {
          type ietf:mac-address;
        }
        leaf ipv4 {
          type inet:ipv4-address;
        }
        leaf flagstr {
          type string;
        }
        leaf port_status {
          type string;
        }
        leaf mtu {
          type uint32;
        }
        leaf metric {
          type uint32;
        }
        leaf rx_pak {
          type uint32;
        }
        leaf rx_errors {
          type uint32;
        }
        leaf rx_dropped {
          type uint32;
        }
        leaf rx_overruns {
          type uint32;
        }
        leaf rx_frame {
          type uint32;
        }
        leaf tx_pak {
          type uint32;
        }
        leaf tx_errors {
          type uint32;
        }
        leaf tx_dropped {
          type uint32;
        }
        leaf tx_overruns {
          type uint32;
        }
        leaf tx_carrier {
          type uint32;
        }
        leaf collisions {
          type uint32;
        }
        leaf tx_queuelen {
          type uint32;
        }
        leaf rx_bytes {
          type uint64;
        }
        leaf tx_bytes {
          type uint64;
        }
        leaf intf_num {
          type uint32;
        }
      }
    }
  }

  grouping mac-pool-oper-group {
    // NCS drop config false container macpool
  }

  grouping platform-summary-oper-group {
    container summary {
      list location {
        key "location";
        leaf location {
          type calvados:location-id;
        }
        container summary-data {
          leaf card_type {
            type string;
          }
          leaf hw_state {
            type string;
          }
          leaf sw_state {
            type string;
          }
          leaf config_state {
            type string;
          }
        }
      }
    }
  }

  grouping platform-detail-oper-group {
    container detail {
      list location {
        key "location";
        leaf location {
          type calvados:location-id;
        }
        container detail-data {
          leaf pid {
            type string;
          }
          leaf description {
            type string;
          }
          leaf vid_sn {
            type string;
          }
          leaf hw_state {
            type string;
          }
          leaf sw_state {
            type string;
          }
          leaf config_wordy {
            type string;
          }
          leaf hw_ver {
            type string;
          }
          leaf last_event {
            type string;
          }
          leaf last_ev_reason_str {
            type string;
          }
        }
      }
    }
  }

  grouping platform-slices-oper-group {
    container slices {
      list location {
        key "location";
        leaf location {
          type calvados:location-id;
        }
        list slice_values {
          key "slice_idx";
          leaf slice_idx {
            type uint32;
          }
          container slice {
            leaf slice_num {
              type uint32;
            }
            leaf admin_state {
              type string;
            }
            leaf oper_state {
              type string;
            }
          }
        }
      }
    }
  }

  grouping chassis-brief-oper-group {
    container brief {
      list chassis_serial {
        key "serial_number";
        leaf serial_number {
          type string;
        }
        container brief-data {
          leaf racknum {
            type string;
          }
          leaf rack_type {
            type string;
          }
          leaf rack_state {
            type string;
          }
          leaf data_plane {
            type string;
          }
          leaf ctrl_plane {
            type string;
          }
        }
      }
    }
  }

  grouping mac-pool-brief-oper-group {
    container brief {
      list rack {
        key "serial_number";
        leaf serial_number {
          type string;
        }
        container brief-data {
          leaf racknum {
            type string;
          }
          leaf mac_base {
            type ietf:mac-address;
          }
          leaf mac_count {
            type uint32;
          }
          leaf is_selected {
            type boolean;
          }
          leaf allocated_count {
            type uint32;
          }
        }
      }
    }
  }

  grouping sm-config-group {
    container config {
      // NCS dropped explicit config true
      uses chassis-config-group;
      uses mgmt-interfaces-config-group;
      uses virtual-macaddr-config-group;
    }
  }

  grouping chassis-config-group {
    container chassis {
      list serial {
        key "serial";
        unique "rack";
        leaf serial {
          type string;
          mandatory true;
        }
        leaf rack {
          type string {
            pattern '[eE][0-3]|[bB][0-9]|[dD][0-1]|[fF][0-7]|[0-9]|[1][0-9]|[2-5][0-9]|[6][0-3]|[2][4][0-7]';
          }
          mandatory true;
        }
      }
    }
  }

  grouping mgmt-interfaces-config-group {
    container interface {
      container MgmtEth {
        list locport {
          key "rack slot intf port";
          leaf rack {
            type string {
              pattern '[fF][0-7]|[0-9]|[1][0-5]|[bB][0-9]|[eE][0-3]';
            }
          }
          leaf slot {
            type string {
              pattern '[Rr][Pp][0-1]|[Rr][Ss][Pp][0-1]|[Ss][Cc][0-1]|[cC][bB][0-9]|[cC][eE][0-3]';
            }
          }
          leaf intf {
            type uint32 {
              range "0";
            }
          }
          leaf port {
            type uint32 {
              range "0";
            }
          }
          container ipv4 {
            leaf address {
              type string {
                pattern '(([0-9]|[1-9][0-9]|1[0-9][0-9]|2[0-4][0-9]|25[0-5])\.){3}([0-9]|[1-9][0-9]|1[0-9][0-9]|2[0-4][0-9]|25[0-5])(( (([0-9]|[1-9][0-9]|1[0-9][0-9]|2[0-4][0-9]|25[0-5])\.){3}([0-9]|[1-9][0-9]|1[0-9][0-9]|2[0-4][0-9]|25[0-5]))|(/([0-9]+)))';
              }
            }
          }
          leaf shutdown {
            type empty;
          }
          leaf mtu {
            type uint32 {
              range "48..9000";
            }
          }
          leaf default-gw {
            type inet:ipv4-address;
          }
          container arp {
            list ip {
              key "ip";
              leaf ip {
                type inet:ipv4-address;
                mandatory true;
              }
              leaf mac {
                type ietf:mac-address;
                mandatory true;
              }
            }
          }
        }
      }
    }
    container domain {
      list name {
        key "name";
        leaf name {
          type string;
        }
      }
      list name-server {
        key "name-server";
        leaf name-server {
          type inet:ipv4-address;
        }
      }
    }
  }

  grouping virtual-macaddr-config-group {
    container virtual-macaddr-range {
      leaf base {
        type ietf:mac-address;
      }
      leaf count {
        type uint32 {
          range "1..65535";
        }
      }
    }
  }

  grouping sm-action-group {
    // NCS drop config false container actions
  }

  grouping reload-action-group;

  augment "/ncs:devices/ncs:device/ncs:config" {
    uses sm-oper-group;
    uses sm-config-group {
      refine config {
        tailf:ncs-device-type "netconf";
        tailf:display-when "not(../../ncs:module) or ../../ncs:module[ncs:name='Cisco-IOS-XR-sysadmin-sm']";
      }
    }
    uses sm-action-group;
  }
  augment "/ncs:devices/ncs:device/ncs:live-status" {
    uses live_ncs_sm-oper-group {
      refine oper {
        tailf:ncs-device-type "netconf";
        tailf:display-when "not(../../ncs:module) or ../../ncs:module[ncs:name='Cisco-IOS-XR-sysadmin-sm'] or (../../ncs:live-status-protocol[not(ncs:capability)]) or (../../ncs:live-status-protocol/ncs:capability/ncs:module[.='Cisco-IOS-XR-sysadmin-sm'])";
      }
    }
    uses live_ncs_sm-config-group {
      refine config {
        tailf:ncs-device-type "netconf";
        tailf:display-when "not(../../ncs:module) or ../../ncs:module[ncs:name='Cisco-IOS-XR-sysadmin-sm'] or (../../ncs:live-status-protocol[not(ncs:capability)]) or (../../ncs:live-status-protocol/ncs:capability/ncs:module[.='Cisco-IOS-XR-sysadmin-sm'])";
      }
    }
    uses live_ncs_sm-action-group {
      refine actions {
        tailf:ncs-device-type "netconf";
        tailf:display-when "not(../../ncs:module) or ../../ncs:module[ncs:name='Cisco-IOS-XR-sysadmin-sm'] or (../../ncs:live-status-protocol[not(ncs:capability)]) or (../../ncs:live-status-protocol/ncs:capability/ncs:module[.='Cisco-IOS-XR-sysadmin-sm'])";
      }
    }
  }
  augment "/ncs:devices/ncs:template/ncs:ned-id/ncs:config" {
    uses ncs_template_sm-oper-group;
    uses ncs_template_sm-config-group;
    uses ncs_template_sm-action-group;
  }
}

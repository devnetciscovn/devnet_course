submodule Cisco-IOS-XR-icpe-infra-oper-sub9 {
  // Generated by yanger -t ncs
  tailf:mount-id "cisco-iosxr-nc-7.3:cisco-iosxr-nc-7.3";

  belongs-to Cisco-IOS-XR-icpe-infra-oper {
    prefix Cisco-IOS-XR-icpe-infra-oper;
  }

  import cisco-semver {
    prefix semver;
  }
  include Cisco-IOS-XR-icpe-infra-oper-sub4 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR icpe-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_ICPE-GCO-PRIORITY-OPER-TYPE {
    description
      "Satellite priority information";
    leaf satellite-id-xr {
      type string;
      description
        "Satellite ID";
    }
    leaf rgid {
      type string;
      description
        "RG ID";
    }
    leaf best-path-hops {
      type string;
      description
        "Best path hops";
    }
    leaf configured-priority {
      type string;
      description
        "Configured priority";
    }
    leaf host-priority {
      type string;
      description
        "Host priority";
    }
    leaf partner-priority {
      type string;
      description
        "Partner priority";
    }
    leaf multichassis-redundancy {
      type ncs_template_Icpe-oper-multichassis-redundancy;
      description
        "Multichassis redundancy";
    }
  }

  grouping ncs_rpc_notif_ICPE-GCO-PRIORITY-OPER-TYPE {
    description
      "Satellite priority information";
    leaf satellite-id-xr {
      type uint16;
      description
        "Satellite ID";
    }
    leaf rgid {
      type uint32;
      description
        "RG ID";
    }
    leaf best-path-hops {
      type uint32;
      description
        "Best path hops";
    }
    leaf configured-priority {
      type uint8;
      description
        "Configured priority";
    }
    leaf host-priority {
      type uint64;
      description
        "Host priority";
    }
    leaf partner-priority {
      type uint64;
      description
        "Partner priority";
    }
    leaf multichassis-redundancy {
      type ncs_rpc_notif_Icpe-oper-multichassis-redundancy;
      description
        "Multichassis redundancy";
    }
  }

  grouping live_ncs_ICPE-GCO-PRIORITY-OPER-TYPE {
    description
      "Satellite priority information";
    leaf satellite-id-xr {
      type uint16;
      description
        "Satellite ID";
    }
    leaf rgid {
      type uint32;
      description
        "RG ID";
    }
    leaf best-path-hops {
      type uint32;
      description
        "Best path hops";
    }
    leaf configured-priority {
      type uint8;
      description
        "Configured priority";
    }
    leaf host-priority {
      type uint64;
      description
        "Host priority";
    }
    leaf partner-priority {
      type uint64;
      description
        "Partner priority";
    }
    leaf multichassis-redundancy {
      type live_ncs_Icpe-oper-multichassis-redundancy;
      description
        "Multichassis redundancy";
    }
  }

  grouping ICPE-GCO-PRIORITY-OPER-TYPE {
    description
      "Satellite priority information";
    leaf satellite-id-xr {
      type uint16;
      description
        "Satellite ID";
    }
    leaf rgid {
      type uint32;
      description
        "RG ID";
    }
    leaf best-path-hops {
      type uint32;
      description
        "Best path hops";
    }
    leaf configured-priority {
      type uint8;
      description
        "Configured priority";
    }
    leaf host-priority {
      type uint64;
      description
        "Host priority";
    }
    leaf partner-priority {
      type uint64;
      description
        "Partner priority";
    }
    leaf multichassis-redundancy {
      type Icpe-oper-multichassis-redundancy;
      description
        "Multichassis redundancy";
    }
  }
}

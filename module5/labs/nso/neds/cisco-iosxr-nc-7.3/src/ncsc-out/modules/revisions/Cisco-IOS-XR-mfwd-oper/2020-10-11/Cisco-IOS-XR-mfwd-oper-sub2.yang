submodule Cisco-IOS-XR-mfwd-oper-sub2 {
  // Generated by yanger -t ncs
  tailf:mount-id "cisco-iosxr-nc-7.3:cisco-iosxr-nc-7.3";

  belongs-to Cisco-IOS-XR-mfwd-oper {
    prefix Cisco-IOS-XR-mfwd-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mfwd package operational data.

     Copyright (c) 2013-2020 by Cisco Systems, Inc.
     All rights reserved.";

  revision 2020-10-11 {
    description
      "Backward compatible addition in leaf ul-interface, customer-mdt-data-tree-sidacl-name, is-customer-mdt-data-tree-sidacl-present and ,is-all-customer-routes-for-tree-sid-data-mdt";
    semver:module-version "1.0.0";
  }
  revision 2019-08-27 {
    description
      "Initial IOS-XR MFWD native model";
  }
  revision 2019-04-05 {
    description
      "Establish semantic version baseline.";
  }
  revision 2015-11-09 {
    description
      "IOS XR 6.0 revision.";
  }

  typedef ncs_template_If-ul-id {
    type string;
    description
      "If ul id";
  }

  typedef ncs_template_Ipv6-address {
    type string;
    description
      "IPV6 Address type";
  }

  typedef ncs_rpc_notif_If-ul-id {
    type uint16;
    description
      "If ul id";
  }

  typedef ncs_rpc_notif_Ipv6-address {
    type inet:ipv6-address;
    description
      "IPV6 Address type";
  }

  typedef live_ncs_If-ul-id {
    type uint16;
    description
      "If ul id";
  }

  typedef live_ncs_Ipv6-address {
    type inet:ipv6-address;
    description
      "IPV6 Address type";
  }

  typedef If-ul-id {
    type uint16;
    description
      "If ul id";
  }

  typedef Ipv6-address {
    type inet:ipv6-address;
    description
      "IPV6 Address type";
  }
}

module Cisco-IOS-XR-infra-xtc-oper {
  // Generated by yanger -t ncs
  tailf:mount-id "cisco-iosxr-nc-7.3:cisco-iosxr-nc-7.3";
  tailf:ncs-device-type "netconf";

  namespace "http://cisco.com/ns/yang/Cisco-IOS-XR-infra-xtc-oper";
  prefix infra-xtc-oper;

  import ietf-inet-types {
    prefix inet;
  }
  import Cisco-IOS-XR-types {
    prefix xr;
  }
  import cisco-semver {
    prefix semver;
  }
  include Cisco-IOS-XR-infra-xtc-oper-sub1 {
    revision-date 2021-06-21;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-xtc package operational data.

     This module contains definitions
     for the following management objects:
       pce-lsp-data: PCE LSP's data
       pce-peer: PCE peer data
       pce-topology: PCE topology data
       pce: PCE operational data

     Copyright (c) 2013-2021 by Cisco Systems, Inc.
     All rights reserved.";

  revision 2021-06-21 {
    description
      "un-hide cspf-srv6 option in cspf srv6 path calculation.
       2021-05-26
         Added keys to topology-summary list.
       2021-04-08
         Change protection type from integer to enum.
       2021-03-31
         Added new enumeration Api-peer-stats-info-oper. Changed type of type in API-PEER-STATS-INFO to use Api-peer-stats-info-oper. This is a non backward compatible change.
       2021-03-04
         Added MSD list per topology link. Added SRLB list per topology node.
       2021-01-29
         Updated SRv6 Endpoint function from int to enum.";
    semver:module-version "4.0.0";
  }
  revision 2020-12-13 {
    description
      "Added performance-measurement liveness-detecion oper schema.
       2020-09-16
       Adding operational nodes for new features path invalidation drop protected and unprotected path Operational nodes for PCE segment-routing traffic-eng policy
       2020-07-13
       Added NodeID fields in the uN SID object in the IPv6 topology. IosSetYangSchemaRev Cisco-IOS-XR-infra-xtc-oper";
    semver:module-version "3.0.0";
  }
  revision 2020-03-17 {
    description
      "Add flex-algo related operational nodes. Updated description of statistics-nodes. Add SR-PAG related operational nodes. Add PCE authentication related operational nodes.
       2020-02-03
       Added TCP AuthenticationOption related operational model. Implemented show pce authentication. Added classes AuthenticationKeyTable and AuthenticationKey.
       2019-11-07
       Adding leaf preference, leaf interface-name, and leaf profile-id to support a new HTTP API bindpoint for sibling PCEs.
       2019-10-09
       Adding enum sr-flex-algo-prefix-sid, enum pce-cspf-flex-algo-definition-mistmatch, leaf flex-algo-prefix-sids, list sr-flex-algo, and container flex-algos to support Flex-algo info.";
    semver:module-version "2.0.0";
  }
  revision 2019-10-02 {
    description
      "Added REST peer statistic information.
       2019-09-27
       Implement new show pce lsp and show pce initiated tunnels commands for Optima";
    semver:module-version "1.1.0";
  }
  revision 2019-04-05 {
    description
      "Establish semantic version baseline.";
    semver:module-version "1.0.0";
  }
  revision 2017-09-07 {
    description
      "Fixed type translation error.";
  }
  revision 2017-08-24 {
    description
      "Added C flag to pcep flags.";
  }
  revision 2017-06-26 {
    description
      "Change identifiers to be more readable.";
  }
  revision 2017-05-01 {
    description
      "Fixing backward compatibility error in module.";
  }
  revision 2016-05-31 {
    description
      "Revision description string.";
  }
  revision 2015-11-09 {
    description
      "IOS XR 6.0 revision.";
  }

  typedef ncs_template_Pce-address-family-summary {
    type string;
    description
      "Pce address family summary";
  }

  typedef ncs_template_Pceigp-protocol {
    type string;
    description
      "Pceigp protocol";
  }

  typedef ncs_template_Pceigp-protocol-summary {
    type string;
    description
      "Pceigp protocol summary";
  }

  typedef ncs_template_Pce-asso {
    type string;
    description
      "Pce asso";
  }

  typedef ncs_template_Xtc-adj-sid-protection {
    type string;
    description
      "Xtc adj sid protection";
  }

  typedef ncs_template_Pce-address-family {
    type string;
    description
      "Pce address family";
  }

  typedef ncs_rpc_notif_Pce-address-family-summary {
    type enumeration {
      enum "ipv4" {
        value 1;
        description
          "IPv4 address family";
      }
      enum "ipv6" {
        value 2;
        description
          "IPv6 address family";
      }
      enum "all" {
        value 3;
        description
          "All address families";
      }
    }
    description
      "Pce address family summary";
  }

  typedef ncs_rpc_notif_Pceigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
    }
    description
      "Pceigp protocol";
  }

  typedef ncs_rpc_notif_Pceigp-protocol-summary {
    type enumeration {
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
      enum "all" {
        value 5;
        description
          "All protocols";
      }
    }
    description
      "Pceigp protocol summary";
  }

  typedef ncs_rpc_notif_Pce-asso {
    type enumeration {
      enum "unknown" {
        value 0;
        description
          "Unknown type";
      }
      enum "link" {
        value 1;
        description
          "LINK";
      }
      enum "node" {
        value 2;
        description
          "NODE";
      }
      enum "srlg" {
        value 3;
        description
          "SRLG";
      }
    }
    description
      "Pce asso";
  }

  typedef ncs_rpc_notif_Xtc-adj-sid-protection {
    type enumeration {
      enum "protected-preferred" {
        value 0;
        description
          "Protected adj SID preferred";
      }
      enum "unprotected" {
        value 1;
        description
          "Unprotected adj SID only";
      }
      enum "protected-only" {
        value 2;
        description
          "Protected adj SID only";
      }
      enum "unprotected-preferred" {
        value 3;
        description
          "Unprotected adj SID preferred";
      }
    }
    description
      "Xtc adj sid protection";
  }

  typedef ncs_rpc_notif_Pce-address-family {
    type enumeration {
      enum "ipv4" {
        value 1;
        description
          "IPv4 address family";
      }
      enum "ipv6" {
        value 2;
        description
          "IPv6 address family";
      }
    }
    description
      "Pce address family";
  }

  typedef live_ncs_Pce-address-family-summary {
    type enumeration {
      enum "ipv4" {
        value 1;
        description
          "IPv4 address family";
      }
      enum "ipv6" {
        value 2;
        description
          "IPv6 address family";
      }
      enum "all" {
        value 3;
        description
          "All address families";
      }
    }
    description
      "Pce address family summary";
  }

  typedef live_ncs_Pceigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
    }
    description
      "Pceigp protocol";
  }

  typedef live_ncs_Pceigp-protocol-summary {
    type enumeration {
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
      enum "all" {
        value 5;
        description
          "All protocols";
      }
    }
    description
      "Pceigp protocol summary";
  }

  typedef live_ncs_Pce-asso {
    type enumeration {
      enum "unknown" {
        value 0;
        description
          "Unknown type";
      }
      enum "link" {
        value 1;
        description
          "LINK";
      }
      enum "node" {
        value 2;
        description
          "NODE";
      }
      enum "srlg" {
        value 3;
        description
          "SRLG";
      }
    }
    description
      "Pce asso";
  }

  typedef live_ncs_Xtc-adj-sid-protection {
    type enumeration {
      enum "protected-preferred" {
        value 0;
        description
          "Protected adj SID preferred";
      }
      enum "unprotected" {
        value 1;
        description
          "Unprotected adj SID only";
      }
      enum "protected-only" {
        value 2;
        description
          "Protected adj SID only";
      }
      enum "unprotected-preferred" {
        value 3;
        description
          "Unprotected adj SID preferred";
      }
    }
    description
      "Xtc adj sid protection";
  }

  typedef live_ncs_Pce-address-family {
    type enumeration {
      enum "ipv4" {
        value 1;
        description
          "IPv4 address family";
      }
      enum "ipv6" {
        value 2;
        description
          "IPv6 address family";
      }
    }
    description
      "Pce address family";
  }

  typedef Pce-address-family-summary {
    type enumeration {
      enum "ipv4" {
        value 1;
        description
          "IPv4 address family";
      }
      enum "ipv6" {
        value 2;
        description
          "IPv6 address family";
      }
      enum "all" {
        value 3;
        description
          "All address families";
      }
    }
    description
      "Pce address family summary";
  }

  typedef Pceigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
    }
    description
      "Pceigp protocol";
  }

  typedef Pceigp-protocol-summary {
    type enumeration {
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
      enum "all" {
        value 5;
        description
          "All protocols";
      }
    }
    description
      "Pceigp protocol summary";
  }

  typedef Pce-asso {
    type enumeration {
      enum "unknown" {
        value 0;
        description
          "Unknown type";
      }
      enum "link" {
        value 1;
        description
          "LINK";
      }
      enum "node" {
        value 2;
        description
          "NODE";
      }
      enum "srlg" {
        value 3;
        description
          "SRLG";
      }
    }
    description
      "Pce asso";
  }

  typedef Xtc-adj-sid-protection {
    type enumeration {
      enum "protected-preferred" {
        value 0;
        description
          "Protected adj SID preferred";
      }
      enum "unprotected" {
        value 1;
        description
          "Unprotected adj SID only";
      }
      enum "protected-only" {
        value 2;
        description
          "Protected adj SID only";
      }
      enum "unprotected-preferred" {
        value 3;
        description
          "Unprotected adj SID preferred";
      }
    }
    description
      "Xtc adj sid protection";
  }

  typedef Pce-address-family {
    type enumeration {
      enum "ipv4" {
        value 1;
        description
          "IPv4 address family";
      }
      enum "ipv6" {
        value 2;
        description
          "IPv6 address family";
      }
    }
    description
      "Pce address family";
  }

  grouping ncs_template_PEER-TABLE {
    description
      "Common node of pce, pce-peer";
    container peer-infos {
      description
        "Peers database in XTC";
      list peer-info {
        // NCS patched for predictable order
        ordered-by user;
        key "peer-address";
        description
          "PCE peer information";
        leaf peer-address {
          type string;
          description
            "Peer Address";
        }
        uses ncs_template_PCE-PEER-BAG;
      }
    }
  }

  grouping ncs_template_PEER-DETAIL-TABLE {
    description
      "Common node of pce, pce-peer";
    container peer-detail-infos {
      description
        "Detailed peers database in XTC";
      list peer-detail-info {
        // NCS patched for predictable order
        ordered-by user;
        key "peer-address";
        description
          "Detailed PCE peer information";
        leaf peer-address {
          type string;
          description
            "Peer Address";
        }
        uses ncs_template_PCE-PEER-DETAIL-BAG;
      }
    }
  }

  grouping ncs_template_PREFIX-TABLE {
    description
      "Common node of pce, pce-topology";
    container prefix-infos {
      description
        "Prefixes database in XTC";
      list prefix-info {
        // NCS patched for predictable order
        ordered-by user;
        key "node-identifier";
        description
          "PCE prefix information";
        leaf node-identifier {
          type string;
          description
            "Node ID";
        }
        uses ncs_template_PCE-PFX-BAG;
      }
    }
  }

  grouping ncs_template_TUNNEL-TABLE {
    description
      "Common node of pce, pce-lsp-data";
    container tunnel-infos {
      description
        "Tunnel database in XTC";
      list tunnel-info {
        // NCS patched for predictable order
        ordered-by user;
        key "peer-address plsp-id tunnel-name";
        description
          "Tunnel information";
        leaf peer-address {
          type string;
          description
            "Peer Address";
        }
        leaf plsp-id {
          type string;
          description
            "PCEP LSP ID";
        }
        leaf tunnel-name {
          type string;
          description
            "Tunnel name";
        }
        uses ncs_template_PCE-TUN-BAG;
      }
    }
  }

  grouping ncs_template_REMOTE-PREFIX-TABLE {
    description
      "Common node of pce, pce-topology";
    container remote-prefixes {
      description
        "Remote Prefixes database in PCE";
      list remote-prefix {
        // NCS patched for predictable order
        ordered-by user;
        key "remote-pce-id";
        description
          "PCE remote prefix information";
        leaf remote-pce-id {
          type string;
          description
            "Remote PCE ID";
        }
        uses ncs_template_PCE-REMOTE-PFX-BAG;
      }
    }
  }

  grouping ncs_template_LSP-SUMMARY {
    description
      "Common node of pce, pce-lsp-data";
    container lsp-summary {
      description
        "LSP summary database in XTC";
      uses ncs_template_PCE-LSP-SUMMARY-BAG;
    }
  }

  grouping ncs_template_TOPOLOGY-SUMMARY-TABLE {
    description
      "Common node of pce, pce-topology";
    container topology-summaries {
      description
        "Node summary database in XTC";
      list topology-summary {
        // NCS patched for predictable order
        ordered-by user;
        key "af protocol";
        description
          "Node summary database in XTC";
        leaf af {
          type ncs_template_Pce-address-family-summary;
          description
            "Only show data related to the specified
             address family";
        }
        leaf protocol {
          type ncs_template_Pceigp-protocol-summary;
          description
            "Match nodes from the specified IGP protocol";
        }
        uses ncs_template_PCE-NODE-SUMMARY-BAG;
      }
    }
  }

  grouping ncs_template_TOPOLOGY-NODE-TABLE {
    description
      "Common node of pce, pce-topology";
    container topology-nodes {
      description
        "Node database in XTC";
      list topology-node {
        // NCS patched for predictable order
        ordered-by user;
        key "node-identifier";
        description
          "Node information";
        leaf node-identifier {
          type string;
          description
            "Node Identifier";
        }
        uses ncs_template_PCE-XTC-NODE-BAG;
      }
    }
  }

  grouping ncs_template_TUNNEL-DETAIL-TABLE {
    description
      "Common node of pce, pce-lsp-data";
    container tunnel-detail-infos {
      description
        "Detailed tunnel database in XTC";
      list tunnel-detail-info {
        // NCS patched for predictable order
        ordered-by user;
        key "peer-address plsp-id tunnel-name";
        description
          "Detailed tunnel information";
        leaf peer-address {
          type string;
          description
            "Peer Address";
        }
        leaf plsp-id {
          type string;
          description
            "PCEP LSP ID";
        }
        leaf tunnel-name {
          type string;
          description
            "Tunnel name";
        }
        uses ncs_template_PCE-TUN-DETAIL-BAG;
      }
    }
  }

  grouping ncs_rpc_notif_PEER-TABLE {
    description
      "Common node of pce, pce-peer";
    container peer-infos {
      description
        "Peers database in XTC";
      list peer-info {
        key "peer-address";
        description
          "PCE peer information";
        leaf peer-address {
          type inet:ip-address-no-zone;
          description
            "Peer Address";
        }
        uses ncs_rpc_notif_PCE-PEER-BAG;
      }
    }
  }

  grouping ncs_rpc_notif_PEER-DETAIL-TABLE {
    description
      "Common node of pce, pce-peer";
    container peer-detail-infos {
      description
        "Detailed peers database in XTC";
      list peer-detail-info {
        key "peer-address";
        description
          "Detailed PCE peer information";
        leaf peer-address {
          type inet:ip-address-no-zone;
          description
            "Peer Address";
        }
        uses ncs_rpc_notif_PCE-PEER-DETAIL-BAG;
      }
    }
  }

  grouping ncs_rpc_notif_PREFIX-TABLE {
    description
      "Common node of pce, pce-topology";
    container prefix-infos {
      description
        "Prefixes database in XTC";
      list prefix-info {
        key "node-identifier";
        description
          "PCE prefix information";
        leaf node-identifier {
          type uint32;
          description
            "Node ID";
        }
        uses ncs_rpc_notif_PCE-PFX-BAG;
      }
    }
  }

  grouping ncs_rpc_notif_TUNNEL-TABLE {
    description
      "Common node of pce, pce-lsp-data";
    container tunnel-infos {
      description
        "Tunnel database in XTC";
      list tunnel-info {
        key "peer-address plsp-id tunnel-name";
        description
          "Tunnel information";
        leaf peer-address {
          type inet:ip-address-no-zone;
          description
            "Peer Address";
        }
        leaf plsp-id {
          type uint32;
          description
            "PCEP LSP ID";
        }
        leaf tunnel-name {
          type string;
          description
            "Tunnel name";
        }
        uses ncs_rpc_notif_PCE-TUN-BAG;
      }
    }
  }

  grouping ncs_rpc_notif_REMOTE-PREFIX-TABLE {
    description
      "Common node of pce, pce-topology";
    container remote-prefixes {
      description
        "Remote Prefixes database in PCE";
      list remote-prefix {
        key "remote-pce-id";
        description
          "PCE remote prefix information";
        leaf remote-pce-id {
          type uint32;
          description
            "Remote PCE ID";
        }
        uses ncs_rpc_notif_PCE-REMOTE-PFX-BAG;
      }
    }
  }

  grouping ncs_rpc_notif_LSP-SUMMARY {
    description
      "Common node of pce, pce-lsp-data";
    container lsp-summary {
      description
        "LSP summary database in XTC";
      uses ncs_rpc_notif_PCE-LSP-SUMMARY-BAG;
    }
  }

  grouping ncs_rpc_notif_TOPOLOGY-SUMMARY-TABLE {
    description
      "Common node of pce, pce-topology";
    container topology-summaries {
      description
        "Node summary database in XTC";
      list topology-summary {
        key "af protocol";
        description
          "Node summary database in XTC";
        leaf af {
          type ncs_rpc_notif_Pce-address-family-summary;
          description
            "Only show data related to the specified
             address family";
        }
        leaf protocol {
          type ncs_rpc_notif_Pceigp-protocol-summary;
          description
            "Match nodes from the specified IGP protocol";
        }
        uses ncs_rpc_notif_PCE-NODE-SUMMARY-BAG;
      }
    }
  }

  grouping ncs_rpc_notif_TOPOLOGY-NODE-TABLE {
    description
      "Common node of pce, pce-topology";
    container topology-nodes {
      description
        "Node database in XTC";
      list topology-node {
        key "node-identifier";
        description
          "Node information";
        leaf node-identifier {
          type uint32;
          description
            "Node Identifier";
        }
        uses ncs_rpc_notif_PCE-XTC-NODE-BAG;
      }
    }
  }

  grouping ncs_rpc_notif_TUNNEL-DETAIL-TABLE {
    description
      "Common node of pce, pce-lsp-data";
    container tunnel-detail-infos {
      description
        "Detailed tunnel database in XTC";
      list tunnel-detail-info {
        key "peer-address plsp-id tunnel-name";
        description
          "Detailed tunnel information";
        leaf peer-address {
          type inet:ip-address-no-zone;
          description
            "Peer Address";
        }
        leaf plsp-id {
          type uint32;
          description
            "PCEP LSP ID";
        }
        leaf tunnel-name {
          type string;
          description
            "Tunnel name";
        }
        uses ncs_rpc_notif_PCE-TUN-DETAIL-BAG;
      }
    }
  }

  grouping live_ncs_PEER-TABLE {
    description
      "Common node of pce, pce-peer";
    container peer-infos {
      description
        "Peers database in XTC";
      list peer-info {
        key "peer-address";
        description
          "PCE peer information";
        leaf peer-address {
          type inet:ip-address-no-zone;
          description
            "Peer Address";
        }
        uses live_ncs_PCE-PEER-BAG;
      }
    }
  }

  grouping live_ncs_PEER-DETAIL-TABLE {
    description
      "Common node of pce, pce-peer";
    container peer-detail-infos {
      description
        "Detailed peers database in XTC";
      list peer-detail-info {
        key "peer-address";
        description
          "Detailed PCE peer information";
        leaf peer-address {
          type inet:ip-address-no-zone;
          description
            "Peer Address";
        }
        uses live_ncs_PCE-PEER-DETAIL-BAG;
      }
    }
  }

  grouping live_ncs_PREFIX-TABLE {
    description
      "Common node of pce, pce-topology";
    container prefix-infos {
      description
        "Prefixes database in XTC";
      list prefix-info {
        key "node-identifier";
        description
          "PCE prefix information";
        leaf node-identifier {
          type uint32;
          description
            "Node ID";
        }
        uses live_ncs_PCE-PFX-BAG;
      }
    }
  }

  grouping live_ncs_TUNNEL-TABLE {
    description
      "Common node of pce, pce-lsp-data";
    container tunnel-infos {
      description
        "Tunnel database in XTC";
      list tunnel-info {
        key "peer-address plsp-id tunnel-name";
        description
          "Tunnel information";
        leaf peer-address {
          type inet:ip-address-no-zone;
          description
            "Peer Address";
        }
        leaf plsp-id {
          type uint32;
          description
            "PCEP LSP ID";
        }
        leaf tunnel-name {
          type string;
          description
            "Tunnel name";
        }
        uses live_ncs_PCE-TUN-BAG;
      }
    }
  }

  grouping live_ncs_REMOTE-PREFIX-TABLE {
    description
      "Common node of pce, pce-topology";
    container remote-prefixes {
      description
        "Remote Prefixes database in PCE";
      list remote-prefix {
        key "remote-pce-id";
        description
          "PCE remote prefix information";
        leaf remote-pce-id {
          type uint32;
          description
            "Remote PCE ID";
        }
        uses live_ncs_PCE-REMOTE-PFX-BAG;
      }
    }
  }

  grouping live_ncs_LSP-SUMMARY {
    description
      "Common node of pce, pce-lsp-data";
    container lsp-summary {
      description
        "LSP summary database in XTC";
      uses live_ncs_PCE-LSP-SUMMARY-BAG;
    }
  }

  grouping live_ncs_TOPOLOGY-SUMMARY-TABLE {
    description
      "Common node of pce, pce-topology";
    container topology-summaries {
      description
        "Node summary database in XTC";
      list topology-summary {
        key "af protocol";
        description
          "Node summary database in XTC";
        leaf af {
          type live_ncs_Pce-address-family-summary;
          description
            "Only show data related to the specified
             address family";
        }
        leaf protocol {
          type live_ncs_Pceigp-protocol-summary;
          description
            "Match nodes from the specified IGP protocol";
        }
        uses live_ncs_PCE-NODE-SUMMARY-BAG;
      }
    }
  }

  grouping live_ncs_TOPOLOGY-NODE-TABLE {
    description
      "Common node of pce, pce-topology";
    container topology-nodes {
      description
        "Node database in XTC";
      list topology-node {
        key "node-identifier";
        description
          "Node information";
        leaf node-identifier {
          type uint32;
          description
            "Node Identifier";
        }
        uses live_ncs_PCE-XTC-NODE-BAG;
      }
    }
  }

  grouping live_ncs_TUNNEL-DETAIL-TABLE {
    description
      "Common node of pce, pce-lsp-data";
    container tunnel-detail-infos {
      description
        "Detailed tunnel database in XTC";
      list tunnel-detail-info {
        key "peer-address plsp-id tunnel-name";
        description
          "Detailed tunnel information";
        leaf peer-address {
          type inet:ip-address-no-zone;
          description
            "Peer Address";
        }
        leaf plsp-id {
          type uint32;
          description
            "PCEP LSP ID";
        }
        leaf tunnel-name {
          type string;
          description
            "Tunnel name";
        }
        uses live_ncs_PCE-TUN-DETAIL-BAG;
      }
    }
  }

  grouping PEER-TABLE {
    description
      "Common node of pce, pce-peer";
    container peer-infos {
      description
        "Peers database in XTC";
      list peer-info {
        key "peer-address";
        description
          "PCE peer information";
        leaf peer-address {
          type inet:ip-address-no-zone;
          description
            "Peer Address";
        }
        uses PCE-PEER-BAG;
      }
    }
  }

  grouping PEER-DETAIL-TABLE {
    description
      "Common node of pce, pce-peer";
    container peer-detail-infos {
      description
        "Detailed peers database in XTC";
      list peer-detail-info {
        key "peer-address";
        description
          "Detailed PCE peer information";
        leaf peer-address {
          type inet:ip-address-no-zone;
          description
            "Peer Address";
        }
        uses PCE-PEER-DETAIL-BAG;
      }
    }
  }

  grouping PREFIX-TABLE {
    description
      "Common node of pce, pce-topology";
    container prefix-infos {
      description
        "Prefixes database in XTC";
      list prefix-info {
        key "node-identifier";
        description
          "PCE prefix information";
        leaf node-identifier {
          type uint32;
          description
            "Node ID";
        }
        uses PCE-PFX-BAG;
      }
    }
  }

  grouping TUNNEL-TABLE {
    description
      "Common node of pce, pce-lsp-data";
    container tunnel-infos {
      description
        "Tunnel database in XTC";
      list tunnel-info {
        key "peer-address plsp-id tunnel-name";
        description
          "Tunnel information";
        leaf peer-address {
          type inet:ip-address-no-zone;
          description
            "Peer Address";
        }
        leaf plsp-id {
          type uint32;
          description
            "PCEP LSP ID";
        }
        leaf tunnel-name {
          type string;
          description
            "Tunnel name";
        }
        uses PCE-TUN-BAG;
      }
    }
  }

  grouping REMOTE-PREFIX-TABLE {
    description
      "Common node of pce, pce-topology";
    container remote-prefixes {
      description
        "Remote Prefixes database in PCE";
      list remote-prefix {
        key "remote-pce-id";
        description
          "PCE remote prefix information";
        leaf remote-pce-id {
          type uint32;
          description
            "Remote PCE ID";
        }
        uses PCE-REMOTE-PFX-BAG;
      }
    }
  }

  grouping LSP-SUMMARY {
    description
      "Common node of pce, pce-lsp-data";
    container lsp-summary {
      description
        "LSP summary database in XTC";
      uses PCE-LSP-SUMMARY-BAG;
    }
  }

  grouping TOPOLOGY-SUMMARY-TABLE {
    description
      "Common node of pce, pce-topology";
    container topology-summaries {
      description
        "Node summary database in XTC";
      list topology-summary {
        key "af protocol";
        description
          "Node summary database in XTC";
        leaf af {
          type Pce-address-family-summary;
          description
            "Only show data related to the specified
             address family";
        }
        leaf protocol {
          type Pceigp-protocol-summary;
          description
            "Match nodes from the specified IGP protocol";
        }
        uses PCE-NODE-SUMMARY-BAG;
      }
    }
  }

  grouping TOPOLOGY-NODE-TABLE {
    description
      "Common node of pce, pce-topology";
    container topology-nodes {
      description
        "Node database in XTC";
      list topology-node {
        key "node-identifier";
        description
          "Node information";
        leaf node-identifier {
          type uint32;
          description
            "Node Identifier";
        }
        uses PCE-XTC-NODE-BAG;
      }
    }
  }

  grouping TUNNEL-DETAIL-TABLE {
    description
      "Common node of pce, pce-lsp-data";
    container tunnel-detail-infos {
      description
        "Detailed tunnel database in XTC";
      list tunnel-detail-info {
        key "peer-address plsp-id tunnel-name";
        description
          "Detailed tunnel information";
        leaf peer-address {
          type inet:ip-address-no-zone;
          description
            "Peer Address";
        }
        leaf plsp-id {
          type uint32;
          description
            "PCEP LSP ID";
        }
        leaf tunnel-name {
          type string;
          description
            "Tunnel name";
        }
        uses PCE-TUN-DETAIL-BAG;
      }
    }
  }

  augment "/ncs:devices/ncs:device/ncs:config" {
    // NCS drop config false container 'pce-lsp-data'
    // NCS drop config false container 'pce-peer'
    // NCS drop config false container 'pce-topology'
    // NCS drop config false container pce
  }
  augment "/ncs:devices/ncs:device/ncs:live-status" {
    container pce-lsp-data {
      tailf:ncs-device-type "netconf";
      tailf:display-when "not(../../ncs:module) or ../../ncs:module[ncs:name='Cisco-IOS-XR-infra-xtc-oper'] or (../../ncs:live-status-protocol[not(ncs:capability)]) or (../../ncs:live-status-protocol/ncs:capability/ncs:module[.='Cisco-IOS-XR-infra-xtc-oper'])";
      description
        "PCE LSP's data";
      uses live_ncs_TUNNEL-TABLE;
      uses live_ncs_LSP-SUMMARY;
      uses live_ncs_TUNNEL-DETAIL-TABLE;
    }
    container pce-peer {
      tailf:ncs-device-type "netconf";
      tailf:display-when "not(../../ncs:module) or ../../ncs:module[ncs:name='Cisco-IOS-XR-infra-xtc-oper'] or (../../ncs:live-status-protocol[not(ncs:capability)]) or (../../ncs:live-status-protocol/ncs:capability/ncs:module[.='Cisco-IOS-XR-infra-xtc-oper'])";
      description
        "PCE peer data";
      uses live_ncs_PEER-DETAIL-TABLE;
      uses live_ncs_PEER-TABLE;
    }
    container pce-topology {
      tailf:ncs-device-type "netconf";
      tailf:display-when "not(../../ncs:module) or ../../ncs:module[ncs:name='Cisco-IOS-XR-infra-xtc-oper'] or (../../ncs:live-status-protocol[not(ncs:capability)]) or (../../ncs:live-status-protocol/ncs:capability/ncs:module[.='Cisco-IOS-XR-infra-xtc-oper'])";
      description
        "PCE topology data";
      uses live_ncs_REMOTE-PREFIX-TABLE;
      uses live_ncs_TOPOLOGY-NODE-TABLE;
      uses live_ncs_TOPOLOGY-SUMMARY-TABLE;
      uses live_ncs_PREFIX-TABLE;
    }
    container pce {
      tailf:ncs-device-type "netconf";
      tailf:display-when "not(../../ncs:module) or ../../ncs:module[ncs:name='Cisco-IOS-XR-infra-xtc-oper'] or (../../ncs:live-status-protocol[not(ncs:capability)]) or (../../ncs:live-status-protocol/ncs:capability/ncs:module[.='Cisco-IOS-XR-infra-xtc-oper'])";
      description
        "PCE operational data";
      container authentication-keys {
        description
          "Authentication keys";
        list authentication-key {
          key "ip-address";
          description
            "PCE peer IP address";
          leaf ip-address {
            type inet:ip-address-no-zone;
            description
              "IP address";
          }
          uses live_ncs_PCE-PEER-AUTH-OPTION-BAG;
        }
      }
      container cspf-sr-mpls {
        description
          "CSPF for SR MPLS path info";
        container cspf-sr-mpls-paths {
          description
            "This table models the path calculation
             capabilities in XTC.A GET operation for the
             complete table will return no entries.";
          list cspf-sr-mpls-path {
            description
              "A GET operation on this class returns the path
               .";
            leaf af {
              type uint32;
              description
                "Address Family";
            }
            leaf source1 {
              type inet:ip-address-no-zone;
              description
                "Source of path 1";
            }
            leaf destination1 {
              type inet:ip-address-no-zone;
              description
                "Destination of path 1";
            }
            leaf metric-type {
              type uint32;
              description
                "Metric type";
            }
            leaf source2 {
              type inet:ip-address-no-zone;
              description
                "Source of path 2";
            }
            leaf destination2 {
              type inet:ip-address-no-zone;
              description
                "Destination of path 2";
            }
            leaf disjoint-level {
              type uint32;
              description
                "Disjointness level";
            }
            leaf disjoint-strict {
              type uint32;
              description
                "Strict disjointness required";
            }
            leaf shortest-path {
              type uint32;
              description
                "Whether path 1 or 2 should be shortest";
            }
            leaf msd1 {
              type uint32;
              description
                "MSD for path 1";
            }
            leaf msd2 {
              type uint32;
              description
                "MSD for path 2";
            }
            leaf relative-margin {
              type uint32;
              description
                "Relative Margin";
            }
            leaf absolute-margin {
              type uint32;
              description
                "Absolute Margin";
            }
            leaf affinity-include-all {
              type uint32;
              description
                "Affinity include-all constraint";
            }
            leaf affinity-include-any {
              type uint32;
              description
                "Affinity include-any constraint";
            }
            leaf affinity-exclude-any {
              type uint32;
              description
                "Affinity exclude-any constraint";
            }
            leaf protection-type1 {
              type live_ncs_Xtc-adj-sid-protection;
              description
                "Protection type for path 1";
            }
            leaf protection-type2 {
              type live_ncs_Xtc-adj-sid-protection;
              description
                "Protection type for path 2";
            }
            leaf flex-algo {
              type uint32;
              description
                "Flex Algo number";
            }
            leaf anycast-include {
              type boolean;
              description
                "Perform anycast SID inclusion";
            }
            uses live_ncs_PCE-SR-MPLS-PATH-LIST-BAG;
          }
        }
      }
      container segment-routing {
        description
          "Segment-Routing related data";
        container traffic-engineering {
          description
            "Traffic-engineering related data";
          container policies {
            description
              "PCE policies";
            list policy {
              description
                "PCE policy";
              leaf pcc-address {
                type inet:ip-address-no-zone;
                description
                  "PCC Address";
              }
              leaf policy-name {
                type xr:live_ncs_Cisco-ios-xr-string;
                description
                  "Policy Name";
              }
              uses live_ncs_PCE-POLICY-BAG;
            }
          }
        }
      }
      container verification-events {
        description
          "PCE Verification events in XTC";
        list verification-event {
          key "event-idx";
          description
            "PCE single verification event";
          leaf event-idx {
            type uint32;
            description
              "Index of an event";
          }
          uses live_ncs_PCE-EVENT-INFO;
        }
      }
      container api {
        description
          "PCE API details";
        container sibling {
          description
            "PCE sibling";
          container synced-lsps {
            description
              "Synced LSP table";
            list synced-lsp {
              description
                "Synced LSP details";
              leaf pcc-address {
                type inet:ip-address-no-zone;
                description
                  "PCC Address";
              }
              leaf lsp-name {
                type string;
                description
                  "Name of the synced LSP";
              }
              leaf remote-flag {
                type boolean;
                description
                  "Flag to indicate lsp data is remote";
              }
              uses live_ncs_PCE-SIBLING-SYNCED-LSP-BAG;
            }
          }
          container connection {
            description
              "Connection information";
            uses live_ncs_PCE-SIBLING-CONN-BAG;
          }
        }
      }
      container p2mp-policies {
        description
          "P2MP policy database in SR-PCE";
        list p2mp-policy {
          key "name";
          description
            "Policy information";
          leaf name {
            type xr:live_ncs_Cisco-ios-xr-string;
            description
              "Policy name";
          }
          uses live_ncs_PCE-TREESID-BAG;
        }
      }
      container peer-summaries {
        description
          "Detailed PCE peer information";
        list peer-summary {
          key "af";
          description
            "Summary PCE peer information";
          leaf af {
            type live_ncs_Pce-address-family;
            description
              "Only show data related to the specified
               address family";
          }
          uses live_ncs_PCE-PEER-SUMMARY-BAG;
        }
      }
      container cspf-srv6 {
        description
          "CSPF for SRV6 path info";
        container cspf-srv6-paths {
          description
            "This table models the path calculation
             capabilities in XTC.A GET operation for the
             complete table will return no entries.";
          list cspf-srv6-path {
            description
              "A GET operation on this class returns the path
               .";
            leaf af {
              type uint32;
              description
                "Address Family";
            }
            leaf source1 {
              type inet:ip-address-no-zone;
              description
                "Source of path 1";
            }
            leaf destination1 {
              type inet:ip-address-no-zone;
              description
                "Destination of path 1";
            }
            leaf metric-type {
              type uint32;
              description
                "Metric type";
            }
            leaf source2 {
              type inet:ip-address-no-zone;
              description
                "Source of path 2";
            }
            leaf destination2 {
              type inet:ip-address-no-zone;
              description
                "Destination of path 2";
            }
            leaf disjoint-level {
              type uint32;
              description
                "Disjointness level";
            }
            leaf disjoint-strict {
              type uint32;
              description
                "Strict disjointness required";
            }
            leaf shortest-path {
              type uint32;
              description
                "Whether path 1 or 2 should be shortest";
            }
            leaf msd1 {
              type uint32;
              description
                "MSD for path 1";
            }
            leaf msd2 {
              type uint32;
              description
                "MSD for path 2";
            }
            leaf relative-margin {
              type uint32;
              description
                "Relative Margin";
            }
            leaf absolute-margin {
              type uint32;
              description
                "Absolute Margin";
            }
            leaf affinity-include-all {
              type uint32;
              description
                "Affinity include-all constraint";
            }
            leaf affinity-include-any {
              type uint32;
              description
                "Affinity include-any constraint";
            }
            leaf affinity-exclude-any {
              type uint32;
              description
                "Affinity exclude-any constraint";
            }
            uses live_ncs_PCE-SR-MPLS-PATH-LIST-BAG;
          }
        }
      }
      container flex-algos {
        description
          "FlexAlgo database in PCE";
        list flex-algo {
          description
            "FlexAlgo Definition";
          leaf igp-type {
            type live_ncs_Pceigp-protocol;
            description
              "Match nodes from the specified IGP protocol";
          }
          leaf domain-id {
            type uint32;
            description
              "Domain ID";
          }
          leaf area-id {
            type uint32;
            description
              "Area ID";
          }
          uses live_ncs_PCE-FLEX-ALGO-AREA;
        }
      }
      container work-nodes {
        description
          "Work node database";
        list work-node {
          key "index";
          description
            "Path work node information";
          leaf index {
            type uint32;
            description
              "Position in work list";
          }
          uses live_ncs_PATH-WORK-NODE;
        }
      }
      container trace-buffer-summaries {
        description
          "Summary of all trace buffers";
        list trace-buffer-summary {
          key "name";
          description
            "Summary of specific trace buffer";
          leaf name {
            type xr:live_ncs_Cisco-ios-xr-string;
            description
              "Trace buffer name";
          }
          uses live_ncs_CMN-TRACE-BUFFER-SUMMARY-BAG;
        }
      }
      container association-infos {
        description
          "Associaition database in XTC";
        list association-info {
          key "group-id";
          description
            "PCE Association information";
          leaf group-id {
            type uint32;
            description
              "Group ID";
          }
          leaf type {
            type live_ncs_Pce-asso;
            description
              "Type";
          }
          leaf sub-id {
            type inet:ip-address-no-zone;
            description
              "Sub ID";
          }
          uses live_ncs_PCE-ASSO-BAG;
        }
      }
      container work-groups {
        description
          "Work group database";
        list work-group {
          key "algo";
          description
            "Path work group information";
          leaf algo {
            type uint32;
            description
              "Algorithm";
          }
          leaf metric-type {
            type uint32;
            description
              "Metric Type";
          }
          leaf msd {
            type uint32;
            description
              "Max SID Depth";
          }
          leaf inc-all {
            type uint32;
            description
              "Include-All affinity";
          }
          leaf exc-any {
            type uint32;
            description
              "Exclude-Any affinity";
          }
          leaf inc-any {
            type uint32;
            description
              "Include-Any affinity";
          }
          leaf source {
            type inet:ip-address-no-zone;
            description
              "Source";
          }
          uses live_ncs_PATH-WORK-GROUP;
        }
      }
      container paths {
        description
          "This table models the path calculation
           capabilities in XTC.A GET operation for the
           complete table will return no entries.";
        list path {
          key "af source destination";
          description
            "A GET operation on this class returns the path.";
          leaf af {
            type uint32;
            description
              "Address Family";
          }
          leaf source {
            type inet:ip-address-no-zone;
            description
              "Source of path";
          }
          leaf destination {
            type inet:ip-address-no-zone;
            description
              "Destination of path";
          }
          uses live_ncs_PCE-PATH-BAG;
        }
      }
      container p2mp-policy-infos {
        description
          "P2MP policy database indexed by Root address in
           XTC";
        list p2mp-policy-info {
          key "root-address tree-id";
          description
            "P2MP Policy information";
          leaf root-address {
            type inet:ip-address-no-zone;
            description
              "Root Address";
          }
          leaf tree-id {
            type uint32;
            description
              "P2MP Policy Tree-ID";
          }
          uses live_ncs_PCE-TREESID-BAG;
        }
      }
      container cspf {
        description
          "CSPF path info";
        container cspf-paths {
          description
            "This table models the path calculation
             capabilities in XTC.A GET operation for the
             complete table will return no entries.";
          list cspf-path {
            description
              "A GET operation on this class returns the path
               .";
            leaf af {
              type uint32;
              description
                "Address Family";
            }
            leaf source1 {
              type inet:ip-address-no-zone;
              description
                "Source of path 1";
            }
            leaf destination1 {
              type inet:ip-address-no-zone;
              description
                "Destination of path 1";
            }
            leaf metric-type {
              type uint32;
              description
                "Metric type";
            }
            leaf source2 {
              type inet:ip-address-no-zone;
              description
                "Source of path 2";
            }
            leaf destination2 {
              type inet:ip-address-no-zone;
              description
                "Destination of path 2";
            }
            leaf disjoint-level {
              type uint32;
              description
                "Disjointness level";
            }
            leaf disjoint-strict {
              type uint32;
              description
                "Strict disjointness required";
            }
            leaf shortest-path {
              type uint32;
              description
                "Whether path 1 or 2 should be shortest";
            }
            uses live_ncs_PCE-PATH-LIST-BAG;
          }
        }
      }
      container statistics-nodes {
        description
          "PCE API peer statistics";
        list statistics-node {
          key "ip";
          description
            "PCE API peer statistics information";
          leaf ip {
            type inet:ip-address-no-zone;
            description
              "Specify IPv4 or v6 Address";
          }
          uses live_ncs_API-PEER-STATS-BAG;
        }
      }
      uses live_ncs_REMOTE-PREFIX-TABLE;
      uses live_ncs_TUNNEL-TABLE;
      uses live_ncs_PEER-DETAIL-TABLE;
      uses live_ncs_TOPOLOGY-NODE-TABLE;
      uses live_ncs_TOPOLOGY-SUMMARY-TABLE;
      uses live_ncs_PREFIX-TABLE;
      uses live_ncs_LSP-SUMMARY;
      uses live_ncs_PEER-TABLE;
      uses live_ncs_TUNNEL-DETAIL-TABLE;
    }
  }
  augment "/ncs:devices/ncs:template/ncs:ned-id/ncs:config" {
    // NCS drop config false container 'pce-lsp-data'
    // NCS drop config false container 'pce-peer'
    // NCS drop config false container 'pce-topology'
    // NCS drop config false container pce
  }
}

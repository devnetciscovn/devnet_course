module Cisco-IOS-XR-crypto-cepki-oper {
  // Generated by yanger -t ncs
  tailf:mount-id "cisco-iosxr-nc-7.3:cisco-iosxr-nc-7.3";
  tailf:ncs-device-type "netconf";

  namespace "http://cisco.com/ns/yang/Cisco-IOS-XR-crypto-cepki-oper";
  prefix crypto-cepki-oper;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-cepki package operational data.

     This module contains definitions
     for the following management objects:
       crypto-certificate-authority: Public Key Infrastructure
         Related Information

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_CERTIFICATE-EXPIRES-ON {
    description
      "Common node of certificate-authority-certificate,
       router-certificate, router-signature-certificate,
       router-encryption-certificate";
    leaf certificate-expires-on {
      type string;
      units "second";
      description
        "Valid before date of the Certificate, in seconds
         since 00:00:00 UTC, January 1, 1970";
    }
  }

  grouping ncs_template_ISSUER {
    description
      "Common node of certificate-authority-certificate,
       router-certificate, router-signature-certificate,
       router-encryption-certificate";
    leaf issuer {
      type string;
      description
        "Issuer Name of the Certificate";
    }
  }

  grouping ncs_template_CRL-DISTRIBUTION-POINT-TABLE {
    description
      "Common node of certificate-authority-certificate,
       router-certificate, router-signature-certificate,
       router-encryption-certificate";
    container crl-distribution-points {
      description
        "Router Certificates CRLDistributionPoint Table";
      list crl-distribution-point {
        // NCS patched for predictable order
        ordered-by user;
        key "index";
        description
          "Certificate CRLDistributionPoint Instance";
        leaf index {
          type string;
          description
            "CDP Entry Index";
        }
        leaf cdp-content {
          type string;
          // NCS drop mandatory statement
          description
            "CRLDistributionPoint Content";
        }
      }
    }
  }

  grouping ncs_template_CERTIFICATE-VALID-FROM {
    description
      "Common node of certificate-authority-certificate,
       router-certificate, router-signature-certificate,
       router-encryption-certificate";
    leaf certificate-valid-from {
      type string;
      units "second";
      description
        "Valid from date of the Certificate, in seconds
         since 00:00:00 UTC, January 1, 1970";
    }
  }

  grouping ncs_template_SUBJECT {
    description
      "Common node of certificate-authority-certificate,
       router-certificate, router-signature-certificate,
       router-encryption-certificate";
    leaf subject {
      type string;
      description
        "Subject Name of the Certificate";
    }
  }

  grouping ncs_rpc_notif_CERTIFICATE-EXPIRES-ON {
    description
      "Common node of certificate-authority-certificate,
       router-certificate, router-signature-certificate,
       router-encryption-certificate";
    leaf certificate-expires-on {
      type uint64;
      units "second";
      description
        "Valid before date of the Certificate, in seconds
         since 00:00:00 UTC, January 1, 1970";
    }
  }

  grouping ncs_rpc_notif_ISSUER {
    description
      "Common node of certificate-authority-certificate,
       router-certificate, router-signature-certificate,
       router-encryption-certificate";
    leaf issuer {
      type string;
      description
        "Issuer Name of the Certificate";
    }
  }

  grouping ncs_rpc_notif_CRL-DISTRIBUTION-POINT-TABLE {
    description
      "Common node of certificate-authority-certificate,
       router-certificate, router-signature-certificate,
       router-encryption-certificate";
    container crl-distribution-points {
      description
        "Router Certificates CRLDistributionPoint Table";
      list crl-distribution-point {
        key "index";
        description
          "Certificate CRLDistributionPoint Instance";
        leaf index {
          type uint32;
          description
            "CDP Entry Index";
        }
        leaf cdp-content {
          type string;
          mandatory true;
          description
            "CRLDistributionPoint Content";
        }
      }
    }
  }

  grouping ncs_rpc_notif_CERTIFICATE-VALID-FROM {
    description
      "Common node of certificate-authority-certificate,
       router-certificate, router-signature-certificate,
       router-encryption-certificate";
    leaf certificate-valid-from {
      type uint64;
      units "second";
      description
        "Valid from date of the Certificate, in seconds
         since 00:00:00 UTC, January 1, 1970";
    }
  }

  grouping ncs_rpc_notif_SUBJECT {
    description
      "Common node of certificate-authority-certificate,
       router-certificate, router-signature-certificate,
       router-encryption-certificate";
    leaf subject {
      type string;
      description
        "Subject Name of the Certificate";
    }
  }

  grouping live_ncs_CERTIFICATE-EXPIRES-ON {
    description
      "Common node of certificate-authority-certificate,
       router-certificate, router-signature-certificate,
       router-encryption-certificate";
    leaf certificate-expires-on {
      type uint64;
      units "second";
      description
        "Valid before date of the Certificate, in seconds
         since 00:00:00 UTC, January 1, 1970";
    }
  }

  grouping live_ncs_ISSUER {
    description
      "Common node of certificate-authority-certificate,
       router-certificate, router-signature-certificate,
       router-encryption-certificate";
    leaf issuer {
      type string;
      description
        "Issuer Name of the Certificate";
    }
  }

  grouping live_ncs_CRL-DISTRIBUTION-POINT-TABLE {
    description
      "Common node of certificate-authority-certificate,
       router-certificate, router-signature-certificate,
       router-encryption-certificate";
    container crl-distribution-points {
      description
        "Router Certificates CRLDistributionPoint Table";
      list crl-distribution-point {
        key "index";
        description
          "Certificate CRLDistributionPoint Instance";
        leaf index {
          type uint32;
          description
            "CDP Entry Index";
        }
        leaf cdp-content {
          type string;
          // NCS drop mandatory statement
          description
            "CRLDistributionPoint Content";
        }
      }
    }
  }

  grouping live_ncs_CERTIFICATE-VALID-FROM {
    description
      "Common node of certificate-authority-certificate,
       router-certificate, router-signature-certificate,
       router-encryption-certificate";
    leaf certificate-valid-from {
      type uint64;
      units "second";
      description
        "Valid from date of the Certificate, in seconds
         since 00:00:00 UTC, January 1, 1970";
    }
  }

  grouping live_ncs_SUBJECT {
    description
      "Common node of certificate-authority-certificate,
       router-certificate, router-signature-certificate,
       router-encryption-certificate";
    leaf subject {
      type string;
      description
        "Subject Name of the Certificate";
    }
  }

  grouping CERTIFICATE-EXPIRES-ON {
    description
      "Common node of certificate-authority-certificate,
       router-certificate, router-signature-certificate,
       router-encryption-certificate";
    leaf certificate-expires-on {
      type uint64;
      units "second";
      description
        "Valid before date of the Certificate, in seconds
         since 00:00:00 UTC, January 1, 1970";
    }
  }

  grouping ISSUER {
    description
      "Common node of certificate-authority-certificate,
       router-certificate, router-signature-certificate,
       router-encryption-certificate";
    leaf issuer {
      type string;
      description
        "Issuer Name of the Certificate";
    }
  }

  grouping CRL-DISTRIBUTION-POINT-TABLE {
    description
      "Common node of certificate-authority-certificate,
       router-certificate, router-signature-certificate,
       router-encryption-certificate";
    container crl-distribution-points {
      description
        "Router Certificates CRLDistributionPoint Table";
      list crl-distribution-point {
        key "index";
        description
          "Certificate CRLDistributionPoint Instance";
        leaf index {
          type uint32;
          description
            "CDP Entry Index";
        }
        leaf cdp-content {
          type string;
          mandatory true;
          description
            "CRLDistributionPoint Content";
        }
      }
    }
  }

  grouping CERTIFICATE-VALID-FROM {
    description
      "Common node of certificate-authority-certificate,
       router-certificate, router-signature-certificate,
       router-encryption-certificate";
    leaf certificate-valid-from {
      type uint64;
      units "second";
      description
        "Valid from date of the Certificate, in seconds
         since 00:00:00 UTC, January 1, 1970";
    }
  }

  grouping SUBJECT {
    description
      "Common node of certificate-authority-certificate,
       router-certificate, router-signature-certificate,
       router-encryption-certificate";
    leaf subject {
      type string;
      description
        "Subject Name of the Certificate";
    }
  }

  augment "/ncs:devices/ncs:device/ncs:config" {
    // NCS drop config false container 'crypto-certificate-authority'
  }
  augment "/ncs:devices/ncs:device/ncs:live-status" {
    container crypto-certificate-authority {
      tailf:ncs-device-type "netconf";
      tailf:display-when "not(../../ncs:module) or ../../ncs:module[ncs:name='Cisco-IOS-XR-crypto-cepki-oper'] or (../../ncs:live-status-protocol[not(ncs:capability)]) or (../../ncs:live-status-protocol/ncs:capability/ncs:module[.='Cisco-IOS-XR-crypto-cepki-oper'])";
      description
        "Public Key Infrastructure Related Information";
      container trustpoints {
        description
          "CA Trustpoint Table Information";
        list trustpoint {
          key "name";
          description
            "Certificate Information for a particular
             Trustpoint";
          container router-certificate {
            description
              "Router Certificate Attributes";
            uses live_ncs_SUBJECT;
            uses live_ncs_CERTIFICATE-VALID-FROM;
            uses live_ncs_CRL-DISTRIBUTION-POINT-TABLE;
            uses live_ncs_CERTIFICATE-EXPIRES-ON;
            uses live_ncs_ISSUER;
          }
          container router-encryption-certificate {
            description
              "Router Encryption Certificate Attributes";
            uses live_ncs_SUBJECT;
            uses live_ncs_CERTIFICATE-VALID-FROM;
            uses live_ncs_CRL-DISTRIBUTION-POINT-TABLE;
            uses live_ncs_CERTIFICATE-EXPIRES-ON;
            uses live_ncs_ISSUER;
          }
          container router-signature-certificate {
            description
              "Router Signature Certificate Attributes";
            uses live_ncs_SUBJECT;
            uses live_ncs_CERTIFICATE-VALID-FROM;
            uses live_ncs_CRL-DISTRIBUTION-POINT-TABLE;
            uses live_ncs_CERTIFICATE-EXPIRES-ON;
            uses live_ncs_ISSUER;
          }
          container certificate-authority-certificate {
            description
              "Certificate Authority Certificate Attributes";
            uses live_ncs_SUBJECT;
            uses live_ncs_CERTIFICATE-VALID-FROM;
            uses live_ncs_CRL-DISTRIBUTION-POINT-TABLE;
            uses live_ncs_CERTIFICATE-EXPIRES-ON;
            uses live_ncs_ISSUER;
          }
          leaf name {
            type xr:live_ncs_Cisco-ios-xr-string;
            description
              "The Trustpoint to query";
          }
        }
      }
    }
  }
  augment "/ncs:devices/ncs:template/ncs:ned-id/ncs:config" {
    // NCS drop config false container 'crypto-certificate-authority'
  }
}

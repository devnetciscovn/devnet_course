submodule Cisco-IOS-XR-l2-eth-infra-oper-sub2 {
  // Generated by yanger -t ncs
  tailf:mount-id "cisco-iosxr-nc-7.3:cisco-iosxr-nc-7.3";

  belongs-to Cisco-IOS-XR-l2-eth-infra-oper {
    prefix Cisco-IOS-XR-l2-eth-infra-oper;
  }

  import ietf-yang-types {
    prefix yang;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR l2-eth-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Vlan-service {
    type string;
    description
      "Layer 2 vs. Layer 3 Terminated Service";
  }

  typedef ncs_template_Vlan-encaps {
    type string;
    description
      "VLAN encapsulation";
  }

  typedef ncs_template_Mac-address {
    type string;
    description
      "MAC address type";
  }

  typedef ncs_template_Efp-payload-etype {
    type string;
    description
      "Payload ethertype match";
  }

  typedef ncs_template_Efp-tag-priority {
    type string;
    description
      "Priority";
  }

  typedef ncs_template_Efp-tag-etype {
    type string;
    description
      "Tag ethertype";
  }

  typedef ncs_template_Vlan-switched-mode {
    type string;
    description
      "VLAN-Switched mode";
  }

  typedef ncs_template_Eth-filtering {
    type string;
    description
      "Ethernet frame filtering";
  }

  typedef ncs_template_Vlan-qinq-outer-etype {
    type string;
    description
      "QinQ Outer Tag Ethertype";
  }

  typedef ncs_template_Vlan-tag-value {
    type string;
    description
      "VLAN Tag Value (1 - 4094)";
  }

  typedef ncs_template_Im-state-enum {
    type string;
    description
      "Im state enum";
  }

  typedef ncs_rpc_notif_Vlan-service {
    type enumeration {
      enum "vlan-service-l2" {
        value 1;
        description
          "Layer 2 Transport Service";
      }
      enum "vlan-service-l3" {
        value 2;
        description
          "Layer 3 Terminated Service";
      }
    }
    description
      "Layer 2 vs. Layer 3 Terminated Service";
  }

  typedef ncs_rpc_notif_Vlan-encaps {
    type enumeration {
      enum "no-encapsulation" {
        value 0;
        description
          "No encapsulation";
      }
      enum "dot1q" {
        value 1;
        description
          "IEEE 802.1Q encapsulation";
      }
      enum "qinq" {
        value 2;
        description
          "Double 802.1Q encapsulation";
      }
      enum "qin-any" {
        value 3;
        description
          "Double 802.1Q wildcarded encapsulation";
      }
      enum "dot1q-native" {
        value 4;
        description
          "IEEE 802.1Q native VLAN encapsulation";
      }
      enum "dot1ad" {
        value 5;
        description
          "IEEE 802.1ad encapsulation";
      }
      enum "dot1ad-native" {
        value 6;
        description
          "IEEE 802.1ad native VLAN encapsulation";
      }
      enum "service-instance" {
        value 7;
        description
          "Ethernet Service Instance";
      }
      enum "dot1ad-dot1q" {
        value 8;
        description
          "IEEE 802.1ad 802.1Q encapsulation";
      }
      enum "dot1ad-any" {
        value 9;
        description
          "IEEE 802.1ad wildcard 802.1Q encapsulation";
      }
    }
    description
      "VLAN encapsulation";
  }

  typedef ncs_rpc_notif_Mac-address {
    type yang:mac-address;
    description
      "MAC address type";
  }

  typedef ncs_rpc_notif_Efp-payload-etype {
    type enumeration {
      enum "payload-ethertype-any" {
        value 0;
        description
          "Any";
      }
      enum "payload-ethertype-ip" {
        value 1;
        description
          "IP";
      }
      enum "payload-ethertype-pppoe" {
        value 2;
        description
          "PPPoE";
      }
    }
    description
      "Payload ethertype match";
  }

  typedef ncs_rpc_notif_Efp-tag-priority {
    type enumeration {
      enum "priority0" {
        value 0;
        description
          "Priority 0";
      }
      enum "priority1" {
        value 1;
        description
          "Priority 1";
      }
      enum "priority2" {
        value 2;
        description
          "Priority 2";
      }
      enum "priority3" {
        value 3;
        description
          "Priority 3";
      }
      enum "priority4" {
        value 4;
        description
          "Priority 4";
      }
      enum "priority5" {
        value 5;
        description
          "Priority 5";
      }
      enum "priority6" {
        value 6;
        description
          "Priority 6";
      }
      enum "priority7" {
        value 7;
        description
          "Priority 7";
      }
      enum "priority-any" {
        value 8;
        description
          "Any priority";
      }
    }
    description
      "Priority";
  }

  typedef ncs_rpc_notif_Efp-tag-etype {
    type enumeration {
      enum "untagged" {
        value 0;
        description
          "Untagged";
      }
      enum "dot1q" {
        value 33024;
        description
          "Dot1Q";
      }
      enum "dot1ad" {
        value 34984;
        description
          "Dot1ad";
      }
    }
    description
      "Tag ethertype";
  }

  typedef ncs_rpc_notif_Vlan-switched-mode {
    type enumeration {
      enum "none" {
        value 0;
        description
          "Disabled";
      }
      enum "trunk-port" {
        value 1;
        description
          "Trunk port";
      }
      enum "access-port" {
        value 2;
        description
          "Access port";
      }
    }
    description
      "VLAN-Switched mode";
  }

  typedef ncs_rpc_notif_Eth-filtering {
    type enumeration {
      enum "no-filtering" {
        value 0;
        description
          "No IEEE 802.1Q/802.1ad/MAC relay multicast MAC
           address filtering";
      }
      enum "dot1q-filtering" {
        value 1;
        description
          "IEEE 802.1q C-VLAN filtering";
      }
      enum "dot1ad-filtering" {
        value 2;
        description
          "IEEE 802.1ad S-VLAN filtering";
      }
      enum "two-port-mac-relay-filtering" {
        value 3;
        description
          "IEEE 802.1aj 2-Port MAC relay filtering";
      }
    }
    description
      "Ethernet frame filtering";
  }

  typedef ncs_rpc_notif_Vlan-qinq-outer-etype {
    type enumeration {
      enum "ether-type8100" {
        value 33024;
        description
          "Dot1Q (0x8100)";
      }
      enum "ether-type9100" {
        value 37120;
        description
          "0x9100";
      }
      enum "ether-type9200" {
        value 37376;
        description
          "0x9200";
      }
    }
    description
      "QinQ Outer Tag Ethertype";
  }

  typedef ncs_rpc_notif_Vlan-tag-value {
    type uint16;
    description
      "VLAN Tag Value (1 - 4094)";
  }

  typedef ncs_rpc_notif_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef live_ncs_Vlan-service {
    type enumeration {
      enum "vlan-service-l2" {
        value 1;
        description
          "Layer 2 Transport Service";
      }
      enum "vlan-service-l3" {
        value 2;
        description
          "Layer 3 Terminated Service";
      }
    }
    description
      "Layer 2 vs. Layer 3 Terminated Service";
  }

  typedef live_ncs_Vlan-encaps {
    type enumeration {
      enum "no-encapsulation" {
        value 0;
        description
          "No encapsulation";
      }
      enum "dot1q" {
        value 1;
        description
          "IEEE 802.1Q encapsulation";
      }
      enum "qinq" {
        value 2;
        description
          "Double 802.1Q encapsulation";
      }
      enum "qin-any" {
        value 3;
        description
          "Double 802.1Q wildcarded encapsulation";
      }
      enum "dot1q-native" {
        value 4;
        description
          "IEEE 802.1Q native VLAN encapsulation";
      }
      enum "dot1ad" {
        value 5;
        description
          "IEEE 802.1ad encapsulation";
      }
      enum "dot1ad-native" {
        value 6;
        description
          "IEEE 802.1ad native VLAN encapsulation";
      }
      enum "service-instance" {
        value 7;
        description
          "Ethernet Service Instance";
      }
      enum "dot1ad-dot1q" {
        value 8;
        description
          "IEEE 802.1ad 802.1Q encapsulation";
      }
      enum "dot1ad-any" {
        value 9;
        description
          "IEEE 802.1ad wildcard 802.1Q encapsulation";
      }
    }
    description
      "VLAN encapsulation";
  }

  typedef live_ncs_Mac-address {
    type yang:mac-address;
    description
      "MAC address type";
  }

  typedef live_ncs_Efp-payload-etype {
    type enumeration {
      enum "payload-ethertype-any" {
        value 0;
        description
          "Any";
      }
      enum "payload-ethertype-ip" {
        value 1;
        description
          "IP";
      }
      enum "payload-ethertype-pppoe" {
        value 2;
        description
          "PPPoE";
      }
    }
    description
      "Payload ethertype match";
  }

  typedef live_ncs_Efp-tag-priority {
    type enumeration {
      enum "priority0" {
        value 0;
        description
          "Priority 0";
      }
      enum "priority1" {
        value 1;
        description
          "Priority 1";
      }
      enum "priority2" {
        value 2;
        description
          "Priority 2";
      }
      enum "priority3" {
        value 3;
        description
          "Priority 3";
      }
      enum "priority4" {
        value 4;
        description
          "Priority 4";
      }
      enum "priority5" {
        value 5;
        description
          "Priority 5";
      }
      enum "priority6" {
        value 6;
        description
          "Priority 6";
      }
      enum "priority7" {
        value 7;
        description
          "Priority 7";
      }
      enum "priority-any" {
        value 8;
        description
          "Any priority";
      }
    }
    description
      "Priority";
  }

  typedef live_ncs_Efp-tag-etype {
    type enumeration {
      enum "untagged" {
        value 0;
        description
          "Untagged";
      }
      enum "dot1q" {
        value 33024;
        description
          "Dot1Q";
      }
      enum "dot1ad" {
        value 34984;
        description
          "Dot1ad";
      }
    }
    description
      "Tag ethertype";
  }

  typedef live_ncs_Vlan-switched-mode {
    type enumeration {
      enum "none" {
        value 0;
        description
          "Disabled";
      }
      enum "trunk-port" {
        value 1;
        description
          "Trunk port";
      }
      enum "access-port" {
        value 2;
        description
          "Access port";
      }
    }
    description
      "VLAN-Switched mode";
  }

  typedef live_ncs_Eth-filtering {
    type enumeration {
      enum "no-filtering" {
        value 0;
        description
          "No IEEE 802.1Q/802.1ad/MAC relay multicast MAC
           address filtering";
      }
      enum "dot1q-filtering" {
        value 1;
        description
          "IEEE 802.1q C-VLAN filtering";
      }
      enum "dot1ad-filtering" {
        value 2;
        description
          "IEEE 802.1ad S-VLAN filtering";
      }
      enum "two-port-mac-relay-filtering" {
        value 3;
        description
          "IEEE 802.1aj 2-Port MAC relay filtering";
      }
    }
    description
      "Ethernet frame filtering";
  }

  typedef live_ncs_Vlan-qinq-outer-etype {
    type enumeration {
      enum "ether-type8100" {
        value 33024;
        description
          "Dot1Q (0x8100)";
      }
      enum "ether-type9100" {
        value 37120;
        description
          "0x9100";
      }
      enum "ether-type9200" {
        value 37376;
        description
          "0x9200";
      }
    }
    description
      "QinQ Outer Tag Ethertype";
  }

  typedef live_ncs_Vlan-tag-value {
    type uint16;
    description
      "VLAN Tag Value (1 - 4094)";
  }

  typedef live_ncs_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Vlan-service {
    type enumeration {
      enum "vlan-service-l2" {
        value 1;
        description
          "Layer 2 Transport Service";
      }
      enum "vlan-service-l3" {
        value 2;
        description
          "Layer 3 Terminated Service";
      }
    }
    description
      "Layer 2 vs. Layer 3 Terminated Service";
  }

  typedef Vlan-encaps {
    type enumeration {
      enum "no-encapsulation" {
        value 0;
        description
          "No encapsulation";
      }
      enum "dot1q" {
        value 1;
        description
          "IEEE 802.1Q encapsulation";
      }
      enum "qinq" {
        value 2;
        description
          "Double 802.1Q encapsulation";
      }
      enum "qin-any" {
        value 3;
        description
          "Double 802.1Q wildcarded encapsulation";
      }
      enum "dot1q-native" {
        value 4;
        description
          "IEEE 802.1Q native VLAN encapsulation";
      }
      enum "dot1ad" {
        value 5;
        description
          "IEEE 802.1ad encapsulation";
      }
      enum "dot1ad-native" {
        value 6;
        description
          "IEEE 802.1ad native VLAN encapsulation";
      }
      enum "service-instance" {
        value 7;
        description
          "Ethernet Service Instance";
      }
      enum "dot1ad-dot1q" {
        value 8;
        description
          "IEEE 802.1ad 802.1Q encapsulation";
      }
      enum "dot1ad-any" {
        value 9;
        description
          "IEEE 802.1ad wildcard 802.1Q encapsulation";
      }
    }
    description
      "VLAN encapsulation";
  }

  typedef Mac-address {
    type yang:mac-address;
    description
      "MAC address type";
  }

  typedef Efp-payload-etype {
    type enumeration {
      enum "payload-ethertype-any" {
        value 0;
        description
          "Any";
      }
      enum "payload-ethertype-ip" {
        value 1;
        description
          "IP";
      }
      enum "payload-ethertype-pppoe" {
        value 2;
        description
          "PPPoE";
      }
    }
    description
      "Payload ethertype match";
  }

  typedef Efp-tag-priority {
    type enumeration {
      enum "priority0" {
        value 0;
        description
          "Priority 0";
      }
      enum "priority1" {
        value 1;
        description
          "Priority 1";
      }
      enum "priority2" {
        value 2;
        description
          "Priority 2";
      }
      enum "priority3" {
        value 3;
        description
          "Priority 3";
      }
      enum "priority4" {
        value 4;
        description
          "Priority 4";
      }
      enum "priority5" {
        value 5;
        description
          "Priority 5";
      }
      enum "priority6" {
        value 6;
        description
          "Priority 6";
      }
      enum "priority7" {
        value 7;
        description
          "Priority 7";
      }
      enum "priority-any" {
        value 8;
        description
          "Any priority";
      }
    }
    description
      "Priority";
  }

  typedef Efp-tag-etype {
    type enumeration {
      enum "untagged" {
        value 0;
        description
          "Untagged";
      }
      enum "dot1q" {
        value 33024;
        description
          "Dot1Q";
      }
      enum "dot1ad" {
        value 34984;
        description
          "Dot1ad";
      }
    }
    description
      "Tag ethertype";
  }

  typedef Vlan-switched-mode {
    type enumeration {
      enum "none" {
        value 0;
        description
          "Disabled";
      }
      enum "trunk-port" {
        value 1;
        description
          "Trunk port";
      }
      enum "access-port" {
        value 2;
        description
          "Access port";
      }
    }
    description
      "VLAN-Switched mode";
  }

  typedef Eth-filtering {
    type enumeration {
      enum "no-filtering" {
        value 0;
        description
          "No IEEE 802.1Q/802.1ad/MAC relay multicast MAC
           address filtering";
      }
      enum "dot1q-filtering" {
        value 1;
        description
          "IEEE 802.1q C-VLAN filtering";
      }
      enum "dot1ad-filtering" {
        value 2;
        description
          "IEEE 802.1ad S-VLAN filtering";
      }
      enum "two-port-mac-relay-filtering" {
        value 3;
        description
          "IEEE 802.1aj 2-Port MAC relay filtering";
      }
    }
    description
      "Ethernet frame filtering";
  }

  typedef Vlan-qinq-outer-etype {
    type enumeration {
      enum "ether-type8100" {
        value 33024;
        description
          "Dot1Q (0x8100)";
      }
      enum "ether-type9100" {
        value 37120;
        description
          "0x9100";
      }
      enum "ether-type9200" {
        value 37376;
        description
          "0x9200";
      }
    }
    description
      "QinQ Outer Tag Ethertype";
  }

  typedef Vlan-tag-value {
    type uint16;
    description
      "VLAN Tag Value (1 - 4094)";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  grouping ncs_template_VLAN-DOUBLE-TAG-STACK {
    description
      "VLAN double tag stack";
    leaf outer-tag {
      type ncs_template_Vlan-tag-value;
      description
        "Outer tag value";
    }
    leaf second-tag {
      type ncs_template_Vlan-tag-value;
      description
        "Second tag value";
    }
  }

  grouping ncs_template_VLAN-TAG-STACK-TYPE {
    description
      "VLAN encapsulation and tag stack";
    container stack {
      // NCS drop when statement
      description
        "Stack value";
      uses ncs_template_VLAN-DOUBLE-TAG-STACK;
    }
    container service-instance-details {
      // NCS drop when statement
      description
        "Service Instance encapsulation";
      uses ncs_template_EFP-DESCRIPTION;
    }
    container dot1ad-dot1q-stack {
      // NCS drop when statement
      description
        "802.1ad 802.1Q stack value";
      uses ncs_template_VLAN-DOUBLE-TAG-STACK;
    }
    leaf vlan-encapsulation {
      type ncs_template_Vlan-encaps;
      description
        "VLANEncapsulation";
    }
    leaf tag {
      // NCS drop when statement
      type ncs_template_Vlan-tag-value;
      description
        "Tag value";
    }
    leaf outer-tag {
      // NCS drop when statement
      type ncs_template_Vlan-tag-value;
      description
        "Outer tag value";
    }
    leaf native-tag {
      // NCS drop when statement
      type ncs_template_Vlan-tag-value;
      description
        "Native tag value";
    }
    leaf dot1ad-tag {
      // NCS drop when statement
      type ncs_template_Vlan-tag-value;
      description
        "802.1ad tag value";
    }
    leaf dot1ad-native-tag {
      // NCS drop when statement
      type ncs_template_Vlan-tag-value;
      description
        "802.1ad native tag value";
    }
    leaf dot1ad-outer-tag {
      // NCS drop when statement
      type ncs_template_Vlan-tag-value;
      description
        "802.1ad Outer tag value";
    }
  }

  grouping ncs_template_VLAN-INTF {
    description
      "VLAN Interface information";
    container encapsulation-details {
      description
        "Encapsulation type and tag stack";
      uses ncs_template_VLAN-TAG-STACK-TYPE;
    }
    leaf interface-xr {
      type xr:ncs_template_Interface-name;
      description
        "Interface";
    }
    leaf parent-interface {
      type xr:ncs_template_Interface-name;
      description
        "Parent interface";
    }
    leaf service {
      type ncs_template_Vlan-service;
      description
        "Service type";
    }
    leaf state {
      type ncs_template_Im-state-enum;
      description
        "Interface state";
    }
    leaf mtu {
      type string;
      description
        "L2 MTU";
    }
    leaf switched-mtu {
      type string;
      description
        "L2 switched MTU";
    }
  }

  grouping ncs_template_EFP-TAG-LOCAL-TRAFFIC-STACK {
    description
      "EFP TAG LOCAL TRAFFIC STACK";
    list local-traffic-tag {
      // NCS patched for predictable order
      ordered-by user;
      description
        "VLAN tags for locally-sourced traffic";
      uses ncs_template_EFP-VLAN-TAG;
    }
  }

  grouping ncs_template_EFP-VLAN-TAG {
    description
      "EFP VLAN TAG";
    leaf ethertype {
      type ncs_template_Efp-tag-etype;
      description
        "Ethertype of tag";
    }
    leaf vlan-id {
      type ncs_template_Vlan-tag-value;
      description
        "VLAN Id";
    }
  }

  grouping ncs_template_EFP-RANGE-TYPE {
    description
      "EFP RANGE TYPE";
    leaf vlan-id-low {
      type ncs_template_Vlan-tag-value;
      description
        "VLAN ID Low";
    }
    leaf vlan-id-high {
      type ncs_template_Vlan-tag-value;
      description
        "VLAN ID High";
    }
  }

  grouping ncs_template_EFP-TAG-MATCH {
    description
      "EFP TAG MATCH";
    leaf ethertype {
      type ncs_template_Efp-tag-etype;
      description
        "Ethertype of tag to match";
    }
    leaf priority {
      type ncs_template_Efp-tag-priority;
      description
        "Priority to match";
    }
    list vlan-range {
      // NCS patched for predictable order
      ordered-by user;
      description
        "VLAN Ids to match";
      uses ncs_template_EFP-RANGE-TYPE;
    }
  }

  grouping ncs_template_EFP-DESCRIPTION {
    description
      "EFP DESCRIPTION";
    container local-traffic-stack {
      description
        "VLAN tags for locally-sourced traffic";
      uses ncs_template_EFP-TAG-LOCAL-TRAFFIC-STACK;
    }
    leaf payload-ethertype {
      type ncs_template_Efp-payload-etype;
      description
        "Payload Ethertype to match";
    }
    leaf tags-popped {
      type string;
      description
        "Number of tags popped on ingress";
    }
    leaf is-exact-match {
      type string;
      description
        "Whether the packet must match the encapsulation
         exactly, with no further inner tags";
    }
    leaf is-native-vlan {
      type string;
      description
        "Whether this represents the native VLAN on the
         port";
    }
    leaf is-native-preserving {
      type string;
      description
        "Whether the native VLAN is customer-tag
         preserving";
    }
    leaf source-mac-match {
      type ncs_template_Mac-address;
      description
        "The source MAC address to match on ingress";
    }
    leaf destination-mac-match {
      type ncs_template_Mac-address;
      description
        "The destination MAC address to match on ingress";
    }
    list tags-to-match {
      // NCS patched for predictable order
      ordered-by user;
      description
        "Tags to match on ingress packets";
      uses ncs_template_EFP-TAG-MATCH;
    }
    list pushe {
      // NCS patched for predictable order
      ordered-by user;
      description
        "VLAN tags pushed on egress";
      uses ncs_template_EFP-VLAN-TAG;
    }
  }

  grouping ncs_template_VLAN-SWITCHED-INFO {
    description
      "VLAN-Switched information";
    container trunk-vlan-ranges {
      description
        "VLAN-Switched Trunk VLAN ranges";
      uses ncs_template_EFP-DESCRIPTION;
    }
    leaf mode {
      type ncs_template_Vlan-switched-mode;
      description
        "VLAN-Switched mode";
    }
    leaf access-vlan {
      type ncs_template_Vlan-tag-value;
      description
        "VLAN-Switched Access VLAN";
    }
  }

  grouping ncs_template_VLAN-TRUNK-L3-SUB-INTFS {
    description
      "Layer 3 Terminated Subinterfaces";
    container state-counters {
      description
        "Numbers of subinterfaces up, down or
         administratively shut down";
      uses ncs_template_VLAN-TRUNK-SUB-INTF-STATE-COUNTERS;
    }
    leaf total-count {
      type string;
      description
        "Total number of Layer 3 subinterfaces configured";
    }
    leaf dot1q-count {
      type string;
      description
        "Number of single tagged subinterfaces";
    }
    leaf qin-q-count {
      type string;
      description
        "Number of double tagged subinterfaces";
    }
    leaf untagged-count {
      type string;
      description
        "Number of subinterfaces without VLAN tag
         configuration";
    }
    leaf native-vlan {
      type ncs_template_Vlan-tag-value;
      description
        "Native VLAN ID configured on trunk";
    }
  }

  grouping ncs_template_VLAN-TRUNK-SUB-INTF-STATE-COUNTERS {
    description
      "Subinterface counters";
    leaf up {
      type string;
      description
        "Number of subinterfaces which are up";
    }
    leaf down {
      type string;
      description
        "Number of subinterfaces which are down";
    }
    leaf admin-down {
      type string;
      description
        "Number of subinterfaces which are
         administrativelyshutdown";
    }
  }

  grouping ncs_template_VLAN-TRUNK-L2-SUB-INTFS {
    description
      "Layer 2 Transport Subinterfaces";
    container state-counters {
      description
        "Numbers of subinterfaces up, down or
         administratively shut down";
      uses ncs_template_VLAN-TRUNK-SUB-INTF-STATE-COUNTERS;
    }
    leaf total-count {
      type string;
      description
        "Total number of Layer 2 subinterfaces configured";
    }
    leaf dot1q-count {
      type string;
      description
        "Number of single tagged subinterfaces";
    }
    leaf qin-q-count {
      type string;
      description
        "Number of double tagged subinterfaces with
         explicit inner tag";
    }
    leaf qin-any-count {
      type string;
      description
        "Number of double tagged subinterfaces with
         wildcarded inner tag";
    }
    leaf untagged-count {
      type string;
      description
        "Number of subinterfaces without VLAN tag
         configuration";
    }
  }

  grouping ncs_template_VLAN-TRUNK {
    description
      "VLAN trunk interface information";
    container layer2-sub-interfaces {
      description
        "Layer 2 Transport Subinterfaces";
      uses ncs_template_VLAN-TRUNK-L2-SUB-INTFS;
    }
    container layer3-sub-interfaces {
      description
        "Layer 3 Terminated Subinterfaces";
      uses ncs_template_VLAN-TRUNK-L3-SUB-INTFS;
    }
    container vlan-switched {
      description
        "VLAN-Switched information";
      uses ncs_template_VLAN-SWITCHED-INFO;
    }
    leaf interface-xr {
      type xr:ncs_template_Interface-name;
      description
        "Interface name";
    }
    leaf state {
      type ncs_template_Im-state-enum;
      description
        "Interface state";
    }
    leaf mtu {
      type string;
      description
        "L2 MTU";
    }
    leaf qinq-outer-ether-type {
      type ncs_template_Vlan-qinq-outer-etype;
      description
        "QinQ Outer Tag Ether Type";
    }
    leaf dot1ad-count {
      type string;
      description
        "Number of subinterfaces with 802.1ad outer tag";
    }
    leaf untagged-interface {
      type xr:ncs_template_Interface-name;
      description
        "Interface/Sub-interface handling untagged frames";
    }
    leaf mac-filtering {
      type ncs_template_Eth-filtering;
      description
        "IEEE 802.1Q/802.1ad multicast MAC address
         filtering";
    }
  }

  grouping ncs_rpc_notif_VLAN-DOUBLE-TAG-STACK {
    description
      "VLAN double tag stack";
    leaf outer-tag {
      type ncs_rpc_notif_Vlan-tag-value;
      description
        "Outer tag value";
    }
    leaf second-tag {
      type ncs_rpc_notif_Vlan-tag-value;
      description
        "Second tag value";
    }
  }

  grouping ncs_rpc_notif_VLAN-TAG-STACK-TYPE {
    description
      "VLAN encapsulation and tag stack";
    container stack {
      when "../vlan-encapsulation = 'qinq'" {
        tailf:xpath-root 3;
        description
          "../VLANEncapsulation = 'QinQ'";
      }
      description
        "Stack value";
      uses ncs_rpc_notif_VLAN-DOUBLE-TAG-STACK;
    }
    container service-instance-details {
      when "../vlan-encapsulation = 'service-instance'" {
        tailf:xpath-root 3;
        description
          "../VLANEncapsulation = 'ServiceInstance'";
      }
      description
        "Service Instance encapsulation";
      uses ncs_rpc_notif_EFP-DESCRIPTION;
    }
    container dot1ad-dot1q-stack {
      when "../vlan-encapsulation = 'dot1ad-dot1q'" {
        tailf:xpath-root 3;
        description
          "../VLANEncapsulation = 'Dot1adDot1Q'";
      }
      description
        "802.1ad 802.1Q stack value";
      uses ncs_rpc_notif_VLAN-DOUBLE-TAG-STACK;
    }
    leaf vlan-encapsulation {
      type ncs_rpc_notif_Vlan-encaps;
      description
        "VLANEncapsulation";
    }
    leaf tag {
      when "../vlan-encapsulation = 'dot1q'" {
        tailf:xpath-root 3;
        description
          "../VLANEncapsulation = 'Dot1Q'";
      }
      type ncs_rpc_notif_Vlan-tag-value;
      description
        "Tag value";
    }
    leaf outer-tag {
      when "../vlan-encapsulation = 'qin-any'" {
        tailf:xpath-root 3;
        description
          "../VLANEncapsulation = 'QinAny'";
      }
      type ncs_rpc_notif_Vlan-tag-value;
      description
        "Outer tag value";
    }
    leaf native-tag {
      when "../vlan-encapsulation = 'dot1q-native'" {
        tailf:xpath-root 3;
        description
          "../VLANEncapsulation = 'Dot1QNative'";
      }
      type ncs_rpc_notif_Vlan-tag-value;
      description
        "Native tag value";
    }
    leaf dot1ad-tag {
      when "../vlan-encapsulation = 'dot1ad'" {
        tailf:xpath-root 3;
        description
          "../VLANEncapsulation = 'Dot1ad'";
      }
      type ncs_rpc_notif_Vlan-tag-value;
      description
        "802.1ad tag value";
    }
    leaf dot1ad-native-tag {
      when "../vlan-encapsulation = 'dot1ad-native'" {
        tailf:xpath-root 3;
        description
          "../VLANEncapsulation = 'Dot1adNative'";
      }
      type ncs_rpc_notif_Vlan-tag-value;
      description
        "802.1ad native tag value";
    }
    leaf dot1ad-outer-tag {
      when "../vlan-encapsulation = 'dot1ad-any'" {
        tailf:xpath-root 3;
        description
          "../VLANEncapsulation = 'Dot1adAny'";
      }
      type ncs_rpc_notif_Vlan-tag-value;
      description
        "802.1ad Outer tag value";
    }
  }

  grouping ncs_rpc_notif_VLAN-INTF {
    description
      "VLAN Interface information";
    container encapsulation-details {
      description
        "Encapsulation type and tag stack";
      uses ncs_rpc_notif_VLAN-TAG-STACK-TYPE;
    }
    leaf interface-xr {
      type xr:ncs_rpc_notif_Interface-name;
      description
        "Interface";
    }
    leaf parent-interface {
      type xr:ncs_rpc_notif_Interface-name;
      description
        "Parent interface";
    }
    leaf service {
      type ncs_rpc_notif_Vlan-service;
      description
        "Service type";
    }
    leaf state {
      type ncs_rpc_notif_Im-state-enum;
      description
        "Interface state";
    }
    leaf mtu {
      type uint16;
      description
        "L2 MTU";
    }
    leaf switched-mtu {
      type uint16;
      description
        "L2 switched MTU";
    }
  }

  grouping ncs_rpc_notif_EFP-TAG-LOCAL-TRAFFIC-STACK {
    description
      "EFP TAG LOCAL TRAFFIC STACK";
    list local-traffic-tag {
      description
        "VLAN tags for locally-sourced traffic";
      uses ncs_rpc_notif_EFP-VLAN-TAG;
    }
  }

  grouping ncs_rpc_notif_EFP-VLAN-TAG {
    description
      "EFP VLAN TAG";
    leaf ethertype {
      type ncs_rpc_notif_Efp-tag-etype;
      description
        "Ethertype of tag";
    }
    leaf vlan-id {
      type ncs_rpc_notif_Vlan-tag-value;
      description
        "VLAN Id";
    }
  }

  grouping ncs_rpc_notif_EFP-RANGE-TYPE {
    description
      "EFP RANGE TYPE";
    leaf vlan-id-low {
      type ncs_rpc_notif_Vlan-tag-value;
      description
        "VLAN ID Low";
    }
    leaf vlan-id-high {
      type ncs_rpc_notif_Vlan-tag-value;
      description
        "VLAN ID High";
    }
  }

  grouping ncs_rpc_notif_EFP-TAG-MATCH {
    description
      "EFP TAG MATCH";
    leaf ethertype {
      type ncs_rpc_notif_Efp-tag-etype;
      description
        "Ethertype of tag to match";
    }
    leaf priority {
      type ncs_rpc_notif_Efp-tag-priority;
      description
        "Priority to match";
    }
    list vlan-range {
      description
        "VLAN Ids to match";
      uses ncs_rpc_notif_EFP-RANGE-TYPE;
    }
  }

  grouping ncs_rpc_notif_EFP-DESCRIPTION {
    description
      "EFP DESCRIPTION";
    container local-traffic-stack {
      description
        "VLAN tags for locally-sourced traffic";
      uses ncs_rpc_notif_EFP-TAG-LOCAL-TRAFFIC-STACK;
    }
    leaf payload-ethertype {
      type ncs_rpc_notif_Efp-payload-etype;
      description
        "Payload Ethertype to match";
    }
    leaf tags-popped {
      type uint16;
      description
        "Number of tags popped on ingress";
    }
    leaf is-exact-match {
      type boolean;
      description
        "Whether the packet must match the encapsulation
         exactly, with no further inner tags";
    }
    leaf is-native-vlan {
      type boolean;
      description
        "Whether this represents the native VLAN on the
         port";
    }
    leaf is-native-preserving {
      type boolean;
      description
        "Whether the native VLAN is customer-tag
         preserving";
    }
    leaf source-mac-match {
      type ncs_rpc_notif_Mac-address;
      description
        "The source MAC address to match on ingress";
    }
    leaf destination-mac-match {
      type ncs_rpc_notif_Mac-address;
      description
        "The destination MAC address to match on ingress";
    }
    list tags-to-match {
      description
        "Tags to match on ingress packets";
      uses ncs_rpc_notif_EFP-TAG-MATCH;
    }
    list pushe {
      description
        "VLAN tags pushed on egress";
      uses ncs_rpc_notif_EFP-VLAN-TAG;
    }
  }

  grouping ncs_rpc_notif_VLAN-SWITCHED-INFO {
    description
      "VLAN-Switched information";
    container trunk-vlan-ranges {
      description
        "VLAN-Switched Trunk VLAN ranges";
      uses ncs_rpc_notif_EFP-DESCRIPTION;
    }
    leaf mode {
      type ncs_rpc_notif_Vlan-switched-mode;
      description
        "VLAN-Switched mode";
    }
    leaf access-vlan {
      type ncs_rpc_notif_Vlan-tag-value;
      description
        "VLAN-Switched Access VLAN";
    }
  }

  grouping ncs_rpc_notif_VLAN-TRUNK-L3-SUB-INTFS {
    description
      "Layer 3 Terminated Subinterfaces";
    container state-counters {
      description
        "Numbers of subinterfaces up, down or
         administratively shut down";
      uses ncs_rpc_notif_VLAN-TRUNK-SUB-INTF-STATE-COUNTERS;
    }
    leaf total-count {
      type uint32;
      description
        "Total number of Layer 3 subinterfaces configured";
    }
    leaf dot1q-count {
      type uint32;
      description
        "Number of single tagged subinterfaces";
    }
    leaf qin-q-count {
      type uint32;
      description
        "Number of double tagged subinterfaces";
    }
    leaf untagged-count {
      type uint32;
      description
        "Number of subinterfaces without VLAN tag
         configuration";
    }
    leaf native-vlan {
      type ncs_rpc_notif_Vlan-tag-value;
      description
        "Native VLAN ID configured on trunk";
    }
  }

  grouping ncs_rpc_notif_VLAN-TRUNK-SUB-INTF-STATE-COUNTERS {
    description
      "Subinterface counters";
    leaf up {
      type uint32;
      description
        "Number of subinterfaces which are up";
    }
    leaf down {
      type uint32;
      description
        "Number of subinterfaces which are down";
    }
    leaf admin-down {
      type uint32;
      description
        "Number of subinterfaces which are
         administrativelyshutdown";
    }
  }

  grouping ncs_rpc_notif_VLAN-TRUNK-L2-SUB-INTFS {
    description
      "Layer 2 Transport Subinterfaces";
    container state-counters {
      description
        "Numbers of subinterfaces up, down or
         administratively shut down";
      uses ncs_rpc_notif_VLAN-TRUNK-SUB-INTF-STATE-COUNTERS;
    }
    leaf total-count {
      type uint32;
      description
        "Total number of Layer 2 subinterfaces configured";
    }
    leaf dot1q-count {
      type uint32;
      description
        "Number of single tagged subinterfaces";
    }
    leaf qin-q-count {
      type uint32;
      description
        "Number of double tagged subinterfaces with
         explicit inner tag";
    }
    leaf qin-any-count {
      type uint32;
      description
        "Number of double tagged subinterfaces with
         wildcarded inner tag";
    }
    leaf untagged-count {
      type uint32;
      description
        "Number of subinterfaces without VLAN tag
         configuration";
    }
  }

  grouping ncs_rpc_notif_VLAN-TRUNK {
    description
      "VLAN trunk interface information";
    container layer2-sub-interfaces {
      description
        "Layer 2 Transport Subinterfaces";
      uses ncs_rpc_notif_VLAN-TRUNK-L2-SUB-INTFS;
    }
    container layer3-sub-interfaces {
      description
        "Layer 3 Terminated Subinterfaces";
      uses ncs_rpc_notif_VLAN-TRUNK-L3-SUB-INTFS;
    }
    container vlan-switched {
      description
        "VLAN-Switched information";
      uses ncs_rpc_notif_VLAN-SWITCHED-INFO;
    }
    leaf interface-xr {
      type xr:ncs_rpc_notif_Interface-name;
      description
        "Interface name";
    }
    leaf state {
      type ncs_rpc_notif_Im-state-enum;
      description
        "Interface state";
    }
    leaf mtu {
      type uint16;
      description
        "L2 MTU";
    }
    leaf qinq-outer-ether-type {
      type ncs_rpc_notif_Vlan-qinq-outer-etype;
      description
        "QinQ Outer Tag Ether Type";
    }
    leaf dot1ad-count {
      type uint32;
      description
        "Number of subinterfaces with 802.1ad outer tag";
    }
    leaf untagged-interface {
      type xr:ncs_rpc_notif_Interface-name;
      description
        "Interface/Sub-interface handling untagged frames";
    }
    leaf mac-filtering {
      type ncs_rpc_notif_Eth-filtering;
      description
        "IEEE 802.1Q/802.1ad multicast MAC address
         filtering";
    }
  }

  grouping live_ncs_VLAN-DOUBLE-TAG-STACK {
    description
      "VLAN double tag stack";
    leaf outer-tag {
      type live_ncs_Vlan-tag-value;
      description
        "Outer tag value";
    }
    leaf second-tag {
      type live_ncs_Vlan-tag-value;
      description
        "Second tag value";
    }
  }

  grouping live_ncs_VLAN-TAG-STACK-TYPE {
    description
      "VLAN encapsulation and tag stack";
    container stack {
      // NCS drop when statement
      description
        "Stack value";
      uses live_ncs_VLAN-DOUBLE-TAG-STACK;
    }
    container service-instance-details {
      // NCS drop when statement
      description
        "Service Instance encapsulation";
      uses live_ncs_EFP-DESCRIPTION;
    }
    container dot1ad-dot1q-stack {
      // NCS drop when statement
      description
        "802.1ad 802.1Q stack value";
      uses live_ncs_VLAN-DOUBLE-TAG-STACK;
    }
    leaf vlan-encapsulation {
      type live_ncs_Vlan-encaps;
      description
        "VLANEncapsulation";
    }
    leaf tag {
      // NCS drop when statement
      type live_ncs_Vlan-tag-value;
      description
        "Tag value";
    }
    leaf outer-tag {
      // NCS drop when statement
      type live_ncs_Vlan-tag-value;
      description
        "Outer tag value";
    }
    leaf native-tag {
      // NCS drop when statement
      type live_ncs_Vlan-tag-value;
      description
        "Native tag value";
    }
    leaf dot1ad-tag {
      // NCS drop when statement
      type live_ncs_Vlan-tag-value;
      description
        "802.1ad tag value";
    }
    leaf dot1ad-native-tag {
      // NCS drop when statement
      type live_ncs_Vlan-tag-value;
      description
        "802.1ad native tag value";
    }
    leaf dot1ad-outer-tag {
      // NCS drop when statement
      type live_ncs_Vlan-tag-value;
      description
        "802.1ad Outer tag value";
    }
  }

  grouping live_ncs_VLAN-INTF {
    description
      "VLAN Interface information";
    container encapsulation-details {
      description
        "Encapsulation type and tag stack";
      uses live_ncs_VLAN-TAG-STACK-TYPE;
    }
    leaf interface-xr {
      type xr:live_ncs_Interface-name;
      description
        "Interface";
    }
    leaf parent-interface {
      type xr:live_ncs_Interface-name;
      description
        "Parent interface";
    }
    leaf service {
      type live_ncs_Vlan-service;
      description
        "Service type";
    }
    leaf state {
      type live_ncs_Im-state-enum;
      description
        "Interface state";
    }
    leaf mtu {
      type uint16;
      description
        "L2 MTU";
    }
    leaf switched-mtu {
      type uint16;
      description
        "L2 switched MTU";
    }
  }

  grouping live_ncs_EFP-TAG-LOCAL-TRAFFIC-STACK {
    description
      "EFP TAG LOCAL TRAFFIC STACK";
    list local-traffic-tag {
      description
        "VLAN tags for locally-sourced traffic";
      uses live_ncs_EFP-VLAN-TAG;
    }
  }

  grouping live_ncs_EFP-VLAN-TAG {
    description
      "EFP VLAN TAG";
    leaf ethertype {
      type live_ncs_Efp-tag-etype;
      description
        "Ethertype of tag";
    }
    leaf vlan-id {
      type live_ncs_Vlan-tag-value;
      description
        "VLAN Id";
    }
  }

  grouping live_ncs_EFP-RANGE-TYPE {
    description
      "EFP RANGE TYPE";
    leaf vlan-id-low {
      type live_ncs_Vlan-tag-value;
      description
        "VLAN ID Low";
    }
    leaf vlan-id-high {
      type live_ncs_Vlan-tag-value;
      description
        "VLAN ID High";
    }
  }

  grouping live_ncs_EFP-TAG-MATCH {
    description
      "EFP TAG MATCH";
    leaf ethertype {
      type live_ncs_Efp-tag-etype;
      description
        "Ethertype of tag to match";
    }
    leaf priority {
      type live_ncs_Efp-tag-priority;
      description
        "Priority to match";
    }
    list vlan-range {
      description
        "VLAN Ids to match";
      uses live_ncs_EFP-RANGE-TYPE;
    }
  }

  grouping live_ncs_EFP-DESCRIPTION {
    description
      "EFP DESCRIPTION";
    container local-traffic-stack {
      description
        "VLAN tags for locally-sourced traffic";
      uses live_ncs_EFP-TAG-LOCAL-TRAFFIC-STACK;
    }
    leaf payload-ethertype {
      type live_ncs_Efp-payload-etype;
      description
        "Payload Ethertype to match";
    }
    leaf tags-popped {
      type uint16;
      description
        "Number of tags popped on ingress";
    }
    leaf is-exact-match {
      type boolean;
      description
        "Whether the packet must match the encapsulation
         exactly, with no further inner tags";
    }
    leaf is-native-vlan {
      type boolean;
      description
        "Whether this represents the native VLAN on the
         port";
    }
    leaf is-native-preserving {
      type boolean;
      description
        "Whether the native VLAN is customer-tag
         preserving";
    }
    leaf source-mac-match {
      type live_ncs_Mac-address;
      description
        "The source MAC address to match on ingress";
    }
    leaf destination-mac-match {
      type live_ncs_Mac-address;
      description
        "The destination MAC address to match on ingress";
    }
    list tags-to-match {
      description
        "Tags to match on ingress packets";
      uses live_ncs_EFP-TAG-MATCH;
    }
    list pushe {
      description
        "VLAN tags pushed on egress";
      uses live_ncs_EFP-VLAN-TAG;
    }
  }

  grouping live_ncs_VLAN-SWITCHED-INFO {
    description
      "VLAN-Switched information";
    container trunk-vlan-ranges {
      description
        "VLAN-Switched Trunk VLAN ranges";
      uses live_ncs_EFP-DESCRIPTION;
    }
    leaf mode {
      type live_ncs_Vlan-switched-mode;
      description
        "VLAN-Switched mode";
    }
    leaf access-vlan {
      type live_ncs_Vlan-tag-value;
      description
        "VLAN-Switched Access VLAN";
    }
  }

  grouping live_ncs_VLAN-TRUNK-L3-SUB-INTFS {
    description
      "Layer 3 Terminated Subinterfaces";
    container state-counters {
      description
        "Numbers of subinterfaces up, down or
         administratively shut down";
      uses live_ncs_VLAN-TRUNK-SUB-INTF-STATE-COUNTERS;
    }
    leaf total-count {
      type uint32;
      description
        "Total number of Layer 3 subinterfaces configured";
    }
    leaf dot1q-count {
      type uint32;
      description
        "Number of single tagged subinterfaces";
    }
    leaf qin-q-count {
      type uint32;
      description
        "Number of double tagged subinterfaces";
    }
    leaf untagged-count {
      type uint32;
      description
        "Number of subinterfaces without VLAN tag
         configuration";
    }
    leaf native-vlan {
      type live_ncs_Vlan-tag-value;
      description
        "Native VLAN ID configured on trunk";
    }
  }

  grouping live_ncs_VLAN-TRUNK-SUB-INTF-STATE-COUNTERS {
    description
      "Subinterface counters";
    leaf up {
      type uint32;
      description
        "Number of subinterfaces which are up";
    }
    leaf down {
      type uint32;
      description
        "Number of subinterfaces which are down";
    }
    leaf admin-down {
      type uint32;
      description
        "Number of subinterfaces which are
         administrativelyshutdown";
    }
  }

  grouping live_ncs_VLAN-TRUNK-L2-SUB-INTFS {
    description
      "Layer 2 Transport Subinterfaces";
    container state-counters {
      description
        "Numbers of subinterfaces up, down or
         administratively shut down";
      uses live_ncs_VLAN-TRUNK-SUB-INTF-STATE-COUNTERS;
    }
    leaf total-count {
      type uint32;
      description
        "Total number of Layer 2 subinterfaces configured";
    }
    leaf dot1q-count {
      type uint32;
      description
        "Number of single tagged subinterfaces";
    }
    leaf qin-q-count {
      type uint32;
      description
        "Number of double tagged subinterfaces with
         explicit inner tag";
    }
    leaf qin-any-count {
      type uint32;
      description
        "Number of double tagged subinterfaces with
         wildcarded inner tag";
    }
    leaf untagged-count {
      type uint32;
      description
        "Number of subinterfaces without VLAN tag
         configuration";
    }
  }

  grouping live_ncs_VLAN-TRUNK {
    description
      "VLAN trunk interface information";
    container layer2-sub-interfaces {
      description
        "Layer 2 Transport Subinterfaces";
      uses live_ncs_VLAN-TRUNK-L2-SUB-INTFS;
    }
    container layer3-sub-interfaces {
      description
        "Layer 3 Terminated Subinterfaces";
      uses live_ncs_VLAN-TRUNK-L3-SUB-INTFS;
    }
    container vlan-switched {
      description
        "VLAN-Switched information";
      uses live_ncs_VLAN-SWITCHED-INFO;
    }
    leaf interface-xr {
      type xr:live_ncs_Interface-name;
      description
        "Interface name";
    }
    leaf state {
      type live_ncs_Im-state-enum;
      description
        "Interface state";
    }
    leaf mtu {
      type uint16;
      description
        "L2 MTU";
    }
    leaf qinq-outer-ether-type {
      type live_ncs_Vlan-qinq-outer-etype;
      description
        "QinQ Outer Tag Ether Type";
    }
    leaf dot1ad-count {
      type uint32;
      description
        "Number of subinterfaces with 802.1ad outer tag";
    }
    leaf untagged-interface {
      type xr:live_ncs_Interface-name;
      description
        "Interface/Sub-interface handling untagged frames";
    }
    leaf mac-filtering {
      type live_ncs_Eth-filtering;
      description
        "IEEE 802.1Q/802.1ad multicast MAC address
         filtering";
    }
  }

  grouping VLAN-DOUBLE-TAG-STACK {
    description
      "VLAN double tag stack";
    leaf outer-tag {
      type Vlan-tag-value;
      description
        "Outer tag value";
    }
    leaf second-tag {
      type Vlan-tag-value;
      description
        "Second tag value";
    }
  }

  grouping VLAN-TAG-STACK-TYPE {
    description
      "VLAN encapsulation and tag stack";
    container stack {
      when "../vlan-encapsulation = 'qinq'" {
        tailf:xpath-root 3;
        description
          "../VLANEncapsulation = 'QinQ'";
      }
      description
        "Stack value";
      uses VLAN-DOUBLE-TAG-STACK;
    }
    container service-instance-details {
      when "../vlan-encapsulation = 'service-instance'" {
        tailf:xpath-root 3;
        description
          "../VLANEncapsulation = 'ServiceInstance'";
      }
      description
        "Service Instance encapsulation";
      uses EFP-DESCRIPTION;
    }
    container dot1ad-dot1q-stack {
      when "../vlan-encapsulation = 'dot1ad-dot1q'" {
        tailf:xpath-root 3;
        description
          "../VLANEncapsulation = 'Dot1adDot1Q'";
      }
      description
        "802.1ad 802.1Q stack value";
      uses VLAN-DOUBLE-TAG-STACK;
    }
    leaf vlan-encapsulation {
      type Vlan-encaps;
      description
        "VLANEncapsulation";
    }
    leaf tag {
      when "../vlan-encapsulation = 'dot1q'" {
        tailf:xpath-root 3;
        description
          "../VLANEncapsulation = 'Dot1Q'";
      }
      type Vlan-tag-value;
      description
        "Tag value";
    }
    leaf outer-tag {
      when "../vlan-encapsulation = 'qin-any'" {
        tailf:xpath-root 3;
        description
          "../VLANEncapsulation = 'QinAny'";
      }
      type Vlan-tag-value;
      description
        "Outer tag value";
    }
    leaf native-tag {
      when "../vlan-encapsulation = 'dot1q-native'" {
        tailf:xpath-root 3;
        description
          "../VLANEncapsulation = 'Dot1QNative'";
      }
      type Vlan-tag-value;
      description
        "Native tag value";
    }
    leaf dot1ad-tag {
      when "../vlan-encapsulation = 'dot1ad'" {
        tailf:xpath-root 3;
        description
          "../VLANEncapsulation = 'Dot1ad'";
      }
      type Vlan-tag-value;
      description
        "802.1ad tag value";
    }
    leaf dot1ad-native-tag {
      when "../vlan-encapsulation = 'dot1ad-native'" {
        tailf:xpath-root 3;
        description
          "../VLANEncapsulation = 'Dot1adNative'";
      }
      type Vlan-tag-value;
      description
        "802.1ad native tag value";
    }
    leaf dot1ad-outer-tag {
      when "../vlan-encapsulation = 'dot1ad-any'" {
        tailf:xpath-root 3;
        description
          "../VLANEncapsulation = 'Dot1adAny'";
      }
      type Vlan-tag-value;
      description
        "802.1ad Outer tag value";
    }
  }

  grouping VLAN-INTF {
    description
      "VLAN Interface information";
    container encapsulation-details {
      description
        "Encapsulation type and tag stack";
      uses VLAN-TAG-STACK-TYPE;
    }
    leaf interface-xr {
      type xr:Interface-name;
      description
        "Interface";
    }
    leaf parent-interface {
      type xr:Interface-name;
      description
        "Parent interface";
    }
    leaf service {
      type Vlan-service;
      description
        "Service type";
    }
    leaf state {
      type Im-state-enum;
      description
        "Interface state";
    }
    leaf mtu {
      type uint16;
      description
        "L2 MTU";
    }
    leaf switched-mtu {
      type uint16;
      description
        "L2 switched MTU";
    }
  }

  grouping EFP-TAG-LOCAL-TRAFFIC-STACK {
    description
      "EFP TAG LOCAL TRAFFIC STACK";
    list local-traffic-tag {
      description
        "VLAN tags for locally-sourced traffic";
      uses EFP-VLAN-TAG;
    }
  }

  grouping EFP-VLAN-TAG {
    description
      "EFP VLAN TAG";
    leaf ethertype {
      type Efp-tag-etype;
      description
        "Ethertype of tag";
    }
    leaf vlan-id {
      type Vlan-tag-value;
      description
        "VLAN Id";
    }
  }

  grouping EFP-RANGE-TYPE {
    description
      "EFP RANGE TYPE";
    leaf vlan-id-low {
      type Vlan-tag-value;
      description
        "VLAN ID Low";
    }
    leaf vlan-id-high {
      type Vlan-tag-value;
      description
        "VLAN ID High";
    }
  }

  grouping EFP-TAG-MATCH {
    description
      "EFP TAG MATCH";
    leaf ethertype {
      type Efp-tag-etype;
      description
        "Ethertype of tag to match";
    }
    leaf priority {
      type Efp-tag-priority;
      description
        "Priority to match";
    }
    list vlan-range {
      description
        "VLAN Ids to match";
      uses EFP-RANGE-TYPE;
    }
  }

  grouping EFP-DESCRIPTION {
    description
      "EFP DESCRIPTION";
    container local-traffic-stack {
      description
        "VLAN tags for locally-sourced traffic";
      uses EFP-TAG-LOCAL-TRAFFIC-STACK;
    }
    leaf payload-ethertype {
      type Efp-payload-etype;
      description
        "Payload Ethertype to match";
    }
    leaf tags-popped {
      type uint16;
      description
        "Number of tags popped on ingress";
    }
    leaf is-exact-match {
      type boolean;
      description
        "Whether the packet must match the encapsulation
         exactly, with no further inner tags";
    }
    leaf is-native-vlan {
      type boolean;
      description
        "Whether this represents the native VLAN on the
         port";
    }
    leaf is-native-preserving {
      type boolean;
      description
        "Whether the native VLAN is customer-tag
         preserving";
    }
    leaf source-mac-match {
      type Mac-address;
      description
        "The source MAC address to match on ingress";
    }
    leaf destination-mac-match {
      type Mac-address;
      description
        "The destination MAC address to match on ingress";
    }
    list tags-to-match {
      description
        "Tags to match on ingress packets";
      uses EFP-TAG-MATCH;
    }
    list pushe {
      description
        "VLAN tags pushed on egress";
      uses EFP-VLAN-TAG;
    }
  }

  grouping VLAN-SWITCHED-INFO {
    description
      "VLAN-Switched information";
    container trunk-vlan-ranges {
      description
        "VLAN-Switched Trunk VLAN ranges";
      uses EFP-DESCRIPTION;
    }
    leaf mode {
      type Vlan-switched-mode;
      description
        "VLAN-Switched mode";
    }
    leaf access-vlan {
      type Vlan-tag-value;
      description
        "VLAN-Switched Access VLAN";
    }
  }

  grouping VLAN-TRUNK-L3-SUB-INTFS {
    description
      "Layer 3 Terminated Subinterfaces";
    container state-counters {
      description
        "Numbers of subinterfaces up, down or
         administratively shut down";
      uses VLAN-TRUNK-SUB-INTF-STATE-COUNTERS;
    }
    leaf total-count {
      type uint32;
      description
        "Total number of Layer 3 subinterfaces configured";
    }
    leaf dot1q-count {
      type uint32;
      description
        "Number of single tagged subinterfaces";
    }
    leaf qin-q-count {
      type uint32;
      description
        "Number of double tagged subinterfaces";
    }
    leaf untagged-count {
      type uint32;
      description
        "Number of subinterfaces without VLAN tag
         configuration";
    }
    leaf native-vlan {
      type Vlan-tag-value;
      description
        "Native VLAN ID configured on trunk";
    }
  }

  grouping VLAN-TRUNK-SUB-INTF-STATE-COUNTERS {
    description
      "Subinterface counters";
    leaf up {
      type uint32;
      description
        "Number of subinterfaces which are up";
    }
    leaf down {
      type uint32;
      description
        "Number of subinterfaces which are down";
    }
    leaf admin-down {
      type uint32;
      description
        "Number of subinterfaces which are
         administrativelyshutdown";
    }
  }

  grouping VLAN-TRUNK-L2-SUB-INTFS {
    description
      "Layer 2 Transport Subinterfaces";
    container state-counters {
      description
        "Numbers of subinterfaces up, down or
         administratively shut down";
      uses VLAN-TRUNK-SUB-INTF-STATE-COUNTERS;
    }
    leaf total-count {
      type uint32;
      description
        "Total number of Layer 2 subinterfaces configured";
    }
    leaf dot1q-count {
      type uint32;
      description
        "Number of single tagged subinterfaces";
    }
    leaf qin-q-count {
      type uint32;
      description
        "Number of double tagged subinterfaces with
         explicit inner tag";
    }
    leaf qin-any-count {
      type uint32;
      description
        "Number of double tagged subinterfaces with
         wildcarded inner tag";
    }
    leaf untagged-count {
      type uint32;
      description
        "Number of subinterfaces without VLAN tag
         configuration";
    }
  }

  grouping VLAN-TRUNK {
    description
      "VLAN trunk interface information";
    container layer2-sub-interfaces {
      description
        "Layer 2 Transport Subinterfaces";
      uses VLAN-TRUNK-L2-SUB-INTFS;
    }
    container layer3-sub-interfaces {
      description
        "Layer 3 Terminated Subinterfaces";
      uses VLAN-TRUNK-L3-SUB-INTFS;
    }
    container vlan-switched {
      description
        "VLAN-Switched information";
      uses VLAN-SWITCHED-INFO;
    }
    leaf interface-xr {
      type xr:Interface-name;
      description
        "Interface name";
    }
    leaf state {
      type Im-state-enum;
      description
        "Interface state";
    }
    leaf mtu {
      type uint16;
      description
        "L2 MTU";
    }
    leaf qinq-outer-ether-type {
      type Vlan-qinq-outer-etype;
      description
        "QinQ Outer Tag Ether Type";
    }
    leaf dot1ad-count {
      type uint32;
      description
        "Number of subinterfaces with 802.1ad outer tag";
    }
    leaf untagged-interface {
      type xr:Interface-name;
      description
        "Interface/Sub-interface handling untagged frames";
    }
    leaf mac-filtering {
      type Eth-filtering;
      description
        "IEEE 802.1Q/802.1ad multicast MAC address
         filtering";
    }
  }
}

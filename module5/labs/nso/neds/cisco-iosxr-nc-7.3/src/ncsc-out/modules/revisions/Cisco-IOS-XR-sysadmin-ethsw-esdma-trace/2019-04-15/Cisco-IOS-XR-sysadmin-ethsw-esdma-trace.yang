module Cisco-IOS-XR-sysadmin-ethsw-esdma-trace {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-trace";
  prefix esdma_trace;

  import Cisco-IOS-XR-sysadmin-show-trace {
    prefix show_trace;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch trace' commands.

     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-07-06 {
    description
      "Initial revision with content extracted from esdma_cli.yang.";
  }

  grouping ncs_template_esd-ctrace {
    container esd {
      uses show_trace:ncs_template_traceable_process;
    }
  }

  grouping ncs_template_esd-ctrace-ncs5500 {
    container trace {
      list location {
        // NCS patched for predictable order
        ordered-by user;
        key "location_str";
        leaf location_str {
          type string;
        }
        container esd {
          uses show_trace:ncs_template_traceable_with_keypath_location;
        }
        container esd-EPC-SW {
          uses show_trace:ncs_template_traceable_with_keypath_location;
        }
        container esd-EOBC-SW {
          uses show_trace:ncs_template_traceable_with_keypath_location;
        }
      }
    }
  }

  grouping ncs_template_esdma-ctrace {
    container esdma {
      uses show_trace:ncs_template_traceable;
    }
  }

  grouping ncs_rpc_notif_esd-ctrace {
    container esd {
      uses show_trace:ncs_rpc_notif_traceable_process;
    }
  }

  grouping ncs_rpc_notif_esd-ctrace-ncs5500 {
    container trace {
      list location {
        key "location_str";
        leaf location_str {
          type string;
        }
        container esd {
          uses show_trace:ncs_rpc_notif_traceable_with_keypath_location;
        }
        container esd-EPC-SW {
          uses show_trace:ncs_rpc_notif_traceable_with_keypath_location;
        }
        container esd-EOBC-SW {
          uses show_trace:ncs_rpc_notif_traceable_with_keypath_location;
        }
      }
    }
  }

  grouping ncs_rpc_notif_esdma-ctrace {
    container esdma {
      uses show_trace:ncs_rpc_notif_traceable;
    }
  }

  grouping live_ncs_esd-ctrace {
    container esd {
      uses show_trace:live_ncs_traceable_process;
    }
  }

  grouping live_ncs_esd-ctrace-ncs5500 {
    container trace {
      list location {
        key "location_str";
        leaf location_str {
          type string;
        }
        container esd {
          uses show_trace:live_ncs_traceable_with_keypath_location;
        }
        container esd-EPC-SW {
          uses show_trace:live_ncs_traceable_with_keypath_location;
        }
        container esd-EOBC-SW {
          uses show_trace:live_ncs_traceable_with_keypath_location;
        }
      }
    }
  }

  grouping live_ncs_esdma-ctrace {
    container esdma {
      uses show_trace:live_ncs_traceable;
    }
  }

  grouping esd-ctrace {
    container esd {
      uses show_trace:traceable_process;
    }
  }

  grouping esd-ctrace-ncs5500 {
    container trace {
      list location {
        key "location_str";
        leaf location_str {
          type string;
        }
        container esd {
          uses show_trace:traceable_with_keypath_location;
        }
        container esd-EPC-SW {
          uses show_trace:traceable_with_keypath_location;
        }
        container esd-EOBC-SW {
          uses show_trace:traceable_with_keypath_location;
        }
      }
    }
  }

  grouping esdma-ctrace {
    container esdma {
      uses show_trace:traceable;
    }
  }
}

module Cisco-IOS-XR-asr9k-np-act {
  // Generated by yanger -t ncs
  tailf:mount-id "cisco-iosxr-nc-7.3:cisco-iosxr-nc-7.3";
  tailf:ncs-device-type "netconf";

  namespace "http://cisco.com/ns/yang/Cisco-IOS-XR-np-act.yang";
  prefix asr9k-np-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2021 by Cisco Systems, Inc.
     All rights reserved.";

  revision 2020-12-08 {
    description
      "IOS XR 7.3.1 revision.";
    semver:module-version "1.0.0";
  }

  augment "/ncs:devices/ncs:device/ncs:rpc" {
    container rpc-prm-np-clear-counters {
      tailf:ncs-device-type "netconf";
      tailf:display-when "not(../../ncs:module) or ../../ncs:module[ncs:name='Cisco-IOS-XR-asr9k-np-act']";
      tailf:action prm-np-clear-counters {
        tailf:actionpoint ncsproxy {
          tailf:internal;
        }
        description
          "Action to clear prm np debug counters";
        input {
          leaf location {
            type string;
            mandatory true;
            description
              "Location string for LC to perform clear on.";
          }
          leaf np {
            type string;
            mandatory true;
            description
              "NP to perform clear operation on. All is accepted.";
          }
        }
        csc:xr-task "system";
        csc:cli-command "clear controller np counters <np> location <location>";
      }
    }
  }
  augment "/ncs:devices/ncs:device-group/ncs:ned-id/ncs:rpc" {
    container rpc-prm-np-clear-counters {
      tailf:ncs-device-type "netconf";
      tailf:display-when "/ncs:devices/ncs:device[ncs:name=current()/../../../ncs:member]/ncs:module[ncs:name='Cisco-IOS-XR-asr9k-np-act']";
      tailf:action prm-np-clear-counters {
        tailf:actionpoint ncsproxy {
          tailf:internal;
        }
        description
          "Action to clear prm np debug counters";
        input {
          leaf location {
            type string;
            mandatory true;
            description
              "Location string for LC to perform clear on.";
          }
          leaf np {
            type string;
            mandatory true;
            description
              "NP to perform clear operation on. All is accepted.";
          }
        }
        csc:xr-task "system";
        csc:cli-command "clear controller np counters <np> location <location>";
      }
    }
  }
}

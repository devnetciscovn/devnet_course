module Cisco-IOS-XR-um-policymap-classmap-cfg {
  // Generated by yanger -t ncs
  tailf:mount-id "cisco-iosxr-nc-7.3:cisco-iosxr-nc-7.3";
  tailf:ncs-device-type "netconf";

  namespace "http://cisco.com/ns/yang/Cisco-IOS-XR-um-policymap-classmap-cfg";
  prefix um-policymap-classmap-cfg;

  import cisco-semver {
    prefix semver;
  }
  import ietf-inet-types {
    prefix inet;
  }
  import ietf-yang-types {
    prefix yang;
  }
  import Cisco-IOS-XR-types {
    prefix xr2;
  }
  import tailf-common {
    prefix tailf;
  }
  import tailf-ncs {
    prefix ncs;
  }

  organization
    "Cisco Systems, Inc.";
  contact
    "
     Cisco Systems, Inc.
     Customer Service

     Postal: 170 W Tasman Drive
     San Jose, CA 95134

     Tel: +1 1800 553-NETS

     E-mail: cs-yang@cisco.com
    ";
  description
    "
     This module contains a collection of IOS-XR YANG model derived from CLI.

     Copyright (c) 2013-2021 by Cisco Systems, Inc.
     All rights reserved.
    ";

  revision 2020-10-05 {
    description
      "Changed ipv4/ipv6/ethernet-services under access-group to leaf-lists";
    semver:module-version "1.1.0";
  }
  revision 2020-08-24 {
    description
      "Removed some nodes which are not supported via YANG";
  }
  revision 2020-01-27 {
    description
      "Added discard-class node under queue-limit";
  }
  revision 2019-06-10 {
    description
      "Establish semantic version baseline.";
    semver:module-version "1.0.0";
  }
  revision 2019-04-01 {
    description
      "Initial version";
  }

  typedef ncs_template_trigger-value {
    type string;
    description
      "Limit as a number";
  }

  typedef ncs_template_event-type {
    type string;
  }

  typedef ncs_template_dscp-value {
    type string;
    description
      "Differentiated services codepoint value";
  }

  typedef ncs_template_protocol-type {
    type string;
  }

  typedef ncs_template_acl-list-name-type {
    type string;
    description
      "Access list name";
  }

  typedef ncs_template_packet-length-type {
    type string;
    description
      "IP packet length";
  }

  typedef ncs_template_precedence-type {
    type string;
    description
      "Precedence value";
  }

  typedef ncs_template_port-number-type {
    type string;
  }

  typedef ncs_template_vlan-id-type {
    type string;
  }

  typedef ncs_template_clear-text-password-type {
    type string;
    description
      "Clear text password";
  }

  typedef ncs_template_flow-monitor-map-name-type {
    type string;
    description
      "Name of the flow monitor map";
  }

  typedef ncs_template_clone-interface-type {
    type xr2:ncs_template_Interface-name;
    description
      "Specify an interface";
  }

  typedef ncs_template_rate-unit-type {
    type string;
  }

  typedef ncs_template_burst-unit-type {
    type string;
  }

  typedef ncs_template_wred-unit-type {
    type string;
  }

  typedef ncs_template_cac-unit-type {
    type string;
  }

  typedef ncs_template_pfc-unit-type {
    type string;
  }

  typedef ncs_template_service-policy-name-type {
    type string;
  }

  typedef ncs_rpc_notif_trigger-value {
    type string {
      pattern '-{0,1}[0-9]+(\\.[0-9]+){0,1}';
    }
    description
      "Limit as a number";
  }

  typedef ncs_rpc_notif_event-type {
    type enumeration {
      enum "account-logoff" {
        description
          "Account logoff event";
      }
      enum "account-logon" {
        description
          "Account logon event";
      }
      enum "authentication-failure" {
        description
          "Authentication failure event";
      }
      enum "authentication-no-response" {
        description
          "Authentication no response event";
      }
      enum "authorization-failure" {
        description
          "Authorization failure event";
      }
      enum "authorization-no-response" {
        description
          "Authorization no response event";
      }
      enum "authorize-dhcp-renew" {
        description
          "Authorize dhcp renew packet event";
      }
      enum "credit-exhausted" {
        description
          "Credit exhaustion event";
      }
      enum "exception" {
        description
          "Exception event";
      }
      enum "idle-timeout" {
        description
          "Idle timeout event";
      }
      enum "quota-depleted" {
        description
          "Quota depletion event";
      }
      enum "service-start" {
        description
          "Service start event";
      }
      enum "service-stop" {
        description
          "Service stop event";
      }
      enum "session-activate" {
        description
          "Session activate event";
      }
      enum "session-established" {
        description
          "session is in activated state (address is assigned to session)";
      }
      enum "session-identity-change" {
        description
          "session identity change event";
      }
      enum "session-start" {
        description
          "Session start event";
      }
      enum "session-stop" {
        description
          "Session stop event";
      }
      enum "session-umi-report" {
        description
          "session umi report event";
      }
      enum "timer-expiry" {
        description
          "Timer expiry event";
      }
    }
  }

  typedef ncs_rpc_notif_dscp-value {
    type union {
      type uint8 {
        range "0..63";
      }
      type string {
        pattern '([0-9]{1,2})-([0-9]{1,2})' {
          description
            "<0-63>-<0-63>";
        }
      }
      type enumeration {
        enum "af11" {
          description
            "Match packets with AF11 dscp (001010)";
        }
        enum "af12" {
          description
            "Match packets with AF12 dscp (001100)";
        }
        enum "af13" {
          description
            "Match packets with AF13 dscp (001110)";
        }
        enum "af21" {
          description
            "Match packets with AF21 dscp (010010)";
        }
        enum "af22" {
          description
            "Match packets with AF22 dscp (010100)";
        }
        enum "af23" {
          description
            "Match packets with AF23 dscp (010110)";
        }
        enum "af31" {
          description
            "Match packets with AF31 dscp (011010)";
        }
        enum "af32" {
          description
            "Match packets with AF32 dscp (011100)";
        }
        enum "af33" {
          description
            "Match packets with AF33 dscp (011110)";
        }
        enum "af41" {
          description
            "Match packets with AF41 dscp (100010)";
        }
        enum "af42" {
          description
            "Match packets with AF42 dscp (100100)";
        }
        enum "af43" {
          description
            "Match packets with AF43 dscp (100110)";
        }
        enum "cs1" {
          description
            "Match packets with CS1(precedence 1) dscp (001000)";
        }
        enum "cs2" {
          description
            "Match packets with CS2(precedence 2) dscp (010000)";
        }
        enum "cs3" {
          description
            "Match packets with CS3(precedence 3) dscp (011000)";
        }
        enum "cs4" {
          description
            "Match packets with CS4(precedence 4) dscp (100000)";
        }
        enum "cs5" {
          description
            "Match packets with CS5(precedence 5) dscp (101000)";
        }
        enum "cs6" {
          description
            "Match packets with CS6(precedence 6) dscp (110000)";
        }
        enum "cs7" {
          description
            "Match packets with CS7(precedence 7) dscp (111000)";
        }
        enum "default" {
          description
            "Match packets with default DSCP (000000)";
        }
        enum "ef" {
          description
            "Match packets with EF dscp (101110)";
        }
      }
    }
    description
      "Differentiated services codepoint value";
  }

  typedef ncs_rpc_notif_protocol-type {
    type union {
      type uint8 {
        range "0..255" {
          description
            "An IP Protocol Number";
        }
      }
      type string {
        pattern '([0-9]{1,3})-([0-9]{1,3})' {
          description
            "Lower/upper limit of protocol range (<0-255>-<0-255>)";
        }
      }
      type enumeration {
        enum "ahp" {
          description
            "Authentication Header Protocol";
        }
        enum "eigrp" {
          description
            "Cisco's EIGRP Routing Protocol";
        }
        enum "esp" {
          description
            "Encapsulation Security Payload";
        }
        enum "gre" {
          description
            "Cisco's GRE Tunneling";
        }
        enum "icmp" {
          description
            "Internet Control Message Protocol";
        }
        enum "igmp" {
          description
            "Internet Gateway Message Protocol";
        }
        enum "igrp" {
          description
            "Cisco's IGRP Routing Protocol";
        }
        enum "ipinip" {
          description
            "IP in IP tunneling";
        }
        enum "ipv4" {
          description
            "Any IPv4 Protocol";
        }
        enum "ipv6" {
          description
            "Any IPv6 Protocol";
        }
        enum "ipv6icmp" {
          description
            "IPV6Internet Control Message Protocol";
        }
        enum "mpls" {
          description
            "Any MPLS Packet";
        }
        enum "nos" {
          description
            "KA9Q NOS Compatible IP over IP Tunneling";
        }
        enum "ospf" {
          description
            "OSPF Routing Protocol";
        }
        enum "pcp" {
          description
            "Payload Compression Protocol";
        }
        enum "pim" {
          description
            "Protocol Independent Multicast";
        }
        enum "sctp" {
          description
            "Stream Control Transmission Protocol";
        }
        enum "tcp" {
          description
            "Transport Control Protocol";
        }
        enum "udp" {
          description
            "User Datagram Protocol";
        }
      }
    }
  }

  typedef ncs_rpc_notif_acl-list-name-type {
    type string {
      length "1..64";
    }
    description
      "Access list name";
  }

  typedef ncs_rpc_notif_packet-length-type {
    type union {
      type uint16 {
        range "0..65535";
      }
      type string {
        pattern '([0-9]{1,5})-([0-9]{1,5})' {
          description
            "Lower/upper limit of packet length to match (<0-65535>-<0-65535>)";
        }
      }
    }
    description
      "IP packet length";
  }

  typedef ncs_rpc_notif_precedence-type {
    type union {
      type uint8 {
        range "0..7";
      }
      type enumeration {
        enum "critical" {
          description
            "Critical precedence (5)";
        }
        enum "flash" {
          description
            "Flash precedence (3)";
        }
        enum "flash-override" {
          description
            "Flash override precedence (4)";
        }
        enum "immediate" {
          description
            "Immediate precedence (2)";
        }
        enum "internet" {
          description
            "Internetwork control precedence (6)";
        }
        enum "network" {
          description
            "Network control precedence (7)";
        }
        enum "priority" {
          description
            "Priority precedence (1)";
        }
        enum "routine" {
          description
            "Routine precedence (0)";
        }
      }
    }
    description
      "Precedence value";
  }

  typedef ncs_rpc_notif_port-number-type {
    type union {
      type uint16 {
        range "0..65535" {
          description
            "A Port Number";
        }
      }
      type string {
        pattern '([0-9]+)-([0-9]+)' {
          description
            "Lower/upper imit of the Port range";
        }
      }
    }
  }

  typedef ncs_rpc_notif_vlan-id-type {
    type union {
      type uint16 {
        range "1..4094" {
          description
            "Vlan Id";
        }
      }
      type string {
        pattern '([1-9][0-9]{0,3})-([1-9][0-9]{0,3})' {
          description
            "Lower/upper limit of the Vlan Id range (<1-4094>-<1-4094>)";
        }
      }
    }
  }

  typedef ncs_rpc_notif_clear-text-password-type {
    type string;
    description
      "Clear text password";
  }

  typedef ncs_rpc_notif_flow-monitor-map-name-type {
    type string {
      length "1..32";
      pattern '[a-zA-Z0-9][a-zA-Z0-9\._@$%+#:=<>\-]{0,62}';
    }
    description
      "Name of the flow monitor map";
  }

  typedef ncs_rpc_notif_clone-interface-type {
    type xr2:ncs_rpc_notif_Interface-name;
    description
      "Specify an interface";
  }

  typedef ncs_rpc_notif_rate-unit-type {
    type enumeration {
      enum "bps" {
        description
          "Bits per second (default)";
      }
      enum "gbps" {
        description
          "Gigabits per second";
      }
      enum "kbps" {
        description
          "Kilobits per second";
      }
      enum "mbps" {
        description
          "Megabits per second";
      }
      enum "cellsps" {
        description
          "Cells per second";
      }
      enum "pps" {
        description
          "Packets per second";
      }
    }
  }

  typedef ncs_rpc_notif_burst-unit-type {
    type enumeration {
      enum "bytes" {
        description
          "Bytes (default)";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets";
      }
    }
  }

  typedef ncs_rpc_notif_wred-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets (default)";
      }
    }
  }

  typedef ncs_rpc_notif_cac-unit-type {
    type enumeration {
      enum "bps" {
        description
          "Bits per second";
      }
      enum "gbps" {
        description
          "Gigabits per second";
      }
      enum "kbps" {
        description
          "Kilobits per second (default)";
      }
      enum "mbps" {
        description
          "Megabits per second";
      }
      enum "cellsps" {
        description
          "Cells per second";
      }
    }
  }

  typedef ncs_rpc_notif_pfc-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "cells" {
        description
          "Cells";
      }
      enum "packets" {
        description
          "Packets";
      }
    }
  }

  typedef ncs_rpc_notif_service-policy-name-type {
    type string {
      pattern '[a-zA-Z0-9][a-zA-Z0-9\._@$%+#:=<>\-]{0,62}';
    }
  }

  typedef live_ncs_trigger-value {
    type string {
      pattern '-{0,1}[0-9]+(\\.[0-9]+){0,1}';
    }
    description
      "Limit as a number";
  }

  typedef live_ncs_event-type {
    type enumeration {
      enum "account-logoff" {
        description
          "Account logoff event";
      }
      enum "account-logon" {
        description
          "Account logon event";
      }
      enum "authentication-failure" {
        description
          "Authentication failure event";
      }
      enum "authentication-no-response" {
        description
          "Authentication no response event";
      }
      enum "authorization-failure" {
        description
          "Authorization failure event";
      }
      enum "authorization-no-response" {
        description
          "Authorization no response event";
      }
      enum "authorize-dhcp-renew" {
        description
          "Authorize dhcp renew packet event";
      }
      enum "credit-exhausted" {
        description
          "Credit exhaustion event";
      }
      enum "exception" {
        description
          "Exception event";
      }
      enum "idle-timeout" {
        description
          "Idle timeout event";
      }
      enum "quota-depleted" {
        description
          "Quota depletion event";
      }
      enum "service-start" {
        description
          "Service start event";
      }
      enum "service-stop" {
        description
          "Service stop event";
      }
      enum "session-activate" {
        description
          "Session activate event";
      }
      enum "session-established" {
        description
          "session is in activated state (address is assigned to session)";
      }
      enum "session-identity-change" {
        description
          "session identity change event";
      }
      enum "session-start" {
        description
          "Session start event";
      }
      enum "session-stop" {
        description
          "Session stop event";
      }
      enum "session-umi-report" {
        description
          "session umi report event";
      }
      enum "timer-expiry" {
        description
          "Timer expiry event";
      }
    }
  }

  typedef live_ncs_dscp-value {
    type union {
      type uint8 {
        range "0..63";
      }
      type string {
        pattern '([0-9]{1,2})-([0-9]{1,2})' {
          description
            "<0-63>-<0-63>";
        }
      }
      type enumeration {
        enum "af11" {
          description
            "Match packets with AF11 dscp (001010)";
        }
        enum "af12" {
          description
            "Match packets with AF12 dscp (001100)";
        }
        enum "af13" {
          description
            "Match packets with AF13 dscp (001110)";
        }
        enum "af21" {
          description
            "Match packets with AF21 dscp (010010)";
        }
        enum "af22" {
          description
            "Match packets with AF22 dscp (010100)";
        }
        enum "af23" {
          description
            "Match packets with AF23 dscp (010110)";
        }
        enum "af31" {
          description
            "Match packets with AF31 dscp (011010)";
        }
        enum "af32" {
          description
            "Match packets with AF32 dscp (011100)";
        }
        enum "af33" {
          description
            "Match packets with AF33 dscp (011110)";
        }
        enum "af41" {
          description
            "Match packets with AF41 dscp (100010)";
        }
        enum "af42" {
          description
            "Match packets with AF42 dscp (100100)";
        }
        enum "af43" {
          description
            "Match packets with AF43 dscp (100110)";
        }
        enum "cs1" {
          description
            "Match packets with CS1(precedence 1) dscp (001000)";
        }
        enum "cs2" {
          description
            "Match packets with CS2(precedence 2) dscp (010000)";
        }
        enum "cs3" {
          description
            "Match packets with CS3(precedence 3) dscp (011000)";
        }
        enum "cs4" {
          description
            "Match packets with CS4(precedence 4) dscp (100000)";
        }
        enum "cs5" {
          description
            "Match packets with CS5(precedence 5) dscp (101000)";
        }
        enum "cs6" {
          description
            "Match packets with CS6(precedence 6) dscp (110000)";
        }
        enum "cs7" {
          description
            "Match packets with CS7(precedence 7) dscp (111000)";
        }
        enum "default" {
          description
            "Match packets with default DSCP (000000)";
        }
        enum "ef" {
          description
            "Match packets with EF dscp (101110)";
        }
      }
    }
    description
      "Differentiated services codepoint value";
  }

  typedef live_ncs_protocol-type {
    type union {
      type uint8 {
        range "0..255" {
          description
            "An IP Protocol Number";
        }
      }
      type string {
        pattern '([0-9]{1,3})-([0-9]{1,3})' {
          description
            "Lower/upper limit of protocol range (<0-255>-<0-255>)";
        }
      }
      type enumeration {
        enum "ahp" {
          description
            "Authentication Header Protocol";
        }
        enum "eigrp" {
          description
            "Cisco's EIGRP Routing Protocol";
        }
        enum "esp" {
          description
            "Encapsulation Security Payload";
        }
        enum "gre" {
          description
            "Cisco's GRE Tunneling";
        }
        enum "icmp" {
          description
            "Internet Control Message Protocol";
        }
        enum "igmp" {
          description
            "Internet Gateway Message Protocol";
        }
        enum "igrp" {
          description
            "Cisco's IGRP Routing Protocol";
        }
        enum "ipinip" {
          description
            "IP in IP tunneling";
        }
        enum "ipv4" {
          description
            "Any IPv4 Protocol";
        }
        enum "ipv6" {
          description
            "Any IPv6 Protocol";
        }
        enum "ipv6icmp" {
          description
            "IPV6Internet Control Message Protocol";
        }
        enum "mpls" {
          description
            "Any MPLS Packet";
        }
        enum "nos" {
          description
            "KA9Q NOS Compatible IP over IP Tunneling";
        }
        enum "ospf" {
          description
            "OSPF Routing Protocol";
        }
        enum "pcp" {
          description
            "Payload Compression Protocol";
        }
        enum "pim" {
          description
            "Protocol Independent Multicast";
        }
        enum "sctp" {
          description
            "Stream Control Transmission Protocol";
        }
        enum "tcp" {
          description
            "Transport Control Protocol";
        }
        enum "udp" {
          description
            "User Datagram Protocol";
        }
      }
    }
  }

  typedef live_ncs_acl-list-name-type {
    type string {
      length "1..64";
    }
    description
      "Access list name";
  }

  typedef live_ncs_packet-length-type {
    type union {
      type uint16 {
        range "0..65535";
      }
      type string {
        pattern '([0-9]{1,5})-([0-9]{1,5})' {
          description
            "Lower/upper limit of packet length to match (<0-65535>-<0-65535>)";
        }
      }
    }
    description
      "IP packet length";
  }

  typedef live_ncs_precedence-type {
    type union {
      type uint8 {
        range "0..7";
      }
      type enumeration {
        enum "critical" {
          description
            "Critical precedence (5)";
        }
        enum "flash" {
          description
            "Flash precedence (3)";
        }
        enum "flash-override" {
          description
            "Flash override precedence (4)";
        }
        enum "immediate" {
          description
            "Immediate precedence (2)";
        }
        enum "internet" {
          description
            "Internetwork control precedence (6)";
        }
        enum "network" {
          description
            "Network control precedence (7)";
        }
        enum "priority" {
          description
            "Priority precedence (1)";
        }
        enum "routine" {
          description
            "Routine precedence (0)";
        }
      }
    }
    description
      "Precedence value";
  }

  typedef live_ncs_port-number-type {
    type union {
      type uint16 {
        range "0..65535" {
          description
            "A Port Number";
        }
      }
      type string {
        pattern '([0-9]+)-([0-9]+)' {
          description
            "Lower/upper imit of the Port range";
        }
      }
    }
  }

  typedef live_ncs_vlan-id-type {
    type union {
      type uint16 {
        range "1..4094" {
          description
            "Vlan Id";
        }
      }
      type string {
        pattern '([1-9][0-9]{0,3})-([1-9][0-9]{0,3})' {
          description
            "Lower/upper limit of the Vlan Id range (<1-4094>-<1-4094>)";
        }
      }
    }
  }

  typedef live_ncs_clear-text-password-type {
    type string;
    description
      "Clear text password";
  }

  typedef live_ncs_flow-monitor-map-name-type {
    type string {
      length "1..32";
      pattern '[a-zA-Z0-9][a-zA-Z0-9\._@$%+#:=<>\-]{0,62}';
    }
    description
      "Name of the flow monitor map";
  }

  typedef live_ncs_clone-interface-type {
    type xr2:live_ncs_Interface-name;
    description
      "Specify an interface";
  }

  typedef live_ncs_rate-unit-type {
    type enumeration {
      enum "bps" {
        description
          "Bits per second (default)";
      }
      enum "gbps" {
        description
          "Gigabits per second";
      }
      enum "kbps" {
        description
          "Kilobits per second";
      }
      enum "mbps" {
        description
          "Megabits per second";
      }
      enum "cellsps" {
        description
          "Cells per second";
      }
      enum "pps" {
        description
          "Packets per second";
      }
    }
  }

  typedef live_ncs_burst-unit-type {
    type enumeration {
      enum "bytes" {
        description
          "Bytes (default)";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets";
      }
    }
  }

  typedef live_ncs_wred-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets (default)";
      }
    }
  }

  typedef live_ncs_cac-unit-type {
    type enumeration {
      enum "bps" {
        description
          "Bits per second";
      }
      enum "gbps" {
        description
          "Gigabits per second";
      }
      enum "kbps" {
        description
          "Kilobits per second (default)";
      }
      enum "mbps" {
        description
          "Megabits per second";
      }
      enum "cellsps" {
        description
          "Cells per second";
      }
    }
  }

  typedef live_ncs_pfc-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "cells" {
        description
          "Cells";
      }
      enum "packets" {
        description
          "Packets";
      }
    }
  }

  typedef live_ncs_service-policy-name-type {
    type string {
      pattern '[a-zA-Z0-9][a-zA-Z0-9\._@$%+#:=<>\-]{0,62}';
    }
  }

  typedef trigger-value {
    type string {
      pattern '-{0,1}[0-9]+(\\.[0-9]+){0,1}';
    }
    description
      "Limit as a number";
  }

  typedef event-type {
    type enumeration {
      enum "account-logoff" {
        description
          "Account logoff event";
      }
      enum "account-logon" {
        description
          "Account logon event";
      }
      enum "authentication-failure" {
        description
          "Authentication failure event";
      }
      enum "authentication-no-response" {
        description
          "Authentication no response event";
      }
      enum "authorization-failure" {
        description
          "Authorization failure event";
      }
      enum "authorization-no-response" {
        description
          "Authorization no response event";
      }
      enum "authorize-dhcp-renew" {
        description
          "Authorize dhcp renew packet event";
      }
      enum "credit-exhausted" {
        description
          "Credit exhaustion event";
      }
      enum "exception" {
        description
          "Exception event";
      }
      enum "idle-timeout" {
        description
          "Idle timeout event";
      }
      enum "quota-depleted" {
        description
          "Quota depletion event";
      }
      enum "service-start" {
        description
          "Service start event";
      }
      enum "service-stop" {
        description
          "Service stop event";
      }
      enum "session-activate" {
        description
          "Session activate event";
      }
      enum "session-established" {
        description
          "session is in activated state (address is assigned to session)";
      }
      enum "session-identity-change" {
        description
          "session identity change event";
      }
      enum "session-start" {
        description
          "Session start event";
      }
      enum "session-stop" {
        description
          "Session stop event";
      }
      enum "session-umi-report" {
        description
          "session umi report event";
      }
      enum "timer-expiry" {
        description
          "Timer expiry event";
      }
    }
  }

  typedef dscp-value {
    type union {
      type uint8 {
        range "0..63";
      }
      type string {
        pattern '([0-9]{1,2})-([0-9]{1,2})' {
          description
            "<0-63>-<0-63>";
        }
      }
      type enumeration {
        enum "af11" {
          description
            "Match packets with AF11 dscp (001010)";
        }
        enum "af12" {
          description
            "Match packets with AF12 dscp (001100)";
        }
        enum "af13" {
          description
            "Match packets with AF13 dscp (001110)";
        }
        enum "af21" {
          description
            "Match packets with AF21 dscp (010010)";
        }
        enum "af22" {
          description
            "Match packets with AF22 dscp (010100)";
        }
        enum "af23" {
          description
            "Match packets with AF23 dscp (010110)";
        }
        enum "af31" {
          description
            "Match packets with AF31 dscp (011010)";
        }
        enum "af32" {
          description
            "Match packets with AF32 dscp (011100)";
        }
        enum "af33" {
          description
            "Match packets with AF33 dscp (011110)";
        }
        enum "af41" {
          description
            "Match packets with AF41 dscp (100010)";
        }
        enum "af42" {
          description
            "Match packets with AF42 dscp (100100)";
        }
        enum "af43" {
          description
            "Match packets with AF43 dscp (100110)";
        }
        enum "cs1" {
          description
            "Match packets with CS1(precedence 1) dscp (001000)";
        }
        enum "cs2" {
          description
            "Match packets with CS2(precedence 2) dscp (010000)";
        }
        enum "cs3" {
          description
            "Match packets with CS3(precedence 3) dscp (011000)";
        }
        enum "cs4" {
          description
            "Match packets with CS4(precedence 4) dscp (100000)";
        }
        enum "cs5" {
          description
            "Match packets with CS5(precedence 5) dscp (101000)";
        }
        enum "cs6" {
          description
            "Match packets with CS6(precedence 6) dscp (110000)";
        }
        enum "cs7" {
          description
            "Match packets with CS7(precedence 7) dscp (111000)";
        }
        enum "default" {
          description
            "Match packets with default DSCP (000000)";
        }
        enum "ef" {
          description
            "Match packets with EF dscp (101110)";
        }
      }
    }
    description
      "Differentiated services codepoint value";
  }

  typedef protocol-type {
    type union {
      type uint8 {
        range "0..255" {
          description
            "An IP Protocol Number";
        }
      }
      type string {
        pattern '([0-9]{1,3})-([0-9]{1,3})' {
          description
            "Lower/upper limit of protocol range (<0-255>-<0-255>)";
        }
      }
      type enumeration {
        enum "ahp" {
          description
            "Authentication Header Protocol";
        }
        enum "eigrp" {
          description
            "Cisco's EIGRP Routing Protocol";
        }
        enum "esp" {
          description
            "Encapsulation Security Payload";
        }
        enum "gre" {
          description
            "Cisco's GRE Tunneling";
        }
        enum "icmp" {
          description
            "Internet Control Message Protocol";
        }
        enum "igmp" {
          description
            "Internet Gateway Message Protocol";
        }
        enum "igrp" {
          description
            "Cisco's IGRP Routing Protocol";
        }
        enum "ipinip" {
          description
            "IP in IP tunneling";
        }
        enum "ipv4" {
          description
            "Any IPv4 Protocol";
        }
        enum "ipv6" {
          description
            "Any IPv6 Protocol";
        }
        enum "ipv6icmp" {
          description
            "IPV6Internet Control Message Protocol";
        }
        enum "mpls" {
          description
            "Any MPLS Packet";
        }
        enum "nos" {
          description
            "KA9Q NOS Compatible IP over IP Tunneling";
        }
        enum "ospf" {
          description
            "OSPF Routing Protocol";
        }
        enum "pcp" {
          description
            "Payload Compression Protocol";
        }
        enum "pim" {
          description
            "Protocol Independent Multicast";
        }
        enum "sctp" {
          description
            "Stream Control Transmission Protocol";
        }
        enum "tcp" {
          description
            "Transport Control Protocol";
        }
        enum "udp" {
          description
            "User Datagram Protocol";
        }
      }
    }
  }

  typedef acl-list-name-type {
    type string {
      length "1..64";
    }
    description
      "Access list name";
  }

  typedef packet-length-type {
    type union {
      type uint16 {
        range "0..65535";
      }
      type string {
        pattern '([0-9]{1,5})-([0-9]{1,5})' {
          description
            "Lower/upper limit of packet length to match (<0-65535>-<0-65535>)";
        }
      }
    }
    description
      "IP packet length";
  }

  typedef precedence-type {
    type union {
      type uint8 {
        range "0..7";
      }
      type enumeration {
        enum "critical" {
          description
            "Critical precedence (5)";
        }
        enum "flash" {
          description
            "Flash precedence (3)";
        }
        enum "flash-override" {
          description
            "Flash override precedence (4)";
        }
        enum "immediate" {
          description
            "Immediate precedence (2)";
        }
        enum "internet" {
          description
            "Internetwork control precedence (6)";
        }
        enum "network" {
          description
            "Network control precedence (7)";
        }
        enum "priority" {
          description
            "Priority precedence (1)";
        }
        enum "routine" {
          description
            "Routine precedence (0)";
        }
      }
    }
    description
      "Precedence value";
  }

  typedef port-number-type {
    type union {
      type uint16 {
        range "0..65535" {
          description
            "A Port Number";
        }
      }
      type string {
        pattern '([0-9]+)-([0-9]+)' {
          description
            "Lower/upper imit of the Port range";
        }
      }
    }
  }

  typedef vlan-id-type {
    type union {
      type uint16 {
        range "1..4094" {
          description
            "Vlan Id";
        }
      }
      type string {
        pattern '([1-9][0-9]{0,3})-([1-9][0-9]{0,3})' {
          description
            "Lower/upper limit of the Vlan Id range (<1-4094>-<1-4094>)";
        }
      }
    }
  }

  typedef clear-text-password-type {
    type string;
    description
      "Clear text password";
  }

  typedef flow-monitor-map-name-type {
    type string {
      length "1..32";
      pattern '[a-zA-Z0-9][a-zA-Z0-9\._@$%+#:=<>\-]{0,62}';
    }
    description
      "Name of the flow monitor map";
  }

  typedef clone-interface-type {
    type xr2:Interface-name {
      pattern '^(Loopback)';
    }
    description
      "Specify an interface";
  }

  typedef rate-unit-type {
    type enumeration {
      enum "bps" {
        description
          "Bits per second (default)";
      }
      enum "gbps" {
        description
          "Gigabits per second";
      }
      enum "kbps" {
        description
          "Kilobits per second";
      }
      enum "mbps" {
        description
          "Megabits per second";
      }
      enum "cellsps" {
        description
          "Cells per second";
      }
      enum "pps" {
        description
          "Packets per second";
      }
    }
  }

  typedef burst-unit-type {
    type enumeration {
      enum "bytes" {
        description
          "Bytes (default)";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets";
      }
    }
  }

  typedef wred-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "packets" {
        description
          "Packets (default)";
      }
    }
  }

  typedef cac-unit-type {
    type enumeration {
      enum "bps" {
        description
          "Bits per second";
      }
      enum "gbps" {
        description
          "Gigabits per second";
      }
      enum "kbps" {
        description
          "Kilobits per second (default)";
      }
      enum "mbps" {
        description
          "Megabits per second";
      }
      enum "cellsps" {
        description
          "Cells per second";
      }
    }
  }

  typedef pfc-unit-type {
    type enumeration {
      enum "bytes" {
        description
          "Bytes";
      }
      enum "gbytes" {
        description
          "Gigabytes";
      }
      enum "kbytes" {
        description
          "Kilobytes";
      }
      enum "mbytes" {
        description
          "Megabytes";
      }
      enum "ms" {
        description
          "Milliseconds";
      }
      enum "us" {
        description
          "Microseconds";
      }
      enum "cells" {
        description
          "Cells";
      }
      enum "packets" {
        description
          "Packets";
      }
    }
  }

  typedef service-policy-name-type {
    type string {
      pattern '[a-zA-Z0-9][a-zA-Z0-9\._@$%+#:=<>\-]{0,62}';
    }
  }

  grouping ncs_template_class-map-common {
    leaf class-map-name {
      type string;
      description
        "Name of the class-map";
    }
    container match-all {
      presence "Match all match criteria";
      description
        "Match all match criteria";
    }
    container match-any {
      presence "Match any match criteria (default)";
      description
        "Match any match criteria (default)";
    }
    leaf description {
      type string;
      description
        "Set description for this class-map";
    }
  }

  grouping ncs_template_match-access-group {
    container access-group {
      description
        "Match access group";
      leaf-list ipv4 {
        // NCS patched for predictable order
        ordered-by user;
        // NCS drop if-feature statement
        type ncs_template_acl-list-name-type;
        description
          "IPv4 access list";
      }
      leaf-list ipv6 {
        // NCS patched for predictable order
        ordered-by user;
        // NCS drop if-feature statement
        type ncs_template_acl-list-name-type;
        description
          "IPv6 access list";
      }
      leaf-list ethernet-services {
        // NCS patched for predictable order
        ordered-by user;
        // NCS drop if-feature statement
        type ncs_template_acl-list-name-type;
        description
          "Ethernet-Services";
      }
    }
  }

  grouping ncs_template_match-atm {
    container atm {
      // NCS drop if-feature statement
      description
        "Match based on ATM specific criteria";
      leaf-list clp {
        // NCS patched for predictable order
        ordered-by user;
        type string;
        // NCS drop max-elements statement
        description
          "Match ATM CLP bit";
      }
      container oam {
        presence "Match ATM OAM";
        description
          "Match ATM OAM";
      }
    }
  }

  grouping ncs_template_match-cac {
    container cac {
      // NCS drop if-feature statement
      description
        "Match based on CAC fields";
      container admitted {
        presence "Match packets admitted by CAC action";
        description
          "Match packets admitted by CAC action";
      }
      container unadmitted {
        presence "Match packets unadmitted by CAC action";
        description
          "Match packets unadmitted by CAC action";
      }
    }
  }

  grouping ncs_template_match-cos {
    container cos {
      // NCS drop if-feature statement
      description
        "Match based on IEEE 802.1Q/ISL Class Of Service value";
      leaf-list value {
        // NCS patched for predictable order
        ordered-by user;
        type string;
        // NCS drop max-elements statement
        description
          "COS value";
      }
    }
    container cos-inner {
      // NCS drop if-feature statement
      description
        "Match inner cos values";
      leaf-list value {
        // NCS patched for predictable order
        ordered-by user;
        type string;
        // NCS drop max-elements statement
        description
          "inner cos value (Upto 8 values)";
      }
    }
  }

  grouping ncs_template_match-dei {
    leaf dei {
      // NCS drop if-feature statement
      type string;
      // NCS drop must statement
      description
        "Match based on DEI bit (0/1)";
    }
    leaf dei-inner {
      // NCS drop if-feature statement
      type string;
      // NCS drop must statement
      description
        "Match inner based on DEI bit (0/1)";
    }
  }

  grouping ncs_template_match-destination-address {
    container destination-address {
      description
        "Match based on destination address";
      container ipv4 {
        // NCS drop if-feature statement
        description
          "Match based on destination IPv4 address";
        list address-prefix {
          // NCS patched for predictable order
          ordered-by user;
          key "address netmask";
          description
            "IPv4 address";
          leaf address {
            type string;
            description
              "IPv4 address.";
          }
          leaf netmask {
            type string;
            description
              "IPv4 netmask.";
          }
        }
      }
      container ipv6 {
        // NCS drop if-feature statement
        description
          "Match based on destination IPv6 address";
        list address-prefix {
          // NCS patched for predictable order
          ordered-by user;
          key "address prefix-length";
          description
            "IPv6 address";
          leaf address {
            type string;
            description
              "IPv6 address.";
          }
          leaf prefix-length {
            type string;
            description
              "Length of the IPv6 Prefix.";
          }
        }
      }
      leaf mac {
        // NCS drop if-feature statement
        type string;
        description
          "MAC Address";
      }
    }
  }

  grouping ncs_template_matchnot-destination-address {
    container destination-address {
      description
        "Match based on destination address";
      container ipv4 {
        description
          "Match based on destination IPv4 address";
        list address-prefix {
          // NCS patched for predictable order
          ordered-by user;
          key "address netmask";
          description
            "IPv4 address";
          leaf address {
            type string;
            description
              "IPv4 address.";
          }
          leaf netmask {
            type string;
            description
              "IPv4 netmask.";
          }
        }
      }
      container ipv6 {
        description
          "Match based on destination IPv6 address";
        list address-prefix {
          // NCS patched for predictable order
          ordered-by user;
          key "address prefix-length";
          description
            "IPv6 address";
          leaf address {
            type string;
            description
              "IPv6 address.";
          }
          leaf prefix-length {
            type string;
            description
              "Length of the IPv6 Prefix.";
          }
        }
      }
      leaf mac {
        // NCS drop if-feature statement
        type string;
        description
          "MAC Address";
      }
    }
  }

  grouping ncs_template_match-destination-port {
    container destination-port {
      // NCS drop if-feature statement
      description
        "Match based on destination port";
      leaf-list port-number {
        // NCS patched for predictable order
        ordered-by user;
        type ncs_template_port-number-type;
        // NCS drop max-elements statement
        description
          "destination port";
      }
    }
  }

  grouping ncs_template_match-discard-class {
    container discard-class {
      // NCS drop if-feature statement
      description
        "Match based on discard class";
      leaf-list id {
        // NCS patched for predictable order
        ordered-by user;
        type string;
        // NCS drop max-elements statement
        description
          "Discard CLass Id";
      }
    }
  }

  grouping ncs_template_match-dscp {
    container dscp {
      // NCS drop if-feature statement
      description
        "Match based on IP DSCP value";
      leaf-list value {
        // NCS patched for predictable order
        ordered-by user;
        type ncs_template_dscp-value;
        description
          "DSCP value";
      }
    }
    container dscp-ipv4 {
      // NCS drop if-feature statement
      description
        "Match based on IPv4 DSCP value";
      leaf-list value {
        // NCS patched for predictable order
        ordered-by user;
        type ncs_template_dscp-value;
        description
          "DSCP value";
      }
    }
    container dscp-ipv6 {
      // NCS drop if-feature statement
      description
        "Match based on IPv6 DSCP value";
      leaf-list value {
        // NCS patched for predictable order
        ordered-by user;
        type ncs_template_dscp-value;
        description
          "DSCP value";
      }
    }
  }

  grouping ncs_template_match-ethertype {
    container ethertype {
      // NCS drop if-feature statement
      description
        "Match based on ethertype";
      leaf-list value {
        // NCS patched for predictable order
        ordered-by user;
        type string;
        // NCS drop max-elements statement
        description
          "Ethertype Value";
      }
    }
  }

  grouping ncs_template_match-flow-key {
    container flow-key {
      // NCS drop if-feature statement
      description
        "Match based on flow keys";
      container five-tuple {
        // NCS drop must statement
        presence "Five tuples to identify a flow";
        description
          "Five tuples to identify a flow";
      }
      container dst-ip {
        // NCS drop must statement
        presence "Destination IP address";
        description
          "Destination IP address";
      }
      container src-ip {
        // NCS drop must statement
        presence "Source IP address";
        description
          "Source IP address";
      }
      container flow-cache {
        description
          "Configure the flow-cache parameters";
        leaf idle-timeout {
          type string;
          description
            "Maximum time of inactivity for a flow.";
        }
      }
    }
  }

  grouping ncs_template_match-flow-tag {
    container flow-tag {
      // NCS drop if-feature statement
      description
        "Match based on flow-tag";
      leaf-list tag-number {
        // NCS patched for predictable order
        ordered-by user;
        type string;
        // NCS drop max-elements statement
        description
          "flow-tag number";
      }
    }
  }

  grouping ncs_template_match-fr-de {
    leaf fr-de {
      // NCS drop if-feature statement
      type string;
      description
        "Match based on FrameRelay DE bit";
    }
  }

  grouping ncs_template_match-fragment-type {
    container fragment-type {
      // NCS drop if-feature statement
      description
        "Fragment type for a packet";
      container dont-fragment {
        presence "Match don't-Fragment bit";
        description
          "Match don't-Fragment bit";
      }
      container first-fragment {
        presence "Match first fragment bit";
        description
          "Match first fragment bit";
      }
      container is-fragment {
        presence "Match is-fragment bit";
        description
          "Match is-fragment bit";
      }
      container last-fragment {
        presence "Match last fragment bit";
        description
          "Match last fragment bit";
      }
    }
  }

  grouping ncs_template_match-frame-relay {
    container frame-relay {
      // NCS drop if-feature statement
      description
        "Match based on frame-relay specific criteria";
      leaf-list dlci {
        // NCS patched for predictable order
        ordered-by user;
        type string;
        // NCS drop max-elements statement
        description
          "Match frame-relay dlci value(s)";
      }
    }
  }

  grouping ncs_template_match-ipv4 {
    container ipv4 {
      description
        "Match based on ipv4 icmp";
      container icmp-code {
        description
          "Match based on ipv4 icmp code";
        leaf-list value {
          // NCS patched for predictable order
          ordered-by user;
          type string;
          // NCS drop max-elements statement
          description
            "IPv4 ICMP code";
        }
      }
      container icmp-type {
        description
          "Match based on ipv4 icmp type";
        leaf-list value {
          // NCS patched for predictable order
          ordered-by user;
          type string;
          // NCS drop max-elements statement
          description
            "IPv4 ICMP type";
        }
      }
    }
  }

  grouping ncs_template_match-ipv6 {
    container ipv6 {
      description
        "Match based on IPv6";
      container icmp-code {
        description
          "IPv6 ICMP code";
        leaf-list value {
          // NCS patched for predictable order
          ordered-by user;
          type string;
          // NCS drop max-elements statement
          description
            "ICMP code";
        }
      }
      container icmp-type {
        description
          "IPv6 ICMP type";
        leaf-list value {
          // NCS patched for predictable order
          ordered-by user;
          type string;
          // NCS drop max-elements statement
          description
            "ICMP type";
        }
      }
    }
  }

  grouping ncs_template_match-mpls {
    container mpls {
      description
        "Match based on MPLS specific values";
      container disposition {
        description
          "Match MPLS Label Disposition";
        container access-group {
          description
            "access group";
          leaf ipv4 {
            // NCS drop if-feature statement
            type string;
            description
              "IPv4 access list";
          }
          leaf ipv6 {
            // NCS drop if-feature statement
            type string;
            description
              "IPv6 access list";
          }
        }
        leaf class-map {
          // NCS drop if-feature statement
          type string;
          description
            "class-map name";
        }
      }
      container experimental {
        description
          "Match MPLS experimental values";
        container imposition {
          // NCS drop if-feature statement
          description
            "Match imposition label";
          leaf-list label {
            // NCS patched for predictable order
            ordered-by user;
            type string;
            // NCS drop max-elements statement
            description
              "MPLS experimental label";
          }
        }
        container topmost {
          // NCS drop if-feature statement
          description
            "Match topmost label";
          leaf-list label {
            // NCS patched for predictable order
            ordered-by user;
            type string;
            // NCS drop max-elements statement
            description
              "MPLS experimental label";
          }
        }
      }
    }
  }

  grouping ncs_template_matchnot-mpls {
    container mpls {
      description
        "Match based on MPLS specific values";
      container disposition {
        description
          "Match MPLS Label Disposition";
        container access-group {
          description
            "access group";
          leaf ipv4 {
            // NCS drop if-feature statement
            type string;
            description
              "IPv4 access list";
          }
          leaf ipv6 {
            // NCS drop if-feature statement
            type string;
            description
              "IPv6 access list";
          }
        }
      }
      container experimental {
        description
          "Match MPLS experimental values";
        container topmost {
          description
            "Match topmost label";
          leaf-list label {
            // NCS patched for predictable order
            ordered-by user;
            type string;
            // NCS drop max-elements statement
            description
              "MPLS experimental label";
          }
        }
      }
    }
  }

  grouping ncs_template_match-packet {
    container packet {
      description
        "Match based on packet length";
      container length {
        description
          "Packet length";
        leaf-list value {
          // NCS patched for predictable order
          ordered-by user;
          type ncs_template_packet-length-type;
          // NCS drop max-elements statement
          description
            "IP Packet Length";
        }
      }
      container length-ipv4 {
        // NCS drop if-feature statement
        description
          "IPV4 Packet Length";
        leaf-list value {
          // NCS patched for predictable order
          ordered-by user;
          type ncs_template_packet-length-type;
          // NCS drop max-elements statement
        }
      }
      container length-ipv6 {
        // NCS drop if-feature statement
        description
          "IPV6 Packet Length";
        leaf-list value {
          // NCS patched for predictable order
          ordered-by user;
          type ncs_template_packet-length-type;
          // NCS drop max-elements statement
        }
      }
    }
  }

  grouping ncs_template_matchnot-packet {
    container packet {
      description
        "Match based on packet length";
      container length {
        description
          "Packet length";
        leaf-list value {
          // NCS patched for predictable order
          ordered-by user;
          type ncs_template_packet-length-type;
          // NCS drop max-elements statement
          description
            "IP Packet Length";
        }
      }
      container length-ipv4 {
        // NCS drop if-feature statement
        description
          "IPV4 Packet Length";
        leaf-list value {
          // NCS patched for predictable order
          ordered-by user;
          type ncs_template_packet-length-type;
          // NCS drop max-elements statement
        }
      }
      container length-ipv6 {
        // NCS drop if-feature statement
        description
          "IPV6 Packet Length";
        leaf-list value {
          // NCS patched for predictable order
          ordered-by user;
          type ncs_template_packet-length-type;
          // NCS drop max-elements statement
        }
      }
    }
  }

  grouping ncs_template_match-precedence {
    container precedence {
      // NCS drop if-feature statement
      description
        "Match based on IP precedence values";
      leaf-list value {
        // NCS patched for predictable order
        ordered-by user;
        type ncs_template_precedence-type;
        // NCS drop max-elements statement
        description
          "IP precedence";
      }
    }
    container precedence-ipv4 {
      // NCS drop if-feature statement
      description
        "Match based on IPV4 precedence";
      leaf-list value {
        // NCS patched for predictable order
        ordered-by user;
        type ncs_template_precedence-type;
        // NCS drop max-elements statement
        description
          "IPV4 precedence";
      }
    }
    container precedence-ipv6 {
      // NCS drop if-feature statement
      description
        "Match based on IPV6 precedence";
      leaf-list value {
        // NCS patched for predictable order
        ordered-by user;
        type ncs_template_precedence-type;
        // NCS drop max-elements statement
        description
          "IPV6 precedence";
      }
    }
  }

  grouping ncs_template_match-protocol {
    container protocol {
      description
        "Match based on L3 protocol (Upto 8 values or ranges)";
      leaf-list number {
        // NCS patched for predictable order
        ordered-by user;
        type ncs_template_protocol-type;
        // NCS drop max-elements statement
        description
          "Protocol Number";
      }
    }
  }

  grouping ncs_template_match-qos-group {
    container qos-group {
      description
        "Match based on QoS Group";
      leaf-list id {
        // NCS patched for predictable order
        ordered-by user;
        type string;
        // NCS drop max-elements statement
        description
          "QoS Group Id";
      }
    }
  }

  grouping ncs_template_match-traffic-class {
    container traffic-class {
      description
        "Match based on Traffic Class";
      leaf-list id {
        // NCS patched for predictable order
        ordered-by user;
        type string;
        // NCS drop max-elements statement
        description
          "Traffic Class Id";
      }
    }
  }

  grouping ncs_template_match-source-address {
    container source-address {
      description
        "Match based on source address";
      container ipv4 {
        // NCS drop if-feature statement
        description
          "Match based on source IPv4 address";
        list address-prefix {
          // NCS patched for predictable order
          ordered-by user;
          key "address netmask";
          description
            "IPv4 address";
          leaf address {
            type string;
            description
              "IPv4 address.";
          }
          leaf netmask {
            type string;
            description
              "IPv4 netmask.";
          }
        }
      }
      container ipv6 {
        // NCS drop if-feature statement
        description
          "Match based on source IPv6 address";
        list address-prefix {
          // NCS patched for predictable order
          ordered-by user;
          key "address prefix-length";
          description
            "IPv6 address";
          leaf address {
            type string;
            description
              "IPv6 address.";
          }
          leaf prefix-length {
            type string;
            description
              "Length of the IPv6 Prefix.";
          }
        }
      }
      leaf mac {
        // NCS drop if-feature statement
        type string;
        description
          "MAC Address";
      }
    }
  }

  grouping ncs_template_matchnot-source-address {
    container source-address {
      description
        "Match based on source address";
      container ipv4 {
        description
          "Match based on source IPv4 address";
        list address-prefix {
          // NCS patched for predictable order
          ordered-by user;
          key "address netmask";
          description
            "IPv4 address";
          leaf address {
            type string;
            description
              "IPv4 address.";
          }
          leaf netmask {
            type string;
            description
              "IPv4 netmask.";
          }
        }
      }
      container ipv6 {
        description
          "Match based on source IPv6 address";
        list address-prefix {
          // NCS patched for predictable order
          ordered-by user;
          key "address prefix-length";
          description
            "IPv6 address";
          leaf address {
            type string;
            description
              "IPv6 address.";
          }
          leaf prefix-length {
            type string;
            description
              "Length of the IPv6 Prefix.";
          }
        }
      }
      leaf mac {
        // NCS drop if-feature statement
        type string;
        description
          "MAC Address";
      }
    }
  }

  grouping ncs_template_match-source-port {
    container source-port {
      // NCS drop if-feature statement
      description
        "Match based on source port";
      leaf-list number {
        // NCS patched for predictable order
        ordered-by user;
        type ncs_template_port-number-type;
        // NCS drop max-elements statement
        description
          "source port";
      }
    }
  }

  grouping ncs_template_match-tcp-flag {
    container tcp-flag {
      description
        "Match based on TCP flags";
      leaf value {
        type string;
        description
          "TCP flags value";
      }
      container any {
        presence "Match based on any bit set";
        description
          "Match based on any bit set";
      }
    }
  }

  grouping ncs_template_match-vlan {
    container vlan {
      // NCS drop if-feature statement
      description
        "Match based on Vlan Ids";
      leaf-list vlan-id {
        // NCS patched for predictable order
        ordered-by user;
        type ncs_template_vlan-id-type;
        // NCS drop max-elements statement
        description
          "Vlan Id";
      }
    }
    container vlan-inner {
      // NCS drop if-feature statement
      description
        "Match based on inner Vlan Ids";
      leaf-list vlan-id {
        // NCS patched for predictable order
        ordered-by user;
        type ncs_template_vlan-id-type;
        // NCS drop max-elements statement
        description
          "inner Vlan Id";
      }
    }
  }

  grouping ncs_template_matchnot-vlan {
    container vlan {
      // NCS drop if-feature statement
      description
        "Match based on Vlan Ids";
      leaf-list vlan-id {
        // NCS patched for predictable order
        ordered-by user;
        type ncs_template_vlan-id-type;
        // NCS drop max-elements statement
        description
          "Vlan Id";
      }
    }
    container vlan-inner {
      // NCS drop if-feature statement
      description
        "Match based on inner Vlan Ids";
      leaf-list vlan-id {
        // NCS patched for predictable order
        ordered-by user;
        type ncs_template_vlan-id-type;
        // NCS drop max-elements statement
        description
          "inner Vlan Id";
      }
    }
  }

  grouping ncs_template_match-vpls {
    container vpls {
      description
        "Match based on VPLS fields";
      container known {
        // NCS drop if-feature statement
        presence "VPLS Known";
        description
          "VPLS Known";
      }
      container unknown {
        // NCS drop if-feature statement
        presence "VPLS Unknown";
        description
          "VPLS Unknown";
      }
      container broadcast {
        presence "VPLS Broadcast";
        description
          "VPLS Broadcast";
      }
      container control {
        // NCS drop if-feature statement
        presence "VPLS Control";
        description
          "VPLS Control";
      }
      container multicast {
        presence "VPLS Multicast";
        description
          "VPLS Multicast";
      }
    }
  }

  grouping ncs_template_matchnot-vpls {
    container vpls {
      description
        "Match based on VPLS fields";
      container known {
        // NCS drop if-feature statement
        presence "VPLS Known";
        description
          "VPLS Known";
      }
      container unknown {
        // NCS drop if-feature statement
        presence "VPLS Unknown";
        description
          "VPLS Unknown";
      }
      container broadcast {
        // NCS drop if-feature statement
        presence "VPLS Broadcast";
        description
          "VPLS Broadcast";
      }
      container control {
        // NCS drop if-feature statement
        presence "VPLS Control";
        description
          "VPLS Control";
      }
      container multicast {
        // NCS drop if-feature statement
        presence "VPLS Multicast";
        description
          "VPLS Multicast";
      }
    }
  }

  grouping ncs_template_match-authen-status {
    leaf authen-status {
      // NCS drop if-feature statement
      type string;
      description
        "Authentication Status";
    }
  }

  grouping ncs_template_match-circuit-id {
    container circuit-id {
      description
        "Match based on circuit ID";
      leaf-list value {
        // NCS patched for predictable order
        ordered-by user;
        type string;
        description
          "circuit ID";
      }
    }
    container circuit-id-regexp {
      description
        "Match based on circuit ID regular expression";
      leaf-list value {
        // NCS patched for predictable order
        ordered-by user;
        type string;
        description
          "Circuit ID regular expression";
      }
    }
  }

  grouping ncs_template_match-dhcp-client-id {
    container dhcp-client-id {
      description
        "Match based on dhcp client id";
      list client-id {
        // NCS patched for predictable order
        ordered-by user;
        key "id flag";
        description
          "client id";
        leaf id {
          type string;
          description
            "client id";
        }
        leaf flag {
          type string;
          description
            "client id flag";
        }
      }
    }
    container dhcp-client-id-regexp {
      description
        "Match based on dhcp client id regular expression";
      list client-id {
        // NCS patched for predictable order
        ordered-by user;
        key "id flag";
        description
          "client id with regular expression";
        leaf id {
          type string;
          description
            "client id with regular expression";
        }
        leaf flag {
          type string;
          description
            "client id flag";
        }
      }
    }
  }

  grouping ncs_template_match-domain {
    container domain {
      description
        "Match base on domain name";
      list domain-name {
        // NCS patched for predictable order
        ordered-by user;
        key "name format";
        description
          "Domain name";
        leaf name {
          type string;
          description
            "Domain name";
        }
        leaf format {
          type string;
          description
            "Domain format name";
        }
      }
    }
    container domain-regexp {
      description
        "Match base on domain name with regular expression";
      list domain-name {
        // NCS patched for predictable order
        ordered-by user;
        key "regexp format";
        description
          "Domain name";
        leaf regexp {
          type string;
          description
            "Domain name with regular expression";
        }
        leaf format {
          type string;
          description
            "Domain format name";
        }
      }
    }
  }

  grouping ncs_template_match-control-protocol {
    container protocol {
      description
        "Match based on protocol";
      leaf-list name {
        // NCS patched for predictable order
        ordered-by user;
        // NCS drop if-feature statement
        type string;
        // NCS drop max-elements statement
        description
          "protocol name";
      }
    }
  }

  grouping ncs_template_match-remote-id {
    container remote-id {
      description
        "Match based on remote ID";
      leaf-list id {
        // NCS patched for predictable order
        ordered-by user;
        type string;
        description
          "remote-id";
      }
    }
    container remote-id-regexp {
      description
        "Remote ID with regular expression";
      leaf-list id {
        // NCS patched for predictable order
        ordered-by user;
        type string;
        description
          "remote-id with regular expression";
      }
    }
  }

  grouping ncs_template_match-service-name {
    container service-name {
      description
        "Match based on service name";
      leaf-list name {
        // NCS patched for predictable order
        ordered-by user;
        type string;
        description
          "Service name";
      }
    }
    container service-name-regexp {
      description
        "Match based on service name with regular expression";
      leaf-list name {
        // NCS patched for predictable order
        ordered-by user;
        type string;
        description
          "Service name with regular expression";
      }
    }
  }

  grouping ncs_template_match-timer {
    container timer {
      // NCS drop if-feature statement
      description
        "Match based on timer";
      leaf-list name {
        // NCS patched for predictable order
        ordered-by user;
        type string;
        description
          "Timer name";
      }
    }
    container timer-regexp {
      description
        "Timer with regular expression";
      leaf-list name {
        // NCS patched for predictable order
        ordered-by user;
        type string;
        description
          "Timer name with regular expression";
      }
    }
  }

  grouping ncs_template_match-username {
    container username {
      // NCS drop if-feature statement
      description
        "Match based on user name";
      leaf-list name {
        // NCS patched for predictable order
        ordered-by user;
        type string;
        description
          "User name";
      }
    }
    container username-regexp {
      // NCS drop if-feature statement
      description
        "Match based on user name with regular expression";
      leaf-list name {
        // NCS patched for predictable order
        ordered-by user;
        type string;
        description
          "User name with regular expression";
      }
    }
  }

  grouping ncs_template_policy-map-common {
    leaf policy-map-name {
      type string;
      description
        "Name of the policymap";
    }
    leaf description {
      type string;
      description
        "Set description for this policy-map";
    }
  }

  grouping ncs_template_policy-action-compress {
    container compress {
      // NCS drop if-feature statement
      description
        "Configure compress action";
      container header {
        description
          "Configure header compression";
        container ip {
          presence "Configure IP header compression";
          description
            "Configure IP header compression";
        }
      }
    }
  }

  grouping ncs_template_policy-action-encap-sequence {
    leaf encap-sequence {
      // NCS drop if-feature statement
      type string;
      description
        "Configure encapsulation sequence";
    }
  }

  grouping ncs_template_aaa-method {
    container aaa {
      description
        "AAA specification";
      leaf list {
        type string;
        description
          "Specify AAA method list that authentication should be made with";
      }
    }
  }

  grouping ncs_template_subscriber-actions {
    container activate {
      description
        "Activate";
      container dynamic-template {
        description
          "actions related to dynamic templates";
        leaf template-name {
          type string;
          description
            "Dynamic template name";
        }
        uses ncs_template_aaa-method;
      }
    }
    container deactivate {
      description
        "Deactivate";
      container dynamic-template {
        description
          "actions related to dynamic templates";
        leaf template-name {
          type string;
          description
            "Dynamic template name";
        }
        uses ncs_template_aaa-method;
      }
    }
    container authenticate {
      // NCS drop if-feature statement
      description
        "Authentication related configuration";
      uses ncs_template_aaa-method;
    }
    container authorize {
      // NCS drop if-feature statement
      description
        "Authorize";
      uses ncs_template_aaa-method;
      leaf format {
        type string;
        description
          "Specify an Authorize format name";
      }
      leaf identifier {
        type string;
        description
          "Specify an Authorize identifier";
      }
      leaf password {
        type string;
        description
          "Specify a password to be used for AAA request";
      }
    }
    container disconnect {
      // NCS drop if-feature statement
      presence "Disconnect session";
      description
        "Disconnect session";
    }
    container monitor {
      // NCS drop if-feature statement
      presence "Monitor session";
      description
        "Monitor session";
    }
    container set-timer {
      // NCS drop if-feature statement
      // NCS drop must statement
      presence "indicates set-timer is configured";
      description
        "Set a timer to execute a rule on its expiry";
      leaf name {
        type string;
        description
          "Name of the timer";
      }
      leaf value {
        type string;
        units "minutes";
      }
    }
    container stop-timer {
      // NCS drop if-feature statement
      description
        "Disable timer before it expires";
      leaf name {
        type string;
        description
          "Name of the timer";
      }
    }
  }

  grouping ncs_template_pbr-actions {
    container drop {
      presence "Drop the packet";
      description
        "Drop the packet";
    }
    leaf http-redirect {
      // NCS drop if-feature statement
      type string;
      description
        "Configure HTTP redirect. Specify the URL HTTP requests should be redirected to";
    }
    container http-enrichment {
      // NCS drop if-feature statement
      description
        "Configure HTTP enrichment";
      container subscriber-mac {
        presence "Subscriber MAC address";
        description
          "Subscriber MAC address";
      }
      container subscriber-ip {
        presence "Subscriber ipv4/ipv6 address";
        description
          "Subscriber ipv4/ipv6 address";
      }
      container hostname {
        presence "Hostname";
        description
          "Hostname";
      }
      container bng-interface {
        presence "BNG identifier interface";
        description
          "BNG identifier interface";
      }
    }
    container police {
      description
        "Police traffic";
      container rate {
        // NCS drop must statement
        presence "indicates rate is configured";
        description
          "Committed Information Rate";
        leaf value {
          type string;
        }
        leaf unit {
          type ncs_template_rate-unit-type;
        }
      }
    }
    container redirect-ipv4 {
      // NCS drop if-feature statement
      description
        "Configure PBF redirect feature with IPv4 configurations";
      container default-route {
        presence "Forward to the default nexthop";
        description
          "Forward to the default nexthop";
      }
      container nexthop1 {
        description
          "Forward to specified nexthop";
        leaf address {
          type string;
          description
            "IPv4 Nexthop address";
        }
        leaf vrf {
          type string;
          description
            "Enter specific VRF Name for this nexthop";
        }
      }
      container nexthop2 {
        description
          "Forward to specified nexthop";
        leaf address {
          type string;
          description
            "IPv4 Nexthop address";
        }
        leaf vrf {
          type string;
          description
            "Enter specific VRF Name for this nexthop";
        }
      }
      container nexthop3 {
        description
          "Forward to specified nexthop";
        leaf address {
          type string;
          description
            "IPv4 Nexthop address";
        }
        leaf vrf {
          type string;
          description
            "Enter specific VRF Name for this nexthop";
        }
      }
    }
    container redirect-ipv6 {
      // NCS drop if-feature statement
      description
        "Configure PBF redirect feature with IPv6 configurations";
      container default-route {
        presence "Forward to the default nexthop";
        description
          "Forward to the default nexthop";
      }
      container nexthop1 {
        description
          "Forward to specified nexthop";
        leaf address {
          type string;
          description
            "IPv6 Nexthop address";
        }
        leaf vrf {
          type string;
          description
            "Enter specific VRF Name for this nexthop";
        }
      }
      container nexthop2 {
        description
          "Forward to specified nexthop";
        leaf address {
          type string;
          description
            "IPv6 Nexthop address";
        }
        leaf vrf {
          type string;
          description
            "Enter specific VRF Name for this nexthop";
        }
      }
      container nexthop3 {
        description
          "Forward to specified nexthop";
        leaf address {
          type string;
          description
            "IPv6 Nexthop address";
        }
        leaf vrf {
          type string;
          description
            "Enter specific VRF Name for this nexthop";
        }
      }
    }
    container redirect-nexthop {
      // NCS drop if-feature statement
      description
        "Configure PBF redirect feature with forwarding to specified nexthop";
      container route-target {
        // NCS drop must statement
        presence "indicates route-target is configured";
        description
          "Enter specific route-target string";
        leaf address {
          type string;
          description
            "IPv4 address.";
        }
        leaf index {
          type string;
          description
            "IPv4 Address:index";
        }
        leaf as-number {
          type string;
          description
            "AS number";
        }
      }
    }
    container service-function-path {
      // NCS drop if-feature statement
      description
        "Configure NSH service function action";
      leaf path-id {
        type string;
        // NCS drop must statement
        description
          "Service function path id";
      }
      leaf index {
        type string;
        // NCS drop must statement
        description
          "Specify service path index";
      }
      leaf metadata {
        type string;
        // NCS drop must statement
        description
          "service-function metadata";
      }
    }
    container set {
      description
        "Configure marking for this class";
      container destination-address {
        // NCS drop if-feature statement
        description
          "Set Destination address";
        leaf ipv4 {
          type string;
          description
            "IPv4 address";
        }
      }
      leaf df {
        // NCS drop if-feature statement
        type string;
        description
          "Set DF bit";
      }
      leaf dscp {
        type ncs_template_dscp-value;
        description
          "Set DSCP";
      }
      leaf forward-class {
        // NCS drop if-feature statement
        type string;
        description
          "Set forward class";
      }
      container source-address {
        // NCS drop if-feature statement
        description
          "Set Source address";
        leaf ipv4 {
          type string;
          description
            "IPv4 address";
        }
      }
    }
    container transmit {
      // NCS drop if-feature statement
      presence "Forward packet to the original destination";
      description
        "Forward packet to the original destination";
    }
    container decapsulate {
      // NCS drop if-feature statement
      description
        "Decapsulate GRE packet";
      container gre {
        presence "Decapsulate GRE packet";
        description
          "Decapsulate GRE packet";
      }
    }
  }

  grouping ncs_template_performance-traffic-actions {
    uses ncs_template_policy-action-compress;
    uses ncs_template_policy-action-encap-sequence;
    list react {
      // NCS patched for predictable order
      ordered-by user;
      // NCS drop if-feature statement
      key "operation-id";
      description
        "Generate alert on the specified event";
      leaf operation-id {
        type string;
        description
          "Specify an operation id (num)";
      }
      container delay-factor {
        presence "React criterion delay factor of policy-map action.";
        description
          "React criterion delay factor of policy-map action.";
      }
      container media-stop {
        presence "React criterion media stop of policy-map action.";
        description
          "React criterion media stop of policy-map action.";
      }
      container mrv {
        presence "React criterion mrv of policy-map action.";
        description
          "React criterion mrv of policy-map action.";
      }
      container flow-count {
        presence "React criterion flow count of policy-map action.";
        description
          "React criterion flow count of policy-map action.";
      }
      container packet-rate {
        presence "React criterion packet rate of the policy-map action.";
        description
          "React criterion packet rate of the policy-map action.";
      }
      leaf description {
        type string;
        description
          "Set Description for this alert action";
      }
      container trigger {
        description
          "Set the event trigger";
        container value {
          // NCS drop must statement
          presence "indicates value is configured";
          description
            "Set the trigger criterion";
          leaf lt {
            type ncs_template_trigger-value;
            description
              "trigger only if metric is less than the given value";
          }
          leaf le {
            type ncs_template_trigger-value;
            description
              "trigger only if metric is less than or equal to the given value";
          }
          leaf gt {
            type ncs_template_trigger-value;
            description
              "trigger only if metric is greater than the given value";
          }
          leaf ge {
            type ncs_template_trigger-value;
            description
              "trigger only if metric is greater than or equal to the given value";
          }
          leaf range {
            type ncs_template_trigger-value;
            description
              "trigger only if metric is in the inclusive range";
          }
        }
        container type {
          // NCS drop must statement
          presence "indicates type is configured";
          description
            "Set the trigger type";
          container immediate {
            presence "Immediate trigger";
            description
              "Immediate trigger";
          }
          leaf average {
            type string;
            description
              "Trigger averaged over N intervals.";
          }
        }
      }
      container action {
        description
          "Set the event action";
        container syslog {
          presence "Report via syslog";
          description
            "Report via syslog";
        }
        container snmp {
          // NCS drop if-feature statement
          presence "Report via syslog";
          description
            "Report via syslog";
        }
      }
      container alarm {
        // NCS drop if-feature statement
        description
          "Configure alarms";
        container type {
          // NCS drop must statement
          presence "indicates type is configured";
          description
            "Set the alarm type";
          container discrete {
            presence "Discrete alarms";
            description
              "Discrete alarms";
          }
          container grouped {
            // NCS drop if-feature statement
            description
              "Grouped alarms";
            leaf count {
              type string;
              units "number of flows";
              // NCS drop must statement
              description
                "Grouped on num-flows";
            }
            leaf percent {
              type string;
              units "percentage";
              // NCS drop must statement
              description
                "Grouped on percentage of flows";
            }
          }
        }
        leaf severity {
          type string;
          description
            "Set the alarm severity";
        }
      }
    }
  }

  grouping ncs_template_action-common {
    leaf cos {
      type string;
      description
        "Sets the specific IEEE 802.1Q Layer 2 CoS value of an
         outgoing packet.
         This command should be used by a router if a user wants
         to mark a packet that is being sent to a switch.
         Switches can leverage Layer 2 header information,
         including a CoS value marking. Packets entering an
         interface cannot be set with a CoS value.";
    }
    leaf cos-inner {
      type string;
      description
        "Set inner COS";
    }
    leaf dei {
      type string;
      description
        "Set DEI";
    }
    leaf dei-imposition {
      type string;
      description
        "Set DEI imposition bit.";
    }
    leaf discard-class {
      type string;
      description
        "Sets the discard class on IPv4 or MPLS packets.
         The discard-class can be used only in service policies
         that are attached in the ingress policy.";
    }
    leaf dscp {
      type ncs_template_dscp-value;
      description
        "Set IP DSCP (DiffServ CodePoint)";
    }
    leaf dscp-tunnel {
      type ncs_template_dscp-value;
      description
        "Set DSCP Tunnel(for ipsec tunnels)";
    }
    leaf fr-de {
      // NCS drop if-feature statement
      type string;
      description
        "Set frame relay discard-eligible bit";
    }
    container mpls {
      description
        "Set MPLS specific values";
      container experimental {
        description
          "Set experimental";
        leaf imposition {
          type string;
          description
            "Sets the experimental value of the MPLS packet
             imposition labels.
             Imposition can be used only in service policies that
             are attached in the ingress policy";
        }
        leaf topmost {
          type string;
          description
            "Sets the experimental value of the MPLS packet top-most
             labels.";
        }
      }
    }
    leaf precedence {
      type ncs_template_precedence-type;
      description
        "Set IP Precedence";
    }
    leaf precedence-tunnel {
      type ncs_template_precedence-type;
      description
        "Set Precedence tunnel(for ipsec tunnels)";
    }
    leaf qos-group {
      type string;
      description
        "Sets the QoS group identifiers on IPv4 or MPLS packets.
         The set qos-group is supported only on an ingress policy.";
    }
  }

  grouping ncs_template_police-actions {
    container transmit {
      presence "Transmit packet";
      description
        "Transmit packet";
    }
    container drop {
      presence "Drop packet";
      description
        "Drop packet";
    }
    container set {
      description
        "Conditional marking";
      uses ncs_template_action-common;
    }
  }

  grouping ncs_template_qos-actions {
    container admit {
      // NCS drop if-feature statement
      description
        "Call admission control";
      container cac {
        description
          "Call admission control (CAC) functionality";
        container local {
          // NCS drop must statement
          presence "indicates local is configured";
          description
            "CAC local flow type (default type)";
          container flow {
            description
              "Flow attributes";
            leaf idle-timeout {
              type string;
              description
                "Maximum time of inactivity for a flow";
            }
            container rate {
              // NCS drop must statement
              presence "indicates rate is configured";
              description
                "Per flow rate";
              leaf value {
                type string;
              }
              leaf unit {
                type ncs_template_cac-unit-type;
              }
            }
          }
          container rate {
            // NCS drop must statement
            presence "indicates rate is configured";
            description
              "Maximum rate for all flows";
            leaf value {
              type string;
            }
            leaf unit {
              type ncs_template_cac-unit-type;
            }
          }
        }
      }
    }
    container bandwidth {
      // NCS drop if-feature statement
      // NCS drop must statement
      presence "indicates bandwidth is configured";
      description
        "Configure bandwidth for this class";
      leaf value {
        type string;
      }
      leaf unit {
        type string;
      }
    }
    container bandwidth-remaining {
      // NCS drop if-feature statement
      // NCS drop must statement
      presence "indicates bandwidth-remaining is configured";
      description
        "Allocate left over bandwidth";
      leaf unit {
        type string;
        description
          "Bandwidth value unit";
      }
      leaf value {
        type string;
        description
          "Bandwidth value";
      }
    }
    uses ncs_template_policy-action-compress;
    uses ncs_template_policy-action-encap-sequence;
    leaf fragment {
      // NCS drop if-feature statement
      type string;
      description
        "Refer to an existing service fragment. Reference to a Service fragment.";
    }
    container pause {
      // NCS drop if-feature statement
      presence "Configure PFC feature";
      description
        "Configure PFC feature";
      container buffer-size {
        // NCS drop must statement
        presence "indicates buffer-size is configured";
        description
          "Configure buffer size";
        leaf value {
          type string;
          description
            "Range of buffer size";
        }
        leaf unit {
          type ncs_template_pfc-unit-type;
        }
      }
      container pause-threshold {
        // NCS drop must statement
        presence "indicates pause-threshold is configured";
        description
          "Configure pasue threshold";
        leaf value {
          type string;
          description
            "Range of pause threshold";
        }
        leaf unit {
          type ncs_template_pfc-unit-type;
        }
      }
      container resume-threshold {
        // NCS drop must statement
        presence "indicates resume-threshold is configured";
        description
          "Configure resume threshold";
        leaf value {
          type string;
          description
            "Range of resume threshold";
        }
        leaf unit {
          type ncs_template_pfc-unit-type;
        }
      }
    }
    container police {
      description
        "Police traffic";
      container conditional {
        presence "Conditional policer for priority traffic";
        description
          "Conditional policer for priority traffic";
      }
      container rate {
        // NCS drop must statement
        presence "indicates rate is configured";
        description
          "Committed Information Rate";
        leaf value {
          type string;
          description
            "Committed Information Rate";
        }
        leaf unit {
          type string;
          description
            "Rate unit";
        }
      }
      container burst {
        description
          "Burst size (BC)";
        leaf value {
          type string;
          description
            "Burst size (BC)";
        }
        leaf unit {
          type ncs_template_burst-unit-type;
          description
            "Burst size unit";
        }
      }
      container peak-burst {
        // NCS drop if-feature statement
        description
          "Excess Burst size (BE)";
        leaf value {
          type string;
          description
            "Exess burst size (BC)";
        }
        leaf unit {
          type ncs_template_burst-unit-type;
          description
            "Burst size unit";
        }
      }
      container peak-rate {
        // NCS drop must statement
        presence "indicates peak-rate is configured";
        description
          "Peak Information Rate";
        leaf value {
          type string;
          description
            "Peak Information Rate";
        }
        leaf unit {
          type string;
        }
      }
      container conform-action {
        description
          "Action for conforming traffic";
        uses ncs_template_police-actions;
      }
      container exceed-action {
        description
          "Action for exceeding traffic";
        uses ncs_template_police-actions;
      }
      container violate-action {
        description
          "Action for violating traffic";
        uses ncs_template_police-actions;
      }
      leaf conform-color {
        // NCS drop if-feature statement
        type string;
        description
          "Configure conform color class for color aware policing. Conform color class name.";
      }
      leaf exceed-color {
        // NCS drop if-feature statement
        type string;
        description
          "Configure exceed color class for color aware policing. Exceed color class name.";
      }
      container child-conform-aware {
        // NCS drop if-feature statement
        presence "Enable coupled policing";
        description
          "Enable coupled policing";
      }
    }
    container priority {
      description
        "Assign priority to this class";
      leaf level {
        type string;
        description
          "Configure a priority level";
      }
    }
    container queue-limits {
      description
        "Queue Limit Node";
      list queue-limit {
        // NCS patched for predictable order
        ordered-by user;
        key "value unit";
        description
          "Configure queue-limit (taildrop threshold) for this class";
        leaf value {
          type string;
          description
            "queue-limit value";
        }
        leaf unit {
          type string;
          description
            "queue-limit unit";
        }
        container discard-classes {
          description
            "discard class container";
          leaf-list discard-class {
            // NCS patched for predictable order
            ordered-by user;
            type string;
            description
              "Remaining bandwidth value.";
          }
        }
      }
    }
    container random-detect-default {
      presence "Enable RED with default min and max thresholds";
      description
        "Enable RED with default min and max thresholds";
    }
    container random-detect-ecn {
      presence "Enable ECN based WRED";
      description
        "ECN based WRED";
    }
    list random-detect {
      // NCS patched for predictable order
      ordered-by user;
      key "minimum-threshold-value minimum-threshold-unit maximum-threshold-value maximum-threshold-unit";
      description
        "Enable Random Early Detection.
         All RED profiles in a class must be based
         on the same field.";
      leaf minimum-threshold-value {
        type string;
        description
          "Minimum threshold";
      }
      leaf minimum-threshold-unit {
        type ncs_template_wred-unit-type;
        description
          "threshold unit";
      }
      leaf maximum-threshold-value {
        type string;
        description
          "Maximum threshold";
      }
      leaf maximum-threshold-unit {
        type ncs_template_wred-unit-type;
        description
          "threshold unit";
      }
      leaf-list cos {
        // NCS patched for predictable order
        ordered-by user;
        type string;
        // NCS drop max-elements statement
        description
          "COS based WRED (upto 8 values)";
      }
      leaf-list dei {
        // NCS patched for predictable order
        ordered-by user;
        type string;
        // NCS drop max-elements statement
        description
          "DEI based WRED";
      }
      leaf-list discard-class {
        // NCS patched for predictable order
        ordered-by user;
        type string;
        // NCS drop max-elements statement
        description
          "Discard Class based WRED";
      }
      leaf-list dscp {
        // NCS patched for predictable order
        ordered-by user;
        type ncs_template_dscp-value;
        // NCS drop max-elements statement
        description
          "DSCP based WRED";
      }
      leaf-list exp {
        // NCS patched for predictable order
        ordered-by user;
        type string;
        // NCS drop max-elements statement
        description
          "MPLS Experimental value based WRED";
      }
      leaf-list precedence {
        // NCS patched for predictable order
        ordered-by user;
        type string;
        // NCS drop max-elements statement
        description
          "Precedence based WRED";
      }
    }
    leaf service-fragment {
      // NCS drop if-feature statement
      type string;
      description
        "Define a service fragment. Name of Service fragment";
    }
    container service-policy {
      description
        "Configure a child service policy";
      leaf name {
        type ncs_template_service-policy-name-type;
        description
          "Name of the child service policy";
      }
      leaf type {
        type string;
        description
          "The type of policy-map";
      }
    }
    container set {
      description
        "Configure marking for this class";
      container atm-clp {
        // NCS drop if-feature statement
        presence "Set atm cell-loss-priority bit";
        description
          "Set atm cell-loss-priority bit";
      }
      leaf traffic-class {
        // NCS drop if-feature statement
        type string;
        description
          "Sets the Traffic Class identifiers on IPv4 or MPLS packets.
           The set traffic-class is supported only on an ingress policy.";
      }
      leaf forward-class {
        // NCS drop if-feature statement
        type string;
        description
          "Set forward class";
      }
      uses ncs_template_action-common;
    }
    container shape {
      description
        "Configure shaping for this class";
      container average {
        description
          "Average rate shaping";
        container rate {
          // NCS drop must statement
          presence "indicates rate is configured";
          description
            "Shape rate";
          leaf value {
            type string;
          }
          leaf unit {
            type string;
            description
              "Shape rate unit";
          }
        }
        container excess-burst {
          // NCS drop if-feature statement
          // NCS drop must statement
          presence "indicates excess-burst is configured";
          description
            "Excess burst size";
          leaf size {
            type string;
          }
          leaf unit {
            type string;
          }
        }
      }
    }
  }

  grouping ncs_template_redirect-actions {
    uses ncs_template_policy-action-compress;
    uses ncs_template_policy-action-encap-sequence;
    container priority {
      presence "Test command";
      description
        "Test command";
    }
  }

  grouping ncs_rpc_notif_class-map-common {
    leaf class-map-name {
      type string {
        pattern '[a-zA-Z0-9][a-zA-Z0-9\._@$%+#:=<>\-]{0,62}' {
          description
            "Any string except 'type'";
        }
      }
      description
        "Name of the class-map";
    }
    container match-all {
      presence "Match all match criteria";
      description
        "Match all match criteria";
    }
    container match-any {
      presence "Match any match criteria (default)";
      description
        "Match any match criteria (default)";
    }
    leaf description {
      type string;
      description
        "Set description for this class-map";
    }
  }

  grouping ncs_rpc_notif_match-access-group {
    container access-group {
      description
        "Match access group";
      leaf-list ipv4 {
        tailf:display-when "not(../../ncs:module) or boolean(/ncs:devices/ncs:device[ncs:name=current()/../../ncs:name]/capability/feature='match-ipv4-acl')";
        type ncs_rpc_notif_acl-list-name-type;
        description
          "IPv4 access list";
      }
      leaf-list ipv6 {
        tailf:display-when "not(../../ncs:module) or boolean(/ncs:devices/ncs:device[ncs:name=current()/../../ncs:name]/capability/feature='match-ipv6-acl')";
        type ncs_rpc_notif_acl-list-name-type;
        description
          "IPv6 access list";
      }
      leaf-list ethernet-services {
        tailf:display-when "not(../../ncs:module) or boolean(/ncs:devices/ncs:device[ncs:name=current()/../../ncs:name]/capability/feature='match-ethernet-services-acl')";
        type ncs_rpc_notif_acl-list-name-type;
        description
          "Ethernet-Services";
      }
    }
  }

  grouping ncs_rpc_notif_match-atm {
    container atm {
      tailf:display-when "not(../ncs:module) or boolean(/ncs:devices/ncs:device[ncs:name=current()/../ncs:name]/capability/feature='match-atm')";
      description
        "Match based on ATM specific criteria";
      leaf-list clp {
        type uint8 {
          range "0..1";
        }
        max-elements 2;
        ordered-by user;
        description
          "Match ATM CLP bit";
      }
      container oam {
        presence "Match ATM OAM";
        description
          "Match ATM OAM";
      }
    }
  }

  grouping ncs_rpc_notif_match-cac {
    container cac {
      tailf:display-when "not(../ncs:module) or boolean(/ncs:devices/ncs:device[ncs:name=current()/../ncs:name]/capability/feature='match-cac')";
      description
        "Match based on CAC fields";
      container admitted {
        presence "Match packets admitted by CAC action";
        description
          "Match packets admitted by CAC action";
      }
      container unadmitted {
        presence "Match packets unadmitted by CAC action";
        description
          "Match packets unadmitted by CAC action";
      }
    }
  }

  grouping ncs_rpc_notif_match-cos {
    container cos {
      tailf:display-when "not(../ncs:module) or boolean(/ncs:devices/ncs:device[ncs:name=current()/../ncs:name]/capability/feature='match-cos')";
      description
        "Match based on IEEE 802.1Q/ISL Class Of Service value";
      leaf-list value {
        type uint8 {
          range "0..7";
        }
        max-elements 8;
        description
          "COS value";
      }
    }
    container cos-inner {
      tailf:display-when "not(../ncs:module) or boolean(/ncs:devices/ncs:device[ncs:name=current()/../ncs:name]/capability/feature='match-cos-inner')";
      description
        "Match inner cos values";
      leaf-list value {
        type uint8 {
          range "0..7";
        }
        max-elements 8;
        description
          "inner cos value (Upto 8 values)";
      }
    }
  }

  grouping ncs_rpc_notif_match-dei {
    leaf dei {
      tailf:display-when "not(../ncs:module) or boolean(/ncs:devices/ncs:device[ncs:name=current()/../ncs:name]/capability/feature='match-dei')";
      type uint8 {
        range "0..1" {
          description
            "DEI value";
        }
      }
      must 'not(../dei-inner)' {
        tailf:xpath-root 3;
      }
      description
        "Match based on DEI bit (0/1)";
    }
    leaf dei-inner {
      tailf:display-when "not(../ncs:module) or boolean(/ncs:devices/ncs:device[ncs:name=current()/../ncs:name]/capability/feature='match-dei-inner')";
      type uint8 {
        range "0..1" {
          description
            "DEI value";
        }
      }
      must 'not(../dei)' {
        tailf:xpath-root 3;
      }
      description
        "Match inner based on DEI bit (0/1)";
    }
  }

  grouping ncs_rpc_notif_match-destination-address {
    container destination-address {
      description
        "Match based on destination address";
      container ipv4 {
        tailf:display-when "not(../../ncs:module) or boolean(/ncs:devices/ncs:device[ncs:name=current()/../../ncs:name]/capability/feature='match-dst-addr-ipv4')";
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        tailf:display-when "not(../../ncs:module) or boolean(/ncs:devices/ncs:device[ncs:name=current()/../../ncs:name]/capability/feature='match-dst-addr-ipv6')";
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='match-dst-mac')";
        type yang:mac-address;
        description
          "MAC Address";
      }
    }
  }

  grouping ncs_rpc_notif_matchnot-destination-address {
    container destination-address {
      description
        "Match based on destination address";
      container ipv4 {
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='matchnot-mac-address')";
        type yang:mac-address;
        description
          "MAC Address";
      }
    }
  }

  grouping ncs_rpc_notif_match-destination-port {
    container destination-port {
      tailf:display-when "not(../ncs:module) or boolean(/ncs:devices/ncs:device[ncs:name=current()/../ncs:name]/capability/feature='match-destination-port')";
      description
        "Match based on destination port";
      leaf-list port-number {
        type ncs_rpc_notif_port-number-type;
        max-elements 5;
        description
          "destination port";
      }
    }
  }

  grouping ncs_rpc_notif_match-discard-class {
    container discard-class {
      tailf:display-when "not(../ncs:module) or boolean(/ncs:devices/ncs:device[ncs:name=current()/../ncs:name]/capability/feature='match-discard-class')";
      description
        "Match based on discard class";
      leaf-list id {
        type uint8 {
          range "0..7";
        }
        max-elements 8;
        description
          "Discard CLass Id";
      }
    }
  }

  grouping ncs_rpc_notif_match-dscp {
    container dscp {
      tailf:display-when "not(../ncs:module) or boolean(/ncs:devices/ncs:device[ncs:name=current()/../ncs:name]/capability/feature='match-dscp')";
      description
        "Match based on IP DSCP value";
      leaf-list value {
        type ncs_rpc_notif_dscp-value;
        description
          "DSCP value";
      }
    }
    container dscp-ipv4 {
      tailf:display-when "not(../ncs:module) or boolean(/ncs:devices/ncs:device[ncs:name=current()/../ncs:name]/capability/feature='match-ipv4-dscp')";
      description
        "Match based on IPv4 DSCP value";
      leaf-list value {
        type ncs_rpc_notif_dscp-value;
        description
          "DSCP value";
      }
    }
    container dscp-ipv6 {
      tailf:display-when "not(../ncs:module) or boolean(/ncs:devices/ncs:device[ncs:name=current()/../ncs:name]/capability/feature='match-ipv6-dscp')";
      description
        "Match based on IPv6 DSCP value";
      leaf-list value {
        type ncs_rpc_notif_dscp-value;
        description
          "DSCP value";
      }
    }
  }

  grouping ncs_rpc_notif_match-ethertype {
    container ethertype {
      tailf:display-when "not(../ncs:module) or boolean(/ncs:devices/ncs:device[ncs:name=current()/../ncs:name]/capability/feature='match-ethertype')";
      description
        "Match based on ethertype";
      leaf-list value {
        type union {
          type uint16 {
            range "1536..65535";
          }
          type enumeration {
            enum "arp" {
              value 0;
              description
                "Any ARP Ethertype";
            }
            enum "ipv4" {
              value 1;
              description
                "Any IPv4 Ethertype";
            }
            enum "ipv6" {
              value 2;
              description
                "Any IPv6 Ethertype";
            }
          }
        }
        max-elements 8;
        description
          "Ethertype Value";
      }
    }
  }

  grouping ncs_rpc_notif_match-flow-key {
    container flow-key {
      tailf:display-when "not(../ncs:module) or boolean(/ncs:devices/ncs:device[ncs:name=current()/../ncs:name]/capability/feature='match-flow-key')";
      description
        "Match based on flow keys";
      container five-tuple {
        must 'not(../dst-ip or ../src-ip)' {
          tailf:xpath-root 3;
        }
        presence "Five tuples to identify a flow";
        description
          "Five tuples to identify a flow";
      }
      container dst-ip {
        must 'not(../five-tuple)' {
          tailf:xpath-root 3;
        }
        presence "Destination IP address";
        description
          "Destination IP address";
      }
      container src-ip {
        must 'not(../five-tuple)' {
          tailf:xpath-root 3;
        }
        presence "Source IP address";
        description
          "Source IP address";
      }
      container flow-cache {
        description
          "Configure the flow-cache parameters";
        leaf idle-timeout {
          type union {
            type uint16 {
              range "1..65534" {
                description
                  "The idle timeout period (in seconds)";
              }
            }
            type enumeration {
              enum "None" {
                value 0;
                description
                  "The flow does not expire";
              }
            }
          }
          description
            "Maximum time of inactivity for a flow.";
        }
      }
    }
  }

  grouping ncs_rpc_notif_match-flow-tag {
    container flow-tag {
      tailf:display-when "not(../ncs:module) or boolean(/ncs:devices/ncs:device[ncs:name=current()/../ncs:name]/capability/feature='matchnot-flow-tag')";
      description
        "Match based on flow-tag";
      leaf-list tag-number {
        type union {
          type uint8 {
            range "1..63";
          }
          type string {
            pattern '([1-9][0-9]{0,1})-([1-9][0-9]{0,1})' {
              description
                "<1-63>-<1-63>";
            }
          }
        }
        max-elements 5;
        description
          "flow-tag number";
      }
    }
  }

  grouping ncs_rpc_notif_match-fr-de {
    leaf fr-de {
      tailf:display-when "not(../ncs:module) or boolean(/ncs:devices/ncs:device[ncs:name=current()/../ncs:name]/capability/feature='match-fr-de')";
      type union {
        type string {
          pattern '1';
        }
        type uint8 {
          range "0..1";
        }
      }
      description
        "Match based on FrameRelay DE bit";
    }
  }

  grouping ncs_rpc_notif_match-fragment-type {
    container fragment-type {
      tailf:display-when "not(../ncs:module) or boolean(/ncs:devices/ncs:device[ncs:name=current()/../ncs:name]/capability/feature='match-fragment-type')";
      description
        "Fragment type for a packet";
      container dont-fragment {
        presence "Match don't-Fragment bit";
        description
          "Match don't-Fragment bit";
      }
      container first-fragment {
        presence "Match first fragment bit";
        description
          "Match first fragment bit";
      }
      container is-fragment {
        presence "Match is-fragment bit";
        description
          "Match is-fragment bit";
      }
      container last-fragment {
        presence "Match last fragment bit";
        description
          "Match last fragment bit";
      }
    }
  }

  grouping ncs_rpc_notif_match-frame-relay {
    container frame-relay {
      tailf:display-when "not(../ncs:module) or boolean(/ncs:devices/ncs:device[ncs:name=current()/../ncs:name]/capability/feature='match-fr')";
      description
        "Match based on frame-relay specific criteria";
      leaf-list dlci {
        type union {
          type uint16 {
            range "16..1007";
          }
          type string {
            pattern '([1-9][0-9]{1,3})-([1-9][0-9]{1,3})' {
              description
                "<16-1007>-<16-1007>";
            }
          }
        }
        max-elements 8;
        description
          "Match frame-relay dlci value(s)";
      }
    }
  }

  grouping ncs_rpc_notif_match-ipv4 {
    container ipv4 {
      description
        "Match based on ipv4 icmp";
      container icmp-code {
        description
          "Match based on ipv4 icmp code";
        leaf-list value {
          type union {
            type uint8 {
              range "0..255";
            }
            type string {
              pattern '([0-9]{1,3})-([0-9]{1,3})' {
                description
                  "<0-255>-<0-255>";
              }
            }
          }
          max-elements 5;
          description
            "IPv4 ICMP code";
        }
      }
      container icmp-type {
        description
          "Match based on ipv4 icmp type";
        leaf-list value {
          type union {
            type uint8 {
              range "0..255";
            }
            type string {
              pattern '([0-9]{1,3})-([0-9]{1,3})' {
                description
                  "<0-255>-<0-255>";
              }
            }
          }
          max-elements 5;
          description
            "IPv4 ICMP type";
        }
      }
    }
  }

  grouping ncs_rpc_notif_match-ipv6 {
    container ipv6 {
      description
        "Match based on IPv6";
      container icmp-code {
        description
          "IPv6 ICMP code";
        leaf-list value {
          type union {
            type uint8 {
              range "0..255";
            }
            type string {
              pattern '([0-9]{1,3})-([0-9]{1,3})' {
                description
                  "<0-255>-<0-255>";
              }
            }
          }
          max-elements 5;
          description
            "ICMP code";
        }
      }
      container icmp-type {
        description
          "IPv6 ICMP type";
        leaf-list value {
          type union {
            type uint8 {
              range "0..255";
            }
            type string {
              pattern '([0-9]{1,3})-([0-9]{1,3})' {
                description
                  "<0-255>-<0-255>";
              }
            }
          }
          max-elements 5;
          description
            "ICMP type";
        }
      }
    }
  }

  grouping ncs_rpc_notif_match-mpls {
    container mpls {
      description
        "Match based on MPLS specific values";
      container disposition {
        description
          "Match MPLS Label Disposition";
        container access-group {
          description
            "access group";
          leaf ipv4 {
            tailf:display-when "not(../../../../ncs:module) or boolean(/ncs:devices/ncs:device[ncs:name=current()/../../../../ncs:name]/capability/feature='match-mpls-disp-ipv4-acl')";
            type string {
              length "1..64";
            }
            description
              "IPv4 access list";
          }
          leaf ipv6 {
            tailf:display-when "not(../../../../ncs:module) or boolean(/ncs:devices/ncs:device[ncs:name=current()/../../../../ncs:name]/capability/feature='match-mpls-disp-ipv6-acl')";
            type string {
              length "1..64";
            }
            description
              "IPv6 access list";
          }
        }
        leaf class-map {
          tailf:display-when "not(../../../ncs:module) or boolean(/ncs:devices/ncs:device[ncs:name=current()/../../../ncs:name]/capability/feature='match-mpls-disp-cmap')";
          type string {
            length "1..32";
          }
          description
            "class-map name";
        }
      }
      container experimental {
        description
          "Match MPLS experimental values";
        container imposition {
          tailf:display-when "not(../../../ncs:module) or boolean(/ncs:devices/ncs:device[ncs:name=current()/../../../ncs:name]/capability/feature='match-mpls-exp-imposition')";
          description
            "Match imposition label";
          leaf-list label {
            type uint8 {
              range "0..7";
            }
            max-elements 8;
            description
              "MPLS experimental label";
          }
        }
        container topmost {
          tailf:display-when "not(../../../ncs:module) or boolean(/ncs:devices/ncs:device[ncs:name=current()/../../../ncs:name]/capability/feature='match-mpls-exp-top')";
          description
            "Match topmost label";
          leaf-list label {
            type uint8 {
              range "0..7";
            }
            max-elements 8;
            description
              "MPLS experimental label";
          }
        }
      }
    }
  }

  grouping ncs_rpc_notif_matchnot-mpls {
    container mpls {
      description
        "Match based on MPLS specific values";
      container disposition {
        description
          "Match MPLS Label Disposition";
        container access-group {
          description
            "access group";
          leaf ipv4 {
            tailf:display-when "not(../../../../ncs:module) or boolean(/ncs:devices/ncs:device[ncs:name=current()/../../../../ncs:name]/capability/feature='matchnot-mpls-disp-ipv4-acl')";
            type string {
              length "1..64";
            }
            description
              "IPv4 access list";
          }
          leaf ipv6 {
            tailf:display-when "not(../../../../ncs:module) or boolean(/ncs:devices/ncs:device[ncs:name=current()/../../../../ncs:name]/capability/feature='matchnot-mpls-disp-ipv6-acl')";
            type string {
              length "1..64";
            }
            description
              "IPv6 access list";
          }
        }
      }
      container experimental {
        description
          "Match MPLS experimental values";
        container topmost {
          description
            "Match topmost label";
          leaf-list label {
            type uint8 {
              range "0..7";
            }
            max-elements 8;
            description
              "MPLS experimental label";
          }
        }
      }
    }
  }

  grouping ncs_rpc_notif_match-packet {
    container packet {
      description
        "Match based on packet length";
      container length {
        description
          "Packet length";
        leaf-list value {
          type ncs_rpc_notif_packet-length-type;
          max-elements 5;
          description
            "IP Packet Length";
        }
      }
      container length-ipv4 {
        tailf:display-when "not(../../ncs:module) or boolean(/ncs:devices/ncs:device[ncs:name=current()/../../ncs:name]/capability/feature='match-ipv4-packet-length')";
        description
          "IPV4 Packet Length";
        leaf-list value {
          type ncs_rpc_notif_packet-length-type;
          max-elements 5;
        }
      }
      container length-ipv6 {
        tailf:display-when "not(../../ncs:module) or boolean(/ncs:devices/ncs:device[ncs:name=current()/../../ncs:name]/capability/feature='match-ipv6-packet-length')";
        description
          "IPV6 Packet Length";
        leaf-list value {
          type ncs_rpc_notif_packet-length-type;
          max-elements 5;
        }
      }
    }
  }

  grouping ncs_rpc_notif_matchnot-packet {
    container packet {
      description
        "Match based on packet length";
      container length {
        description
          "Packet length";
        leaf-list value {
          type ncs_rpc_notif_packet-length-type;
          max-elements 5;
          description
            "IP Packet Length";
        }
      }
      container length-ipv4 {
        tailf:display-when "not(../../ncs:module) or boolean(/ncs:devices/ncs:device[ncs:name=current()/../../ncs:name]/capability/feature='matchnot-ipv4-packet-length')";
        description
          "IPV4 Packet Length";
        leaf-list value {
          type ncs_rpc_notif_packet-length-type;
          max-elements 5;
        }
      }
      container length-ipv6 {
        tailf:display-when "not(../../ncs:module) or boolean(/ncs:devices/ncs:device[ncs:name=current()/../../ncs:name]/capability/feature='matchnot-ipv6-packet-length')";
        description
          "IPV6 Packet Length";
        leaf-list value {
          type ncs_rpc_notif_packet-length-type;
          max-elements 5;
        }
      }
    }
  }

  grouping ncs_rpc_notif_match-precedence {
    container precedence {
      tailf:display-when "not(../ncs:module) or boolean(/ncs:devices/ncs:device[ncs:name=current()/../ncs:name]/capability/feature='match-prec')";
      description
        "Match based on IP precedence values";
      leaf-list value {
        type ncs_rpc_notif_precedence-type;
        max-elements 8;
        description
          "IP precedence";
      }
    }
    container precedence-ipv4 {
      tailf:display-when "not(../ncs:module) or boolean(/ncs:devices/ncs:device[ncs:name=current()/../ncs:name]/capability/feature='match-ipv4-prec')";
      description
        "Match based on IPV4 precedence";
      leaf-list value {
        type ncs_rpc_notif_precedence-type;
        max-elements 8;
        description
          "IPV4 precedence";
      }
    }
    container precedence-ipv6 {
      tailf:display-when "not(../ncs:module) or boolean(/ncs:devices/ncs:device[ncs:name=current()/../ncs:name]/capability/feature='match-ipv6-prec')";
      description
        "Match based on IPV6 precedence";
      leaf-list value {
        type ncs_rpc_notif_precedence-type;
        max-elements 8;
        description
          "IPV6 precedence";
      }
    }
  }

  grouping ncs_rpc_notif_match-protocol {
    container protocol {
      description
        "Match based on L3 protocol (Upto 8 values or ranges)";
      leaf-list number {
        type ncs_rpc_notif_protocol-type;
        max-elements 8;
        description
          "Protocol Number";
      }
    }
  }

  grouping ncs_rpc_notif_match-qos-group {
    container qos-group {
      description
        "Match based on QoS Group";
      leaf-list id {
        type union {
          type uint16 {
            range "0..512";
          }
          type string {
            pattern '([0-9]{1,3})-([0-9]{1,3})' {
              description
                "Lower and upper limit of QoS Group range (<0-512>-<0-512>)";
            }
          }
        }
        max-elements 8;
        description
          "QoS Group Id";
      }
    }
  }

  grouping ncs_rpc_notif_match-traffic-class {
    container traffic-class {
      description
        "Match based on Traffic Class";
      leaf-list id {
        type union {
          type uint8 {
            range "0..63";
          }
          type string {
            pattern '([0-9]{1,2})-([0-9]{1,2})' {
              description
                "Lower and upper limit of Traffic Class range (<0-63>-<0-63>)";
            }
          }
        }
        max-elements 8;
        description
          "Traffic Class Id";
      }
    }
  }

  grouping ncs_rpc_notif_match-source-address {
    container source-address {
      description
        "Match based on source address";
      container ipv4 {
        tailf:display-when "not(../../ncs:module) or boolean(/ncs:devices/ncs:device[ncs:name=current()/../../ncs:name]/capability/feature='match-src-addr-ipv4')";
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        tailf:display-when "not(../../ncs:module) or boolean(/ncs:devices/ncs:device[ncs:name=current()/../../ncs:name]/capability/feature='match-src-addr-ipv6')";
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='match-src-mac')";
        type yang:mac-address;
        description
          "MAC Address";
      }
    }
  }

  grouping ncs_rpc_notif_matchnot-source-address {
    container source-address {
      description
        "Match based on source address";
      container ipv4 {
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='matchnot-mac-address')";
        type yang:mac-address;
        description
          "MAC Address";
      }
    }
  }

  grouping ncs_rpc_notif_match-source-port {
    container source-port {
      tailf:display-when "not(../ncs:module) or boolean(/ncs:devices/ncs:device[ncs:name=current()/../ncs:name]/capability/feature='match-source-port')";
      description
        "Match based on source port";
      leaf-list number {
        type ncs_rpc_notif_port-number-type;
        max-elements 5;
        description
          "source port";
      }
    }
  }

  grouping ncs_rpc_notif_match-tcp-flag {
    container tcp-flag {
      description
        "Match based on TCP flags";
      leaf value {
        type uint16 {
          range "0..4095";
        }
        description
          "TCP flags value";
      }
      container any {
        presence "Match based on any bit set";
        description
          "Match based on any bit set";
      }
    }
  }

  grouping ncs_rpc_notif_match-vlan {
    container vlan {
      tailf:display-when "not(../ncs:module) or boolean(/ncs:devices/ncs:device[ncs:name=current()/../ncs:name]/capability/feature='match-vlan')";
      description
        "Match based on Vlan Ids";
      leaf-list vlan-id {
        type ncs_rpc_notif_vlan-id-type;
        max-elements 8;
        description
          "Vlan Id";
      }
    }
    container vlan-inner {
      tailf:display-when "not(../ncs:module) or boolean(/ncs:devices/ncs:device[ncs:name=current()/../ncs:name]/capability/feature='match-vlan-inner')";
      description
        "Match based on inner Vlan Ids";
      leaf-list vlan-id {
        type ncs_rpc_notif_vlan-id-type;
        max-elements 8;
        description
          "inner Vlan Id";
      }
    }
  }

  grouping ncs_rpc_notif_matchnot-vlan {
    container vlan {
      tailf:display-when "not(../ncs:module) or boolean(/ncs:devices/ncs:device[ncs:name=current()/../ncs:name]/capability/feature='matchnot-vlan')";
      description
        "Match based on Vlan Ids";
      leaf-list vlan-id {
        type ncs_rpc_notif_vlan-id-type;
        max-elements 8;
        description
          "Vlan Id";
      }
    }
    container vlan-inner {
      tailf:display-when "not(../ncs:module) or boolean(/ncs:devices/ncs:device[ncs:name=current()/../ncs:name]/capability/feature='matchnot-vlan-inner')";
      description
        "Match based on inner Vlan Ids";
      leaf-list vlan-id {
        type ncs_rpc_notif_vlan-id-type;
        max-elements 8;
        description
          "inner Vlan Id";
      }
    }
  }

  grouping ncs_rpc_notif_match-vpls {
    container vpls {
      description
        "Match based on VPLS fields";
      container known {
        tailf:display-when "not(../../ncs:module) or boolean(/ncs:devices/ncs:device[ncs:name=current()/../../ncs:name]/capability/feature='match-vpls-known')";
        presence "VPLS Known";
        description
          "VPLS Known";
      }
      container unknown {
        tailf:display-when "not(../../ncs:module) or boolean(/ncs:devices/ncs:device[ncs:name=current()/../../ncs:name]/capability/feature='match-vpls-unknown')";
        presence "VPLS Unknown";
        description
          "VPLS Unknown";
      }
      container broadcast {
        presence "VPLS Broadcast";
        description
          "VPLS Broadcast";
      }
      container control {
        tailf:display-when "not(../../ncs:module) or boolean(/ncs:devices/ncs:device[ncs:name=current()/../../ncs:name]/capability/feature='match-vpls-control')";
        presence "VPLS Control";
        description
          "VPLS Control";
      }
      container multicast {
        presence "VPLS Multicast";
        description
          "VPLS Multicast";
      }
    }
  }

  grouping ncs_rpc_notif_matchnot-vpls {
    container vpls {
      description
        "Match based on VPLS fields";
      container known {
        tailf:display-when "not(../../ncs:module) or boolean(/ncs:devices/ncs:device[ncs:name=current()/../../ncs:name]/capability/feature='matchnot-vpls-known')";
        presence "VPLS Known";
        description
          "VPLS Known";
      }
      container unknown {
        tailf:display-when "not(../../ncs:module) or boolean(/ncs:devices/ncs:device[ncs:name=current()/../../ncs:name]/capability/feature='matchnot-vpls-unknown')";
        presence "VPLS Unknown";
        description
          "VPLS Unknown";
      }
      container broadcast {
        tailf:display-when "not(../../ncs:module) or boolean(/ncs:devices/ncs:device[ncs:name=current()/../../ncs:name]/capability/feature='matchnot-vpls-bcast')";
        presence "VPLS Broadcast";
        description
          "VPLS Broadcast";
      }
      container control {
        tailf:display-when "not(../../ncs:module) or boolean(/ncs:devices/ncs:device[ncs:name=current()/../../ncs:name]/capability/feature='matchnot-vpls-control')";
        presence "VPLS Control";
        description
          "VPLS Control";
      }
      container multicast {
        tailf:display-when "not(../../ncs:module) or boolean(/ncs:devices/ncs:device[ncs:name=current()/../../ncs:name]/capability/feature='matchnot-vpls-mcast')";
        presence "VPLS Multicast";
        description
          "VPLS Multicast";
      }
    }
  }

  grouping ncs_rpc_notif_match-authen-status {
    leaf authen-status {
      tailf:display-when "not(../ncs:module) or boolean(/ncs:devices/ncs:device[ncs:name=current()/../ncs:name]/capability/feature='match-authen-status')";
      type enumeration {
        enum "authenticated" {
          value 0;
          description
            "Authenticated";
        }
        enum "unauthenticated" {
          value 1;
          description
            "Unauthenticated";
        }
      }
      description
        "Authentication Status";
    }
  }

  grouping ncs_rpc_notif_match-circuit-id {
    container circuit-id {
      description
        "Match based on circuit ID";
      leaf-list value {
        type string {
          length "1..32" {
            description
              "Any string except 'regexp'";
          }
        }
        description
          "circuit ID";
      }
    }
    container circuit-id-regexp {
      description
        "Match based on circuit ID regular expression";
      leaf-list value {
        type string {
          length "1..32";
        }
        description
          "Circuit ID regular expression";
      }
    }
  }

  grouping ncs_rpc_notif_match-dhcp-client-id {
    container dhcp-client-id {
      description
        "Match based on dhcp client id";
      list client-id {
        key "id flag";
        description
          "client id";
        leaf id {
          type string {
            length "1..32";
          }
          description
            "client id";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
    container dhcp-client-id-regexp {
      description
        "Match based on dhcp client id regular expression";
      list client-id {
        key "id flag";
        description
          "client id with regular expression";
        leaf id {
          type string {
            length "1..32";
          }
          description
            "client id with regular expression";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
  }

  grouping ncs_rpc_notif_match-domain {
    container domain {
      description
        "Match base on domain name";
      list domain-name {
        key "name format";
        description
          "Domain name";
        leaf name {
          type string {
            length "1..32";
          }
          description
            "Domain name";
        }
        leaf format {
          type string {
            length "1..32";
          }
          description
            "Domain format name";
        }
      }
    }
    container domain-regexp {
      description
        "Match base on domain name with regular expression";
      list domain-name {
        key "regexp format";
        description
          "Domain name";
        leaf regexp {
          type string {
            length "1..32";
          }
          description
            "Domain name with regular expression";
        }
        leaf format {
          type string {
            length "1..32";
          }
          description
            "Domain format name";
        }
      }
    }
  }

  grouping ncs_rpc_notif_match-control-protocol {
    container protocol {
      description
        "Match based on protocol";
      leaf-list name {
        tailf:display-when "not(../../ncs:module) or boolean(/ncs:devices/ncs:device[ncs:name=current()/../../ncs:name]/capability/feature='match-proto')";
        type enumeration {
          enum "dhcpv4" {
            value 0;
            description
              "dhcpv4";
          }
          enum "dhcpv6" {
            value 1;
            description
              "dhcpv6";
          }
          enum "ppp" {
            value 2;
            description
              "ppp";
          }
        }
        max-elements 3;
        description
          "protocol name";
      }
    }
  }

  grouping ncs_rpc_notif_match-remote-id {
    container remote-id {
      description
        "Match based on remote ID";
      leaf-list id {
        type string {
          length "1..32";
        }
        description
          "remote-id";
      }
    }
    container remote-id-regexp {
      description
        "Remote ID with regular expression";
      leaf-list id {
        type string {
          length "1..32";
        }
        description
          "remote-id with regular expression";
      }
    }
  }

  grouping ncs_rpc_notif_match-service-name {
    container service-name {
      description
        "Match based on service name";
      leaf-list name {
        type string {
          length "1..32";
        }
        description
          "Service name";
      }
    }
    container service-name-regexp {
      description
        "Match based on service name with regular expression";
      leaf-list name {
        type string {
          length "1..32";
        }
        description
          "Service name with regular expression";
      }
    }
  }

  grouping ncs_rpc_notif_match-timer {
    container timer {
      tailf:display-when "not(../ncs:module) or boolean(/ncs:devices/ncs:device[ncs:name=current()/../ncs:name]/capability/feature='match-timer')";
      description
        "Match based on timer";
      leaf-list name {
        type string {
          length "1..32";
        }
        description
          "Timer name";
      }
    }
    container timer-regexp {
      description
        "Timer with regular expression";
      leaf-list name {
        type string {
          length "1..32";
        }
        description
          "Timer name with regular expression";
      }
    }
  }

  grouping ncs_rpc_notif_match-username {
    container username {
      tailf:display-when "not(../ncs:module) or boolean(/ncs:devices/ncs:device[ncs:name=current()/../ncs:name]/capability/feature='match-username')";
      description
        "Match based on user name";
      leaf-list name {
        type string {
          length "1..32";
        }
        description
          "User name";
      }
    }
    container username-regexp {
      tailf:display-when "not(../ncs:module) or boolean(/ncs:devices/ncs:device[ncs:name=current()/../ncs:name]/capability/feature='match-username')";
      description
        "Match based on user name with regular expression";
      leaf-list name {
        type string {
          length "1..32";
        }
        description
          "User name with regular expression";
      }
    }
  }

  grouping ncs_rpc_notif_policy-map-common {
    leaf policy-map-name {
      type string;
      description
        "Name of the policymap";
    }
    leaf description {
      type string;
      description
        "Set description for this policy-map";
    }
  }

  grouping ncs_rpc_notif_policy-action-compress {
    container compress {
      tailf:display-when "not(../ncs:module) or boolean(/ncs:devices/ncs:device[ncs:name=current()/../ncs:name]/capability/feature='action-compress-header-ip')";
      description
        "Configure compress action";
      container header {
        description
          "Configure header compression";
        container ip {
          presence "Configure IP header compression";
          description
            "Configure IP header compression";
        }
      }
    }
  }

  grouping ncs_rpc_notif_policy-action-encap-sequence {
    leaf encap-sequence {
      tailf:display-when "not(../ncs:module) or boolean(/ncs:devices/ncs:device[ncs:name=current()/../ncs:name]/capability/feature='action-encap-sequence')";
      type union {
        type uint8 {
          range "1..15" {
            description
              "Encapsulation sequence number";
          }
        }
        type enumeration {
          enum "none" {
            value 0;
            description
              "Encapsulation sequence none";
          }
        }
      }
      description
        "Configure encapsulation sequence";
    }
  }

  grouping ncs_rpc_notif_aaa-method {
    container aaa {
      description
        "AAA specification";
      leaf list {
        type union {
          type string;
          type enumeration {
            enum "default" {
              value 0;
              description
                "default AAA method list";
            }
          }
        }
        description
          "Specify AAA method list that authentication should be made with";
      }
    }
  }

  grouping ncs_rpc_notif_subscriber-actions {
    container activate {
      description
        "Activate";
      container dynamic-template {
        description
          "actions related to dynamic templates";
        leaf template-name {
          type string;
          description
            "Dynamic template name";
        }
        uses ncs_rpc_notif_aaa-method;
      }
    }
    container deactivate {
      description
        "Deactivate";
      container dynamic-template {
        description
          "actions related to dynamic templates";
        leaf template-name {
          type string;
          description
            "Dynamic template name";
        }
        uses ncs_rpc_notif_aaa-method;
      }
    }
    container authenticate {
      tailf:display-when "not(../ncs:module) or boolean(/ncs:devices/ncs:device[ncs:name=current()/../ncs:name]/capability/feature='action-authenticate')";
      description
        "Authentication related configuration";
      uses ncs_rpc_notif_aaa-method;
    }
    container authorize {
      tailf:display-when "not(../ncs:module) or boolean(/ncs:devices/ncs:device[ncs:name=current()/../ncs:name]/capability/feature='action-authorize')";
      description
        "Authorize";
      uses ncs_rpc_notif_aaa-method;
      leaf format {
        type string;
        description
          "Specify an Authorize format name";
      }
      leaf identifier {
        type enumeration {
          enum "circuit-id" {
            value 0;
            description
              "Authorize circuit ID";
          }
          enum "dhcp-client-id" {
            value 1;
            description
              "Authorize dhcp client ID";
          }
          enum "remote-id" {
            value 2;
            description
              "Authorize remote ID";
          }
          enum "service-name" {
            value 3;
            description
              "Authorize Service Name";
          }
          enum "source-address-ipv4" {
            value 4;
            description
              "Authorize source IPv4 address";
          }
          enum "source-address-ipv6" {
            value 5;
            description
              "Authorize source IPv6 address";
          }
          enum "source-address-mac" {
            value 6;
            description
              "Authorize source MAC address";
          }
          enum "username" {
            value 7;
            description
              "Authorize username";
          }
        }
        description
          "Specify an Authorize identifier";
      }
      leaf password {
        type union {
          type ncs_rpc_notif_clear-text-password-type;
          type enumeration {
            enum "blank" {
              value 0;
              description
                "use blank password";
            }
            enum "use-from-line" {
              value 1;
              description
                "use from line";
            }
          }
        }
        description
          "Specify a password to be used for AAA request";
      }
    }
    container disconnect {
      tailf:display-when "not(../ncs:module) or boolean(/ncs:devices/ncs:device[ncs:name=current()/../ncs:name]/capability/feature='action-disconnect')";
      presence "Disconnect session";
      description
        "Disconnect session";
    }
    container monitor {
      tailf:display-when "not(../ncs:module) or boolean(/ncs:devices/ncs:device[ncs:name=current()/../ncs:name]/capability/feature='action-monitor')";
      presence "Monitor session";
      description
        "Monitor session";
    }
    container set-timer {
      tailf:display-when "not(../ncs:module) or boolean(/ncs:devices/ncs:device[ncs:name=current()/../ncs:name]/capability/feature='action-set-timer')";
      must 'name and value' {
        tailf:xpath-root 3;
      }
      presence "indicates set-timer is configured";
      description
        "Set a timer to execute a rule on its expiry";
      leaf name {
        type string;
        description
          "Name of the timer";
      }
      leaf value {
        type uint32 {
          range "1..4294967295" {
            description
              "Timer value in minutes";
          }
        }
        units "minutes";
      }
    }
    container stop-timer {
      tailf:display-when "not(../ncs:module) or boolean(/ncs:devices/ncs:device[ncs:name=current()/../ncs:name]/capability/feature='action-stop-timer')";
      description
        "Disable timer before it expires";
      leaf name {
        type string;
        description
          "Name of the timer";
      }
    }
  }

  grouping ncs_rpc_notif_pbr-actions {
    container drop {
      presence "Drop the packet";
      description
        "Drop the packet";
    }
    leaf http-redirect {
      tailf:display-when "not(../ncs:module) or boolean(/ncs:devices/ncs:device[ncs:name=current()/../ncs:name]/capability/feature='action-http-redirect')";
      type string;
      description
        "Configure HTTP redirect. Specify the URL HTTP requests should be redirected to";
    }
    container http-enrichment {
      tailf:display-when "not(../ncs:module) or boolean(/ncs:devices/ncs:device[ncs:name=current()/../ncs:name]/capability/feature='action-http-enrichment')";
      description
        "Configure HTTP enrichment";
      container subscriber-mac {
        presence "Subscriber MAC address";
        description
          "Subscriber MAC address";
      }
      container subscriber-ip {
        presence "Subscriber ipv4/ipv6 address";
        description
          "Subscriber ipv4/ipv6 address";
      }
      container hostname {
        presence "Hostname";
        description
          "Hostname";
      }
      container bng-interface {
        presence "BNG identifier interface";
        description
          "BNG identifier interface";
      }
    }
    container police {
      description
        "Police traffic";
      container rate {
        must 'value and unit' {
          tailf:xpath-root 3;
        }
        presence "indicates rate is configured";
        description
          "Committed Information Rate";
        leaf value {
          type uint32 {
            range "1..4294967295" {
              description
                "Committed Information Rate";
            }
          }
        }
        leaf unit {
          type ncs_rpc_notif_rate-unit-type;
        }
      }
    }
    container redirect-ipv4 {
      tailf:display-when "not(../ncs:module) or boolean(/ncs:devices/ncs:device[ncs:name=current()/../ncs:name]/capability/feature='action-redirect-nexthop')";
      description
        "Configure PBF redirect feature with IPv4 configurations";
      container default-route {
        presence "Forward to the default nexthop";
        description
          "Forward to the default nexthop";
      }
      container nexthop1 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
    }
    container redirect-ipv6 {
      tailf:display-when "not(../ncs:module) or boolean(/ncs:devices/ncs:device[ncs:name=current()/../ncs:name]/capability/feature='action-redirect-nexthop')";
      description
        "Configure PBF redirect feature with IPv6 configurations";
      container default-route {
        presence "Forward to the default nexthop";
        description
          "Forward to the default nexthop";
      }
      container nexthop1 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
    }
    container redirect-nexthop {
      tailf:display-when "not(../ncs:module) or boolean(/ncs:devices/ncs:device[ncs:name=current()/../ncs:name]/capability/feature='action-redirect-rt')";
      description
        "Configure PBF redirect feature with forwarding to specified nexthop";
      container route-target {
        must '(address and index) or as-number' {
          tailf:xpath-root 3;
        }
        presence "indicates route-target is configured";
        description
          "Enter specific route-target string";
        leaf address {
          type inet:ipv4-address-no-zone;
          description
            "IPv4 address.";
        }
        leaf index {
          type uint16 {
            range "0..65535" {
              description
                "IPv4 Address:index";
            }
          }
          description
            "IPv4 Address:index";
        }
        leaf as-number {
          type union {
            type string {
              pattern '([1-9][0-9]{0,4}):(0|[1-9][0-9]{0,4})' {
                description
                  "<1-65535>:<0-65535> 2-byte AS number";
              }
            }
            type string {
              pattern '(65536:|[1-9][0-9]{0,10}:)(0|[1-9][0-9]{0,4})' {
                description
                  "<65536-4294967295>:<0-65535> 4-byte AS number in asplain format";
              }
            }
          }
          description
            "AS number";
        }
      }
    }
    container service-function-path {
      tailf:display-when "not(../ncs:module) or boolean(/ncs:devices/ncs:device[ncs:name=current()/../ncs:name]/capability/feature='action-service-function')";
      description
        "Configure NSH service function action";
      leaf path-id {
        type uint32 {
          range "1..16777215";
        }
        must '../index' {
          tailf:xpath-root 3;
        }
        description
          "Service function path id";
      }
      leaf index {
        type uint8 {
          range "1..255" {
            description
              "Service function path index";
          }
        }
        must '../path-id' {
          tailf:xpath-root 3;
        }
        description
          "Specify service path index";
      }
      leaf metadata {
        type string;
        must '../index and ../path-id' {
          tailf:xpath-root 3;
        }
        description
          "service-function metadata";
      }
    }
    container set {
      description
        "Configure marking for this class";
      container destination-address {
        tailf:display-when "not(../../ncs:module) or boolean(/ncs:devices/ncs:device[ncs:name=current()/../../ncs:name]/capability/feature='action-set-dst-address')";
        description
          "Set Destination address";
        leaf ipv4 {
          type inet:ipv4-address;
          description
            "IPv4 address";
        }
      }
      leaf df {
        tailf:display-when "not(../../ncs:module) or boolean(/ncs:devices/ncs:device[ncs:name=current()/../../ncs:name]/capability/feature='action-set-df')";
        type uint8 {
          range "0..1" {
            description
              "DF bit";
          }
        }
        description
          "Set DF bit";
      }
      leaf dscp {
        type ncs_rpc_notif_dscp-value;
        description
          "Set DSCP";
      }
      leaf forward-class {
        tailf:display-when "not(../../ncs:module) or boolean(/ncs:devices/ncs:device[ncs:name=current()/../../ncs:name]/capability/feature='action-set-fwd-class')";
        type uint8 {
          range "1..7" {
            description
              "Forward class value";
          }
        }
        description
          "Set forward class";
      }
      container source-address {
        tailf:display-when "not(../../ncs:module) or boolean(/ncs:devices/ncs:device[ncs:name=current()/../../ncs:name]/capability/feature='action-set-src-address')";
        description
          "Set Source address";
        leaf ipv4 {
          type inet:ipv4-address;
          description
            "IPv4 address";
        }
      }
    }
    container transmit {
      tailf:display-when "not(../ncs:module) or boolean(/ncs:devices/ncs:device[ncs:name=current()/../ncs:name]/capability/feature='action-transmit')";
      presence "Forward packet to the original destination";
      description
        "Forward packet to the original destination";
    }
    container decapsulate {
      tailf:display-when "not(../ncs:module) or boolean(/ncs:devices/ncs:device[ncs:name=current()/../ncs:name]/capability/feature='action-decap-gre')";
      description
        "Decapsulate GRE packet";
      container gre {
        presence "Decapsulate GRE packet";
        description
          "Decapsulate GRE packet";
      }
    }
  }

  grouping ncs_rpc_notif_performance-traffic-actions {
    uses ncs_rpc_notif_policy-action-compress;
    uses ncs_rpc_notif_policy-action-encap-sequence;
    list react {
      tailf:display-when "not(ncs:module) or boolean(/ncs:devices/ncs:device[ncs:name=current()/ncs:name]/capability/feature='action-react')";
      key "operation-id";
      description
        "Generate alert on the specified event";
      leaf operation-id {
        type uint32 {
          range "1..4294967294";
        }
        description
          "Specify an operation id (num)";
      }
      container delay-factor {
        presence "React criterion delay factor of policy-map action.";
        description
          "React criterion delay factor of policy-map action.";
      }
      container media-stop {
        presence "React criterion media stop of policy-map action.";
        description
          "React criterion media stop of policy-map action.";
      }
      container mrv {
        presence "React criterion mrv of policy-map action.";
        description
          "React criterion mrv of policy-map action.";
      }
      container flow-count {
        presence "React criterion flow count of policy-map action.";
        description
          "React criterion flow count of policy-map action.";
      }
      container packet-rate {
        presence "React criterion packet rate of the policy-map action.";
        description
          "React criterion packet rate of the policy-map action.";
      }
      leaf description {
        type string;
        description
          "Set Description for this alert action";
      }
      container trigger {
        description
          "Set the event trigger";
        container value {
          must 'lt or le or gt or ge or range' {
            tailf:xpath-root 3;
          }
          presence "indicates value is configured";
          description
            "Set the trigger criterion";
          leaf lt {
            type ncs_rpc_notif_trigger-value;
            description
              "trigger only if metric is less than the given value";
          }
          leaf le {
            type ncs_rpc_notif_trigger-value;
            description
              "trigger only if metric is less than or equal to the given value";
          }
          leaf gt {
            type ncs_rpc_notif_trigger-value;
            description
              "trigger only if metric is greater than the given value";
          }
          leaf ge {
            type ncs_rpc_notif_trigger-value;
            description
              "trigger only if metric is greater than or equal to the given value";
          }
          leaf range {
            type ncs_rpc_notif_trigger-value;
            description
              "trigger only if metric is in the inclusive range";
          }
        }
        container type {
          must 'immediate or average' {
            tailf:xpath-root 3;
          }
          presence "indicates type is configured";
          description
            "Set the trigger type";
          container immediate {
            presence "Immediate trigger";
            description
              "Immediate trigger";
          }
          leaf average {
            type uint32 {
              range "1..60";
            }
            description
              "Trigger averaged over N intervals.";
          }
        }
      }
      container action {
        description
          "Set the event action";
        container syslog {
          presence "Report via syslog";
          description
            "Report via syslog";
        }
        container snmp {
          tailf:display-when "not(../../../ncs:module) or boolean(/ncs:devices/ncs:device[ncs:name=current()/../../../ncs:name]/capability/feature='action-react-snmp')";
          presence "Report via syslog";
          description
            "Report via syslog";
        }
      }
      container alarm {
        tailf:display-when "not(../../ncs:module) or boolean(/ncs:devices/ncs:device[ncs:name=current()/../../ncs:name]/capability/feature='action-react-alarm')";
        description
          "Configure alarms";
        container type {
          must 'discrete or grouped' {
            tailf:xpath-root 3;
          }
          presence "indicates type is configured";
          description
            "Set the alarm type";
          container discrete {
            presence "Discrete alarms";
            description
              "Discrete alarms";
          }
          container grouped {
            tailf:display-when "not(../../../../ncs:module) or boolean(/ncs:devices/ncs:device[ncs:name=current()/../../../../ncs:name]/capability/feature='action-react-grouped-alarm')";
            description
              "Grouped alarms";
            leaf count {
              type uint16 {
                range "1..65535" {
                  description
                    "Number of flows with alarm";
                }
              }
              units "number of flows";
              must 'not(../percent)' {
                tailf:xpath-root 3;
              }
              description
                "Grouped on num-flows";
            }
            leaf percent {
              type uint8 {
                range "1..100" {
                  description
                    "Percentage of flows with alarm";
                }
              }
              units "percentage";
              must 'not(../count)' {
                tailf:xpath-root 3;
              }
              description
                "Grouped on percentage of flows";
            }
          }
        }
        leaf severity {
          type enumeration {
            enum "error" {
              value 0;
              description
                "Error level alarm";
            }
            enum "critical" {
              value 1;
              description
                "Critical level alarm";
            }
            enum "alert" {
              value 2;
              description
                "Alert level alarm";
            }
            enum "emergency" {
              value 3;
              description
                "Emergency level alarm";
            }
          }
          description
            "Set the alarm severity";
        }
      }
    }
  }

  grouping ncs_rpc_notif_action-common {
    leaf cos {
      type uint8 {
        range "0..7";
      }
      description
        "Sets the specific IEEE 802.1Q Layer 2 CoS value of an
         outgoing packet.
         This command should be used by a router if a user wants
         to mark a packet that is being sent to a switch.
         Switches can leverage Layer 2 header information,
         including a CoS value marking. Packets entering an
         interface cannot be set with a CoS value.";
    }
    leaf cos-inner {
      type uint8 {
        range "0..7";
      }
      description
        "Set inner COS";
    }
    leaf dei {
      type uint8 {
        range "0..1";
      }
      description
        "Set DEI";
    }
    leaf dei-imposition {
      type uint8 {
        range "0..1";
      }
      description
        "Set DEI imposition bit.";
    }
    leaf discard-class {
      type uint8 {
        range "0..7" {
          description
            "discard-class value";
        }
      }
      description
        "Sets the discard class on IPv4 or MPLS packets.
         The discard-class can be used only in service policies
         that are attached in the ingress policy.";
    }
    leaf dscp {
      type ncs_rpc_notif_dscp-value;
      description
        "Set IP DSCP (DiffServ CodePoint)";
    }
    leaf dscp-tunnel {
      type ncs_rpc_notif_dscp-value;
      description
        "Set DSCP Tunnel(for ipsec tunnels)";
    }
    leaf fr-de {
      tailf:display-when "not(../ncs:module) or boolean(/ncs:devices/ncs:device[ncs:name=current()/../ncs:name]/capability/feature='action-police-set-fr-de')";
      type uint8 {
        range "0..1";
      }
      description
        "Set frame relay discard-eligible bit";
    }
    container mpls {
      description
        "Set MPLS specific values";
      container experimental {
        description
          "Set experimental";
        leaf imposition {
          type uint8 {
            range "0..7";
          }
          description
            "Sets the experimental value of the MPLS packet
             imposition labels.
             Imposition can be used only in service policies that
             are attached in the ingress policy";
        }
        leaf topmost {
          type uint8 {
            range "0..7";
          }
          description
            "Sets the experimental value of the MPLS packet top-most
             labels.";
        }
      }
    }
    leaf precedence {
      type ncs_rpc_notif_precedence-type;
      description
        "Set IP Precedence";
    }
    leaf precedence-tunnel {
      type ncs_rpc_notif_precedence-type;
      description
        "Set Precedence tunnel(for ipsec tunnels)";
    }
    leaf qos-group {
      type uint16 {
        range "0..512" {
          description
            "QoS group value";
        }
      }
      description
        "Sets the QoS group identifiers on IPv4 or MPLS packets.
         The set qos-group is supported only on an ingress policy.";
    }
  }

  grouping ncs_rpc_notif_police-actions {
    container transmit {
      presence "Transmit packet";
      description
        "Transmit packet";
    }
    container drop {
      presence "Drop packet";
      description
        "Drop packet";
    }
    container set {
      description
        "Conditional marking";
      uses ncs_rpc_notif_action-common;
    }
  }

  grouping ncs_rpc_notif_qos-actions {
    container admit {
      tailf:display-when "not(../ncs:module) or boolean(/ncs:devices/ncs:device[ncs:name=current()/../ncs:name]/capability/feature='action-cac')";
      description
        "Call admission control";
      container cac {
        description
          "Call admission control (CAC) functionality";
        container local {
          must 'rate and flow/rate' {
            tailf:xpath-root 3;
          }
          presence "indicates local is configured";
          description
            "CAC local flow type (default type)";
          container flow {
            description
              "Flow attributes";
            leaf idle-timeout {
              type union {
                type uint16 {
                  range "10..2550" {
                    description
                      "The idle timeout period (in seconds)";
                  }
                }
                type enumeration {
                  enum "None" {
                    value 0;
                    description
                      "The flow does not expire";
                  }
                }
              }
              description
                "Maximum time of inactivity for a flow";
            }
            container rate {
              must 'value and unit' {
                tailf:xpath-root 3;
              }
              presence "indicates rate is configured";
              description
                "Per flow rate";
              leaf value {
                type uint32 {
                  range "1..4294967294" {
                    description
                      "Committed per flow rate";
                  }
                }
              }
              leaf unit {
                type ncs_rpc_notif_cac-unit-type;
              }
            }
          }
          container rate {
            must 'value and unit' {
              tailf:xpath-root 3;
            }
            presence "indicates rate is configured";
            description
              "Maximum rate for all flows";
            leaf value {
              type uint32 {
                range "1..4294967294" {
                  description
                    "Committed aggregate rate for all flows";
                }
              }
            }
            leaf unit {
              type ncs_rpc_notif_cac-unit-type;
            }
          }
        }
      }
    }
    container bandwidth {
      tailf:display-when "not(../ncs:module) or boolean(/ncs:devices/ncs:device[ncs:name=current()/../ncs:name]/capability/feature='action-bandwidth')";
      must 'value and unit' {
        tailf:xpath-root 3;
      }
      presence "indicates bandwidth is configured";
      description
        "Configure bandwidth for this class";
      leaf value {
        type union {
          type uint32 {
            range "1..4294967295" {
              description
                "Bandwidth value";
            }
          }
          type uint16 {
            range "1..1000" {
              description
                "Parts per-thousand bandwidth value";
            }
          }
          type uint32 {
            range "1..1000000" {
              description
                "Parts per-million bandwidth value";
            }
          }
          type uint32 {
            range "1..100" {
              description
                "Percentage bandwidth value";
            }
          }
        }
      }
      leaf unit {
        type enumeration {
          enum "bps" {
            value 0;
            description
              "Bits per second";
          }
          enum "gbps" {
            value 1;
            description
              "Gigabits per second";
          }
          enum "kbps" {
            value 2;
            description
              "Kilobits per second";
          }
          enum "mbps" {
            value 3;
            description
              "Megabits per second";
          }
          enum "cellsps" {
            value 4;
            description
              "Cells per second";
          }
          enum "per-thousand" {
            value 5;
            description
              "configure parts per-thousand bandwidth";
          }
          enum "per-million" {
            value 6;
            description
              "configure parts per-million bandwidth";
          }
          enum "percent" {
            value 7;
            description
              "configure a percentage bandwidth";
          }
        }
      }
    }
    container bandwidth-remaining {
      tailf:display-when "not(../ncs:module) or boolean(/ncs:devices/ncs:device[ncs:name=current()/../ncs:name]/capability/feature='action-bandwidth')";
      must 'unit and value' {
        tailf:xpath-root 3;
      }
      presence "indicates bandwidth-remaining is configured";
      description
        "Allocate left over bandwidth";
      leaf unit {
        type enumeration {
          enum "percent" {
            value 0;
            description
              "Allocate remaining bandwidth as percentage";
          }
          enum "ratio" {
            value 1;
            description
              "Allocate remaining bandwidth as a ratio";
          }
        }
        description
          "Bandwidth value unit";
      }
      leaf value {
        type union {
          type uint8 {
            range "1..100" {
              description
                "Percentage bandwidth value";
            }
          }
          type uint32 {
            range "1..4294967295" {
              description
                "Bandwidth ratio";
            }
          }
        }
        description
          "Bandwidth value";
      }
    }
    uses ncs_rpc_notif_policy-action-compress;
    uses ncs_rpc_notif_policy-action-encap-sequence;
    leaf fragment {
      tailf:display-when "not(../ncs:module) or boolean(/ncs:devices/ncs:device[ncs:name=current()/../ncs:name]/capability/feature='action-service-fragment')";
      type string {
        length "1..64" {
          description
            "Reference to a Service fragment";
        }
      }
      description
        "Refer to an existing service fragment. Reference to a Service fragment.";
    }
    container pause {
      tailf:display-when "not(../ncs:module) or boolean(/ncs:devices/ncs:device[ncs:name=current()/../ncs:name]/capability/feature='action-pfc')";
      presence "Configure PFC feature";
      description
        "Configure PFC feature";
      container buffer-size {
        must 'value and unit' {
          tailf:xpath-root 3;
        }
        presence "indicates buffer-size is configured";
        description
          "Configure buffer size";
        leaf value {
          type uint32 {
            range "1..4294967295";
          }
          description
            "Range of buffer size";
        }
        leaf unit {
          type ncs_rpc_notif_pfc-unit-type;
        }
      }
      container pause-threshold {
        must 'value and unit' {
          tailf:xpath-root 3;
        }
        presence "indicates pause-threshold is configured";
        description
          "Configure pasue threshold";
        leaf value {
          type uint32 {
            range "1..4294967295";
          }
          description
            "Range of pause threshold";
        }
        leaf unit {
          type ncs_rpc_notif_pfc-unit-type;
        }
      }
      container resume-threshold {
        must 'value and unit' {
          tailf:xpath-root 3;
        }
        presence "indicates resume-threshold is configured";
        description
          "Configure resume threshold";
        leaf value {
          type uint32 {
            range "1..4294967295";
          }
          description
            "Range of resume threshold";
        }
        leaf unit {
          type ncs_rpc_notif_pfc-unit-type;
        }
      }
    }
    container police {
      description
        "Police traffic";
      container conditional {
        presence "Conditional policer for priority traffic";
        description
          "Conditional policer for priority traffic";
      }
      container rate {
        must 'value and unit' {
          tailf:xpath-root 3;
        }
        presence "indicates rate is configured";
        description
          "Committed Information Rate";
        leaf value {
          type union {
            type uint32 {
              range "1..4294967295";
            }
            type uint8 {
              range "1..100" {
                description
                  "Committed Information Rate in percentage of link bandwidth";
              }
            }
            type uint16 {
              range "1..1000" {
                description
                  "Committed Information Rate in per-thousand of link bandwidth";
              }
            }
            type uint32 {
              range "1..1000000" {
                description
                  "Committed Information Rate in per-million of link bandwidth";
              }
            }
          }
          description
            "Committed Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
            enum "per-thousand" {
              value 7;
              description
                "Parts per-thousand of the link bandwidth";
            }
            enum "per-million" {
              value 8;
              description
                "Parts per-million of the link bandwidth";
            }
          }
          description
            "Rate unit";
        }
      }
      container burst {
        description
          "Burst size (BC)";
        leaf value {
          type uint32 {
            range "1..4294967295";
          }
          description
            "Burst size (BC)";
        }
        leaf unit {
          type ncs_rpc_notif_burst-unit-type;
          description
            "Burst size unit";
        }
      }
      container peak-burst {
        tailf:display-when "not(../../ncs:module) or boolean(/ncs:devices/ncs:device[ncs:name=current()/../../ncs:name]/capability/feature='action-police-peak-burst')";
        description
          "Excess Burst size (BE)";
        leaf value {
          type uint32 {
            range "1..4294967295";
          }
          description
            "Exess burst size (BC)";
        }
        leaf unit {
          type ncs_rpc_notif_burst-unit-type;
          description
            "Burst size unit";
        }
      }
      container peak-rate {
        must 'value and unit' {
          tailf:xpath-root 3;
        }
        presence "indicates peak-rate is configured";
        description
          "Peak Information Rate";
        leaf value {
          type union {
            type uint32 {
              range "1..4294967295";
            }
            type uint8 {
              range "1..100" {
                description
                  "Committed Information Rate in percentage of link bandwidth";
              }
            }
          }
          description
            "Peak Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
          }
        }
      }
      container conform-action {
        description
          "Action for conforming traffic";
        uses ncs_rpc_notif_police-actions;
      }
      container exceed-action {
        description
          "Action for exceeding traffic";
        uses ncs_rpc_notif_police-actions;
      }
      container violate-action {
        description
          "Action for violating traffic";
        uses ncs_rpc_notif_police-actions;
      }
      leaf conform-color {
        tailf:display-when "not(../../ncs:module) or boolean(/ncs:devices/ncs:device[ncs:name=current()/../../ncs:name]/capability/feature='action-police-conform-color')";
        type string;
        description
          "Configure conform color class for color aware policing. Conform color class name.";
      }
      leaf exceed-color {
        tailf:display-when "not(../../ncs:module) or boolean(/ncs:devices/ncs:device[ncs:name=current()/../../ncs:name]/capability/feature='action-police-exceed-color')";
        type string;
        description
          "Configure exceed color class for color aware policing. Exceed color class name.";
      }
      container child-conform-aware {
        tailf:display-when "not(../../ncs:module) or boolean(/ncs:devices/ncs:device[ncs:name=current()/../../ncs:name]/capability/feature='action-police-coupled')";
        presence "Enable coupled policing";
        description
          "Enable coupled policing";
      }
    }
    container priority {
      description
        "Assign priority to this class";
      leaf level {
        type uint8 {
          range "1..7" {
            description
              "Priority level";
          }
        }
        description
          "Configure a priority level";
      }
    }
    container queue-limits {
      description
        "Queue Limit Node";
      list queue-limit {
        key "value unit";
        description
          "Configure queue-limit (taildrop threshold) for this class";
        leaf value {
          type union {
            type uint32 {
              range "1..4294967295" {
                description
                  "Max Threshold for tail drop";
              }
            }
            type uint8 {
              range "1..100" {
                description
                  "Percentage value";
              }
            }
          }
          description
            "queue-limit value";
        }
        leaf unit {
          type enumeration {
            enum "bytes" {
              value 0;
              description
                "Bytes";
            }
            enum "kbytes" {
              value 1;
              description
                "Kilobytes";
            }
            enum "mbytes" {
              value 2;
              description
                "Megabytes";
            }
            enum "ms" {
              value 3;
              description
                "Milliseconds";
            }
            enum "packets" {
              value 4;
              description
                "Packets (default)";
            }
            enum "us" {
              value 5;
              description
                "Microseconds";
            }
            enum "percent" {
              value 6;
              description
                "Configure queue limit value in percentage";
            }
          }
          description
            "queue-limit unit";
        }
        container discard-classes {
          description
            "discard class container";
          leaf-list discard-class {
            type uint8 {
              range "0..7";
            }
            description
              "Remaining bandwidth value.";
          }
        }
      }
    }
    container random-detect-default {
      presence "Enable RED with default min and max thresholds";
      description
        "Enable RED with default min and max thresholds";
    }
    container random-detect-ecn {
      presence "Enable ECN based WRED";
      description
        "ECN based WRED";
    }
    list random-detect {
      key "minimum-threshold-value minimum-threshold-unit maximum-threshold-value maximum-threshold-unit";
      description
        "Enable Random Early Detection.
         All RED profiles in a class must be based
         on the same field.";
      leaf minimum-threshold-value {
        type uint32 {
          range "0..1073741823";
        }
        description
          "Minimum threshold";
      }
      leaf minimum-threshold-unit {
        type ncs_rpc_notif_wred-unit-type;
        description
          "threshold unit";
      }
      leaf maximum-threshold-value {
        type uint32 {
          range "0..1073741823";
        }
        description
          "Maximum threshold";
      }
      leaf maximum-threshold-unit {
        type ncs_rpc_notif_wred-unit-type;
        description
          "threshold unit";
      }
      leaf-list cos {
        type uint8 {
          range "0..7" {
            description
              "COS  value";
          }
        }
        max-elements 8;
        description
          "COS based WRED (upto 8 values)";
      }
      leaf-list dei {
        type uint8 {
          range "0..1" {
            description
              "DEI value";
          }
        }
        max-elements 8;
        description
          "DEI based WRED";
      }
      leaf-list discard-class {
        type uint8 {
          range "0..7" {
            description
              "Discard Class  value";
          }
        }
        max-elements 8;
        description
          "Discard Class based WRED";
      }
      leaf-list dscp {
        type ncs_rpc_notif_dscp-value;
        max-elements 8;
        description
          "DSCP based WRED";
      }
      leaf-list exp {
        type uint8 {
          range "0..7" {
            description
              "MPLS Experimental  value";
          }
        }
        max-elements 8;
        description
          "MPLS Experimental value based WRED";
      }
      leaf-list precedence {
        type union {
          type uint8 {
            range "0..7" {
              description
                "Precedence value";
            }
          }
          type enumeration {
            enum "critical" {
              value 0;
              description
                "Critical precedence (5)";
            }
            enum "flash" {
              value 1;
              description
                "Flash precedence (3)";
            }
            enum "flash-override" {
              value 2;
              description
                "Flash override precedence (4)";
            }
            enum "immediate" {
              value 3;
              description
                "Immediate precedence (2)";
            }
            enum "internet" {
              value 4;
              description
                "Internetwork control precedence (6)";
            }
            enum "network" {
              value 5;
              description
                "Network control precedence (7)";
            }
            enum "priority" {
              value 6;
              description
                "Priority precedence (1)";
            }
            enum "routine" {
              value 7;
              description
                "Routine precedence (0)";
            }
          }
        }
        max-elements 8;
        description
          "Precedence based WRED";
      }
    }
    leaf service-fragment {
      tailf:display-when "not(../ncs:module) or boolean(/ncs:devices/ncs:device[ncs:name=current()/../ncs:name]/capability/feature='action-service-fragment')";
      type string {
        length "1..64" {
          description
            "Name of Service fragment";
        }
      }
      description
        "Define a service fragment. Name of Service fragment";
    }
    container service-policy {
      description
        "Configure a child service policy";
      leaf name {
        type ncs_rpc_notif_service-policy-name-type;
        description
          "Name of the child service policy";
      }
      leaf type {
        type enumeration {
          enum "pbr" {
            value 0;
            description
              "PBR policy-map";
          }
          enum "performance-traffic" {
            value 1;
            description
              "Performance traffic policy-map";
          }
          enum "qos" {
            value 2;
            description
              "QoS policy-map (default)";
          }
          enum "redirect" {
            value 3;
            description
              "Redirect policy-map";
          }
          enum "traffic" {
            value 4;
            description
              "Traffic policy-map";
          }
        }
        description
          "The type of policy-map";
      }
    }
    container set {
      description
        "Configure marking for this class";
      container atm-clp {
        tailf:display-when "not(../../ncs:module) or boolean(/ncs:devices/ncs:device[ncs:name=current()/../../ncs:name]/capability/feature='action-set-atm-clp')";
        presence "Set atm cell-loss-priority bit";
        description
          "Set atm cell-loss-priority bit";
      }
      leaf traffic-class {
        tailf:display-when "not(../../ncs:module) or boolean(/ncs:devices/ncs:device[ncs:name=current()/../../ncs:name]/capability/feature='action-set-traffic-class')";
        type uint8 {
          range "0..8" {
            description
              "Traffic class value";
          }
        }
        description
          "Sets the Traffic Class identifiers on IPv4 or MPLS packets.
           The set traffic-class is supported only on an ingress policy.";
      }
      leaf forward-class {
        tailf:display-when "not(../../ncs:module) or boolean(/ncs:devices/ncs:device[ncs:name=current()/../../ncs:name]/capability/feature='action-set-fwd-class')";
        type uint8 {
          range "1..7" {
            description
              "Forward class value";
          }
        }
        description
          "Set forward class";
      }
      uses ncs_rpc_notif_action-common;
    }
    container shape {
      description
        "Configure shaping for this class";
      container average {
        description
          "Average rate shaping";
        container rate {
          must 'value and unit' {
            tailf:xpath-root 3;
          }
          presence "indicates rate is configured";
          description
            "Shape rate";
          leaf value {
            type union {
              type uint32 {
                range "1..4294967295" {
                  description
                    "Shape rate";
                }
              }
              type uint16 {
                range "1..1000" {
                  description
                    "Shape rate as parts per-thousand of available bandwidth";
                }
              }
              type uint32 {
                range "1..1000000" {
                  description
                    "Shape rate as parts per-million of available bandwidth";
                }
              }
              type uint8 {
                range "1..100" {
                  description
                    "Shape rate as percentage of available bandwidth";
                }
              }
              type string {
                pattern '[$][a-zA-Z0-9][a-zA-Z0-9\._@%+:\-]{0,32}[ ][=][ ]\d{1,10}';
              }
            }
          }
          leaf unit {
            type enumeration {
              enum "bps" {
                value 0;
                description
                  "Bits per second";
              }
              enum "cellsps" {
                value 1;
                description
                  "Cells per second";
              }
              enum "gbps" {
                value 2;
                description
                  "Gigabits per second";
              }
              enum "kbps" {
                value 3;
                description
                  "Kilobits per second";
              }
              enum "mbps" {
                value 4;
                description
                  "Megabits per second";
              }
              enum "per-thousand" {
                value 5;
                description
                  "Configure shape rate in per-thousand";
              }
              enum "per-million" {
                value 6;
                description
                  "Configure shape rate in per-million";
              }
              enum "percent" {
                value 7;
                description
                  "Configure shape rate in percentage";
              }
            }
            description
              "Shape rate unit";
          }
        }
        container excess-burst {
          tailf:display-when "not(../../../ncs:module) or boolean(/ncs:devices/ncs:device[ncs:name=current()/../../../ncs:name]/capability/feature='action-shape-burst')";
          must 'size and unit' {
            tailf:xpath-root 3;
          }
          presence "indicates excess-burst is configured";
          description
            "Excess burst size";
          leaf size {
            type uint32 {
              range "1..4294967295" {
                description
                  "Excess burst size";
              }
            }
          }
          leaf unit {
            type enumeration {
              enum "bytes" {
                value 0;
                description
                  "Bytes";
              }
              enum "cells" {
                value 1;
                description
                  "Cells";
              }
              enum "gbytes" {
                value 2;
                description
                  "Gigabytes";
              }
              enum "kbytes" {
                value 3;
                description
                  "Kilobytes";
              }
              enum "mbytes" {
                value 4;
                description
                  "Megabytes";
              }
              enum "ms" {
                value 5;
                description
                  "Milliseconds";
              }
              enum "packets" {
                value 6;
                description
                  "Packets";
              }
              enum "us" {
                value 7;
                description
                  "Microseconds";
              }
            }
          }
        }
      }
    }
  }

  grouping ncs_rpc_notif_redirect-actions {
    uses ncs_rpc_notif_policy-action-compress;
    uses ncs_rpc_notif_policy-action-encap-sequence;
    container priority {
      presence "Test command";
      description
        "Test command";
    }
  }

  grouping live_ncs_class-map-common {
    leaf class-map-name {
      type string {
        pattern '[a-zA-Z0-9][a-zA-Z0-9\._@$%+#:=<>\-]{0,62}' {
          description
            "Any string except 'type'";
        }
      }
      description
        "Name of the class-map";
    }
    container match-all {
      presence "Match all match criteria";
      description
        "Match all match criteria";
    }
    container match-any {
      presence "Match any match criteria (default)";
      description
        "Match any match criteria (default)";
    }
    leaf description {
      type string;
      description
        "Set description for this class-map";
    }
  }

  grouping live_ncs_match-access-group {
    container access-group {
      description
        "Match access group";
      leaf-list ipv4 {
        // NCS drop if-feature statement
        type live_ncs_acl-list-name-type;
        description
          "IPv4 access list";
      }
      leaf-list ipv6 {
        // NCS drop if-feature statement
        type live_ncs_acl-list-name-type;
        description
          "IPv6 access list";
      }
      leaf-list ethernet-services {
        // NCS drop if-feature statement
        type live_ncs_acl-list-name-type;
        description
          "Ethernet-Services";
      }
    }
  }

  grouping live_ncs_match-atm {
    container atm {
      // NCS drop if-feature statement
      description
        "Match based on ATM specific criteria";
      leaf-list clp {
        type uint8 {
          range "0..1";
        }
        // NCS drop max-elements statement
        ordered-by user;
        description
          "Match ATM CLP bit";
      }
      container oam {
        presence "Match ATM OAM";
        description
          "Match ATM OAM";
      }
    }
  }

  grouping live_ncs_match-cac {
    container cac {
      // NCS drop if-feature statement
      description
        "Match based on CAC fields";
      container admitted {
        presence "Match packets admitted by CAC action";
        description
          "Match packets admitted by CAC action";
      }
      container unadmitted {
        presence "Match packets unadmitted by CAC action";
        description
          "Match packets unadmitted by CAC action";
      }
    }
  }

  grouping live_ncs_match-cos {
    container cos {
      // NCS drop if-feature statement
      description
        "Match based on IEEE 802.1Q/ISL Class Of Service value";
      leaf-list value {
        type uint8 {
          range "0..7";
        }
        // NCS drop max-elements statement
        description
          "COS value";
      }
    }
    container cos-inner {
      // NCS drop if-feature statement
      description
        "Match inner cos values";
      leaf-list value {
        type uint8 {
          range "0..7";
        }
        // NCS drop max-elements statement
        description
          "inner cos value (Upto 8 values)";
      }
    }
  }

  grouping live_ncs_match-dei {
    leaf dei {
      // NCS drop if-feature statement
      type uint8 {
        range "0..1" {
          description
            "DEI value";
        }
      }
      // NCS drop must statement
      description
        "Match based on DEI bit (0/1)";
    }
    leaf dei-inner {
      // NCS drop if-feature statement
      type uint8 {
        range "0..1" {
          description
            "DEI value";
        }
      }
      // NCS drop must statement
      description
        "Match inner based on DEI bit (0/1)";
    }
  }

  grouping live_ncs_match-destination-address {
    container destination-address {
      description
        "Match based on destination address";
      container ipv4 {
        // NCS drop if-feature statement
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        // NCS drop if-feature statement
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        // NCS drop if-feature statement
        type yang:mac-address;
        description
          "MAC Address";
      }
    }
  }

  grouping live_ncs_matchnot-destination-address {
    container destination-address {
      description
        "Match based on destination address";
      container ipv4 {
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        // NCS drop if-feature statement
        type yang:mac-address;
        description
          "MAC Address";
      }
    }
  }

  grouping live_ncs_match-destination-port {
    container destination-port {
      // NCS drop if-feature statement
      description
        "Match based on destination port";
      leaf-list port-number {
        type live_ncs_port-number-type;
        // NCS drop max-elements statement
        description
          "destination port";
      }
    }
  }

  grouping live_ncs_match-discard-class {
    container discard-class {
      // NCS drop if-feature statement
      description
        "Match based on discard class";
      leaf-list id {
        type uint8 {
          range "0..7";
        }
        // NCS drop max-elements statement
        description
          "Discard CLass Id";
      }
    }
  }

  grouping live_ncs_match-dscp {
    container dscp {
      // NCS drop if-feature statement
      description
        "Match based on IP DSCP value";
      leaf-list value {
        type live_ncs_dscp-value;
        description
          "DSCP value";
      }
    }
    container dscp-ipv4 {
      // NCS drop if-feature statement
      description
        "Match based on IPv4 DSCP value";
      leaf-list value {
        type live_ncs_dscp-value;
        description
          "DSCP value";
      }
    }
    container dscp-ipv6 {
      // NCS drop if-feature statement
      description
        "Match based on IPv6 DSCP value";
      leaf-list value {
        type live_ncs_dscp-value;
        description
          "DSCP value";
      }
    }
  }

  grouping live_ncs_match-ethertype {
    container ethertype {
      // NCS drop if-feature statement
      description
        "Match based on ethertype";
      leaf-list value {
        type union {
          type uint16 {
            range "1536..65535";
          }
          type enumeration {
            enum "arp" {
              value 0;
              description
                "Any ARP Ethertype";
            }
            enum "ipv4" {
              value 1;
              description
                "Any IPv4 Ethertype";
            }
            enum "ipv6" {
              value 2;
              description
                "Any IPv6 Ethertype";
            }
          }
        }
        // NCS drop max-elements statement
        description
          "Ethertype Value";
      }
    }
  }

  grouping live_ncs_match-flow-key {
    container flow-key {
      // NCS drop if-feature statement
      description
        "Match based on flow keys";
      container five-tuple {
        // NCS drop must statement
        presence "Five tuples to identify a flow";
        description
          "Five tuples to identify a flow";
      }
      container dst-ip {
        // NCS drop must statement
        presence "Destination IP address";
        description
          "Destination IP address";
      }
      container src-ip {
        // NCS drop must statement
        presence "Source IP address";
        description
          "Source IP address";
      }
      container flow-cache {
        description
          "Configure the flow-cache parameters";
        leaf idle-timeout {
          type union {
            type uint16 {
              range "1..65534" {
                description
                  "The idle timeout period (in seconds)";
              }
            }
            type enumeration {
              enum "None" {
                value 0;
                description
                  "The flow does not expire";
              }
            }
          }
          description
            "Maximum time of inactivity for a flow.";
        }
      }
    }
  }

  grouping live_ncs_match-flow-tag {
    container flow-tag {
      // NCS drop if-feature statement
      description
        "Match based on flow-tag";
      leaf-list tag-number {
        type union {
          type uint8 {
            range "1..63";
          }
          type string {
            pattern '([1-9][0-9]{0,1})-([1-9][0-9]{0,1})' {
              description
                "<1-63>-<1-63>";
            }
          }
        }
        // NCS drop max-elements statement
        description
          "flow-tag number";
      }
    }
  }

  grouping live_ncs_match-fr-de {
    leaf fr-de {
      // NCS drop if-feature statement
      type union {
        type string {
          pattern '1';
        }
        type uint8 {
          range "0..1";
        }
      }
      description
        "Match based on FrameRelay DE bit";
    }
  }

  grouping live_ncs_match-fragment-type {
    container fragment-type {
      // NCS drop if-feature statement
      description
        "Fragment type for a packet";
      container dont-fragment {
        presence "Match don't-Fragment bit";
        description
          "Match don't-Fragment bit";
      }
      container first-fragment {
        presence "Match first fragment bit";
        description
          "Match first fragment bit";
      }
      container is-fragment {
        presence "Match is-fragment bit";
        description
          "Match is-fragment bit";
      }
      container last-fragment {
        presence "Match last fragment bit";
        description
          "Match last fragment bit";
      }
    }
  }

  grouping live_ncs_match-frame-relay {
    container frame-relay {
      // NCS drop if-feature statement
      description
        "Match based on frame-relay specific criteria";
      leaf-list dlci {
        type union {
          type uint16 {
            range "16..1007";
          }
          type string {
            pattern '([1-9][0-9]{1,3})-([1-9][0-9]{1,3})' {
              description
                "<16-1007>-<16-1007>";
            }
          }
        }
        // NCS drop max-elements statement
        description
          "Match frame-relay dlci value(s)";
      }
    }
  }

  grouping live_ncs_match-ipv4 {
    container ipv4 {
      description
        "Match based on ipv4 icmp";
      container icmp-code {
        description
          "Match based on ipv4 icmp code";
        leaf-list value {
          type union {
            type uint8 {
              range "0..255";
            }
            type string {
              pattern '([0-9]{1,3})-([0-9]{1,3})' {
                description
                  "<0-255>-<0-255>";
              }
            }
          }
          // NCS drop max-elements statement
          description
            "IPv4 ICMP code";
        }
      }
      container icmp-type {
        description
          "Match based on ipv4 icmp type";
        leaf-list value {
          type union {
            type uint8 {
              range "0..255";
            }
            type string {
              pattern '([0-9]{1,3})-([0-9]{1,3})' {
                description
                  "<0-255>-<0-255>";
              }
            }
          }
          // NCS drop max-elements statement
          description
            "IPv4 ICMP type";
        }
      }
    }
  }

  grouping live_ncs_match-ipv6 {
    container ipv6 {
      description
        "Match based on IPv6";
      container icmp-code {
        description
          "IPv6 ICMP code";
        leaf-list value {
          type union {
            type uint8 {
              range "0..255";
            }
            type string {
              pattern '([0-9]{1,3})-([0-9]{1,3})' {
                description
                  "<0-255>-<0-255>";
              }
            }
          }
          // NCS drop max-elements statement
          description
            "ICMP code";
        }
      }
      container icmp-type {
        description
          "IPv6 ICMP type";
        leaf-list value {
          type union {
            type uint8 {
              range "0..255";
            }
            type string {
              pattern '([0-9]{1,3})-([0-9]{1,3})' {
                description
                  "<0-255>-<0-255>";
              }
            }
          }
          // NCS drop max-elements statement
          description
            "ICMP type";
        }
      }
    }
  }

  grouping live_ncs_match-mpls {
    container mpls {
      description
        "Match based on MPLS specific values";
      container disposition {
        description
          "Match MPLS Label Disposition";
        container access-group {
          description
            "access group";
          leaf ipv4 {
            // NCS drop if-feature statement
            type string {
              length "1..64";
            }
            description
              "IPv4 access list";
          }
          leaf ipv6 {
            // NCS drop if-feature statement
            type string {
              length "1..64";
            }
            description
              "IPv6 access list";
          }
        }
        leaf class-map {
          // NCS drop if-feature statement
          type string {
            length "1..32";
          }
          description
            "class-map name";
        }
      }
      container experimental {
        description
          "Match MPLS experimental values";
        container imposition {
          // NCS drop if-feature statement
          description
            "Match imposition label";
          leaf-list label {
            type uint8 {
              range "0..7";
            }
            // NCS drop max-elements statement
            description
              "MPLS experimental label";
          }
        }
        container topmost {
          // NCS drop if-feature statement
          description
            "Match topmost label";
          leaf-list label {
            type uint8 {
              range "0..7";
            }
            // NCS drop max-elements statement
            description
              "MPLS experimental label";
          }
        }
      }
    }
  }

  grouping live_ncs_matchnot-mpls {
    container mpls {
      description
        "Match based on MPLS specific values";
      container disposition {
        description
          "Match MPLS Label Disposition";
        container access-group {
          description
            "access group";
          leaf ipv4 {
            // NCS drop if-feature statement
            type string {
              length "1..64";
            }
            description
              "IPv4 access list";
          }
          leaf ipv6 {
            // NCS drop if-feature statement
            type string {
              length "1..64";
            }
            description
              "IPv6 access list";
          }
        }
      }
      container experimental {
        description
          "Match MPLS experimental values";
        container topmost {
          description
            "Match topmost label";
          leaf-list label {
            type uint8 {
              range "0..7";
            }
            // NCS drop max-elements statement
            description
              "MPLS experimental label";
          }
        }
      }
    }
  }

  grouping live_ncs_match-packet {
    container packet {
      description
        "Match based on packet length";
      container length {
        description
          "Packet length";
        leaf-list value {
          type live_ncs_packet-length-type;
          // NCS drop max-elements statement
          description
            "IP Packet Length";
        }
      }
      container length-ipv4 {
        // NCS drop if-feature statement
        description
          "IPV4 Packet Length";
        leaf-list value {
          type live_ncs_packet-length-type;
          // NCS drop max-elements statement
        }
      }
      container length-ipv6 {
        // NCS drop if-feature statement
        description
          "IPV6 Packet Length";
        leaf-list value {
          type live_ncs_packet-length-type;
          // NCS drop max-elements statement
        }
      }
    }
  }

  grouping live_ncs_matchnot-packet {
    container packet {
      description
        "Match based on packet length";
      container length {
        description
          "Packet length";
        leaf-list value {
          type live_ncs_packet-length-type;
          // NCS drop max-elements statement
          description
            "IP Packet Length";
        }
      }
      container length-ipv4 {
        // NCS drop if-feature statement
        description
          "IPV4 Packet Length";
        leaf-list value {
          type live_ncs_packet-length-type;
          // NCS drop max-elements statement
        }
      }
      container length-ipv6 {
        // NCS drop if-feature statement
        description
          "IPV6 Packet Length";
        leaf-list value {
          type live_ncs_packet-length-type;
          // NCS drop max-elements statement
        }
      }
    }
  }

  grouping live_ncs_match-precedence {
    container precedence {
      // NCS drop if-feature statement
      description
        "Match based on IP precedence values";
      leaf-list value {
        type live_ncs_precedence-type;
        // NCS drop max-elements statement
        description
          "IP precedence";
      }
    }
    container precedence-ipv4 {
      // NCS drop if-feature statement
      description
        "Match based on IPV4 precedence";
      leaf-list value {
        type live_ncs_precedence-type;
        // NCS drop max-elements statement
        description
          "IPV4 precedence";
      }
    }
    container precedence-ipv6 {
      // NCS drop if-feature statement
      description
        "Match based on IPV6 precedence";
      leaf-list value {
        type live_ncs_precedence-type;
        // NCS drop max-elements statement
        description
          "IPV6 precedence";
      }
    }
  }

  grouping live_ncs_match-protocol {
    container protocol {
      description
        "Match based on L3 protocol (Upto 8 values or ranges)";
      leaf-list number {
        type live_ncs_protocol-type;
        // NCS drop max-elements statement
        description
          "Protocol Number";
      }
    }
  }

  grouping live_ncs_match-qos-group {
    container qos-group {
      description
        "Match based on QoS Group";
      leaf-list id {
        type union {
          type uint16 {
            range "0..512";
          }
          type string {
            pattern '([0-9]{1,3})-([0-9]{1,3})' {
              description
                "Lower and upper limit of QoS Group range (<0-512>-<0-512>)";
            }
          }
        }
        // NCS drop max-elements statement
        description
          "QoS Group Id";
      }
    }
  }

  grouping live_ncs_match-traffic-class {
    container traffic-class {
      description
        "Match based on Traffic Class";
      leaf-list id {
        type union {
          type uint8 {
            range "0..63";
          }
          type string {
            pattern '([0-9]{1,2})-([0-9]{1,2})' {
              description
                "Lower and upper limit of Traffic Class range (<0-63>-<0-63>)";
            }
          }
        }
        // NCS drop max-elements statement
        description
          "Traffic Class Id";
      }
    }
  }

  grouping live_ncs_match-source-address {
    container source-address {
      description
        "Match based on source address";
      container ipv4 {
        // NCS drop if-feature statement
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        // NCS drop if-feature statement
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        // NCS drop if-feature statement
        type yang:mac-address;
        description
          "MAC Address";
      }
    }
  }

  grouping live_ncs_matchnot-source-address {
    container source-address {
      description
        "Match based on source address";
      container ipv4 {
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        // NCS drop if-feature statement
        type yang:mac-address;
        description
          "MAC Address";
      }
    }
  }

  grouping live_ncs_match-source-port {
    container source-port {
      // NCS drop if-feature statement
      description
        "Match based on source port";
      leaf-list number {
        type live_ncs_port-number-type;
        // NCS drop max-elements statement
        description
          "source port";
      }
    }
  }

  grouping live_ncs_match-tcp-flag {
    container tcp-flag {
      description
        "Match based on TCP flags";
      leaf value {
        type uint16 {
          range "0..4095";
        }
        description
          "TCP flags value";
      }
      container any {
        presence "Match based on any bit set";
        description
          "Match based on any bit set";
      }
    }
  }

  grouping live_ncs_match-vlan {
    container vlan {
      // NCS drop if-feature statement
      description
        "Match based on Vlan Ids";
      leaf-list vlan-id {
        type live_ncs_vlan-id-type;
        // NCS drop max-elements statement
        description
          "Vlan Id";
      }
    }
    container vlan-inner {
      // NCS drop if-feature statement
      description
        "Match based on inner Vlan Ids";
      leaf-list vlan-id {
        type live_ncs_vlan-id-type;
        // NCS drop max-elements statement
        description
          "inner Vlan Id";
      }
    }
  }

  grouping live_ncs_matchnot-vlan {
    container vlan {
      // NCS drop if-feature statement
      description
        "Match based on Vlan Ids";
      leaf-list vlan-id {
        type live_ncs_vlan-id-type;
        // NCS drop max-elements statement
        description
          "Vlan Id";
      }
    }
    container vlan-inner {
      // NCS drop if-feature statement
      description
        "Match based on inner Vlan Ids";
      leaf-list vlan-id {
        type live_ncs_vlan-id-type;
        // NCS drop max-elements statement
        description
          "inner Vlan Id";
      }
    }
  }

  grouping live_ncs_match-vpls {
    container vpls {
      description
        "Match based on VPLS fields";
      container known {
        // NCS drop if-feature statement
        presence "VPLS Known";
        description
          "VPLS Known";
      }
      container unknown {
        // NCS drop if-feature statement
        presence "VPLS Unknown";
        description
          "VPLS Unknown";
      }
      container broadcast {
        presence "VPLS Broadcast";
        description
          "VPLS Broadcast";
      }
      container control {
        // NCS drop if-feature statement
        presence "VPLS Control";
        description
          "VPLS Control";
      }
      container multicast {
        presence "VPLS Multicast";
        description
          "VPLS Multicast";
      }
    }
  }

  grouping live_ncs_matchnot-vpls {
    container vpls {
      description
        "Match based on VPLS fields";
      container known {
        // NCS drop if-feature statement
        presence "VPLS Known";
        description
          "VPLS Known";
      }
      container unknown {
        // NCS drop if-feature statement
        presence "VPLS Unknown";
        description
          "VPLS Unknown";
      }
      container broadcast {
        // NCS drop if-feature statement
        presence "VPLS Broadcast";
        description
          "VPLS Broadcast";
      }
      container control {
        // NCS drop if-feature statement
        presence "VPLS Control";
        description
          "VPLS Control";
      }
      container multicast {
        // NCS drop if-feature statement
        presence "VPLS Multicast";
        description
          "VPLS Multicast";
      }
    }
  }

  grouping live_ncs_match-authen-status {
    leaf authen-status {
      // NCS drop if-feature statement
      type enumeration {
        enum "authenticated" {
          value 0;
          description
            "Authenticated";
        }
        enum "unauthenticated" {
          value 1;
          description
            "Unauthenticated";
        }
      }
      description
        "Authentication Status";
    }
  }

  grouping live_ncs_match-circuit-id {
    container circuit-id {
      description
        "Match based on circuit ID";
      leaf-list value {
        type string {
          length "1..32" {
            description
              "Any string except 'regexp'";
          }
        }
        description
          "circuit ID";
      }
    }
    container circuit-id-regexp {
      description
        "Match based on circuit ID regular expression";
      leaf-list value {
        type string {
          length "1..32";
        }
        description
          "Circuit ID regular expression";
      }
    }
  }

  grouping live_ncs_match-dhcp-client-id {
    container dhcp-client-id {
      description
        "Match based on dhcp client id";
      list client-id {
        key "id flag";
        description
          "client id";
        leaf id {
          type string {
            length "1..32";
          }
          description
            "client id";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
    container dhcp-client-id-regexp {
      description
        "Match based on dhcp client id regular expression";
      list client-id {
        key "id flag";
        description
          "client id with regular expression";
        leaf id {
          type string {
            length "1..32";
          }
          description
            "client id with regular expression";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
  }

  grouping live_ncs_match-domain {
    container domain {
      description
        "Match base on domain name";
      list domain-name {
        key "name format";
        description
          "Domain name";
        leaf name {
          type string {
            length "1..32";
          }
          description
            "Domain name";
        }
        leaf format {
          type string {
            length "1..32";
          }
          description
            "Domain format name";
        }
      }
    }
    container domain-regexp {
      description
        "Match base on domain name with regular expression";
      list domain-name {
        key "regexp format";
        description
          "Domain name";
        leaf regexp {
          type string {
            length "1..32";
          }
          description
            "Domain name with regular expression";
        }
        leaf format {
          type string {
            length "1..32";
          }
          description
            "Domain format name";
        }
      }
    }
  }

  grouping live_ncs_match-control-protocol {
    container protocol {
      description
        "Match based on protocol";
      leaf-list name {
        // NCS drop if-feature statement
        type enumeration {
          enum "dhcpv4" {
            value 0;
            description
              "dhcpv4";
          }
          enum "dhcpv6" {
            value 1;
            description
              "dhcpv6";
          }
          enum "ppp" {
            value 2;
            description
              "ppp";
          }
        }
        // NCS drop max-elements statement
        description
          "protocol name";
      }
    }
  }

  grouping live_ncs_match-remote-id {
    container remote-id {
      description
        "Match based on remote ID";
      leaf-list id {
        type string {
          length "1..32";
        }
        description
          "remote-id";
      }
    }
    container remote-id-regexp {
      description
        "Remote ID with regular expression";
      leaf-list id {
        type string {
          length "1..32";
        }
        description
          "remote-id with regular expression";
      }
    }
  }

  grouping live_ncs_match-service-name {
    container service-name {
      description
        "Match based on service name";
      leaf-list name {
        type string {
          length "1..32";
        }
        description
          "Service name";
      }
    }
    container service-name-regexp {
      description
        "Match based on service name with regular expression";
      leaf-list name {
        type string {
          length "1..32";
        }
        description
          "Service name with regular expression";
      }
    }
  }

  grouping live_ncs_match-timer {
    container timer {
      // NCS drop if-feature statement
      description
        "Match based on timer";
      leaf-list name {
        type string {
          length "1..32";
        }
        description
          "Timer name";
      }
    }
    container timer-regexp {
      description
        "Timer with regular expression";
      leaf-list name {
        type string {
          length "1..32";
        }
        description
          "Timer name with regular expression";
      }
    }
  }

  grouping live_ncs_match-username {
    container username {
      // NCS drop if-feature statement
      description
        "Match based on user name";
      leaf-list name {
        type string {
          length "1..32";
        }
        description
          "User name";
      }
    }
    container username-regexp {
      // NCS drop if-feature statement
      description
        "Match based on user name with regular expression";
      leaf-list name {
        type string {
          length "1..32";
        }
        description
          "User name with regular expression";
      }
    }
  }

  grouping live_ncs_policy-map-common {
    leaf policy-map-name {
      type string;
      description
        "Name of the policymap";
    }
    leaf description {
      type string;
      description
        "Set description for this policy-map";
    }
  }

  grouping live_ncs_policy-action-compress {
    container compress {
      // NCS drop if-feature statement
      description
        "Configure compress action";
      container header {
        description
          "Configure header compression";
        container ip {
          presence "Configure IP header compression";
          description
            "Configure IP header compression";
        }
      }
    }
  }

  grouping live_ncs_policy-action-encap-sequence {
    leaf encap-sequence {
      // NCS drop if-feature statement
      type union {
        type uint8 {
          range "1..15" {
            description
              "Encapsulation sequence number";
          }
        }
        type enumeration {
          enum "none" {
            value 0;
            description
              "Encapsulation sequence none";
          }
        }
      }
      description
        "Configure encapsulation sequence";
    }
  }

  grouping live_ncs_aaa-method {
    container aaa {
      description
        "AAA specification";
      leaf list {
        type union {
          type string;
          type enumeration {
            enum "default" {
              value 0;
              description
                "default AAA method list";
            }
          }
        }
        description
          "Specify AAA method list that authentication should be made with";
      }
    }
  }

  grouping live_ncs_subscriber-actions {
    container activate {
      description
        "Activate";
      container dynamic-template {
        description
          "actions related to dynamic templates";
        leaf template-name {
          type string;
          description
            "Dynamic template name";
        }
        uses live_ncs_aaa-method;
      }
    }
    container deactivate {
      description
        "Deactivate";
      container dynamic-template {
        description
          "actions related to dynamic templates";
        leaf template-name {
          type string;
          description
            "Dynamic template name";
        }
        uses live_ncs_aaa-method;
      }
    }
    container authenticate {
      // NCS drop if-feature statement
      description
        "Authentication related configuration";
      uses live_ncs_aaa-method;
    }
    container authorize {
      // NCS drop if-feature statement
      description
        "Authorize";
      uses live_ncs_aaa-method;
      leaf format {
        type string;
        description
          "Specify an Authorize format name";
      }
      leaf identifier {
        type enumeration {
          enum "circuit-id" {
            value 0;
            description
              "Authorize circuit ID";
          }
          enum "dhcp-client-id" {
            value 1;
            description
              "Authorize dhcp client ID";
          }
          enum "remote-id" {
            value 2;
            description
              "Authorize remote ID";
          }
          enum "service-name" {
            value 3;
            description
              "Authorize Service Name";
          }
          enum "source-address-ipv4" {
            value 4;
            description
              "Authorize source IPv4 address";
          }
          enum "source-address-ipv6" {
            value 5;
            description
              "Authorize source IPv6 address";
          }
          enum "source-address-mac" {
            value 6;
            description
              "Authorize source MAC address";
          }
          enum "username" {
            value 7;
            description
              "Authorize username";
          }
        }
        description
          "Specify an Authorize identifier";
      }
      leaf password {
        type union {
          type live_ncs_clear-text-password-type;
          type enumeration {
            enum "blank" {
              value 0;
              description
                "use blank password";
            }
            enum "use-from-line" {
              value 1;
              description
                "use from line";
            }
          }
        }
        description
          "Specify a password to be used for AAA request";
      }
    }
    container disconnect {
      // NCS drop if-feature statement
      presence "Disconnect session";
      description
        "Disconnect session";
    }
    container monitor {
      // NCS drop if-feature statement
      presence "Monitor session";
      description
        "Monitor session";
    }
    container set-timer {
      // NCS drop if-feature statement
      // NCS drop must statement
      presence "indicates set-timer is configured";
      description
        "Set a timer to execute a rule on its expiry";
      leaf name {
        type string;
        description
          "Name of the timer";
      }
      leaf value {
        type uint32 {
          range "1..4294967295" {
            description
              "Timer value in minutes";
          }
        }
        units "minutes";
      }
    }
    container stop-timer {
      // NCS drop if-feature statement
      description
        "Disable timer before it expires";
      leaf name {
        type string;
        description
          "Name of the timer";
      }
    }
  }

  grouping live_ncs_pbr-actions {
    container drop {
      presence "Drop the packet";
      description
        "Drop the packet";
    }
    leaf http-redirect {
      // NCS drop if-feature statement
      type string;
      description
        "Configure HTTP redirect. Specify the URL HTTP requests should be redirected to";
    }
    container http-enrichment {
      // NCS drop if-feature statement
      description
        "Configure HTTP enrichment";
      container subscriber-mac {
        presence "Subscriber MAC address";
        description
          "Subscriber MAC address";
      }
      container subscriber-ip {
        presence "Subscriber ipv4/ipv6 address";
        description
          "Subscriber ipv4/ipv6 address";
      }
      container hostname {
        presence "Hostname";
        description
          "Hostname";
      }
      container bng-interface {
        presence "BNG identifier interface";
        description
          "BNG identifier interface";
      }
    }
    container police {
      description
        "Police traffic";
      container rate {
        // NCS drop must statement
        presence "indicates rate is configured";
        description
          "Committed Information Rate";
        leaf value {
          type uint32 {
            range "1..4294967295" {
              description
                "Committed Information Rate";
            }
          }
        }
        leaf unit {
          type live_ncs_rate-unit-type;
        }
      }
    }
    container redirect-ipv4 {
      // NCS drop if-feature statement
      description
        "Configure PBF redirect feature with IPv4 configurations";
      container default-route {
        presence "Forward to the default nexthop";
        description
          "Forward to the default nexthop";
      }
      container nexthop1 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
    }
    container redirect-ipv6 {
      // NCS drop if-feature statement
      description
        "Configure PBF redirect feature with IPv6 configurations";
      container default-route {
        presence "Forward to the default nexthop";
        description
          "Forward to the default nexthop";
      }
      container nexthop1 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
    }
    container redirect-nexthop {
      // NCS drop if-feature statement
      description
        "Configure PBF redirect feature with forwarding to specified nexthop";
      container route-target {
        // NCS drop must statement
        presence "indicates route-target is configured";
        description
          "Enter specific route-target string";
        leaf address {
          type inet:ipv4-address-no-zone;
          description
            "IPv4 address.";
        }
        leaf index {
          type uint16 {
            range "0..65535" {
              description
                "IPv4 Address:index";
            }
          }
          description
            "IPv4 Address:index";
        }
        leaf as-number {
          type union {
            type string {
              pattern '([1-9][0-9]{0,4}):(0|[1-9][0-9]{0,4})' {
                description
                  "<1-65535>:<0-65535> 2-byte AS number";
              }
            }
            type string {
              pattern '(65536:|[1-9][0-9]{0,10}:)(0|[1-9][0-9]{0,4})' {
                description
                  "<65536-4294967295>:<0-65535> 4-byte AS number in asplain format";
              }
            }
          }
          description
            "AS number";
        }
      }
    }
    container service-function-path {
      // NCS drop if-feature statement
      description
        "Configure NSH service function action";
      leaf path-id {
        type uint32 {
          range "1..16777215";
        }
        // NCS drop must statement
        description
          "Service function path id";
      }
      leaf index {
        type uint8 {
          range "1..255" {
            description
              "Service function path index";
          }
        }
        // NCS drop must statement
        description
          "Specify service path index";
      }
      leaf metadata {
        type string;
        // NCS drop must statement
        description
          "service-function metadata";
      }
    }
    container set {
      description
        "Configure marking for this class";
      container destination-address {
        // NCS drop if-feature statement
        description
          "Set Destination address";
        leaf ipv4 {
          type inet:ipv4-address;
          description
            "IPv4 address";
        }
      }
      leaf df {
        // NCS drop if-feature statement
        type uint8 {
          range "0..1" {
            description
              "DF bit";
          }
        }
        description
          "Set DF bit";
      }
      leaf dscp {
        type live_ncs_dscp-value;
        description
          "Set DSCP";
      }
      leaf forward-class {
        // NCS drop if-feature statement
        type uint8 {
          range "1..7" {
            description
              "Forward class value";
          }
        }
        description
          "Set forward class";
      }
      container source-address {
        // NCS drop if-feature statement
        description
          "Set Source address";
        leaf ipv4 {
          type inet:ipv4-address;
          description
            "IPv4 address";
        }
      }
    }
    container transmit {
      // NCS drop if-feature statement
      presence "Forward packet to the original destination";
      description
        "Forward packet to the original destination";
    }
    container decapsulate {
      // NCS drop if-feature statement
      description
        "Decapsulate GRE packet";
      container gre {
        presence "Decapsulate GRE packet";
        description
          "Decapsulate GRE packet";
      }
    }
  }

  grouping live_ncs_performance-traffic-actions {
    uses live_ncs_policy-action-compress;
    uses live_ncs_policy-action-encap-sequence;
    list react {
      // NCS drop if-feature statement
      key "operation-id";
      description
        "Generate alert on the specified event";
      leaf operation-id {
        type uint32 {
          range "1..4294967294";
        }
        description
          "Specify an operation id (num)";
      }
      container delay-factor {
        presence "React criterion delay factor of policy-map action.";
        description
          "React criterion delay factor of policy-map action.";
      }
      container media-stop {
        presence "React criterion media stop of policy-map action.";
        description
          "React criterion media stop of policy-map action.";
      }
      container mrv {
        presence "React criterion mrv of policy-map action.";
        description
          "React criterion mrv of policy-map action.";
      }
      container flow-count {
        presence "React criterion flow count of policy-map action.";
        description
          "React criterion flow count of policy-map action.";
      }
      container packet-rate {
        presence "React criterion packet rate of the policy-map action.";
        description
          "React criterion packet rate of the policy-map action.";
      }
      leaf description {
        type string;
        description
          "Set Description for this alert action";
      }
      container trigger {
        description
          "Set the event trigger";
        container value {
          // NCS drop must statement
          presence "indicates value is configured";
          description
            "Set the trigger criterion";
          leaf lt {
            type live_ncs_trigger-value;
            description
              "trigger only if metric is less than the given value";
          }
          leaf le {
            type live_ncs_trigger-value;
            description
              "trigger only if metric is less than or equal to the given value";
          }
          leaf gt {
            type live_ncs_trigger-value;
            description
              "trigger only if metric is greater than the given value";
          }
          leaf ge {
            type live_ncs_trigger-value;
            description
              "trigger only if metric is greater than or equal to the given value";
          }
          leaf range {
            type live_ncs_trigger-value;
            description
              "trigger only if metric is in the inclusive range";
          }
        }
        container type {
          // NCS drop must statement
          presence "indicates type is configured";
          description
            "Set the trigger type";
          container immediate {
            presence "Immediate trigger";
            description
              "Immediate trigger";
          }
          leaf average {
            type uint32 {
              range "1..60";
            }
            description
              "Trigger averaged over N intervals.";
          }
        }
      }
      container action {
        description
          "Set the event action";
        container syslog {
          presence "Report via syslog";
          description
            "Report via syslog";
        }
        container snmp {
          // NCS drop if-feature statement
          presence "Report via syslog";
          description
            "Report via syslog";
        }
      }
      container alarm {
        // NCS drop if-feature statement
        description
          "Configure alarms";
        container type {
          // NCS drop must statement
          presence "indicates type is configured";
          description
            "Set the alarm type";
          container discrete {
            presence "Discrete alarms";
            description
              "Discrete alarms";
          }
          container grouped {
            // NCS drop if-feature statement
            description
              "Grouped alarms";
            leaf count {
              type uint16 {
                range "1..65535" {
                  description
                    "Number of flows with alarm";
                }
              }
              units "number of flows";
              // NCS drop must statement
              description
                "Grouped on num-flows";
            }
            leaf percent {
              type uint8 {
                range "1..100" {
                  description
                    "Percentage of flows with alarm";
                }
              }
              units "percentage";
              // NCS drop must statement
              description
                "Grouped on percentage of flows";
            }
          }
        }
        leaf severity {
          type enumeration {
            enum "error" {
              value 0;
              description
                "Error level alarm";
            }
            enum "critical" {
              value 1;
              description
                "Critical level alarm";
            }
            enum "alert" {
              value 2;
              description
                "Alert level alarm";
            }
            enum "emergency" {
              value 3;
              description
                "Emergency level alarm";
            }
          }
          description
            "Set the alarm severity";
        }
      }
    }
  }

  grouping live_ncs_action-common {
    leaf cos {
      type uint8 {
        range "0..7";
      }
      description
        "Sets the specific IEEE 802.1Q Layer 2 CoS value of an
         outgoing packet.
         This command should be used by a router if a user wants
         to mark a packet that is being sent to a switch.
         Switches can leverage Layer 2 header information,
         including a CoS value marking. Packets entering an
         interface cannot be set with a CoS value.";
    }
    leaf cos-inner {
      type uint8 {
        range "0..7";
      }
      description
        "Set inner COS";
    }
    leaf dei {
      type uint8 {
        range "0..1";
      }
      description
        "Set DEI";
    }
    leaf dei-imposition {
      type uint8 {
        range "0..1";
      }
      description
        "Set DEI imposition bit.";
    }
    leaf discard-class {
      type uint8 {
        range "0..7" {
          description
            "discard-class value";
        }
      }
      description
        "Sets the discard class on IPv4 or MPLS packets.
         The discard-class can be used only in service policies
         that are attached in the ingress policy.";
    }
    leaf dscp {
      type live_ncs_dscp-value;
      description
        "Set IP DSCP (DiffServ CodePoint)";
    }
    leaf dscp-tunnel {
      type live_ncs_dscp-value;
      description
        "Set DSCP Tunnel(for ipsec tunnels)";
    }
    leaf fr-de {
      // NCS drop if-feature statement
      type uint8 {
        range "0..1";
      }
      description
        "Set frame relay discard-eligible bit";
    }
    container mpls {
      description
        "Set MPLS specific values";
      container experimental {
        description
          "Set experimental";
        leaf imposition {
          type uint8 {
            range "0..7";
          }
          description
            "Sets the experimental value of the MPLS packet
             imposition labels.
             Imposition can be used only in service policies that
             are attached in the ingress policy";
        }
        leaf topmost {
          type uint8 {
            range "0..7";
          }
          description
            "Sets the experimental value of the MPLS packet top-most
             labels.";
        }
      }
    }
    leaf precedence {
      type live_ncs_precedence-type;
      description
        "Set IP Precedence";
    }
    leaf precedence-tunnel {
      type live_ncs_precedence-type;
      description
        "Set Precedence tunnel(for ipsec tunnels)";
    }
    leaf qos-group {
      type uint16 {
        range "0..512" {
          description
            "QoS group value";
        }
      }
      description
        "Sets the QoS group identifiers on IPv4 or MPLS packets.
         The set qos-group is supported only on an ingress policy.";
    }
  }

  grouping live_ncs_police-actions {
    container transmit {
      presence "Transmit packet";
      description
        "Transmit packet";
    }
    container drop {
      presence "Drop packet";
      description
        "Drop packet";
    }
    container set {
      description
        "Conditional marking";
      uses live_ncs_action-common;
    }
  }

  grouping live_ncs_qos-actions {
    container admit {
      // NCS drop if-feature statement
      description
        "Call admission control";
      container cac {
        description
          "Call admission control (CAC) functionality";
        container local {
          // NCS drop must statement
          presence "indicates local is configured";
          description
            "CAC local flow type (default type)";
          container flow {
            description
              "Flow attributes";
            leaf idle-timeout {
              type union {
                type uint16 {
                  range "10..2550" {
                    description
                      "The idle timeout period (in seconds)";
                  }
                }
                type enumeration {
                  enum "None" {
                    value 0;
                    description
                      "The flow does not expire";
                  }
                }
              }
              description
                "Maximum time of inactivity for a flow";
            }
            container rate {
              // NCS drop must statement
              presence "indicates rate is configured";
              description
                "Per flow rate";
              leaf value {
                type uint32 {
                  range "1..4294967294" {
                    description
                      "Committed per flow rate";
                  }
                }
              }
              leaf unit {
                type live_ncs_cac-unit-type;
              }
            }
          }
          container rate {
            // NCS drop must statement
            presence "indicates rate is configured";
            description
              "Maximum rate for all flows";
            leaf value {
              type uint32 {
                range "1..4294967294" {
                  description
                    "Committed aggregate rate for all flows";
                }
              }
            }
            leaf unit {
              type live_ncs_cac-unit-type;
            }
          }
        }
      }
    }
    container bandwidth {
      // NCS drop if-feature statement
      // NCS drop must statement
      presence "indicates bandwidth is configured";
      description
        "Configure bandwidth for this class";
      leaf value {
        type union {
          type uint32 {
            range "1..4294967295" {
              description
                "Bandwidth value";
            }
          }
          type uint16 {
            range "1..1000" {
              description
                "Parts per-thousand bandwidth value";
            }
          }
          type uint32 {
            range "1..1000000" {
              description
                "Parts per-million bandwidth value";
            }
          }
          type uint32 {
            range "1..100" {
              description
                "Percentage bandwidth value";
            }
          }
        }
      }
      leaf unit {
        type enumeration {
          enum "bps" {
            value 0;
            description
              "Bits per second";
          }
          enum "gbps" {
            value 1;
            description
              "Gigabits per second";
          }
          enum "kbps" {
            value 2;
            description
              "Kilobits per second";
          }
          enum "mbps" {
            value 3;
            description
              "Megabits per second";
          }
          enum "cellsps" {
            value 4;
            description
              "Cells per second";
          }
          enum "per-thousand" {
            value 5;
            description
              "configure parts per-thousand bandwidth";
          }
          enum "per-million" {
            value 6;
            description
              "configure parts per-million bandwidth";
          }
          enum "percent" {
            value 7;
            description
              "configure a percentage bandwidth";
          }
        }
      }
    }
    container bandwidth-remaining {
      // NCS drop if-feature statement
      // NCS drop must statement
      presence "indicates bandwidth-remaining is configured";
      description
        "Allocate left over bandwidth";
      leaf unit {
        type enumeration {
          enum "percent" {
            value 0;
            description
              "Allocate remaining bandwidth as percentage";
          }
          enum "ratio" {
            value 1;
            description
              "Allocate remaining bandwidth as a ratio";
          }
        }
        description
          "Bandwidth value unit";
      }
      leaf value {
        type union {
          type uint8 {
            range "1..100" {
              description
                "Percentage bandwidth value";
            }
          }
          type uint32 {
            range "1..4294967295" {
              description
                "Bandwidth ratio";
            }
          }
        }
        description
          "Bandwidth value";
      }
    }
    uses live_ncs_policy-action-compress;
    uses live_ncs_policy-action-encap-sequence;
    leaf fragment {
      // NCS drop if-feature statement
      type string {
        length "1..64" {
          description
            "Reference to a Service fragment";
        }
      }
      description
        "Refer to an existing service fragment. Reference to a Service fragment.";
    }
    container pause {
      // NCS drop if-feature statement
      presence "Configure PFC feature";
      description
        "Configure PFC feature";
      container buffer-size {
        // NCS drop must statement
        presence "indicates buffer-size is configured";
        description
          "Configure buffer size";
        leaf value {
          type uint32 {
            range "1..4294967295";
          }
          description
            "Range of buffer size";
        }
        leaf unit {
          type live_ncs_pfc-unit-type;
        }
      }
      container pause-threshold {
        // NCS drop must statement
        presence "indicates pause-threshold is configured";
        description
          "Configure pasue threshold";
        leaf value {
          type uint32 {
            range "1..4294967295";
          }
          description
            "Range of pause threshold";
        }
        leaf unit {
          type live_ncs_pfc-unit-type;
        }
      }
      container resume-threshold {
        // NCS drop must statement
        presence "indicates resume-threshold is configured";
        description
          "Configure resume threshold";
        leaf value {
          type uint32 {
            range "1..4294967295";
          }
          description
            "Range of resume threshold";
        }
        leaf unit {
          type live_ncs_pfc-unit-type;
        }
      }
    }
    container police {
      description
        "Police traffic";
      container conditional {
        presence "Conditional policer for priority traffic";
        description
          "Conditional policer for priority traffic";
      }
      container rate {
        // NCS drop must statement
        presence "indicates rate is configured";
        description
          "Committed Information Rate";
        leaf value {
          type union {
            type uint32 {
              range "1..4294967295";
            }
            type uint8 {
              range "1..100" {
                description
                  "Committed Information Rate in percentage of link bandwidth";
              }
            }
            type uint16 {
              range "1..1000" {
                description
                  "Committed Information Rate in per-thousand of link bandwidth";
              }
            }
            type uint32 {
              range "1..1000000" {
                description
                  "Committed Information Rate in per-million of link bandwidth";
              }
            }
          }
          description
            "Committed Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
            enum "per-thousand" {
              value 7;
              description
                "Parts per-thousand of the link bandwidth";
            }
            enum "per-million" {
              value 8;
              description
                "Parts per-million of the link bandwidth";
            }
          }
          description
            "Rate unit";
        }
      }
      container burst {
        description
          "Burst size (BC)";
        leaf value {
          type uint32 {
            range "1..4294967295";
          }
          description
            "Burst size (BC)";
        }
        leaf unit {
          type live_ncs_burst-unit-type;
          description
            "Burst size unit";
        }
      }
      container peak-burst {
        // NCS drop if-feature statement
        description
          "Excess Burst size (BE)";
        leaf value {
          type uint32 {
            range "1..4294967295";
          }
          description
            "Exess burst size (BC)";
        }
        leaf unit {
          type live_ncs_burst-unit-type;
          description
            "Burst size unit";
        }
      }
      container peak-rate {
        // NCS drop must statement
        presence "indicates peak-rate is configured";
        description
          "Peak Information Rate";
        leaf value {
          type union {
            type uint32 {
              range "1..4294967295";
            }
            type uint8 {
              range "1..100" {
                description
                  "Committed Information Rate in percentage of link bandwidth";
              }
            }
          }
          description
            "Peak Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
          }
        }
      }
      container conform-action {
        description
          "Action for conforming traffic";
        uses live_ncs_police-actions;
      }
      container exceed-action {
        description
          "Action for exceeding traffic";
        uses live_ncs_police-actions;
      }
      container violate-action {
        description
          "Action for violating traffic";
        uses live_ncs_police-actions;
      }
      leaf conform-color {
        // NCS drop if-feature statement
        type string;
        description
          "Configure conform color class for color aware policing. Conform color class name.";
      }
      leaf exceed-color {
        // NCS drop if-feature statement
        type string;
        description
          "Configure exceed color class for color aware policing. Exceed color class name.";
      }
      container child-conform-aware {
        // NCS drop if-feature statement
        presence "Enable coupled policing";
        description
          "Enable coupled policing";
      }
    }
    container priority {
      description
        "Assign priority to this class";
      leaf level {
        type uint8 {
          range "1..7" {
            description
              "Priority level";
          }
        }
        description
          "Configure a priority level";
      }
    }
    container queue-limits {
      description
        "Queue Limit Node";
      list queue-limit {
        key "value unit";
        description
          "Configure queue-limit (taildrop threshold) for this class";
        leaf value {
          type union {
            type uint32 {
              range "1..4294967295" {
                description
                  "Max Threshold for tail drop";
              }
            }
            type uint8 {
              range "1..100" {
                description
                  "Percentage value";
              }
            }
          }
          description
            "queue-limit value";
        }
        leaf unit {
          type enumeration {
            enum "bytes" {
              value 0;
              description
                "Bytes";
            }
            enum "kbytes" {
              value 1;
              description
                "Kilobytes";
            }
            enum "mbytes" {
              value 2;
              description
                "Megabytes";
            }
            enum "ms" {
              value 3;
              description
                "Milliseconds";
            }
            enum "packets" {
              value 4;
              description
                "Packets (default)";
            }
            enum "us" {
              value 5;
              description
                "Microseconds";
            }
            enum "percent" {
              value 6;
              description
                "Configure queue limit value in percentage";
            }
          }
          description
            "queue-limit unit";
        }
        container discard-classes {
          description
            "discard class container";
          leaf-list discard-class {
            type uint8 {
              range "0..7";
            }
            description
              "Remaining bandwidth value.";
          }
        }
      }
    }
    container random-detect-default {
      presence "Enable RED with default min and max thresholds";
      description
        "Enable RED with default min and max thresholds";
    }
    container random-detect-ecn {
      presence "Enable ECN based WRED";
      description
        "ECN based WRED";
    }
    list random-detect {
      key "minimum-threshold-value minimum-threshold-unit maximum-threshold-value maximum-threshold-unit";
      description
        "Enable Random Early Detection.
         All RED profiles in a class must be based
         on the same field.";
      leaf minimum-threshold-value {
        type uint32 {
          range "0..1073741823";
        }
        description
          "Minimum threshold";
      }
      leaf minimum-threshold-unit {
        type live_ncs_wred-unit-type;
        description
          "threshold unit";
      }
      leaf maximum-threshold-value {
        type uint32 {
          range "0..1073741823";
        }
        description
          "Maximum threshold";
      }
      leaf maximum-threshold-unit {
        type live_ncs_wred-unit-type;
        description
          "threshold unit";
      }
      leaf-list cos {
        type uint8 {
          range "0..7" {
            description
              "COS  value";
          }
        }
        // NCS drop max-elements statement
        description
          "COS based WRED (upto 8 values)";
      }
      leaf-list dei {
        type uint8 {
          range "0..1" {
            description
              "DEI value";
          }
        }
        // NCS drop max-elements statement
        description
          "DEI based WRED";
      }
      leaf-list discard-class {
        type uint8 {
          range "0..7" {
            description
              "Discard Class  value";
          }
        }
        // NCS drop max-elements statement
        description
          "Discard Class based WRED";
      }
      leaf-list dscp {
        type live_ncs_dscp-value;
        // NCS drop max-elements statement
        description
          "DSCP based WRED";
      }
      leaf-list exp {
        type uint8 {
          range "0..7" {
            description
              "MPLS Experimental  value";
          }
        }
        // NCS drop max-elements statement
        description
          "MPLS Experimental value based WRED";
      }
      leaf-list precedence {
        type union {
          type uint8 {
            range "0..7" {
              description
                "Precedence value";
            }
          }
          type enumeration {
            enum "critical" {
              value 0;
              description
                "Critical precedence (5)";
            }
            enum "flash" {
              value 1;
              description
                "Flash precedence (3)";
            }
            enum "flash-override" {
              value 2;
              description
                "Flash override precedence (4)";
            }
            enum "immediate" {
              value 3;
              description
                "Immediate precedence (2)";
            }
            enum "internet" {
              value 4;
              description
                "Internetwork control precedence (6)";
            }
            enum "network" {
              value 5;
              description
                "Network control precedence (7)";
            }
            enum "priority" {
              value 6;
              description
                "Priority precedence (1)";
            }
            enum "routine" {
              value 7;
              description
                "Routine precedence (0)";
            }
          }
        }
        // NCS drop max-elements statement
        description
          "Precedence based WRED";
      }
    }
    leaf service-fragment {
      // NCS drop if-feature statement
      type string {
        length "1..64" {
          description
            "Name of Service fragment";
        }
      }
      description
        "Define a service fragment. Name of Service fragment";
    }
    container service-policy {
      description
        "Configure a child service policy";
      leaf name {
        type live_ncs_service-policy-name-type;
        description
          "Name of the child service policy";
      }
      leaf type {
        type enumeration {
          enum "pbr" {
            value 0;
            description
              "PBR policy-map";
          }
          enum "performance-traffic" {
            value 1;
            description
              "Performance traffic policy-map";
          }
          enum "qos" {
            value 2;
            description
              "QoS policy-map (default)";
          }
          enum "redirect" {
            value 3;
            description
              "Redirect policy-map";
          }
          enum "traffic" {
            value 4;
            description
              "Traffic policy-map";
          }
        }
        description
          "The type of policy-map";
      }
    }
    container set {
      description
        "Configure marking for this class";
      container atm-clp {
        // NCS drop if-feature statement
        presence "Set atm cell-loss-priority bit";
        description
          "Set atm cell-loss-priority bit";
      }
      leaf traffic-class {
        // NCS drop if-feature statement
        type uint8 {
          range "0..8" {
            description
              "Traffic class value";
          }
        }
        description
          "Sets the Traffic Class identifiers on IPv4 or MPLS packets.
           The set traffic-class is supported only on an ingress policy.";
      }
      leaf forward-class {
        // NCS drop if-feature statement
        type uint8 {
          range "1..7" {
            description
              "Forward class value";
          }
        }
        description
          "Set forward class";
      }
      uses live_ncs_action-common;
    }
    container shape {
      description
        "Configure shaping for this class";
      container average {
        description
          "Average rate shaping";
        container rate {
          // NCS drop must statement
          presence "indicates rate is configured";
          description
            "Shape rate";
          leaf value {
            type union {
              type uint32 {
                range "1..4294967295" {
                  description
                    "Shape rate";
                }
              }
              type uint16 {
                range "1..1000" {
                  description
                    "Shape rate as parts per-thousand of available bandwidth";
                }
              }
              type uint32 {
                range "1..1000000" {
                  description
                    "Shape rate as parts per-million of available bandwidth";
                }
              }
              type uint8 {
                range "1..100" {
                  description
                    "Shape rate as percentage of available bandwidth";
                }
              }
              type string {
                pattern '[$][a-zA-Z0-9][a-zA-Z0-9\._@%+:\-]{0,32}[ ][=][ ]\d{1,10}';
              }
            }
          }
          leaf unit {
            type enumeration {
              enum "bps" {
                value 0;
                description
                  "Bits per second";
              }
              enum "cellsps" {
                value 1;
                description
                  "Cells per second";
              }
              enum "gbps" {
                value 2;
                description
                  "Gigabits per second";
              }
              enum "kbps" {
                value 3;
                description
                  "Kilobits per second";
              }
              enum "mbps" {
                value 4;
                description
                  "Megabits per second";
              }
              enum "per-thousand" {
                value 5;
                description
                  "Configure shape rate in per-thousand";
              }
              enum "per-million" {
                value 6;
                description
                  "Configure shape rate in per-million";
              }
              enum "percent" {
                value 7;
                description
                  "Configure shape rate in percentage";
              }
            }
            description
              "Shape rate unit";
          }
        }
        container excess-burst {
          // NCS drop if-feature statement
          // NCS drop must statement
          presence "indicates excess-burst is configured";
          description
            "Excess burst size";
          leaf size {
            type uint32 {
              range "1..4294967295" {
                description
                  "Excess burst size";
              }
            }
          }
          leaf unit {
            type enumeration {
              enum "bytes" {
                value 0;
                description
                  "Bytes";
              }
              enum "cells" {
                value 1;
                description
                  "Cells";
              }
              enum "gbytes" {
                value 2;
                description
                  "Gigabytes";
              }
              enum "kbytes" {
                value 3;
                description
                  "Kilobytes";
              }
              enum "mbytes" {
                value 4;
                description
                  "Megabytes";
              }
              enum "ms" {
                value 5;
                description
                  "Milliseconds";
              }
              enum "packets" {
                value 6;
                description
                  "Packets";
              }
              enum "us" {
                value 7;
                description
                  "Microseconds";
              }
            }
          }
        }
      }
    }
  }

  grouping live_ncs_redirect-actions {
    uses live_ncs_policy-action-compress;
    uses live_ncs_policy-action-encap-sequence;
    container priority {
      presence "Test command";
      description
        "Test command";
    }
  }

  grouping class-map-common {
    leaf class-map-name {
      type string {
        pattern '[a-zA-Z0-9][a-zA-Z0-9\._@$%+#:=<>\-]{0,62}' {
          description
            "Any string except 'type'";
        }
      }
      description
        "Name of the class-map";
    }
    container match-all {
      presence "Match all match criteria";
      description
        "Match all match criteria";
    }
    container match-any {
      presence "Match any match criteria (default)";
      description
        "Match any match criteria (default)";
    }
    leaf description {
      type string;
      description
        "Set description for this class-map";
    }
  }

  grouping match-access-group {
    container access-group {
      description
        "Match access group";
      leaf-list ipv4 {
        tailf:display-when "not(../../ncs:module) or boolean(/ncs:devices/ncs:device[ncs:name=current()/../../ncs:name]/capability/feature='match-ipv4-acl')";
        type acl-list-name-type;
        description
          "IPv4 access list";
      }
      leaf-list ipv6 {
        tailf:display-when "not(../../ncs:module) or boolean(/ncs:devices/ncs:device[ncs:name=current()/../../ncs:name]/capability/feature='match-ipv6-acl')";
        type acl-list-name-type;
        description
          "IPv6 access list";
      }
      leaf-list ethernet-services {
        tailf:display-when "not(../../ncs:module) or boolean(/ncs:devices/ncs:device[ncs:name=current()/../../ncs:name]/capability/feature='match-ethernet-services-acl')";
        type acl-list-name-type;
        description
          "Ethernet-Services";
      }
    }
  }

  grouping match-atm {
    container atm {
      tailf:display-when "not(../ncs:module) or boolean(/ncs:devices/ncs:device[ncs:name=current()/../ncs:name]/capability/feature='match-atm')";
      description
        "Match based on ATM specific criteria";
      leaf-list clp {
        type uint8 {
          range "0..1";
        }
        max-elements 2;
        ordered-by user;
        description
          "Match ATM CLP bit";
      }
      container oam {
        presence "Match ATM OAM";
        description
          "Match ATM OAM";
      }
    }
  }

  grouping match-cac {
    container cac {
      tailf:display-when "not(../ncs:module) or boolean(/ncs:devices/ncs:device[ncs:name=current()/../ncs:name]/capability/feature='match-cac')";
      description
        "Match based on CAC fields";
      container admitted {
        presence "Match packets admitted by CAC action";
        description
          "Match packets admitted by CAC action";
      }
      container unadmitted {
        presence "Match packets unadmitted by CAC action";
        description
          "Match packets unadmitted by CAC action";
      }
    }
  }

  grouping match-cos {
    container cos {
      tailf:display-when "not(../ncs:module) or boolean(/ncs:devices/ncs:device[ncs:name=current()/../ncs:name]/capability/feature='match-cos')";
      description
        "Match based on IEEE 802.1Q/ISL Class Of Service value";
      leaf-list value {
        type uint8 {
          range "0..7";
        }
        max-elements 8;
        description
          "COS value";
      }
    }
    container cos-inner {
      tailf:display-when "not(../ncs:module) or boolean(/ncs:devices/ncs:device[ncs:name=current()/../ncs:name]/capability/feature='match-cos-inner')";
      description
        "Match inner cos values";
      leaf-list value {
        type uint8 {
          range "0..7";
        }
        max-elements 8;
        description
          "inner cos value (Upto 8 values)";
      }
    }
  }

  grouping match-dei {
    leaf dei {
      tailf:display-when "not(../ncs:module) or boolean(/ncs:devices/ncs:device[ncs:name=current()/../ncs:name]/capability/feature='match-dei')";
      type uint8 {
        range "0..1" {
          description
            "DEI value";
        }
      }
      must 'not(../dei-inner)' {
        tailf:xpath-root 3;
      }
      description
        "Match based on DEI bit (0/1)";
    }
    leaf dei-inner {
      tailf:display-when "not(../ncs:module) or boolean(/ncs:devices/ncs:device[ncs:name=current()/../ncs:name]/capability/feature='match-dei-inner')";
      type uint8 {
        range "0..1" {
          description
            "DEI value";
        }
      }
      must 'not(../dei)' {
        tailf:xpath-root 3;
      }
      description
        "Match inner based on DEI bit (0/1)";
    }
  }

  grouping match-destination-address {
    container destination-address {
      description
        "Match based on destination address";
      container ipv4 {
        tailf:display-when "not(../../ncs:module) or boolean(/ncs:devices/ncs:device[ncs:name=current()/../../ncs:name]/capability/feature='match-dst-addr-ipv4')";
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        tailf:display-when "not(../../ncs:module) or boolean(/ncs:devices/ncs:device[ncs:name=current()/../../ncs:name]/capability/feature='match-dst-addr-ipv6')";
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='match-dst-mac')";
        type yang:mac-address;
        description
          "MAC Address";
      }
    }
  }

  grouping matchnot-destination-address {
    container destination-address {
      description
        "Match based on destination address";
      container ipv4 {
        description
          "Match based on destination IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on destination IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='matchnot-mac-address')";
        type yang:mac-address;
        description
          "MAC Address";
      }
    }
  }

  grouping match-destination-port {
    container destination-port {
      tailf:display-when "not(../ncs:module) or boolean(/ncs:devices/ncs:device[ncs:name=current()/../ncs:name]/capability/feature='match-destination-port')";
      description
        "Match based on destination port";
      leaf-list port-number {
        type port-number-type;
        max-elements 5;
        description
          "destination port";
      }
    }
  }

  grouping match-discard-class {
    container discard-class {
      tailf:display-when "not(../ncs:module) or boolean(/ncs:devices/ncs:device[ncs:name=current()/../ncs:name]/capability/feature='match-discard-class')";
      description
        "Match based on discard class";
      leaf-list id {
        type uint8 {
          range "0..7";
        }
        max-elements 8;
        description
          "Discard CLass Id";
      }
    }
  }

  grouping match-dscp {
    container dscp {
      tailf:display-when "not(../ncs:module) or boolean(/ncs:devices/ncs:device[ncs:name=current()/../ncs:name]/capability/feature='match-dscp')";
      description
        "Match based on IP DSCP value";
      leaf-list value {
        type dscp-value;
        description
          "DSCP value";
      }
    }
    container dscp-ipv4 {
      tailf:display-when "not(../ncs:module) or boolean(/ncs:devices/ncs:device[ncs:name=current()/../ncs:name]/capability/feature='match-ipv4-dscp')";
      description
        "Match based on IPv4 DSCP value";
      leaf-list value {
        type dscp-value;
        description
          "DSCP value";
      }
    }
    container dscp-ipv6 {
      tailf:display-when "not(../ncs:module) or boolean(/ncs:devices/ncs:device[ncs:name=current()/../ncs:name]/capability/feature='match-ipv6-dscp')";
      description
        "Match based on IPv6 DSCP value";
      leaf-list value {
        type dscp-value;
        description
          "DSCP value";
      }
    }
  }

  grouping match-ethertype {
    container ethertype {
      tailf:display-when "not(../ncs:module) or boolean(/ncs:devices/ncs:device[ncs:name=current()/../ncs:name]/capability/feature='match-ethertype')";
      description
        "Match based on ethertype";
      leaf-list value {
        type union {
          type uint16 {
            range "1536..65535";
          }
          type enumeration {
            enum "arp" {
              value 0;
              description
                "Any ARP Ethertype";
            }
            enum "ipv4" {
              value 1;
              description
                "Any IPv4 Ethertype";
            }
            enum "ipv6" {
              value 2;
              description
                "Any IPv6 Ethertype";
            }
          }
        }
        max-elements 8;
        description
          "Ethertype Value";
      }
    }
  }

  grouping match-flow-key {
    container flow-key {
      tailf:display-when "not(../ncs:module) or boolean(/ncs:devices/ncs:device[ncs:name=current()/../ncs:name]/capability/feature='match-flow-key')";
      description
        "Match based on flow keys";
      container five-tuple {
        must 'not(../dst-ip or ../src-ip)' {
          tailf:xpath-root 3;
        }
        presence "Five tuples to identify a flow";
        description
          "Five tuples to identify a flow";
      }
      container dst-ip {
        must 'not(../five-tuple)' {
          tailf:xpath-root 3;
        }
        presence "Destination IP address";
        description
          "Destination IP address";
      }
      container src-ip {
        must 'not(../five-tuple)' {
          tailf:xpath-root 3;
        }
        presence "Source IP address";
        description
          "Source IP address";
      }
      container flow-cache {
        description
          "Configure the flow-cache parameters";
        leaf idle-timeout {
          type union {
            type uint16 {
              range "1..65534" {
                description
                  "The idle timeout period (in seconds)";
              }
            }
            type enumeration {
              enum "None" {
                value 0;
                description
                  "The flow does not expire";
              }
            }
          }
          description
            "Maximum time of inactivity for a flow.";
        }
      }
    }
  }

  grouping match-flow-tag {
    container flow-tag {
      tailf:display-when "not(../ncs:module) or boolean(/ncs:devices/ncs:device[ncs:name=current()/../ncs:name]/capability/feature='matchnot-flow-tag')";
      description
        "Match based on flow-tag";
      leaf-list tag-number {
        type union {
          type uint8 {
            range "1..63";
          }
          type string {
            pattern '([1-9][0-9]{0,1})-([1-9][0-9]{0,1})' {
              description
                "<1-63>-<1-63>";
            }
          }
        }
        max-elements 5;
        description
          "flow-tag number";
      }
    }
  }

  grouping match-fr-de {
    leaf fr-de {
      tailf:display-when "not(../ncs:module) or boolean(/ncs:devices/ncs:device[ncs:name=current()/../ncs:name]/capability/feature='match-fr-de')";
      type union {
        type string {
          pattern '1';
        }
        type uint8 {
          range "0..1";
        }
      }
      description
        "Match based on FrameRelay DE bit";
    }
  }

  grouping match-fragment-type {
    container fragment-type {
      tailf:display-when "not(../ncs:module) or boolean(/ncs:devices/ncs:device[ncs:name=current()/../ncs:name]/capability/feature='match-fragment-type')";
      description
        "Fragment type for a packet";
      container dont-fragment {
        presence "Match don't-Fragment bit";
        description
          "Match don't-Fragment bit";
      }
      container first-fragment {
        presence "Match first fragment bit";
        description
          "Match first fragment bit";
      }
      container is-fragment {
        presence "Match is-fragment bit";
        description
          "Match is-fragment bit";
      }
      container last-fragment {
        presence "Match last fragment bit";
        description
          "Match last fragment bit";
      }
    }
  }

  grouping match-frame-relay {
    container frame-relay {
      tailf:display-when "not(../ncs:module) or boolean(/ncs:devices/ncs:device[ncs:name=current()/../ncs:name]/capability/feature='match-fr')";
      description
        "Match based on frame-relay specific criteria";
      leaf-list dlci {
        type union {
          type uint16 {
            range "16..1007";
          }
          type string {
            pattern '([1-9][0-9]{1,3})-([1-9][0-9]{1,3})' {
              description
                "<16-1007>-<16-1007>";
            }
          }
        }
        max-elements 8;
        description
          "Match frame-relay dlci value(s)";
      }
    }
  }

  grouping match-ipv4 {
    container ipv4 {
      description
        "Match based on ipv4 icmp";
      container icmp-code {
        description
          "Match based on ipv4 icmp code";
        leaf-list value {
          type union {
            type uint8 {
              range "0..255";
            }
            type string {
              pattern '([0-9]{1,3})-([0-9]{1,3})' {
                description
                  "<0-255>-<0-255>";
              }
            }
          }
          max-elements 5;
          description
            "IPv4 ICMP code";
        }
      }
      container icmp-type {
        description
          "Match based on ipv4 icmp type";
        leaf-list value {
          type union {
            type uint8 {
              range "0..255";
            }
            type string {
              pattern '([0-9]{1,3})-([0-9]{1,3})' {
                description
                  "<0-255>-<0-255>";
              }
            }
          }
          max-elements 5;
          description
            "IPv4 ICMP type";
        }
      }
    }
  }

  grouping match-ipv6 {
    container ipv6 {
      description
        "Match based on IPv6";
      container icmp-code {
        description
          "IPv6 ICMP code";
        leaf-list value {
          type union {
            type uint8 {
              range "0..255";
            }
            type string {
              pattern '([0-9]{1,3})-([0-9]{1,3})' {
                description
                  "<0-255>-<0-255>";
              }
            }
          }
          max-elements 5;
          description
            "ICMP code";
        }
      }
      container icmp-type {
        description
          "IPv6 ICMP type";
        leaf-list value {
          type union {
            type uint8 {
              range "0..255";
            }
            type string {
              pattern '([0-9]{1,3})-([0-9]{1,3})' {
                description
                  "<0-255>-<0-255>";
              }
            }
          }
          max-elements 5;
          description
            "ICMP type";
        }
      }
    }
  }

  grouping match-mpls {
    container mpls {
      description
        "Match based on MPLS specific values";
      container disposition {
        description
          "Match MPLS Label Disposition";
        container access-group {
          description
            "access group";
          leaf ipv4 {
            tailf:display-when "not(../../../../ncs:module) or boolean(/ncs:devices/ncs:device[ncs:name=current()/../../../../ncs:name]/capability/feature='match-mpls-disp-ipv4-acl')";
            type string {
              length "1..64";
            }
            description
              "IPv4 access list";
          }
          leaf ipv6 {
            tailf:display-when "not(../../../../ncs:module) or boolean(/ncs:devices/ncs:device[ncs:name=current()/../../../../ncs:name]/capability/feature='match-mpls-disp-ipv6-acl')";
            type string {
              length "1..64";
            }
            description
              "IPv6 access list";
          }
        }
        leaf class-map {
          tailf:display-when "not(../../../ncs:module) or boolean(/ncs:devices/ncs:device[ncs:name=current()/../../../ncs:name]/capability/feature='match-mpls-disp-cmap')";
          type string {
            length "1..32";
          }
          description
            "class-map name";
        }
      }
      container experimental {
        description
          "Match MPLS experimental values";
        container imposition {
          tailf:display-when "not(../../../ncs:module) or boolean(/ncs:devices/ncs:device[ncs:name=current()/../../../ncs:name]/capability/feature='match-mpls-exp-imposition')";
          description
            "Match imposition label";
          leaf-list label {
            type uint8 {
              range "0..7";
            }
            max-elements 8;
            description
              "MPLS experimental label";
          }
        }
        container topmost {
          tailf:display-when "not(../../../ncs:module) or boolean(/ncs:devices/ncs:device[ncs:name=current()/../../../ncs:name]/capability/feature='match-mpls-exp-top')";
          description
            "Match topmost label";
          leaf-list label {
            type uint8 {
              range "0..7";
            }
            max-elements 8;
            description
              "MPLS experimental label";
          }
        }
      }
    }
  }

  grouping matchnot-mpls {
    container mpls {
      description
        "Match based on MPLS specific values";
      container disposition {
        description
          "Match MPLS Label Disposition";
        container access-group {
          description
            "access group";
          leaf ipv4 {
            tailf:display-when "not(../../../../ncs:module) or boolean(/ncs:devices/ncs:device[ncs:name=current()/../../../../ncs:name]/capability/feature='matchnot-mpls-disp-ipv4-acl')";
            type string {
              length "1..64";
            }
            description
              "IPv4 access list";
          }
          leaf ipv6 {
            tailf:display-when "not(../../../../ncs:module) or boolean(/ncs:devices/ncs:device[ncs:name=current()/../../../../ncs:name]/capability/feature='matchnot-mpls-disp-ipv6-acl')";
            type string {
              length "1..64";
            }
            description
              "IPv6 access list";
          }
        }
      }
      container experimental {
        description
          "Match MPLS experimental values";
        container topmost {
          description
            "Match topmost label";
          leaf-list label {
            type uint8 {
              range "0..7";
            }
            max-elements 8;
            description
              "MPLS experimental label";
          }
        }
      }
    }
  }

  grouping match-packet {
    container packet {
      description
        "Match based on packet length";
      container length {
        description
          "Packet length";
        leaf-list value {
          type packet-length-type;
          max-elements 5;
          description
            "IP Packet Length";
        }
      }
      container length-ipv4 {
        tailf:display-when "not(../../ncs:module) or boolean(/ncs:devices/ncs:device[ncs:name=current()/../../ncs:name]/capability/feature='match-ipv4-packet-length')";
        description
          "IPV4 Packet Length";
        leaf-list value {
          type packet-length-type;
          max-elements 5;
        }
      }
      container length-ipv6 {
        tailf:display-when "not(../../ncs:module) or boolean(/ncs:devices/ncs:device[ncs:name=current()/../../ncs:name]/capability/feature='match-ipv6-packet-length')";
        description
          "IPV6 Packet Length";
        leaf-list value {
          type packet-length-type;
          max-elements 5;
        }
      }
    }
  }

  grouping matchnot-packet {
    container packet {
      description
        "Match based on packet length";
      container length {
        description
          "Packet length";
        leaf-list value {
          type packet-length-type;
          max-elements 5;
          description
            "IP Packet Length";
        }
      }
      container length-ipv4 {
        tailf:display-when "not(../../ncs:module) or boolean(/ncs:devices/ncs:device[ncs:name=current()/../../ncs:name]/capability/feature='matchnot-ipv4-packet-length')";
        description
          "IPV4 Packet Length";
        leaf-list value {
          type packet-length-type;
          max-elements 5;
        }
      }
      container length-ipv6 {
        tailf:display-when "not(../../ncs:module) or boolean(/ncs:devices/ncs:device[ncs:name=current()/../../ncs:name]/capability/feature='matchnot-ipv6-packet-length')";
        description
          "IPV6 Packet Length";
        leaf-list value {
          type packet-length-type;
          max-elements 5;
        }
      }
    }
  }

  grouping match-precedence {
    container precedence {
      tailf:display-when "not(../ncs:module) or boolean(/ncs:devices/ncs:device[ncs:name=current()/../ncs:name]/capability/feature='match-prec')";
      description
        "Match based on IP precedence values";
      leaf-list value {
        type precedence-type;
        max-elements 8;
        description
          "IP precedence";
      }
    }
    container precedence-ipv4 {
      tailf:display-when "not(../ncs:module) or boolean(/ncs:devices/ncs:device[ncs:name=current()/../ncs:name]/capability/feature='match-ipv4-prec')";
      description
        "Match based on IPV4 precedence";
      leaf-list value {
        type precedence-type;
        max-elements 8;
        description
          "IPV4 precedence";
      }
    }
    container precedence-ipv6 {
      tailf:display-when "not(../ncs:module) or boolean(/ncs:devices/ncs:device[ncs:name=current()/../ncs:name]/capability/feature='match-ipv6-prec')";
      description
        "Match based on IPV6 precedence";
      leaf-list value {
        type precedence-type;
        max-elements 8;
        description
          "IPV6 precedence";
      }
    }
  }

  grouping match-protocol {
    container protocol {
      description
        "Match based on L3 protocol (Upto 8 values or ranges)";
      leaf-list number {
        type protocol-type;
        max-elements 8;
        description
          "Protocol Number";
      }
    }
  }

  grouping match-qos-group {
    container qos-group {
      description
        "Match based on QoS Group";
      leaf-list id {
        type union {
          type uint16 {
            range "0..512";
          }
          type string {
            pattern '([0-9]{1,3})-([0-9]{1,3})' {
              description
                "Lower and upper limit of QoS Group range (<0-512>-<0-512>)";
            }
          }
        }
        max-elements 8;
        description
          "QoS Group Id";
      }
    }
  }

  grouping match-traffic-class {
    container traffic-class {
      description
        "Match based on Traffic Class";
      leaf-list id {
        type union {
          type uint8 {
            range "0..63";
          }
          type string {
            pattern '([0-9]{1,2})-([0-9]{1,2})' {
              description
                "Lower and upper limit of Traffic Class range (<0-63>-<0-63>)";
            }
          }
        }
        max-elements 8;
        description
          "Traffic Class Id";
      }
    }
  }

  grouping match-source-address {
    container source-address {
      description
        "Match based on source address";
      container ipv4 {
        tailf:display-when "not(../../ncs:module) or boolean(/ncs:devices/ncs:device[ncs:name=current()/../../ncs:name]/capability/feature='match-src-addr-ipv4')";
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        tailf:display-when "not(../../ncs:module) or boolean(/ncs:devices/ncs:device[ncs:name=current()/../../ncs:name]/capability/feature='match-src-addr-ipv6')";
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='match-src-mac')";
        type yang:mac-address;
        description
          "MAC Address";
      }
    }
  }

  grouping matchnot-source-address {
    container source-address {
      description
        "Match based on source address";
      container ipv4 {
        description
          "Match based on source IPv4 address";
        list address-prefix {
          key "address netmask";
          description
            "IPv4 address";
          leaf address {
            type inet:ipv4-address-no-zone;
            description
              "IPv4 address.";
          }
          leaf netmask {
            type inet:ipv4-address-no-zone;
            description
              "IPv4 netmask.";
          }
        }
      }
      container ipv6 {
        description
          "Match based on source IPv6 address";
        list address-prefix {
          key "address prefix-length";
          description
            "IPv6 address";
          leaf address {
            type inet:ipv6-address-no-zone;
            description
              "IPv6 address.";
          }
          leaf prefix-length {
            type uint8 {
              range "0..128";
            }
            description
              "Length of the IPv6 Prefix.";
          }
        }
      }
      leaf mac {
        tailf:display-when "not(../../ncs:module) or boolean(/ncs:devices/ncs:device[ncs:name=current()/../../ncs:name]/capability/feature='matchnot-mac-address')";
        type yang:mac-address;
        description
          "MAC Address";
      }
    }
  }

  grouping match-source-port {
    container source-port {
      tailf:display-when "not(../ncs:module) or boolean(/ncs:devices/ncs:device[ncs:name=current()/../ncs:name]/capability/feature='match-source-port')";
      description
        "Match based on source port";
      leaf-list number {
        type port-number-type;
        max-elements 5;
        description
          "source port";
      }
    }
  }

  grouping match-tcp-flag {
    container tcp-flag {
      description
        "Match based on TCP flags";
      leaf value {
        type uint16 {
          range "0..4095";
        }
        description
          "TCP flags value";
      }
      container any {
        presence "Match based on any bit set";
        description
          "Match based on any bit set";
      }
    }
  }

  grouping match-vlan {
    container vlan {
      tailf:display-when "not(../ncs:module) or boolean(/ncs:devices/ncs:device[ncs:name=current()/../ncs:name]/capability/feature='match-vlan')";
      description
        "Match based on Vlan Ids";
      leaf-list vlan-id {
        type vlan-id-type;
        max-elements 8;
        description
          "Vlan Id";
      }
    }
    container vlan-inner {
      tailf:display-when "not(../ncs:module) or boolean(/ncs:devices/ncs:device[ncs:name=current()/../ncs:name]/capability/feature='match-vlan-inner')";
      description
        "Match based on inner Vlan Ids";
      leaf-list vlan-id {
        type vlan-id-type;
        max-elements 8;
        description
          "inner Vlan Id";
      }
    }
  }

  grouping matchnot-vlan {
    container vlan {
      tailf:display-when "not(../ncs:module) or boolean(/ncs:devices/ncs:device[ncs:name=current()/../ncs:name]/capability/feature='matchnot-vlan')";
      description
        "Match based on Vlan Ids";
      leaf-list vlan-id {
        type vlan-id-type;
        max-elements 8;
        description
          "Vlan Id";
      }
    }
    container vlan-inner {
      tailf:display-when "not(../ncs:module) or boolean(/ncs:devices/ncs:device[ncs:name=current()/../ncs:name]/capability/feature='matchnot-vlan-inner')";
      description
        "Match based on inner Vlan Ids";
      leaf-list vlan-id {
        type vlan-id-type;
        max-elements 8;
        description
          "inner Vlan Id";
      }
    }
  }

  grouping match-vpls {
    container vpls {
      description
        "Match based on VPLS fields";
      container known {
        tailf:display-when "not(../../ncs:module) or boolean(/ncs:devices/ncs:device[ncs:name=current()/../../ncs:name]/capability/feature='match-vpls-known')";
        presence "VPLS Known";
        description
          "VPLS Known";
      }
      container unknown {
        tailf:display-when "not(../../ncs:module) or boolean(/ncs:devices/ncs:device[ncs:name=current()/../../ncs:name]/capability/feature='match-vpls-unknown')";
        presence "VPLS Unknown";
        description
          "VPLS Unknown";
      }
      container broadcast {
        presence "VPLS Broadcast";
        description
          "VPLS Broadcast";
      }
      container control {
        tailf:display-when "not(../../ncs:module) or boolean(/ncs:devices/ncs:device[ncs:name=current()/../../ncs:name]/capability/feature='match-vpls-control')";
        presence "VPLS Control";
        description
          "VPLS Control";
      }
      container multicast {
        presence "VPLS Multicast";
        description
          "VPLS Multicast";
      }
    }
  }

  grouping matchnot-vpls {
    container vpls {
      description
        "Match based on VPLS fields";
      container known {
        tailf:display-when "not(../../ncs:module) or boolean(/ncs:devices/ncs:device[ncs:name=current()/../../ncs:name]/capability/feature='matchnot-vpls-known')";
        presence "VPLS Known";
        description
          "VPLS Known";
      }
      container unknown {
        tailf:display-when "not(../../ncs:module) or boolean(/ncs:devices/ncs:device[ncs:name=current()/../../ncs:name]/capability/feature='matchnot-vpls-unknown')";
        presence "VPLS Unknown";
        description
          "VPLS Unknown";
      }
      container broadcast {
        tailf:display-when "not(../../ncs:module) or boolean(/ncs:devices/ncs:device[ncs:name=current()/../../ncs:name]/capability/feature='matchnot-vpls-bcast')";
        presence "VPLS Broadcast";
        description
          "VPLS Broadcast";
      }
      container control {
        tailf:display-when "not(../../ncs:module) or boolean(/ncs:devices/ncs:device[ncs:name=current()/../../ncs:name]/capability/feature='matchnot-vpls-control')";
        presence "VPLS Control";
        description
          "VPLS Control";
      }
      container multicast {
        tailf:display-when "not(../../ncs:module) or boolean(/ncs:devices/ncs:device[ncs:name=current()/../../ncs:name]/capability/feature='matchnot-vpls-mcast')";
        presence "VPLS Multicast";
        description
          "VPLS Multicast";
      }
    }
  }

  grouping match-authen-status {
    leaf authen-status {
      tailf:display-when "not(../ncs:module) or boolean(/ncs:devices/ncs:device[ncs:name=current()/../ncs:name]/capability/feature='match-authen-status')";
      type enumeration {
        enum "authenticated" {
          value 0;
          description
            "Authenticated";
        }
        enum "unauthenticated" {
          value 1;
          description
            "Unauthenticated";
        }
      }
      description
        "Authentication Status";
    }
  }

  grouping match-circuit-id {
    container circuit-id {
      description
        "Match based on circuit ID";
      leaf-list value {
        type string {
          length "1..32" {
            description
              "Any string except 'regexp'";
          }
        }
        description
          "circuit ID";
      }
    }
    container circuit-id-regexp {
      description
        "Match based on circuit ID regular expression";
      leaf-list value {
        type string {
          length "1..32";
        }
        description
          "Circuit ID regular expression";
      }
    }
  }

  grouping match-dhcp-client-id {
    container dhcp-client-id {
      description
        "Match based on dhcp client id";
      list client-id {
        key "id flag";
        description
          "client id";
        leaf id {
          type string {
            length "1..32";
          }
          description
            "client id";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
    container dhcp-client-id-regexp {
      description
        "Match based on dhcp client id regular expression";
      list client-id {
        key "id flag";
        description
          "client id with regular expression";
        leaf id {
          type string {
            length "1..32";
          }
          description
            "client id with regular expression";
        }
        leaf flag {
          type enumeration {
            enum "ascii" {
              value 0;
              description
                "Ascii value";
            }
            enum "hex" {
              value 1;
              description
                "Hex value";
            }
            enum "none" {
              value 2;
              description
                "No flag set";
            }
          }
          description
            "client id flag";
        }
      }
    }
  }

  grouping match-domain {
    container domain {
      description
        "Match base on domain name";
      list domain-name {
        key "name format";
        description
          "Domain name";
        leaf name {
          type string {
            length "1..32";
          }
          description
            "Domain name";
        }
        leaf format {
          type string {
            length "1..32";
          }
          description
            "Domain format name";
        }
      }
    }
    container domain-regexp {
      description
        "Match base on domain name with regular expression";
      list domain-name {
        key "regexp format";
        description
          "Domain name";
        leaf regexp {
          type string {
            length "1..32";
          }
          description
            "Domain name with regular expression";
        }
        leaf format {
          type string {
            length "1..32";
          }
          description
            "Domain format name";
        }
      }
    }
  }

  grouping match-control-protocol {
    container protocol {
      description
        "Match based on protocol";
      leaf-list name {
        tailf:display-when "not(../../ncs:module) or boolean(/ncs:devices/ncs:device[ncs:name=current()/../../ncs:name]/capability/feature='match-proto')";
        type enumeration {
          enum "dhcpv4" {
            value 0;
            description
              "dhcpv4";
          }
          enum "dhcpv6" {
            value 1;
            description
              "dhcpv6";
          }
          enum "ppp" {
            value 2;
            description
              "ppp";
          }
        }
        max-elements 3;
        description
          "protocol name";
      }
    }
  }

  grouping match-remote-id {
    container remote-id {
      description
        "Match based on remote ID";
      leaf-list id {
        type string {
          length "1..32";
        }
        description
          "remote-id";
      }
    }
    container remote-id-regexp {
      description
        "Remote ID with regular expression";
      leaf-list id {
        type string {
          length "1..32";
        }
        description
          "remote-id with regular expression";
      }
    }
  }

  grouping match-service-name {
    container service-name {
      description
        "Match based on service name";
      leaf-list name {
        type string {
          length "1..32";
        }
        description
          "Service name";
      }
    }
    container service-name-regexp {
      description
        "Match based on service name with regular expression";
      leaf-list name {
        type string {
          length "1..32";
        }
        description
          "Service name with regular expression";
      }
    }
  }

  grouping match-timer {
    container timer {
      tailf:display-when "not(../ncs:module) or boolean(/ncs:devices/ncs:device[ncs:name=current()/../ncs:name]/capability/feature='match-timer')";
      description
        "Match based on timer";
      leaf-list name {
        type string {
          length "1..32";
        }
        description
          "Timer name";
      }
    }
    container timer-regexp {
      description
        "Timer with regular expression";
      leaf-list name {
        type string {
          length "1..32";
        }
        description
          "Timer name with regular expression";
      }
    }
  }

  grouping match-username {
    container username {
      tailf:display-when "not(../ncs:module) or boolean(/ncs:devices/ncs:device[ncs:name=current()/../ncs:name]/capability/feature='match-username')";
      description
        "Match based on user name";
      leaf-list name {
        type string {
          length "1..32";
        }
        description
          "User name";
      }
    }
    container username-regexp {
      tailf:display-when "not(../ncs:module) or boolean(/ncs:devices/ncs:device[ncs:name=current()/../ncs:name]/capability/feature='match-username')";
      description
        "Match based on user name with regular expression";
      leaf-list name {
        type string {
          length "1..32";
        }
        description
          "User name with regular expression";
      }
    }
  }

  grouping policy-map-common {
    leaf policy-map-name {
      type string;
      description
        "Name of the policymap";
    }
    leaf description {
      type string;
      description
        "Set description for this policy-map";
    }
  }

  grouping policy-action-compress {
    container compress {
      tailf:display-when "not(../ncs:module) or boolean(/ncs:devices/ncs:device[ncs:name=current()/../ncs:name]/capability/feature='action-compress-header-ip')";
      description
        "Configure compress action";
      container header {
        description
          "Configure header compression";
        container ip {
          presence "Configure IP header compression";
          description
            "Configure IP header compression";
        }
      }
    }
  }

  grouping policy-action-encap-sequence {
    leaf encap-sequence {
      tailf:display-when "not(../ncs:module) or boolean(/ncs:devices/ncs:device[ncs:name=current()/../ncs:name]/capability/feature='action-encap-sequence')";
      type union {
        type uint8 {
          range "1..15" {
            description
              "Encapsulation sequence number";
          }
        }
        type enumeration {
          enum "none" {
            value 0;
            description
              "Encapsulation sequence none";
          }
        }
      }
      description
        "Configure encapsulation sequence";
    }
  }

  grouping aaa-method {
    container aaa {
      description
        "AAA specification";
      leaf list {
        type union {
          type string;
          type enumeration {
            enum "default" {
              value 0;
              description
                "default AAA method list";
            }
          }
        }
        description
          "Specify AAA method list that authentication should be made with";
      }
    }
  }

  grouping subscriber-actions {
    container activate {
      description
        "Activate";
      container dynamic-template {
        description
          "actions related to dynamic templates";
        leaf template-name {
          type string;
          description
            "Dynamic template name";
        }
        uses aaa-method;
      }
    }
    container deactivate {
      description
        "Deactivate";
      container dynamic-template {
        description
          "actions related to dynamic templates";
        leaf template-name {
          type string;
          description
            "Dynamic template name";
        }
        uses aaa-method;
      }
    }
    container authenticate {
      tailf:display-when "not(../ncs:module) or boolean(/ncs:devices/ncs:device[ncs:name=current()/../ncs:name]/capability/feature='action-authenticate')";
      description
        "Authentication related configuration";
      uses aaa-method;
    }
    container authorize {
      tailf:display-when "not(../ncs:module) or boolean(/ncs:devices/ncs:device[ncs:name=current()/../ncs:name]/capability/feature='action-authorize')";
      description
        "Authorize";
      uses aaa-method;
      leaf format {
        type string;
        description
          "Specify an Authorize format name";
      }
      leaf identifier {
        type enumeration {
          enum "circuit-id" {
            value 0;
            description
              "Authorize circuit ID";
          }
          enum "dhcp-client-id" {
            value 1;
            description
              "Authorize dhcp client ID";
          }
          enum "remote-id" {
            value 2;
            description
              "Authorize remote ID";
          }
          enum "service-name" {
            value 3;
            description
              "Authorize Service Name";
          }
          enum "source-address-ipv4" {
            value 4;
            description
              "Authorize source IPv4 address";
          }
          enum "source-address-ipv6" {
            value 5;
            description
              "Authorize source IPv6 address";
          }
          enum "source-address-mac" {
            value 6;
            description
              "Authorize source MAC address";
          }
          enum "username" {
            value 7;
            description
              "Authorize username";
          }
        }
        description
          "Specify an Authorize identifier";
      }
      leaf password {
        type union {
          type clear-text-password-type;
          type enumeration {
            enum "blank" {
              value 0;
              description
                "use blank password";
            }
            enum "use-from-line" {
              value 1;
              description
                "use from line";
            }
          }
        }
        description
          "Specify a password to be used for AAA request";
      }
    }
    container disconnect {
      tailf:display-when "not(../ncs:module) or boolean(/ncs:devices/ncs:device[ncs:name=current()/../ncs:name]/capability/feature='action-disconnect')";
      presence "Disconnect session";
      description
        "Disconnect session";
    }
    container monitor {
      tailf:display-when "not(../ncs:module) or boolean(/ncs:devices/ncs:device[ncs:name=current()/../ncs:name]/capability/feature='action-monitor')";
      presence "Monitor session";
      description
        "Monitor session";
    }
    container set-timer {
      tailf:display-when "not(../ncs:module) or boolean(/ncs:devices/ncs:device[ncs:name=current()/../ncs:name]/capability/feature='action-set-timer')";
      must 'name and value' {
        tailf:xpath-root 3;
      }
      presence "indicates set-timer is configured";
      description
        "Set a timer to execute a rule on its expiry";
      leaf name {
        type string;
        description
          "Name of the timer";
      }
      leaf value {
        type uint32 {
          range "1..4294967295" {
            description
              "Timer value in minutes";
          }
        }
        units "minutes";
      }
    }
    container stop-timer {
      tailf:display-when "not(../ncs:module) or boolean(/ncs:devices/ncs:device[ncs:name=current()/../ncs:name]/capability/feature='action-stop-timer')";
      description
        "Disable timer before it expires";
      leaf name {
        type string;
        description
          "Name of the timer";
      }
    }
  }

  grouping pbr-actions {
    container drop {
      presence "Drop the packet";
      description
        "Drop the packet";
    }
    leaf http-redirect {
      tailf:display-when "not(../ncs:module) or boolean(/ncs:devices/ncs:device[ncs:name=current()/../ncs:name]/capability/feature='action-http-redirect')";
      type string;
      description
        "Configure HTTP redirect. Specify the URL HTTP requests should be redirected to";
    }
    container http-enrichment {
      tailf:display-when "not(../ncs:module) or boolean(/ncs:devices/ncs:device[ncs:name=current()/../ncs:name]/capability/feature='action-http-enrichment')";
      description
        "Configure HTTP enrichment";
      container subscriber-mac {
        presence "Subscriber MAC address";
        description
          "Subscriber MAC address";
      }
      container subscriber-ip {
        presence "Subscriber ipv4/ipv6 address";
        description
          "Subscriber ipv4/ipv6 address";
      }
      container hostname {
        presence "Hostname";
        description
          "Hostname";
      }
      container bng-interface {
        presence "BNG identifier interface";
        description
          "BNG identifier interface";
      }
    }
    container police {
      description
        "Police traffic";
      container rate {
        must 'value and unit' {
          tailf:xpath-root 3;
        }
        presence "indicates rate is configured";
        description
          "Committed Information Rate";
        leaf value {
          type uint32 {
            range "1..4294967295" {
              description
                "Committed Information Rate";
            }
          }
        }
        leaf unit {
          type rate-unit-type;
        }
      }
    }
    container redirect-ipv4 {
      tailf:display-when "not(../ncs:module) or boolean(/ncs:devices/ncs:device[ncs:name=current()/../ncs:name]/capability/feature='action-redirect-nexthop')";
      description
        "Configure PBF redirect feature with IPv4 configurations";
      container default-route {
        presence "Forward to the default nexthop";
        description
          "Forward to the default nexthop";
      }
      container nexthop1 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv4-address;
          description
            "IPv4 Nexthop address";
        }
        leaf vrf {
          type union {
            type string;
            type enumeration {
              enum "default" {
                value 0;
                description
                  "Redirect to the default vrf";
              }
            }
          }
          description
            "Enter specific VRF Name for this nexthop";
        }
      }
    }
    container redirect-ipv6 {
      tailf:display-when "not(../ncs:module) or boolean(/ncs:devices/ncs:device[ncs:name=current()/../ncs:name]/capability/feature='action-redirect-nexthop')";
      description
        "Configure PBF redirect feature with IPv6 configurations";
      container default-route {
        presence "Forward to the default nexthop";
        description
          "Forward to the default nexthop";
      }
      container nexthop1 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop2 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
      container nexthop3 {
        description
          "Forward to specified nexthop";
        leaf address {
          type inet:ipv6-address;
          description
            "IPv6 Nexthop address";
        }
        leaf vrf {
          type union {
            type string;
            type enumeration {
              enum "default" {
                value 0;
                description
                  "Redirect to the default vrf";
              }
            }
          }
          description
            "Enter specific VRF Name for this nexthop";
        }
      }
    }
    container redirect-nexthop {
      tailf:display-when "not(../ncs:module) or boolean(/ncs:devices/ncs:device[ncs:name=current()/../ncs:name]/capability/feature='action-redirect-rt')";
      description
        "Configure PBF redirect feature with forwarding to specified nexthop";
      container route-target {
        must '(address and index) or as-number' {
          tailf:xpath-root 3;
        }
        presence "indicates route-target is configured";
        description
          "Enter specific route-target string";
        leaf address {
          type inet:ipv4-address-no-zone;
          description
            "IPv4 address.";
        }
        leaf index {
          type uint16 {
            range "0..65535" {
              description
                "IPv4 Address:index";
            }
          }
          description
            "IPv4 Address:index";
        }
        leaf as-number {
          type union {
            type string {
              pattern '([1-9][0-9]{0,4}):(0|[1-9][0-9]{0,4})' {
                description
                  "<1-65535>:<0-65535> 2-byte AS number";
              }
            }
            type string {
              pattern '(65536:|[1-9][0-9]{0,10}:)(0|[1-9][0-9]{0,4})' {
                description
                  "<65536-4294967295>:<0-65535> 4-byte AS number in asplain format";
              }
            }
          }
          description
            "AS number";
        }
      }
    }
    container service-function-path {
      tailf:display-when "not(../ncs:module) or boolean(/ncs:devices/ncs:device[ncs:name=current()/../ncs:name]/capability/feature='action-service-function')";
      description
        "Configure NSH service function action";
      leaf path-id {
        type uint32 {
          range "1..16777215";
        }
        must '../index' {
          tailf:xpath-root 3;
        }
        description
          "Service function path id";
      }
      leaf index {
        type uint8 {
          range "1..255" {
            description
              "Service function path index";
          }
        }
        must '../path-id' {
          tailf:xpath-root 3;
        }
        description
          "Specify service path index";
      }
      leaf metadata {
        type string;
        must '../index and ../path-id' {
          tailf:xpath-root 3;
        }
        description
          "service-function metadata";
      }
    }
    container set {
      description
        "Configure marking for this class";
      container destination-address {
        tailf:display-when "not(../../ncs:module) or boolean(/ncs:devices/ncs:device[ncs:name=current()/../../ncs:name]/capability/feature='action-set-dst-address')";
        description
          "Set Destination address";
        leaf ipv4 {
          type inet:ipv4-address;
          description
            "IPv4 address";
        }
      }
      leaf df {
        tailf:display-when "not(../../ncs:module) or boolean(/ncs:devices/ncs:device[ncs:name=current()/../../ncs:name]/capability/feature='action-set-df')";
        type uint8 {
          range "0..1" {
            description
              "DF bit";
          }
        }
        description
          "Set DF bit";
      }
      leaf dscp {
        type dscp-value;
        description
          "Set DSCP";
      }
      leaf forward-class {
        tailf:display-when "not(../../ncs:module) or boolean(/ncs:devices/ncs:device[ncs:name=current()/../../ncs:name]/capability/feature='action-set-fwd-class')";
        type uint8 {
          range "1..7" {
            description
              "Forward class value";
          }
        }
        description
          "Set forward class";
      }
      container source-address {
        tailf:display-when "not(../../ncs:module) or boolean(/ncs:devices/ncs:device[ncs:name=current()/../../ncs:name]/capability/feature='action-set-src-address')";
        description
          "Set Source address";
        leaf ipv4 {
          type inet:ipv4-address;
          description
            "IPv4 address";
        }
      }
    }
    container transmit {
      tailf:display-when "not(../ncs:module) or boolean(/ncs:devices/ncs:device[ncs:name=current()/../ncs:name]/capability/feature='action-transmit')";
      presence "Forward packet to the original destination";
      description
        "Forward packet to the original destination";
    }
    container decapsulate {
      tailf:display-when "not(../ncs:module) or boolean(/ncs:devices/ncs:device[ncs:name=current()/../ncs:name]/capability/feature='action-decap-gre')";
      description
        "Decapsulate GRE packet";
      container gre {
        presence "Decapsulate GRE packet";
        description
          "Decapsulate GRE packet";
      }
    }
  }

  grouping performance-traffic-actions {
    uses policy-action-compress;
    uses policy-action-encap-sequence;
    list react {
      tailf:display-when "not(ncs:module) or boolean(/ncs:devices/ncs:device[ncs:name=current()/ncs:name]/capability/feature='action-react')";
      key "operation-id";
      description
        "Generate alert on the specified event";
      leaf operation-id {
        type uint32 {
          range "1..4294967294";
        }
        description
          "Specify an operation id (num)";
      }
      container delay-factor {
        presence "React criterion delay factor of policy-map action.";
        description
          "React criterion delay factor of policy-map action.";
      }
      container media-stop {
        presence "React criterion media stop of policy-map action.";
        description
          "React criterion media stop of policy-map action.";
      }
      container mrv {
        presence "React criterion mrv of policy-map action.";
        description
          "React criterion mrv of policy-map action.";
      }
      container flow-count {
        presence "React criterion flow count of policy-map action.";
        description
          "React criterion flow count of policy-map action.";
      }
      container packet-rate {
        presence "React criterion packet rate of the policy-map action.";
        description
          "React criterion packet rate of the policy-map action.";
      }
      leaf description {
        type string;
        description
          "Set Description for this alert action";
      }
      container trigger {
        description
          "Set the event trigger";
        container value {
          must 'lt or le or gt or ge or range' {
            tailf:xpath-root 3;
          }
          presence "indicates value is configured";
          description
            "Set the trigger criterion";
          leaf lt {
            type trigger-value;
            description
              "trigger only if metric is less than the given value";
          }
          leaf le {
            type trigger-value;
            description
              "trigger only if metric is less than or equal to the given value";
          }
          leaf gt {
            type trigger-value;
            description
              "trigger only if metric is greater than the given value";
          }
          leaf ge {
            type trigger-value;
            description
              "trigger only if metric is greater than or equal to the given value";
          }
          leaf range {
            type trigger-value;
            description
              "trigger only if metric is in the inclusive range";
          }
        }
        container type {
          must 'immediate or average' {
            tailf:xpath-root 3;
          }
          presence "indicates type is configured";
          description
            "Set the trigger type";
          container immediate {
            presence "Immediate trigger";
            description
              "Immediate trigger";
          }
          leaf average {
            type uint32 {
              range "1..60";
            }
            description
              "Trigger averaged over N intervals.";
          }
        }
      }
      container action {
        description
          "Set the event action";
        container syslog {
          presence "Report via syslog";
          description
            "Report via syslog";
        }
        container snmp {
          tailf:display-when "not(../../../ncs:module) or boolean(/ncs:devices/ncs:device[ncs:name=current()/../../../ncs:name]/capability/feature='action-react-snmp')";
          presence "Report via syslog";
          description
            "Report via syslog";
        }
      }
      container alarm {
        tailf:display-when "not(../../ncs:module) or boolean(/ncs:devices/ncs:device[ncs:name=current()/../../ncs:name]/capability/feature='action-react-alarm')";
        description
          "Configure alarms";
        container type {
          must 'discrete or grouped' {
            tailf:xpath-root 3;
          }
          presence "indicates type is configured";
          description
            "Set the alarm type";
          container discrete {
            presence "Discrete alarms";
            description
              "Discrete alarms";
          }
          container grouped {
            tailf:display-when "not(../../../../ncs:module) or boolean(/ncs:devices/ncs:device[ncs:name=current()/../../../../ncs:name]/capability/feature='action-react-grouped-alarm')";
            description
              "Grouped alarms";
            leaf count {
              type uint16 {
                range "1..65535" {
                  description
                    "Number of flows with alarm";
                }
              }
              units "number of flows";
              must 'not(../percent)' {
                tailf:xpath-root 3;
              }
              description
                "Grouped on num-flows";
            }
            leaf percent {
              type uint8 {
                range "1..100" {
                  description
                    "Percentage of flows with alarm";
                }
              }
              units "percentage";
              must 'not(../count)' {
                tailf:xpath-root 3;
              }
              description
                "Grouped on percentage of flows";
            }
          }
        }
        leaf severity {
          type enumeration {
            enum "error" {
              value 0;
              description
                "Error level alarm";
            }
            enum "critical" {
              value 1;
              description
                "Critical level alarm";
            }
            enum "alert" {
              value 2;
              description
                "Alert level alarm";
            }
            enum "emergency" {
              value 3;
              description
                "Emergency level alarm";
            }
          }
          description
            "Set the alarm severity";
        }
      }
    }
  }

  grouping action-common {
    leaf cos {
      type uint8 {
        range "0..7";
      }
      description
        "Sets the specific IEEE 802.1Q Layer 2 CoS value of an
         outgoing packet.
         This command should be used by a router if a user wants
         to mark a packet that is being sent to a switch.
         Switches can leverage Layer 2 header information,
         including a CoS value marking. Packets entering an
         interface cannot be set with a CoS value.";
    }
    leaf cos-inner {
      type uint8 {
        range "0..7";
      }
      description
        "Set inner COS";
    }
    leaf dei {
      type uint8 {
        range "0..1";
      }
      description
        "Set DEI";
    }
    leaf dei-imposition {
      type uint8 {
        range "0..1";
      }
      description
        "Set DEI imposition bit.";
    }
    leaf discard-class {
      type uint8 {
        range "0..7" {
          description
            "discard-class value";
        }
      }
      description
        "Sets the discard class on IPv4 or MPLS packets.
         The discard-class can be used only in service policies
         that are attached in the ingress policy.";
    }
    leaf dscp {
      type dscp-value;
      description
        "Set IP DSCP (DiffServ CodePoint)";
    }
    leaf dscp-tunnel {
      type dscp-value;
      description
        "Set DSCP Tunnel(for ipsec tunnels)";
    }
    leaf fr-de {
      tailf:display-when "not(../ncs:module) or boolean(/ncs:devices/ncs:device[ncs:name=current()/../ncs:name]/capability/feature='action-police-set-fr-de')";
      type uint8 {
        range "0..1";
      }
      description
        "Set frame relay discard-eligible bit";
    }
    container mpls {
      description
        "Set MPLS specific values";
      container experimental {
        description
          "Set experimental";
        leaf imposition {
          type uint8 {
            range "0..7";
          }
          description
            "Sets the experimental value of the MPLS packet
             imposition labels.
             Imposition can be used only in service policies that
             are attached in the ingress policy";
        }
        leaf topmost {
          type uint8 {
            range "0..7";
          }
          description
            "Sets the experimental value of the MPLS packet top-most
             labels.";
        }
      }
    }
    leaf precedence {
      type precedence-type;
      description
        "Set IP Precedence";
    }
    leaf precedence-tunnel {
      type precedence-type;
      description
        "Set Precedence tunnel(for ipsec tunnels)";
    }
    leaf qos-group {
      type uint16 {
        range "0..512" {
          description
            "QoS group value";
        }
      }
      description
        "Sets the QoS group identifiers on IPv4 or MPLS packets.
         The set qos-group is supported only on an ingress policy.";
    }
  }

  grouping police-actions {
    container transmit {
      presence "Transmit packet";
      description
        "Transmit packet";
    }
    container drop {
      presence "Drop packet";
      description
        "Drop packet";
    }
    container set {
      description
        "Conditional marking";
      uses action-common;
    }
  }

  grouping qos-actions {
    container admit {
      tailf:display-when "not(../ncs:module) or boolean(/ncs:devices/ncs:device[ncs:name=current()/../ncs:name]/capability/feature='action-cac')";
      description
        "Call admission control";
      container cac {
        description
          "Call admission control (CAC) functionality";
        container local {
          must 'rate and flow/rate' {
            tailf:xpath-root 3;
          }
          presence "indicates local is configured";
          description
            "CAC local flow type (default type)";
          container flow {
            description
              "Flow attributes";
            leaf idle-timeout {
              type union {
                type uint16 {
                  range "10..2550" {
                    description
                      "The idle timeout period (in seconds)";
                  }
                }
                type enumeration {
                  enum "None" {
                    value 0;
                    description
                      "The flow does not expire";
                  }
                }
              }
              description
                "Maximum time of inactivity for a flow";
            }
            container rate {
              must 'value and unit' {
                tailf:xpath-root 3;
              }
              presence "indicates rate is configured";
              description
                "Per flow rate";
              leaf value {
                type uint32 {
                  range "1..4294967294" {
                    description
                      "Committed per flow rate";
                  }
                }
              }
              leaf unit {
                type cac-unit-type;
              }
            }
          }
          container rate {
            must 'value and unit' {
              tailf:xpath-root 3;
            }
            presence "indicates rate is configured";
            description
              "Maximum rate for all flows";
            leaf value {
              type uint32 {
                range "1..4294967294" {
                  description
                    "Committed aggregate rate for all flows";
                }
              }
            }
            leaf unit {
              type cac-unit-type;
            }
          }
        }
      }
    }
    container bandwidth {
      tailf:display-when "not(../ncs:module) or boolean(/ncs:devices/ncs:device[ncs:name=current()/../ncs:name]/capability/feature='action-bandwidth')";
      must 'value and unit' {
        tailf:xpath-root 3;
      }
      presence "indicates bandwidth is configured";
      description
        "Configure bandwidth for this class";
      leaf value {
        type union {
          type uint32 {
            range "1..4294967295" {
              description
                "Bandwidth value";
            }
          }
          type uint16 {
            range "1..1000" {
              description
                "Parts per-thousand bandwidth value";
            }
          }
          type uint32 {
            range "1..1000000" {
              description
                "Parts per-million bandwidth value";
            }
          }
          type uint32 {
            range "1..100" {
              description
                "Percentage bandwidth value";
            }
          }
        }
      }
      leaf unit {
        type enumeration {
          enum "bps" {
            value 0;
            description
              "Bits per second";
          }
          enum "gbps" {
            value 1;
            description
              "Gigabits per second";
          }
          enum "kbps" {
            value 2;
            description
              "Kilobits per second";
          }
          enum "mbps" {
            value 3;
            description
              "Megabits per second";
          }
          enum "cellsps" {
            value 4;
            description
              "Cells per second";
          }
          enum "per-thousand" {
            value 5;
            description
              "configure parts per-thousand bandwidth";
          }
          enum "per-million" {
            value 6;
            description
              "configure parts per-million bandwidth";
          }
          enum "percent" {
            value 7;
            description
              "configure a percentage bandwidth";
          }
        }
      }
    }
    container bandwidth-remaining {
      tailf:display-when "not(../ncs:module) or boolean(/ncs:devices/ncs:device[ncs:name=current()/../ncs:name]/capability/feature='action-bandwidth')";
      must 'unit and value' {
        tailf:xpath-root 3;
      }
      presence "indicates bandwidth-remaining is configured";
      description
        "Allocate left over bandwidth";
      leaf unit {
        type enumeration {
          enum "percent" {
            value 0;
            description
              "Allocate remaining bandwidth as percentage";
          }
          enum "ratio" {
            value 1;
            description
              "Allocate remaining bandwidth as a ratio";
          }
        }
        description
          "Bandwidth value unit";
      }
      leaf value {
        type union {
          type uint8 {
            range "1..100" {
              description
                "Percentage bandwidth value";
            }
          }
          type uint32 {
            range "1..4294967295" {
              description
                "Bandwidth ratio";
            }
          }
        }
        description
          "Bandwidth value";
      }
    }
    uses policy-action-compress;
    uses policy-action-encap-sequence;
    leaf fragment {
      tailf:display-when "not(../ncs:module) or boolean(/ncs:devices/ncs:device[ncs:name=current()/../ncs:name]/capability/feature='action-service-fragment')";
      type string {
        length "1..64" {
          description
            "Reference to a Service fragment";
        }
      }
      description
        "Refer to an existing service fragment. Reference to a Service fragment.";
    }
    container pause {
      tailf:display-when "not(../ncs:module) or boolean(/ncs:devices/ncs:device[ncs:name=current()/../ncs:name]/capability/feature='action-pfc')";
      presence "Configure PFC feature";
      description
        "Configure PFC feature";
      container buffer-size {
        must 'value and unit' {
          tailf:xpath-root 3;
        }
        presence "indicates buffer-size is configured";
        description
          "Configure buffer size";
        leaf value {
          type uint32 {
            range "1..4294967295";
          }
          description
            "Range of buffer size";
        }
        leaf unit {
          type pfc-unit-type;
        }
      }
      container pause-threshold {
        must 'value and unit' {
          tailf:xpath-root 3;
        }
        presence "indicates pause-threshold is configured";
        description
          "Configure pasue threshold";
        leaf value {
          type uint32 {
            range "1..4294967295";
          }
          description
            "Range of pause threshold";
        }
        leaf unit {
          type pfc-unit-type;
        }
      }
      container resume-threshold {
        must 'value and unit' {
          tailf:xpath-root 3;
        }
        presence "indicates resume-threshold is configured";
        description
          "Configure resume threshold";
        leaf value {
          type uint32 {
            range "1..4294967295";
          }
          description
            "Range of resume threshold";
        }
        leaf unit {
          type pfc-unit-type;
        }
      }
    }
    container police {
      description
        "Police traffic";
      container conditional {
        presence "Conditional policer for priority traffic";
        description
          "Conditional policer for priority traffic";
      }
      container rate {
        must 'value and unit' {
          tailf:xpath-root 3;
        }
        presence "indicates rate is configured";
        description
          "Committed Information Rate";
        leaf value {
          type union {
            type uint32 {
              range "1..4294967295";
            }
            type uint8 {
              range "1..100" {
                description
                  "Committed Information Rate in percentage of link bandwidth";
              }
            }
            type uint16 {
              range "1..1000" {
                description
                  "Committed Information Rate in per-thousand of link bandwidth";
              }
            }
            type uint32 {
              range "1..1000000" {
                description
                  "Committed Information Rate in per-million of link bandwidth";
              }
            }
          }
          description
            "Committed Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
            enum "per-thousand" {
              value 7;
              description
                "Parts per-thousand of the link bandwidth";
            }
            enum "per-million" {
              value 8;
              description
                "Parts per-million of the link bandwidth";
            }
          }
          description
            "Rate unit";
        }
      }
      container burst {
        description
          "Burst size (BC)";
        leaf value {
          type uint32 {
            range "1..4294967295";
          }
          description
            "Burst size (BC)";
        }
        leaf unit {
          type burst-unit-type;
          description
            "Burst size unit";
        }
      }
      container peak-burst {
        tailf:display-when "not(../../ncs:module) or boolean(/ncs:devices/ncs:device[ncs:name=current()/../../ncs:name]/capability/feature='action-police-peak-burst')";
        description
          "Excess Burst size (BE)";
        leaf value {
          type uint32 {
            range "1..4294967295";
          }
          description
            "Exess burst size (BC)";
        }
        leaf unit {
          type burst-unit-type;
          description
            "Burst size unit";
        }
      }
      container peak-rate {
        must 'value and unit' {
          tailf:xpath-root 3;
        }
        presence "indicates peak-rate is configured";
        description
          "Peak Information Rate";
        leaf value {
          type union {
            type uint32 {
              range "1..4294967295";
            }
            type uint8 {
              range "1..100" {
                description
                  "Committed Information Rate in percentage of link bandwidth";
              }
            }
          }
          description
            "Peak Information Rate";
        }
        leaf unit {
          type enumeration {
            enum "bps" {
              value 0;
              description
                "Bits per second (default)";
            }
            enum "gbps" {
              value 1;
              description
                "Gigabits per second";
            }
            enum "kbps" {
              value 2;
              description
                "Kilobits per second";
            }
            enum "mbps" {
              value 3;
              description
                "Megabits per second";
            }
            enum "cellsps" {
              value 4;
              description
                "Cells per second";
            }
            enum "pps" {
              value 5;
              description
                "Packets per second";
            }
            enum "percent" {
              value 6;
              description
                "Percent of the link bandwidth";
            }
          }
        }
      }
      container conform-action {
        description
          "Action for conforming traffic";
        uses police-actions;
      }
      container exceed-action {
        description
          "Action for exceeding traffic";
        uses police-actions;
      }
      container violate-action {
        description
          "Action for violating traffic";
        uses police-actions;
      }
      leaf conform-color {
        tailf:display-when "not(../../ncs:module) or boolean(/ncs:devices/ncs:device[ncs:name=current()/../../ncs:name]/capability/feature='action-police-conform-color')";
        type string;
        description
          "Configure conform color class for color aware policing. Conform color class name.";
      }
      leaf exceed-color {
        tailf:display-when "not(../../ncs:module) or boolean(/ncs:devices/ncs:device[ncs:name=current()/../../ncs:name]/capability/feature='action-police-exceed-color')";
        type string;
        description
          "Configure exceed color class for color aware policing. Exceed color class name.";
      }
      container child-conform-aware {
        tailf:display-when "not(../../ncs:module) or boolean(/ncs:devices/ncs:device[ncs:name=current()/../../ncs:name]/capability/feature='action-police-coupled')";
        presence "Enable coupled policing";
        description
          "Enable coupled policing";
      }
    }
    container priority {
      description
        "Assign priority to this class";
      leaf level {
        type uint8 {
          range "1..7" {
            description
              "Priority level";
          }
        }
        description
          "Configure a priority level";
      }
    }
    container queue-limits {
      description
        "Queue Limit Node";
      list queue-limit {
        key "value unit";
        description
          "Configure queue-limit (taildrop threshold) for this class";
        leaf value {
          type union {
            type uint32 {
              range "1..4294967295" {
                description
                  "Max Threshold for tail drop";
              }
            }
            type uint8 {
              range "1..100" {
                description
                  "Percentage value";
              }
            }
          }
          description
            "queue-limit value";
        }
        leaf unit {
          type enumeration {
            enum "bytes" {
              value 0;
              description
                "Bytes";
            }
            enum "kbytes" {
              value 1;
              description
                "Kilobytes";
            }
            enum "mbytes" {
              value 2;
              description
                "Megabytes";
            }
            enum "ms" {
              value 3;
              description
                "Milliseconds";
            }
            enum "packets" {
              value 4;
              description
                "Packets (default)";
            }
            enum "us" {
              value 5;
              description
                "Microseconds";
            }
            enum "percent" {
              value 6;
              description
                "Configure queue limit value in percentage";
            }
          }
          description
            "queue-limit unit";
        }
        container discard-classes {
          description
            "discard class container";
          leaf-list discard-class {
            type uint8 {
              range "0..7";
            }
            description
              "Remaining bandwidth value.";
          }
        }
      }
    }
    container random-detect-default {
      presence "Enable RED with default min and max thresholds";
      description
        "Enable RED with default min and max thresholds";
    }
    container random-detect-ecn {
      presence "Enable ECN based WRED";
      description
        "ECN based WRED";
    }
    list random-detect {
      key "minimum-threshold-value minimum-threshold-unit maximum-threshold-value maximum-threshold-unit";
      description
        "Enable Random Early Detection.
         All RED profiles in a class must be based
         on the same field.";
      leaf minimum-threshold-value {
        type uint32 {
          range "0..1073741823";
        }
        description
          "Minimum threshold";
      }
      leaf minimum-threshold-unit {
        type wred-unit-type;
        description
          "threshold unit";
      }
      leaf maximum-threshold-value {
        type uint32 {
          range "0..1073741823";
        }
        description
          "Maximum threshold";
      }
      leaf maximum-threshold-unit {
        type wred-unit-type;
        description
          "threshold unit";
      }
      leaf-list cos {
        type uint8 {
          range "0..7" {
            description
              "COS  value";
          }
        }
        max-elements 8;
        description
          "COS based WRED (upto 8 values)";
      }
      leaf-list dei {
        type uint8 {
          range "0..1" {
            description
              "DEI value";
          }
        }
        max-elements 8;
        description
          "DEI based WRED";
      }
      leaf-list discard-class {
        type uint8 {
          range "0..7" {
            description
              "Discard Class  value";
          }
        }
        max-elements 8;
        description
          "Discard Class based WRED";
      }
      leaf-list dscp {
        type dscp-value;
        max-elements 8;
        description
          "DSCP based WRED";
      }
      leaf-list exp {
        type uint8 {
          range "0..7" {
            description
              "MPLS Experimental  value";
          }
        }
        max-elements 8;
        description
          "MPLS Experimental value based WRED";
      }
      leaf-list precedence {
        type union {
          type uint8 {
            range "0..7" {
              description
                "Precedence value";
            }
          }
          type enumeration {
            enum "critical" {
              value 0;
              description
                "Critical precedence (5)";
            }
            enum "flash" {
              value 1;
              description
                "Flash precedence (3)";
            }
            enum "flash-override" {
              value 2;
              description
                "Flash override precedence (4)";
            }
            enum "immediate" {
              value 3;
              description
                "Immediate precedence (2)";
            }
            enum "internet" {
              value 4;
              description
                "Internetwork control precedence (6)";
            }
            enum "network" {
              value 5;
              description
                "Network control precedence (7)";
            }
            enum "priority" {
              value 6;
              description
                "Priority precedence (1)";
            }
            enum "routine" {
              value 7;
              description
                "Routine precedence (0)";
            }
          }
        }
        max-elements 8;
        description
          "Precedence based WRED";
      }
    }
    leaf service-fragment {
      tailf:display-when "not(../ncs:module) or boolean(/ncs:devices/ncs:device[ncs:name=current()/../ncs:name]/capability/feature='action-service-fragment')";
      type string {
        length "1..64" {
          description
            "Name of Service fragment";
        }
      }
      description
        "Define a service fragment. Name of Service fragment";
    }
    container service-policy {
      description
        "Configure a child service policy";
      leaf name {
        type service-policy-name-type;
        description
          "Name of the child service policy";
      }
      leaf type {
        type enumeration {
          enum "pbr" {
            value 0;
            description
              "PBR policy-map";
          }
          enum "performance-traffic" {
            value 1;
            description
              "Performance traffic policy-map";
          }
          enum "qos" {
            value 2;
            description
              "QoS policy-map (default)";
          }
          enum "redirect" {
            value 3;
            description
              "Redirect policy-map";
          }
          enum "traffic" {
            value 4;
            description
              "Traffic policy-map";
          }
        }
        description
          "The type of policy-map";
      }
    }
    container set {
      description
        "Configure marking for this class";
      container atm-clp {
        tailf:display-when "not(../../ncs:module) or boolean(/ncs:devices/ncs:device[ncs:name=current()/../../ncs:name]/capability/feature='action-set-atm-clp')";
        presence "Set atm cell-loss-priority bit";
        description
          "Set atm cell-loss-priority bit";
      }
      leaf traffic-class {
        tailf:display-when "not(../../ncs:module) or boolean(/ncs:devices/ncs:device[ncs:name=current()/../../ncs:name]/capability/feature='action-set-traffic-class')";
        type uint8 {
          range "0..8" {
            description
              "Traffic class value";
          }
        }
        description
          "Sets the Traffic Class identifiers on IPv4 or MPLS packets.
           The set traffic-class is supported only on an ingress policy.";
      }
      leaf forward-class {
        tailf:display-when "not(../../ncs:module) or boolean(/ncs:devices/ncs:device[ncs:name=current()/../../ncs:name]/capability/feature='action-set-fwd-class')";
        type uint8 {
          range "1..7" {
            description
              "Forward class value";
          }
        }
        description
          "Set forward class";
      }
      uses action-common;
    }
    container shape {
      description
        "Configure shaping for this class";
      container average {
        description
          "Average rate shaping";
        container rate {
          must 'value and unit' {
            tailf:xpath-root 3;
          }
          presence "indicates rate is configured";
          description
            "Shape rate";
          leaf value {
            type union {
              type uint32 {
                range "1..4294967295" {
                  description
                    "Shape rate";
                }
              }
              type uint16 {
                range "1..1000" {
                  description
                    "Shape rate as parts per-thousand of available bandwidth";
                }
              }
              type uint32 {
                range "1..1000000" {
                  description
                    "Shape rate as parts per-million of available bandwidth";
                }
              }
              type uint8 {
                range "1..100" {
                  description
                    "Shape rate as percentage of available bandwidth";
                }
              }
              type string {
                pattern '[$][a-zA-Z0-9][a-zA-Z0-9\._@%+:\-]{0,32}[ ][=][ ]\d{1,10}';
              }
            }
          }
          leaf unit {
            type enumeration {
              enum "bps" {
                value 0;
                description
                  "Bits per second";
              }
              enum "cellsps" {
                value 1;
                description
                  "Cells per second";
              }
              enum "gbps" {
                value 2;
                description
                  "Gigabits per second";
              }
              enum "kbps" {
                value 3;
                description
                  "Kilobits per second";
              }
              enum "mbps" {
                value 4;
                description
                  "Megabits per second";
              }
              enum "per-thousand" {
                value 5;
                description
                  "Configure shape rate in per-thousand";
              }
              enum "per-million" {
                value 6;
                description
                  "Configure shape rate in per-million";
              }
              enum "percent" {
                value 7;
                description
                  "Configure shape rate in percentage";
              }
            }
            description
              "Shape rate unit";
          }
        }
        container excess-burst {
          tailf:display-when "not(../../../ncs:module) or boolean(/ncs:devices/ncs:device[ncs:name=current()/../../../ncs:name]/capability/feature='action-shape-burst')";
          must 'size and unit' {
            tailf:xpath-root 3;
          }
          presence "indicates excess-burst is configured";
          description
            "Excess burst size";
          leaf size {
            type uint32 {
              range "1..4294967295" {
                description
                  "Excess burst size";
              }
            }
          }
          leaf unit {
            type enumeration {
              enum "bytes" {
                value 0;
                description
                  "Bytes";
              }
              enum "cells" {
                value 1;
                description
                  "Cells";
              }
              enum "gbytes" {
                value 2;
                description
                  "Gigabytes";
              }
              enum "kbytes" {
                value 3;
                description
                  "Kilobytes";
              }
              enum "mbytes" {
                value 4;
                description
                  "Megabytes";
              }
              enum "ms" {
                value 5;
                description
                  "Milliseconds";
              }
              enum "packets" {
                value 6;
                description
                  "Packets";
              }
              enum "us" {
                value 7;
                description
                  "Microseconds";
              }
            }
          }
        }
      }
    }
  }

  grouping redirect-actions {
    uses policy-action-compress;
    uses policy-action-encap-sequence;
    container priority {
      presence "Test command";
      description
        "Test command";
    }
  }

  augment "/ncs:devices/ncs:device/ncs:config" {
    container class-map {
      tailf:ncs-device-type "netconf";
      tailf:display-when "not(../../ncs:module) or ../../ncs:module[ncs:name='Cisco-IOS-XR-um-policymap-classmap-cfg']";
      description
        "Configure a class-map";
      container type {
        description
          "class-map type";
        list qos {
          tailf:display-when "not(../../ncs:module) or boolean(/ncs:devices/ncs:device[ncs:name=current()/../../ncs:name]/capability/feature='cmap-type-qos')";
          must 'not(match-all and match-any)' {
            tailf:xpath-root 3;
          }
          key "class-map-name";
          description
            "QoS class-map";
          uses class-map-common;
          container match {
            description
              "Configure match criteria for this class.";
            uses match-access-group;
            uses match-atm;
            uses match-cac;
            uses match-cos;
            uses match-dei;
            uses match-destination-address;
            uses match-destination-port;
            uses match-discard-class;
            uses match-dscp;
            uses match-ethertype;
            uses match-flow-key;
            uses match-fr-de;
            uses match-fragment-type;
            uses match-frame-relay;
            uses match-ipv4;
            uses match-ipv6;
            uses match-mpls;
            uses match-packet;
            uses match-precedence;
            uses match-protocol;
            uses match-qos-group;
            uses match-source-address;
            uses match-source-port;
            uses match-tcp-flag;
            uses match-traffic-class;
            uses match-vlan;
            uses match-vpls;
          }
          container match-not {
            description
              "Negate match criteria";
            uses match-access-group {
              // NCS drop if-feature statement
              // NCS drop if-feature statement
              // NCS drop if-feature statement
            }
            uses match-cac {
              // NCS drop if-feature statement
            }
            uses match-cos;
            uses match-dei {
              // NCS drop if-feature statement
            }
            uses matchnot-destination-address;
            uses match-destination-port;
            uses match-discard-class;
            uses match-dscp;
            uses match-ethertype;
            uses match-fragment-type;
            uses match-frame-relay;
            uses match-ipv4;
            uses match-ipv6;
            uses matchnot-mpls;
            uses matchnot-packet;
            uses match-precedence;
            uses match-protocol;
            uses match-qos-group;
            uses matchnot-source-address;
            uses match-source-port;
            uses match-tcp-flag;
            uses match-traffic-class;
            uses matchnot-vlan;
            uses matchnot-vpls;
          }
        }
        list subscriber-control {
          must '(not(match-all) and not(match-any)) or match-all or match-any' {
            tailf:xpath-root 3;
          }
          key "class-map-name";
          description
            "Subscriber control class-map";
          uses class-map-common;
          container match {
            description
              "Configure match criteria for this class.";
            uses match-authen-status;
            uses match-circuit-id;
            uses match-dhcp-client-id;
            uses match-domain;
            uses match-control-protocol;
            uses match-remote-id;
            uses match-service-name;
            uses match-source-address;
            uses match-timer;
            uses match-username;
          }
          container match-not {
            description
              "Negate match criteria";
            uses match-authen-status {
              // NCS drop if-feature statement
            }
            uses match-circuit-id;
            uses match-dhcp-client-id;
            uses match-domain;
            uses match-control-protocol {
              // NCS drop if-feature statement
            }
            uses match-remote-id;
            uses match-service-name;
            uses match-source-address;
            uses match-timer {
              // NCS drop if-feature statement
            }
            uses match-username {
              // NCS drop if-feature statement
            }
          }
        }
        list traffic {
          tailf:display-when "not(../../ncs:module) or boolean(/ncs:devices/ncs:device[ncs:name=current()/../../ncs:name]/capability/feature='cmap-type-traffic')";
          must 'not(match-all and match-any)' {
            tailf:xpath-root 3;
          }
          key "class-map-name";
          description
            "Traffic class-map";
          uses class-map-common;
          container match {
            description
              "Configure match criteria for this class.";
            uses match-access-group;
            uses match-atm;
            uses match-cos;
            uses match-dei;
            uses match-destination-address;
            uses match-destination-port;
            uses match-dscp;
            uses match-ethertype;
            uses match-flow-key;
            uses match-flow-tag;
            uses match-fr-de;
            uses match-fragment-type;
            uses match-frame-relay;
            uses match-ipv4 {
              when 'boolean(../match-all)' {
                tailf:xpath-root 3;
              }
            }
            uses match-ipv6 {
              when 'boolean(../match-all)' {
                tailf:xpath-root 3;
              }
            }
            uses match-mpls;
            uses match-packet;
            uses match-precedence;
            uses match-protocol;
            uses match-source-address;
            uses match-source-port;
            uses match-tcp-flag;
            uses match-vlan;
            uses match-vpls;
          }
          container match-not {
            description
              "Negate match criteria";
            uses match-access-group;
            uses match-atm;
            uses match-cos;
            uses match-dei;
            uses matchnot-destination-address;
            uses match-destination-port;
            uses match-dscp;
            uses match-ethertype {
              // NCS drop if-feature statement
            }
            uses match-flow-tag {
              // NCS drop if-feature statement
            }
            uses match-fr-de {
              // NCS drop if-feature statement
            }
            uses match-fragment-type;
            uses match-frame-relay {
              // NCS drop if-feature statement
            }
            uses match-ipv4 {
              when 'boolean(../match-all)' {
                tailf:xpath-root 3;
              }
            }
            uses match-ipv6 {
              when 'boolean(../match-all)' {
                tailf:xpath-root 3;
              }
            }
            uses matchnot-mpls;
            uses matchnot-packet;
            uses match-precedence;
            uses match-protocol;
            uses matchnot-source-address;
            uses match-source-port;
            uses match-tcp-flag;
            uses matchnot-vlan;
            uses matchnot-vpls;
          }
        }
      }
    }
    container policy-map {
      tailf:ncs-device-type "netconf";
      tailf:display-when "not(../../ncs:module) or ../../ncs:module[ncs:name='Cisco-IOS-XR-um-policymap-classmap-cfg']";
      description
        "Configure a policy-map";
      container type {
        description
          "policy-map type";
        list accounting {
          tailf:display-when "not(../../ncs:module) or boolean(/ncs:devices/ncs:device[ncs:name=current()/../../ncs:name]/capability/feature='pmap-type-accounting')";
          key "policy-map-name";
          description
            "Accounting policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic Classmap.";
                }
              }
              description
                "The type of classmap";
            }
          }
        }
        list subscriber-control {
          tailf:display-when "not(../../ncs:module) or boolean(/ncs:devices/ncs:device[ncs:name=current()/../../ncs:name]/capability/feature='pmap-type-control')";
          key "policy-map-name";
          description
            "Subscriber control policy-map";
          uses policy-map-common;
          list event {
            must 'not(match-all and match-first)' {
              tailf:xpath-root 3;
            }
            key "type";
            description
              "Policy event";
            leaf type {
              type event-type;
              description
                "Policy event type";
            }
            container match-all {
              presence "Execute all the matched classes";
              description
                "Execute all the matched classes";
            }
            container match-first {
              presence "Execute only the first matched class";
              description
                "Execute only the first matched class";
            }
            list class {
              key "name type";
              description
                "Class-map";
              leaf name {
                type string {
                  pattern '[a-zA-Z0-9][a-zA-Z0-9\._@$%+#:=<>\-]{0,62}' {
                    description
                      "Any string except 'type'";
                  }
                }
                description
                  "Name of the class-map";
              }
              leaf type {
                type enumeration {
                  enum "subscriber-control" {
                    value 4;
                    description
                      "Control Subscriber Classmap.";
                  }
                }
                description
                  "The type of classmap";
              }
              leaf action-strategy {
                type enumeration {
                  enum "do-all" {
                    value 0;
                    description
                      "Do all actions";
                  }
                  enum "do-until-failure" {
                    value 1;
                    description
                      "Do all actions until failure";
                  }
                  enum "do-until-success" {
                    value 2;
                    description
                      "Do all actions until success";
                  }
                }
                description
                  "Strategy to execute class-map actions";
              }
              list action {
                key "sequence-number";
                leaf sequence-number {
                  type uint16 {
                    range "1..65535";
                  }
                  description
                    "Sequence number for this action";
                }
                uses subscriber-actions;
              }
            }
          }
        }
        list pbr {
          tailf:display-when "not(../../ncs:module) or boolean(/ncs:devices/ncs:device[ncs:name=current()/../../ncs:name]/capability/feature='pmap-type-pbr')";
          key "policy-map-name";
          description
            "PBR policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses pbr-actions;
          }
        }
        list performance-traffic {
          tailf:display-when "not(../../ncs:module) or boolean(/ncs:devices/ncs:device[ncs:name=current()/../../ncs:name]/capability/feature='pmap-type-afmon')";
          key "policy-map-name";
          description
            "Performance traffic policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses performance-traffic-actions;
          }
        }
        list qos {
          tailf:display-when "not(../../ncs:module) or boolean(/ncs:devices/ncs:device[ncs:name=current()/../../ncs:name]/capability/feature='pmap-type-qos')";
          key "policy-map-name";
          description
            "QoS policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "qos" {
                  value 1;
                  description
                    "QoS class-map.";
                }
                enum "traffic" {
                  value 3;
                  description
                    "Traffic class-map.";
                }
              }
              description
                "The type of class-map";
            }
            uses qos-actions;
          }
        }
        list redirect {
          tailf:display-when "not(../../ncs:module) or boolean(/ncs:devices/ncs:device[ncs:name=current()/../../ncs:name]/capability/feature='pmap-type-redirect')";
          key "policy-map-name";
          description
            "Redirect policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses redirect-actions;
          }
        }
        list traffic {
          tailf:display-when "not(../../ncs:module) or boolean(/ncs:devices/ncs:device[ncs:name=current()/../../ncs:name]/capability/feature='pmap-type-traffic')";
          key "policy-map-name";
          description
            "Traffic policy-map";
          uses policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses policy-action-compress;
            uses policy-action-encap-sequence;
          }
        }
      }
    }
  }
  augment "/ncs:devices/ncs:device/ncs:live-status" {
    container class-map {
      tailf:ncs-device-type "netconf";
      tailf:display-when "not(../../ncs:module) or ../../ncs:module[ncs:name='Cisco-IOS-XR-um-policymap-classmap-cfg'] or (../../ncs:live-status-protocol[not(ncs:capability)]) or (../../ncs:live-status-protocol/ncs:capability/ncs:module[.='Cisco-IOS-XR-um-policymap-classmap-cfg'])";
      description
        "Configure a class-map";
      container type {
        description
          "class-map type";
        list qos {
          // NCS drop if-feature statement
          // NCS drop must statement
          key "class-map-name";
          description
            "QoS class-map";
          uses live_ncs_class-map-common;
          container match {
            description
              "Configure match criteria for this class.";
            uses live_ncs_match-access-group;
            uses live_ncs_match-atm;
            uses live_ncs_match-cac;
            uses live_ncs_match-cos;
            uses live_ncs_match-dei;
            uses live_ncs_match-destination-address;
            uses live_ncs_match-destination-port;
            uses live_ncs_match-discard-class;
            uses live_ncs_match-dscp;
            uses live_ncs_match-ethertype;
            uses live_ncs_match-flow-key;
            uses live_ncs_match-fr-de;
            uses live_ncs_match-fragment-type;
            uses live_ncs_match-frame-relay;
            uses live_ncs_match-ipv4;
            uses live_ncs_match-ipv6;
            uses live_ncs_match-mpls;
            uses live_ncs_match-packet;
            uses live_ncs_match-precedence;
            uses live_ncs_match-protocol;
            uses live_ncs_match-qos-group;
            uses live_ncs_match-source-address;
            uses live_ncs_match-source-port;
            uses live_ncs_match-tcp-flag;
            uses live_ncs_match-traffic-class;
            uses live_ncs_match-vlan;
            uses live_ncs_match-vpls;
          }
          container match-not {
            description
              "Negate match criteria";
            uses live_ncs_match-access-group {
              // NCS drop if-feature statement
              // NCS drop if-feature statement
              // NCS drop if-feature statement
            }
            uses live_ncs_match-cac {
              // NCS drop if-feature statement
            }
            uses live_ncs_match-cos;
            uses live_ncs_match-dei {
              // NCS drop if-feature statement
            }
            uses live_ncs_matchnot-destination-address;
            uses live_ncs_match-destination-port;
            uses live_ncs_match-discard-class;
            uses live_ncs_match-dscp;
            uses live_ncs_match-ethertype;
            uses live_ncs_match-fragment-type;
            uses live_ncs_match-frame-relay;
            uses live_ncs_match-ipv4;
            uses live_ncs_match-ipv6;
            uses live_ncs_matchnot-mpls;
            uses live_ncs_matchnot-packet;
            uses live_ncs_match-precedence;
            uses live_ncs_match-protocol;
            uses live_ncs_match-qos-group;
            uses live_ncs_matchnot-source-address;
            uses live_ncs_match-source-port;
            uses live_ncs_match-tcp-flag;
            uses live_ncs_match-traffic-class;
            uses live_ncs_matchnot-vlan;
            uses live_ncs_matchnot-vpls;
          }
        }
        list subscriber-control {
          // NCS drop must statement
          key "class-map-name";
          description
            "Subscriber control class-map";
          uses live_ncs_class-map-common;
          container match {
            description
              "Configure match criteria for this class.";
            uses live_ncs_match-authen-status;
            uses live_ncs_match-circuit-id;
            uses live_ncs_match-dhcp-client-id;
            uses live_ncs_match-domain;
            uses live_ncs_match-control-protocol;
            uses live_ncs_match-remote-id;
            uses live_ncs_match-service-name;
            uses live_ncs_match-source-address;
            uses live_ncs_match-timer;
            uses live_ncs_match-username;
          }
          container match-not {
            description
              "Negate match criteria";
            uses live_ncs_match-authen-status {
              // NCS drop if-feature statement
            }
            uses live_ncs_match-circuit-id;
            uses live_ncs_match-dhcp-client-id;
            uses live_ncs_match-domain;
            uses live_ncs_match-control-protocol {
              // NCS drop if-feature statement
            }
            uses live_ncs_match-remote-id;
            uses live_ncs_match-service-name;
            uses live_ncs_match-source-address;
            uses live_ncs_match-timer {
              // NCS drop if-feature statement
            }
            uses live_ncs_match-username {
              // NCS drop if-feature statement
            }
          }
        }
        list traffic {
          // NCS drop if-feature statement
          // NCS drop must statement
          key "class-map-name";
          description
            "Traffic class-map";
          uses live_ncs_class-map-common;
          container match {
            description
              "Configure match criteria for this class.";
            uses live_ncs_match-access-group;
            uses live_ncs_match-atm;
            uses live_ncs_match-cos;
            uses live_ncs_match-dei;
            uses live_ncs_match-destination-address;
            uses live_ncs_match-destination-port;
            uses live_ncs_match-dscp;
            uses live_ncs_match-ethertype;
            uses live_ncs_match-flow-key;
            uses live_ncs_match-flow-tag;
            uses live_ncs_match-fr-de;
            uses live_ncs_match-fragment-type;
            uses live_ncs_match-frame-relay;
            uses live_ncs_match-ipv4 {
              // NCS drop when statement
            }
            uses live_ncs_match-ipv6 {
              // NCS drop when statement
            }
            uses live_ncs_match-mpls;
            uses live_ncs_match-packet;
            uses live_ncs_match-precedence;
            uses live_ncs_match-protocol;
            uses live_ncs_match-source-address;
            uses live_ncs_match-source-port;
            uses live_ncs_match-tcp-flag;
            uses live_ncs_match-vlan;
            uses live_ncs_match-vpls;
          }
          container match-not {
            description
              "Negate match criteria";
            uses live_ncs_match-access-group;
            uses live_ncs_match-atm;
            uses live_ncs_match-cos;
            uses live_ncs_match-dei;
            uses live_ncs_matchnot-destination-address;
            uses live_ncs_match-destination-port;
            uses live_ncs_match-dscp;
            uses live_ncs_match-ethertype {
              // NCS drop if-feature statement
            }
            uses live_ncs_match-flow-tag {
              // NCS drop if-feature statement
            }
            uses live_ncs_match-fr-de {
              // NCS drop if-feature statement
            }
            uses live_ncs_match-fragment-type;
            uses live_ncs_match-frame-relay {
              // NCS drop if-feature statement
            }
            uses live_ncs_match-ipv4 {
              // NCS drop when statement
            }
            uses live_ncs_match-ipv6 {
              // NCS drop when statement
            }
            uses live_ncs_matchnot-mpls;
            uses live_ncs_matchnot-packet;
            uses live_ncs_match-precedence;
            uses live_ncs_match-protocol;
            uses live_ncs_matchnot-source-address;
            uses live_ncs_match-source-port;
            uses live_ncs_match-tcp-flag;
            uses live_ncs_matchnot-vlan;
            uses live_ncs_matchnot-vpls;
          }
        }
      }
    }
    container policy-map {
      tailf:ncs-device-type "netconf";
      tailf:display-when "not(../../ncs:module) or ../../ncs:module[ncs:name='Cisco-IOS-XR-um-policymap-classmap-cfg'] or (../../ncs:live-status-protocol[not(ncs:capability)]) or (../../ncs:live-status-protocol/ncs:capability/ncs:module[.='Cisco-IOS-XR-um-policymap-classmap-cfg'])";
      description
        "Configure a policy-map";
      container type {
        description
          "policy-map type";
        list accounting {
          // NCS drop if-feature statement
          key "policy-map-name";
          description
            "Accounting policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic Classmap.";
                }
              }
              description
                "The type of classmap";
            }
          }
        }
        list subscriber-control {
          // NCS drop if-feature statement
          key "policy-map-name";
          description
            "Subscriber control policy-map";
          uses live_ncs_policy-map-common;
          list event {
            // NCS drop must statement
            key "type";
            description
              "Policy event";
            leaf type {
              type live_ncs_event-type;
              description
                "Policy event type";
            }
            container match-all {
              presence "Execute all the matched classes";
              description
                "Execute all the matched classes";
            }
            container match-first {
              presence "Execute only the first matched class";
              description
                "Execute only the first matched class";
            }
            list class {
              key "name type";
              description
                "Class-map";
              leaf name {
                type string {
                  pattern '[a-zA-Z0-9][a-zA-Z0-9\._@$%+#:=<>\-]{0,62}' {
                    description
                      "Any string except 'type'";
                  }
                }
                description
                  "Name of the class-map";
              }
              leaf type {
                type enumeration {
                  enum "subscriber-control" {
                    value 4;
                    description
                      "Control Subscriber Classmap.";
                  }
                }
                description
                  "The type of classmap";
              }
              leaf action-strategy {
                type enumeration {
                  enum "do-all" {
                    value 0;
                    description
                      "Do all actions";
                  }
                  enum "do-until-failure" {
                    value 1;
                    description
                      "Do all actions until failure";
                  }
                  enum "do-until-success" {
                    value 2;
                    description
                      "Do all actions until success";
                  }
                }
                description
                  "Strategy to execute class-map actions";
              }
              list action {
                key "sequence-number";
                leaf sequence-number {
                  type uint16 {
                    range "1..65535";
                  }
                  description
                    "Sequence number for this action";
                }
                uses live_ncs_subscriber-actions;
              }
            }
          }
        }
        list pbr {
          // NCS drop if-feature statement
          key "policy-map-name";
          description
            "PBR policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses live_ncs_pbr-actions;
          }
        }
        list performance-traffic {
          // NCS drop if-feature statement
          key "policy-map-name";
          description
            "Performance traffic policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses live_ncs_performance-traffic-actions;
          }
        }
        list qos {
          // NCS drop if-feature statement
          key "policy-map-name";
          description
            "QoS policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "qos" {
                  value 1;
                  description
                    "QoS class-map.";
                }
                enum "traffic" {
                  value 3;
                  description
                    "Traffic class-map.";
                }
              }
              description
                "The type of class-map";
            }
            uses live_ncs_qos-actions;
          }
        }
        list redirect {
          // NCS drop if-feature statement
          key "policy-map-name";
          description
            "Redirect policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses live_ncs_redirect-actions;
          }
        }
        list traffic {
          // NCS drop if-feature statement
          key "policy-map-name";
          description
            "Traffic policy-map";
          uses live_ncs_policy-map-common;
          list class {
            key "name type";
            leaf name {
              type string {
                pattern '[a-zA-Z0-9][a-zA-Z0-9\._@$%+#:=<>\-]{0,62}' {
                  description
                    "Any string except 'type'";
                }
              }
              description
                "Name of the class-map";
            }
            leaf type {
              type enumeration {
                enum "traffic" {
                  value 3;
                  description
                    "Traffic class-map.";
                }
              }
              description
                "The type of class-map";
            }
            uses live_ncs_policy-action-compress;
            uses live_ncs_policy-action-encap-sequence;
          }
        }
      }
    }
  }
  augment "/ncs:devices/ncs:template/ncs:ned-id/ncs:config" {
    container class-map {
      description
        "Configure a class-map";
      container type {
        description
          "class-map type";
        list qos {
          // NCS patched for predictable order
          ordered-by user;
          // NCS drop if-feature statement
          // NCS drop must statement
          key "class-map-name";
          description
            "QoS class-map";
          uses ncs_template_class-map-common;
          container match {
            description
              "Configure match criteria for this class.";
            uses ncs_template_match-access-group;
            uses ncs_template_match-atm;
            uses ncs_template_match-cac;
            uses ncs_template_match-cos;
            uses ncs_template_match-dei;
            uses ncs_template_match-destination-address;
            uses ncs_template_match-destination-port;
            uses ncs_template_match-discard-class;
            uses ncs_template_match-dscp;
            uses ncs_template_match-ethertype;
            uses ncs_template_match-flow-key;
            uses ncs_template_match-fr-de;
            uses ncs_template_match-fragment-type;
            uses ncs_template_match-frame-relay;
            uses ncs_template_match-ipv4;
            uses ncs_template_match-ipv6;
            uses ncs_template_match-mpls;
            uses ncs_template_match-packet;
            uses ncs_template_match-precedence;
            uses ncs_template_match-protocol;
            uses ncs_template_match-qos-group;
            uses ncs_template_match-source-address;
            uses ncs_template_match-source-port;
            uses ncs_template_match-tcp-flag;
            uses ncs_template_match-traffic-class;
            uses ncs_template_match-vlan;
            uses ncs_template_match-vpls;
          }
          container match-not {
            description
              "Negate match criteria";
            uses ncs_template_match-access-group {
              // NCS drop if-feature statement
              // NCS drop if-feature statement
              // NCS drop if-feature statement
            }
            uses ncs_template_match-cac {
              // NCS drop if-feature statement
            }
            uses ncs_template_match-cos;
            uses ncs_template_match-dei {
              // NCS drop if-feature statement
            }
            uses ncs_template_matchnot-destination-address;
            uses ncs_template_match-destination-port;
            uses ncs_template_match-discard-class;
            uses ncs_template_match-dscp;
            uses ncs_template_match-ethertype;
            uses ncs_template_match-fragment-type;
            uses ncs_template_match-frame-relay;
            uses ncs_template_match-ipv4;
            uses ncs_template_match-ipv6;
            uses ncs_template_matchnot-mpls;
            uses ncs_template_matchnot-packet;
            uses ncs_template_match-precedence;
            uses ncs_template_match-protocol;
            uses ncs_template_match-qos-group;
            uses ncs_template_matchnot-source-address;
            uses ncs_template_match-source-port;
            uses ncs_template_match-tcp-flag;
            uses ncs_template_match-traffic-class;
            uses ncs_template_matchnot-vlan;
            uses ncs_template_matchnot-vpls;
          }
        }
        list subscriber-control {
          // NCS patched for predictable order
          ordered-by user;
          // NCS drop must statement
          key "class-map-name";
          description
            "Subscriber control class-map";
          uses ncs_template_class-map-common;
          container match {
            description
              "Configure match criteria for this class.";
            uses ncs_template_match-authen-status;
            uses ncs_template_match-circuit-id;
            uses ncs_template_match-dhcp-client-id;
            uses ncs_template_match-domain;
            uses ncs_template_match-control-protocol;
            uses ncs_template_match-remote-id;
            uses ncs_template_match-service-name;
            uses ncs_template_match-source-address;
            uses ncs_template_match-timer;
            uses ncs_template_match-username;
          }
          container match-not {
            description
              "Negate match criteria";
            uses ncs_template_match-authen-status {
              // NCS drop if-feature statement
            }
            uses ncs_template_match-circuit-id;
            uses ncs_template_match-dhcp-client-id;
            uses ncs_template_match-domain;
            uses ncs_template_match-control-protocol {
              // NCS drop if-feature statement
            }
            uses ncs_template_match-remote-id;
            uses ncs_template_match-service-name;
            uses ncs_template_match-source-address;
            uses ncs_template_match-timer {
              // NCS drop if-feature statement
            }
            uses ncs_template_match-username {
              // NCS drop if-feature statement
            }
          }
        }
        list traffic {
          // NCS patched for predictable order
          ordered-by user;
          // NCS drop if-feature statement
          // NCS drop must statement
          key "class-map-name";
          description
            "Traffic class-map";
          uses ncs_template_class-map-common;
          container match {
            description
              "Configure match criteria for this class.";
            uses ncs_template_match-access-group;
            uses ncs_template_match-atm;
            uses ncs_template_match-cos;
            uses ncs_template_match-dei;
            uses ncs_template_match-destination-address;
            uses ncs_template_match-destination-port;
            uses ncs_template_match-dscp;
            uses ncs_template_match-ethertype;
            uses ncs_template_match-flow-key;
            uses ncs_template_match-flow-tag;
            uses ncs_template_match-fr-de;
            uses ncs_template_match-fragment-type;
            uses ncs_template_match-frame-relay;
            uses ncs_template_match-ipv4 {
              // NCS drop when statement
            }
            uses ncs_template_match-ipv6 {
              // NCS drop when statement
            }
            uses ncs_template_match-mpls;
            uses ncs_template_match-packet;
            uses ncs_template_match-precedence;
            uses ncs_template_match-protocol;
            uses ncs_template_match-source-address;
            uses ncs_template_match-source-port;
            uses ncs_template_match-tcp-flag;
            uses ncs_template_match-vlan;
            uses ncs_template_match-vpls;
          }
          container match-not {
            description
              "Negate match criteria";
            uses ncs_template_match-access-group;
            uses ncs_template_match-atm;
            uses ncs_template_match-cos;
            uses ncs_template_match-dei;
            uses ncs_template_matchnot-destination-address;
            uses ncs_template_match-destination-port;
            uses ncs_template_match-dscp;
            uses ncs_template_match-ethertype {
              // NCS drop if-feature statement
            }
            uses ncs_template_match-flow-tag {
              // NCS drop if-feature statement
            }
            uses ncs_template_match-fr-de {
              // NCS drop if-feature statement
            }
            uses ncs_template_match-fragment-type;
            uses ncs_template_match-frame-relay {
              // NCS drop if-feature statement
            }
            uses ncs_template_match-ipv4 {
              // NCS drop when statement
            }
            uses ncs_template_match-ipv6 {
              // NCS drop when statement
            }
            uses ncs_template_matchnot-mpls;
            uses ncs_template_matchnot-packet;
            uses ncs_template_match-precedence;
            uses ncs_template_match-protocol;
            uses ncs_template_matchnot-source-address;
            uses ncs_template_match-source-port;
            uses ncs_template_match-tcp-flag;
            uses ncs_template_matchnot-vlan;
            uses ncs_template_matchnot-vpls;
          }
        }
      }
    }
    container policy-map {
      description
        "Configure a policy-map";
      container type {
        description
          "policy-map type";
        list accounting {
          // NCS patched for predictable order
          ordered-by user;
          // NCS drop if-feature statement
          key "policy-map-name";
          description
            "Accounting policy-map";
          uses ncs_template_policy-map-common;
          list class {
            // NCS patched for predictable order
            ordered-by user;
            key "name type";
            leaf name {
              type string;
              description
                "Name of the class-map";
            }
            leaf type {
              type string;
              description
                "The type of classmap";
            }
          }
        }
        list subscriber-control {
          // NCS patched for predictable order
          ordered-by user;
          // NCS drop if-feature statement
          key "policy-map-name";
          description
            "Subscriber control policy-map";
          uses ncs_template_policy-map-common;
          list event {
            // NCS patched for predictable order
            ordered-by user;
            // NCS drop must statement
            key "type";
            description
              "Policy event";
            leaf type {
              type ncs_template_event-type;
              description
                "Policy event type";
            }
            container match-all {
              presence "Execute all the matched classes";
              description
                "Execute all the matched classes";
            }
            container match-first {
              presence "Execute only the first matched class";
              description
                "Execute only the first matched class";
            }
            list class {
              // NCS patched for predictable order
              ordered-by user;
              key "name type";
              description
                "Class-map";
              leaf name {
                type string;
                description
                  "Name of the class-map";
              }
              leaf type {
                type string;
                description
                  "The type of classmap";
              }
              leaf action-strategy {
                type string;
                description
                  "Strategy to execute class-map actions";
              }
              list action {
                // NCS patched for predictable order
                ordered-by user;
                key "sequence-number";
                leaf sequence-number {
                  type string;
                  description
                    "Sequence number for this action";
                }
                uses ncs_template_subscriber-actions;
              }
            }
          }
        }
        list pbr {
          // NCS patched for predictable order
          ordered-by user;
          // NCS drop if-feature statement
          key "policy-map-name";
          description
            "PBR policy-map";
          uses ncs_template_policy-map-common;
          list class {
            // NCS patched for predictable order
            ordered-by user;
            key "name type";
            leaf name {
              type string;
              description
                "Name of the class-map";
            }
            leaf type {
              type string;
              description
                "The type of class-map";
            }
            uses ncs_template_pbr-actions;
          }
        }
        list performance-traffic {
          // NCS patched for predictable order
          ordered-by user;
          // NCS drop if-feature statement
          key "policy-map-name";
          description
            "Performance traffic policy-map";
          uses ncs_template_policy-map-common;
          list class {
            // NCS patched for predictable order
            ordered-by user;
            key "name type";
            leaf name {
              type string;
              description
                "Name of the class-map";
            }
            leaf type {
              type string;
              description
                "The type of class-map";
            }
            uses ncs_template_performance-traffic-actions;
          }
        }
        list qos {
          // NCS patched for predictable order
          ordered-by user;
          // NCS drop if-feature statement
          key "policy-map-name";
          description
            "QoS policy-map";
          uses ncs_template_policy-map-common;
          list class {
            // NCS patched for predictable order
            ordered-by user;
            key "name type";
            leaf name {
              type string;
              description
                "Name of the class-map";
            }
            leaf type {
              type string;
              description
                "The type of class-map";
            }
            uses ncs_template_qos-actions;
          }
        }
        list redirect {
          // NCS patched for predictable order
          ordered-by user;
          // NCS drop if-feature statement
          key "policy-map-name";
          description
            "Redirect policy-map";
          uses ncs_template_policy-map-common;
          list class {
            // NCS patched for predictable order
            ordered-by user;
            key "name type";
            leaf name {
              type string;
              description
                "Name of the class-map";
            }
            leaf type {
              type string;
              description
                "The type of class-map";
            }
            uses ncs_template_redirect-actions;
          }
        }
        list traffic {
          // NCS patched for predictable order
          ordered-by user;
          // NCS drop if-feature statement
          key "policy-map-name";
          description
            "Traffic policy-map";
          uses ncs_template_policy-map-common;
          list class {
            // NCS patched for predictable order
            ordered-by user;
            key "name type";
            leaf name {
              type string;
              description
                "Name of the class-map";
            }
            leaf type {
              type string;
              description
                "The type of class-map";
            }
            uses ncs_template_policy-action-compress;
            uses ncs_template_policy-action-encap-sequence;
          }
        }
      }
    }
  }

  feature action-shape-burst {
    description
      "Excess burst size";
  }

  feature action-set-traffic-class {
    description
      "Set the Traffic Class identifiers on IPv4 or MPLS packets";
  }

  feature action-set-atm-clp {
    description
      "Set atm cell-loss-priority bit";
  }

  feature action-police-set-fr-de {
    description
      "Set frame relay discard-eligible bit";
  }

  feature action-police-coupled {
    description
      "Coupled policing";
  }

  feature action-police-exceed-color {
    description
      "Exceed color class for color aware policing";
  }

  feature action-police-conform-color {
    description
      "Conform color class for color aware policing";
  }

  feature action-police-peak-burst {
    description
      "Excess burst size";
  }

  feature action-pfc {
    description
      "PFC feature";
  }

  feature action-service-fragment {
    description
      "Refer to an existing service fragment";
  }

  feature action-bandwidth {
    description
      "Bandwidth";
  }

  feature action-cac {
    description
      "Call admission control action";
  }

  feature action-react-grouped-alarm {
    description
      "Grouped alarms";
  }

  feature action-react-alarm {
    description
      "Alarms";
  }

  feature action-react-snmp {
    description
      "Report via snmp";
  }

  feature action-react {
    description
      "Generate alert on specific event";
  }

  feature action-decap-gre {
    description
      "Decapsulate GRE packet";
  }

  feature action-transmit {
    description
      "Forward packet to the original destination";
  }

  feature action-set-src-address {
    description
      "Set source address";
  }

  feature action-set-fwd-class {
    description
      "Set forward class";
  }

  feature action-set-df {
    description
      "Set DF bit";
  }

  feature action-set-dst-address {
    description
      "Set destination address";
  }

  feature action-service-function {
    description
      "NSH service function action";
  }

  feature action-redirect-rt {
    description
      "Forward to specific route-target";
  }

  feature action-redirect-nexthop {
    description
      "PBF redirect nexthop action";
  }

  feature action-http-enrichment {
    description
      "HTTP enrichment action";
  }

  feature action-http-redirect {
    description
      "HTTP redirect action";
  }

  feature action-stop-timer {
    description
      "Disable timer before it expires";
  }

  feature action-set-timer {
    description
      "Set a timer to execute a rule on its expiry";
  }

  feature action-monitor {
    description
      "Monitor session";
  }

  feature action-disconnect {
    description
      "Disconnect session";
  }

  feature action-authorize {
    description
      "Authorization related action";
  }

  feature action-authenticate {
    description
      "Authentication related action";
  }

  feature action-encap-sequence {
    description
      "Encapsulation sequence action";
  }

  feature action-compress-header-ip {
    description
      "IP header compression action";
  }

  feature matchnot-mpls-disp-ipv6-acl {
    description
      "Not match based on MPLS Label Disposition IPv6 access list";
  }

  feature matchnot-mpls-disp-ipv4-acl {
    description
      "Not match based on MPLS Label Disposition IPv4 access list";
  }

  feature matchnot-mac-address {
    description
      "Not match based on MAC address";
  }

  feature matchnot-flow-tag {
    description
      "Not match based on flow-tag";
  }

  feature matchnot-vpls-mcast {
    description
      "Not match based on VPLS field multicast";
  }

  feature matchnot-vpls-control {
    description
      "Not match based on VPLS field control";
  }

  feature matchnot-vpls-bcast {
    description
      "Not match based on VPLS field broadcast";
  }

  feature matchnot-vpls-unknown {
    description
      "Not match based on VPLS field unknown";
  }

  feature matchnot-vpls-known {
    description
      "Not match based on VPLS field known";
  }

  feature matchnot-vlan-inner {
    description
      "Not match based on inner Vlan Ids";
  }

  feature matchnot-vlan {
    description
      "Not match based on Vlan Ids";
  }

  feature matchnot-ipv6-packet-length {
    description
      "Not match based on IPV6 packet length";
  }

  feature matchnot-ipv4-packet-length {
    description
      "Not match based on IPV4 packet length";
  }

  feature matchnot-fr {
    description
      "Not match based on FrameRelay";
  }

  feature matchnot-fr-de {
    description
      "Not match based on FR DE";
  }

  feature matchnot-ethertype {
    description
      "Not match based on ethertype";
  }

  feature matchnot-username {
    description
      "Not match based on user name";
  }

  feature matchnot-timer {
    description
      "Not match based on timer";
  }

  feature matchnot-protocol {
    description
      "Not match based on protocol";
  }

  feature matchnot-authen-status {
    description
      "Not match based on authentication status";
  }

  feature matchnot-dei {
    description
      "Not match based on DEI bit";
  }

  feature matchnot-cac-local {
    description
      "Not match based on CAC";
  }

  feature matchnot-es-acl {
    description
      "Not match based on ethernet services access-list";
  }

  feature matchnot-ipv6-acl {
    description
      "Not match based on IPV6 access-list";
  }

  feature matchnot-ipv4-acl {
    description
      "Not match based on IPV4 access-list";
  }

  feature match-vpls-control {
    description
      "Match based on VPLS field control";
  }

  feature match-vpls-unknown {
    description
      "Match based on VPLS field unknown";
  }

  feature match-vpls-known {
    description
      "Match based on VPLS field known";
  }

  feature match-username {
    description
      "Match based on user name";
  }

  feature match-timer {
    description
      "Match based on timer";
  }

  feature match-authen-status {
    description
      "Match based on authentication status";
  }

  feature match-ipv6-packet-length {
    description
      "Match based on IPV6 packet length";
  }

  feature match-ipv4-packet-length {
    description
      "Match based on IPV4 packet length";
  }

  feature match-mpls-exp-imposition {
    description
      "Match based on MPLS experimental imposition label";
  }

  feature match-mpls-disp-cmap {
    description
      "Match based on MPLS Label Disposition class-map";
  }

  feature match-mpls-disp-ipv6-acl {
    description
      "Match based on MPLS Label Disposition IPv6 access list";
  }

  feature match-mpls-disp-ipv4-acl {
    description
      "Match based on MPLS Label Disposition IPv4 access list";
  }

  feature match-fr {
    description
      "Match based on frame-relay specific criteria";
  }

  feature match-fr-de {
    description
      "Match based on FrameRelay DE bit";
  }

  feature match-fragment-type {
    description
      "Match based on fragment type";
  }

  feature match-flow-key {
    description
      "Match based on flow keys";
  }

  feature match-ethertype {
    description
      "Match based on ethertype";
  }

  feature match-discard-class {
    description
      "Match based on discard class";
  }

  feature match-dei-inner {
    description
      "Match inner based on DEI bit";
  }

  feature match-dei {
    description
      "Match based on DEI bit";
  }

  feature match-cac {
    description
      "Match based on CAC fields";
  }

  feature match-atm {
    description
      "Match based on ATM specific criteria";
  }

  feature match-dst-addr-ipv6 {
    description
      "Match based on ipv6 destination address";
  }

  feature match-src-addr-ipv6 {
    description
      "Match based on ipv6 source address";
  }

  feature match-dst-addr-ipv4 {
    description
      "Match based on ipv4 destination address";
  }

  feature match-src-addr-ipv4 {
    description
      "Match based on ipv4 source address";
  }

  feature match-dst-mac {
    description
      "Match based on MAC destination address";
  }

  feature match-src-mac {
    description
      "Match based on MAC source address";
  }

  feature match-destination-port {
    description
      "Match based on destination port";
  }

  feature match-source-port {
    description
      "Match based on source port";
  }

  feature match-vlan-inner {
    description
      "Match based on inner Vlan Ids";
  }

  feature match-vlan {
    description
      "Match based on Vlan Ids";
  }

  feature match-cos-inner {
    description
      "Match inner based on COS";
  }

  feature match-cos {
    description
      "Match based on COS";
  }

  feature match-mpls-exp-top {
    description
      "Match based on mpls experimental topmost";
  }

  feature match-proto {
    description
      "Match based on protocol";
  }

  feature match-prec {
    description
      "Match based on precedence";
  }

  feature match-dscp {
    description
      "Match based on DSCP";
  }

  feature match-ipv6-prec {
    description
      "Match based on ipv6 precedence";
  }

  feature match-ipv6-dscp {
    description
      "Match based on ipv6 DSCP";
  }

  feature match-ipv4-prec {
    description
      "Match based on ipv4 precedence";
  }

  feature match-ipv4-dscp {
    description
      "Match based on ipv4 DSCP";
  }

  feature match-ethernet-services-acl {
    description
      "Match based on Ethernet Services";
  }

  feature match-ipv6-acl {
    description
      "Match based on ipv6 ACL";
  }

  feature match-ipv4-acl {
    description
      "Match based on ipv4 ACL";
  }

  feature cmap-type-traffic {
    description
      "Traffic class-map";
  }

  feature cmap-type-qos {
    description
      "QOS class-map";
  }

  feature pmap-type-afmon {
    description
      "Peformance traffic policy-map";
  }

  feature pmap-type-control {
    description
      "Subscriber control policy-map";
  }

  feature pmap-type-traffic {
    description
      "Traffic policy-map";
  }

  feature pmap-type-redirect {
    description
      "Redirect policy-map";
  }

  feature pmap-type-accounting {
    description
      "Accounting policy-map";
  }

  feature pmap-type-pbr {
    description
      "PBR policy-map";
  }

  feature pmap-type-qos {
    description
      "QoS policy-map";
  }
}

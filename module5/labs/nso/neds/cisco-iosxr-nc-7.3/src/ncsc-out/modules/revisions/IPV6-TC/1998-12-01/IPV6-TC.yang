module IPV6-TC {
  // Generated by yanger -t ncs
  tailf:mount-id "cisco-iosxr-nc-7.3:cisco-iosxr-nc-7.3";
  tailf:ncs-device-type "netconf";

  namespace "http://tail-f.com/ns/mibs/IPV6-TC/199812010000Z";
  prefix IPV6_TC;

  import ietf-inet-types {
    prefix inet;
  }
  import tailf-common {
    prefix tailf;
  }
  import tailf-ncs {
    prefix ncs;
  }

  revision 1998-12-01 {
    description
      "";
  }

  typedef ncs_template_Ipv6Address {
    type string;
  }

  typedef ncs_template_Ipv6AddressPrefix {
    type string;
  }

  typedef ncs_template_Ipv6AddressIfIdentifier {
    type string;
  }

  typedef ncs_template_Ipv6IfIndex {
    type string;
  }

  typedef ncs_template_Ipv6IfIndexOrZero {
    type string;
  }

  typedef ncs_rpc_notif_Ipv6Address {
    type inet:ipv6-address;
  }

  typedef ncs_rpc_notif_Ipv6AddressPrefix {
    type inet:ipv6-prefix;
  }

  typedef ncs_rpc_notif_Ipv6AddressIfIdentifier {
    type string {
      pattern '(((([0-9A-Fa-f]{2}):){0,7}([0-9A-Fa-f]{2}))){0,1}';
    }
  }

  typedef ncs_rpc_notif_Ipv6IfIndex {
    type int32 {
      range "1 .. 2147483647";
    }
  }

  typedef ncs_rpc_notif_Ipv6IfIndexOrZero {
    type int32 {
      range "0 .. 2147483647";
    }
  }

  typedef live_ncs_Ipv6Address {
    type inet:ipv6-address;
  }

  typedef live_ncs_Ipv6AddressPrefix {
    type inet:ipv6-prefix;
  }

  typedef live_ncs_Ipv6AddressIfIdentifier {
    type string {
      pattern '(((([0-9A-Fa-f]{2}):){0,7}([0-9A-Fa-f]{2}))){0,1}';
    }
  }

  typedef live_ncs_Ipv6IfIndex {
    type int32 {
      range "1 .. 2147483647";
    }
  }

  typedef live_ncs_Ipv6IfIndexOrZero {
    type int32 {
      range "0 .. 2147483647";
    }
  }

  typedef Ipv6Address {
    type inet:ipv6-address;
  }

  typedef Ipv6AddressPrefix {
    type inet:ipv6-prefix;
  }

  typedef Ipv6AddressIfIdentifier {
    type string {
      pattern '(((([0-9A-Fa-f]{2}):){0,7}([0-9A-Fa-f]{2}))){0,1}';
    }
  }

  typedef Ipv6IfIndex {
    type int32 {
      range "1 .. 2147483647";
    }
  }

  typedef Ipv6IfIndexOrZero {
    type int32 {
      range "0 .. 2147483647";
    }
  }
}

module Cisco-IOS-XR-lib-type6-act {
  // Generated by yanger -t ncs
  tailf:mount-id "cisco-iosxr-nc-7.3:cisco-iosxr-nc-7.3";
  tailf:ncs-device-type "netconf";

  namespace "http://cisco.com/ns/yang/Cisco-IOS-XR-lib-type6-act";
  prefix lib-type6-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2020 by Cisco Systems, Inc.
     All rights reserved.";

  revision 2020-10-16 {
    description
      "Changed the input type of clear-type6-client to enum";
    semver:module-version "2.0.0";
  }
  revision 2019-10-01 {
    description
      "Made changes to be RFC6087 compliant";
    semver:module-version "1.1.0";
  }
  revision 2019-04-05 {
    description
      "Establish semantic version baseline.";
    semver:module-version "1.0.0";
  }
  revision 2018-10-19 {
    description
      "IOS XR 6.3.1 revision.";
  }

  typedef ncs_template_Client-name {
    type string;
    description
      "Type6 client name";
  }

  typedef ncs_rpc_notif_Client-name {
    type enumeration {
      enum "keychain" {
        value 0;
        description
          "keychain";
      }
      enum "snmp" {
        value 1;
        description
          "snmp";
      }
      enum "radiusd" {
        value 2;
        description
          "radiusd";
      }
      enum "tacacsd" {
        value 3;
        description
          "tacacsd";
      }
    }
    description
      "Type6 client name";
  }

  typedef live_ncs_Client-name {
    type enumeration {
      enum "keychain" {
        value 0;
        description
          "keychain";
      }
      enum "snmp" {
        value 1;
        description
          "snmp";
      }
      enum "radiusd" {
        value 2;
        description
          "radiusd";
      }
      enum "tacacsd" {
        value 3;
        description
          "tacacsd";
      }
    }
    description
      "Type6 client name";
  }

  typedef Client-name {
    type enumeration {
      enum "keychain" {
        value 0;
        description
          "keychain";
      }
      enum "snmp" {
        value 1;
        description
          "snmp";
      }
      enum "radiusd" {
        value 2;
        description
          "radiusd";
      }
      enum "tacacsd" {
        value 3;
        description
          "tacacsd";
      }
    }
    description
      "Type6 client name";
  }

  grouping ncs_template_MASTER-KEY {
    description
      "Master Key Group";
    leaf old-key {
      type string;
      // NCS drop mandatory statement
      description
        "key already added/key to be replaced";
    }
    leaf new-key {
      type string;
      // NCS drop mandatory statement
      description
        "New master key to be added ";
    }
  }

  grouping ncs_rpc_notif_MASTER-KEY {
    description
      "Master Key Group";
    leaf old-key {
      type string;
      mandatory true;
      description
        "key already added/key to be replaced";
    }
    leaf new-key {
      type string;
      mandatory true;
      description
        "New master key to be added ";
    }
  }

  grouping live_ncs_MASTER-KEY {
    description
      "Master Key Group";
    leaf old-key {
      type string;
      // NCS drop mandatory statement
      description
        "key already added/key to be replaced";
    }
    leaf new-key {
      type string;
      // NCS drop mandatory statement
      description
        "New master key to be added ";
    }
  }

  grouping MASTER-KEY {
    description
      "Master Key Group";
    leaf old-key {
      type string;
      mandatory true;
      description
        "key already added/key to be replaced";
    }
    leaf new-key {
      type string;
      mandatory true;
      description
        "New master key to be added ";
    }
  }

  augment "/ncs:devices/ncs:device/ncs:rpc" {
    container rpc-clear-type6-client {
      tailf:ncs-device-type "netconf";
      tailf:display-when "not(../../ncs:module) or ../../ncs:module[ncs:name='Cisco-IOS-XR-lib-type6-act']";
      tailf:action clear-type6-client {
        tailf:actionpoint ncsproxy {
          tailf:internal;
        }
        description
          "To clear type6 client";
        input {
          leaf client-name {
            type ncs_rpc_notif_Client-name;
            mandatory true;
            description
              "Client Name";
          }
        }
      }
    }
  }
  augment "/ncs:devices/ncs:device-group/ncs:ned-id/ncs:rpc" {
    container rpc-clear-type6-client {
      tailf:ncs-device-type "netconf";
      tailf:display-when "/ncs:devices/ncs:device[ncs:name=current()/../../../ncs:member]/ncs:module[ncs:name='Cisco-IOS-XR-lib-type6-act']";
      tailf:action clear-type6-client {
        tailf:actionpoint ncsproxy {
          tailf:internal;
        }
        description
          "To clear type6 client";
        input {
          leaf client-name {
            type ncs_rpc_notif_Client-name;
            mandatory true;
            description
              "Client Name";
          }
        }
      }
    }
  }
  augment "/ncs:devices/ncs:device/ncs:rpc" {
    container rpc-master-key-update {
      tailf:ncs-device-type "netconf";
      tailf:display-when "not(../../ncs:module) or ../../ncs:module[ncs:name='Cisco-IOS-XR-lib-type6-act']";
      tailf:action master-key-update {
        tailf:actionpoint ncsproxy {
          tailf:internal;
        }
        description
          "To update master key";
        input {
          uses ncs_rpc_notif_MASTER-KEY;
        }
      }
    }
  }
  augment "/ncs:devices/ncs:device-group/ncs:ned-id/ncs:rpc" {
    container rpc-master-key-update {
      tailf:ncs-device-type "netconf";
      tailf:display-when "/ncs:devices/ncs:device[ncs:name=current()/../../../ncs:member]/ncs:module[ncs:name='Cisco-IOS-XR-lib-type6-act']";
      tailf:action master-key-update {
        tailf:actionpoint ncsproxy {
          tailf:internal;
        }
        description
          "To update master key";
        input {
          uses ncs_rpc_notif_MASTER-KEY;
        }
      }
    }
  }
  augment "/ncs:devices/ncs:device/ncs:rpc" {
    container rpc-master-key-delete {
      tailf:ncs-device-type "netconf";
      tailf:display-when "not(../../ncs:module) or ../../ncs:module[ncs:name='Cisco-IOS-XR-lib-type6-act']";
      tailf:action master-key-delete {
        tailf:actionpoint ncsproxy {
          tailf:internal;
        }
        description
          "Remove Master key";
      }
    }
  }
  augment "/ncs:devices/ncs:device-group/ncs:ned-id/ncs:rpc" {
    container rpc-master-key-delete {
      tailf:ncs-device-type "netconf";
      tailf:display-when "/ncs:devices/ncs:device[ncs:name=current()/../../../ncs:member]/ncs:module[ncs:name='Cisco-IOS-XR-lib-type6-act']";
      tailf:action master-key-delete {
        tailf:actionpoint ncsproxy {
          tailf:internal;
        }
        description
          "Remove Master key";
      }
    }
  }
  augment "/ncs:devices/ncs:device/ncs:rpc" {
    container rpc-master-key-add {
      tailf:ncs-device-type "netconf";
      tailf:display-when "not(../../ncs:module) or ../../ncs:module[ncs:name='Cisco-IOS-XR-lib-type6-act']";
      tailf:action master-key-add {
        tailf:actionpoint ncsproxy {
          tailf:internal;
        }
        description
          "To add a new master key";
        input {
          leaf new-key {
            type string;
            description
              "New master key to be added";
          }
        }
      }
    }
  }
  augment "/ncs:devices/ncs:device-group/ncs:ned-id/ncs:rpc" {
    container rpc-master-key-add {
      tailf:ncs-device-type "netconf";
      tailf:display-when "/ncs:devices/ncs:device[ncs:name=current()/../../../ncs:member]/ncs:module[ncs:name='Cisco-IOS-XR-lib-type6-act']";
      tailf:action master-key-add {
        tailf:actionpoint ncsproxy {
          tailf:internal;
        }
        description
          "To add a new master key";
        input {
          leaf new-key {
            type string;
            description
              "New master key to be added";
          }
        }
      }
    }
  }
}

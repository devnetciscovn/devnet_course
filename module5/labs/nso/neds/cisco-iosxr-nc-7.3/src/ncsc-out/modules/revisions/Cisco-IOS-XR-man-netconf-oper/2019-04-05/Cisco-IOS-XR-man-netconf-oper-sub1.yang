submodule Cisco-IOS-XR-man-netconf-oper-sub1 {
  // Generated by yanger -t ncs
  tailf:mount-id "cisco-iosxr-nc-7.3:cisco-iosxr-nc-7.3";

  belongs-to Cisco-IOS-XR-man-netconf-oper {
    prefix Cisco-IOS-XR-man-netconf-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR man-netconf package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_NC-STATUS-B {
    description
      "Netconf status bag";
    leaf yfw-state {
      type string;
      description
        "YFW State";
    }
  }

  grouping ncs_template_NC-SESSION-STATS-B {
    description
      "Netconf session statistics bag";
    list entry {
      // NCS patched for predictable order
      ordered-by user;
      // NCS drop max-elements statement
      description
        "Per-type statistics";
      uses ncs_template_NC-STATS-B;
    }
  }

  grouping ncs_template_NC-STATS-B {
    description
      "Netconf statistics bag";
    leaf type {
      type string;
      description
        "Type name";
    }
    leaf request {
      type string;
      description
        "Total operations count";
    }
    leaf total-time {
      type string;
      units "millisecond";
      description
        "Total time for operation in milliseconds since
         the system started";
    }
    leaf min-time-per-request {
      type string;
      units "millisecond";
      description
        "Lowest time for operation in milliseconds since
         the system started";
    }
    leaf max-time-per-request {
      type string;
      units "millisecond";
      description
        "Highest time for operation in milliseconds since
         the system started";
    }
    leaf avg-time-per-request {
      type string;
      units "millisecond";
      description
        "Average time for operation in milliseconds since
         the system started";
    }
  }

  grouping ncs_template_NC-SUMMARY-STATS-B {
    description
      "Netconf summary statistics bag";
    list entry {
      // NCS patched for predictable order
      ordered-by user;
      // NCS drop max-elements statement
      description
        "Per-type statistics";
      uses ncs_template_NC-STATS-B;
    }
  }

  grouping ncs_template_NC-NTFS-STATS-B {
    description
      "Netconf notification subscription statistics bag";
    leaf subscribed-stream {
      type string;
      description
        "Stream name";
    }
    leaf replay-received {
      type string;
      description
        "Number of notifications received during replay";
    }
    leaf non-replay-received {
      type string;
      description
        "Number of non-replay notifications received";
    }
    leaf subscription-state {
      type string;
      description
        "Subscription state";
    }
    leaf replay-start-time {
      type string;
      description
        "Replay startTime in epoch time";
    }
    leaf replay-stop-time {
      type string;
      description
        "Replay stopTime in epoch time";
    }
    leaf subscription-created {
      type string;
      description
        "Time of subscription creation in epoch time";
    }
    leaf replay-complete-time {
      type string;
      description
        "Time of replayComplete notification arrival";
    }
  }

  grouping ncs_template_NC-CAPABILITY-B {
    description
      "Netconf capability bag";
    leaf namespace {
      type string;
      description
        "Namespace";
    }
    leaf module {
      type string;
      description
        "Module";
    }
    leaf revision {
      type string;
      description
        "Revision";
    }
    leaf deviation {
      type string;
      description
        "Deviation";
    }
  }

  grouping ncs_template_NC-CAPABILITIES-B {
    description
      "Netconf capabilities bag";
    list capability {
      // NCS patched for predictable order
      ordered-by user;
      description
        "Capability list";
      uses ncs_template_NC-CAPABILITY-B;
    }
  }

  grouping ncs_template_NC-RATELIMIT-STATS-B {
    description
      "Netconf rate-limit statistics bag";
    leaf total-data-dropped {
      type string;
      units "byte";
      description
        "Total Bytes dropped";
    }
  }

  grouping ncs_template_NC-SESSION-B {
    description
      "Netconf client session bag";
    leaf version {
      type string;
      description
        "Netconf version";
    }
    leaf connect-time {
      type string;
      units "millisecond";
      description
        "How long has a client been connected in
         milliseconds since the system started";
    }
    leaf last-op-time {
      type string;
      units "second";
      description
        "Last operation time in seconds since the system
         started";
    }
    leaf last-op-type {
      type string;
      description
        "Last operation type";
    }
    leaf locked {
      type string;
      description
        "Session locked";
    }
  }

  grouping ncs_rpc_notif_NC-STATUS-B {
    description
      "Netconf status bag";
    leaf yfw-state {
      type string;
      description
        "YFW State";
    }
  }

  grouping ncs_rpc_notif_NC-SESSION-STATS-B {
    description
      "Netconf session statistics bag";
    list entry {
      max-elements 20;
      description
        "Per-type statistics";
      uses ncs_rpc_notif_NC-STATS-B;
    }
  }

  grouping ncs_rpc_notif_NC-STATS-B {
    description
      "Netconf statistics bag";
    leaf type {
      type string;
      description
        "Type name";
    }
    leaf request {
      type uint32;
      description
        "Total operations count";
    }
    leaf total-time {
      type uint64;
      units "millisecond";
      description
        "Total time for operation in milliseconds since
         the system started";
    }
    leaf min-time-per-request {
      type uint32;
      units "millisecond";
      description
        "Lowest time for operation in milliseconds since
         the system started";
    }
    leaf max-time-per-request {
      type uint32;
      units "millisecond";
      description
        "Highest time for operation in milliseconds since
         the system started";
    }
    leaf avg-time-per-request {
      type uint32;
      units "millisecond";
      description
        "Average time for operation in milliseconds since
         the system started";
    }
  }

  grouping ncs_rpc_notif_NC-SUMMARY-STATS-B {
    description
      "Netconf summary statistics bag";
    list entry {
      max-elements 20;
      description
        "Per-type statistics";
      uses ncs_rpc_notif_NC-STATS-B;
    }
  }

  grouping ncs_rpc_notif_NC-NTFS-STATS-B {
    description
      "Netconf notification subscription statistics bag";
    leaf subscribed-stream {
      type string;
      description
        "Stream name";
    }
    leaf replay-received {
      type uint32;
      description
        "Number of notifications received during replay";
    }
    leaf non-replay-received {
      type uint64;
      description
        "Number of non-replay notifications received";
    }
    leaf subscription-state {
      type string;
      description
        "Subscription state";
    }
    leaf replay-start-time {
      type uint64;
      description
        "Replay startTime in epoch time";
    }
    leaf replay-stop-time {
      type uint64;
      description
        "Replay stopTime in epoch time";
    }
    leaf subscription-created {
      type uint64;
      description
        "Time of subscription creation in epoch time";
    }
    leaf replay-complete-time {
      type uint64;
      description
        "Time of replayComplete notification arrival";
    }
  }

  grouping ncs_rpc_notif_NC-CAPABILITY-B {
    description
      "Netconf capability bag";
    leaf namespace {
      type string;
      description
        "Namespace";
    }
    leaf module {
      type string;
      description
        "Module";
    }
    leaf revision {
      type string;
      description
        "Revision";
    }
    leaf deviation {
      type string;
      description
        "Deviation";
    }
  }

  grouping ncs_rpc_notif_NC-CAPABILITIES-B {
    description
      "Netconf capabilities bag";
    list capability {
      description
        "Capability list";
      uses ncs_rpc_notif_NC-CAPABILITY-B;
    }
  }

  grouping ncs_rpc_notif_NC-RATELIMIT-STATS-B {
    description
      "Netconf rate-limit statistics bag";
    leaf total-data-dropped {
      type uint64;
      units "byte";
      description
        "Total Bytes dropped";
    }
  }

  grouping ncs_rpc_notif_NC-SESSION-B {
    description
      "Netconf client session bag";
    leaf version {
      type string;
      description
        "Netconf version";
    }
    leaf connect-time {
      type uint64;
      units "millisecond";
      description
        "How long has a client been connected in
         milliseconds since the system started";
    }
    leaf last-op-time {
      type uint64;
      units "second";
      description
        "Last operation time in seconds since the system
         started";
    }
    leaf last-op-type {
      type string;
      description
        "Last operation type";
    }
    leaf locked {
      type string;
      description
        "Session locked";
    }
  }

  grouping live_ncs_NC-STATUS-B {
    description
      "Netconf status bag";
    leaf yfw-state {
      type string;
      description
        "YFW State";
    }
  }

  grouping live_ncs_NC-SESSION-STATS-B {
    description
      "Netconf session statistics bag";
    list entry {
      // NCS drop max-elements statement
      description
        "Per-type statistics";
      uses live_ncs_NC-STATS-B;
    }
  }

  grouping live_ncs_NC-STATS-B {
    description
      "Netconf statistics bag";
    leaf type {
      type string;
      description
        "Type name";
    }
    leaf request {
      type uint32;
      description
        "Total operations count";
    }
    leaf total-time {
      type uint64;
      units "millisecond";
      description
        "Total time for operation in milliseconds since
         the system started";
    }
    leaf min-time-per-request {
      type uint32;
      units "millisecond";
      description
        "Lowest time for operation in milliseconds since
         the system started";
    }
    leaf max-time-per-request {
      type uint32;
      units "millisecond";
      description
        "Highest time for operation in milliseconds since
         the system started";
    }
    leaf avg-time-per-request {
      type uint32;
      units "millisecond";
      description
        "Average time for operation in milliseconds since
         the system started";
    }
  }

  grouping live_ncs_NC-SUMMARY-STATS-B {
    description
      "Netconf summary statistics bag";
    list entry {
      // NCS drop max-elements statement
      description
        "Per-type statistics";
      uses live_ncs_NC-STATS-B;
    }
  }

  grouping live_ncs_NC-NTFS-STATS-B {
    description
      "Netconf notification subscription statistics bag";
    leaf subscribed-stream {
      type string;
      description
        "Stream name";
    }
    leaf replay-received {
      type uint32;
      description
        "Number of notifications received during replay";
    }
    leaf non-replay-received {
      type uint64;
      description
        "Number of non-replay notifications received";
    }
    leaf subscription-state {
      type string;
      description
        "Subscription state";
    }
    leaf replay-start-time {
      type uint64;
      description
        "Replay startTime in epoch time";
    }
    leaf replay-stop-time {
      type uint64;
      description
        "Replay stopTime in epoch time";
    }
    leaf subscription-created {
      type uint64;
      description
        "Time of subscription creation in epoch time";
    }
    leaf replay-complete-time {
      type uint64;
      description
        "Time of replayComplete notification arrival";
    }
  }

  grouping live_ncs_NC-CAPABILITY-B {
    description
      "Netconf capability bag";
    leaf namespace {
      type string;
      description
        "Namespace";
    }
    leaf module {
      type string;
      description
        "Module";
    }
    leaf revision {
      type string;
      description
        "Revision";
    }
    leaf deviation {
      type string;
      description
        "Deviation";
    }
  }

  grouping live_ncs_NC-CAPABILITIES-B {
    description
      "Netconf capabilities bag";
    list capability {
      description
        "Capability list";
      uses live_ncs_NC-CAPABILITY-B;
    }
  }

  grouping live_ncs_NC-RATELIMIT-STATS-B {
    description
      "Netconf rate-limit statistics bag";
    leaf total-data-dropped {
      type uint64;
      units "byte";
      description
        "Total Bytes dropped";
    }
  }

  grouping live_ncs_NC-SESSION-B {
    description
      "Netconf client session bag";
    leaf version {
      type string;
      description
        "Netconf version";
    }
    leaf connect-time {
      type uint64;
      units "millisecond";
      description
        "How long has a client been connected in
         milliseconds since the system started";
    }
    leaf last-op-time {
      type uint64;
      units "second";
      description
        "Last operation time in seconds since the system
         started";
    }
    leaf last-op-type {
      type string;
      description
        "Last operation type";
    }
    leaf locked {
      type string;
      description
        "Session locked";
    }
  }

  grouping NC-STATUS-B {
    description
      "Netconf status bag";
    leaf yfw-state {
      type string;
      description
        "YFW State";
    }
  }

  grouping NC-SESSION-STATS-B {
    description
      "Netconf session statistics bag";
    list entry {
      max-elements 20;
      description
        "Per-type statistics";
      uses NC-STATS-B;
    }
  }

  grouping NC-STATS-B {
    description
      "Netconf statistics bag";
    leaf type {
      type string;
      description
        "Type name";
    }
    leaf request {
      type uint32;
      description
        "Total operations count";
    }
    leaf total-time {
      type uint64;
      units "millisecond";
      description
        "Total time for operation in milliseconds since
         the system started";
    }
    leaf min-time-per-request {
      type uint32;
      units "millisecond";
      description
        "Lowest time for operation in milliseconds since
         the system started";
    }
    leaf max-time-per-request {
      type uint32;
      units "millisecond";
      description
        "Highest time for operation in milliseconds since
         the system started";
    }
    leaf avg-time-per-request {
      type uint32;
      units "millisecond";
      description
        "Average time for operation in milliseconds since
         the system started";
    }
  }

  grouping NC-SUMMARY-STATS-B {
    description
      "Netconf summary statistics bag";
    list entry {
      max-elements 20;
      description
        "Per-type statistics";
      uses NC-STATS-B;
    }
  }

  grouping NC-NTFS-STATS-B {
    description
      "Netconf notification subscription statistics bag";
    leaf subscribed-stream {
      type string;
      description
        "Stream name";
    }
    leaf replay-received {
      type uint32;
      description
        "Number of notifications received during replay";
    }
    leaf non-replay-received {
      type uint64;
      description
        "Number of non-replay notifications received";
    }
    leaf subscription-state {
      type string;
      description
        "Subscription state";
    }
    leaf replay-start-time {
      type uint64;
      description
        "Replay startTime in epoch time";
    }
    leaf replay-stop-time {
      type uint64;
      description
        "Replay stopTime in epoch time";
    }
    leaf subscription-created {
      type uint64;
      description
        "Time of subscription creation in epoch time";
    }
    leaf replay-complete-time {
      type uint64;
      description
        "Time of replayComplete notification arrival";
    }
  }

  grouping NC-CAPABILITY-B {
    description
      "Netconf capability bag";
    leaf namespace {
      type string;
      description
        "Namespace";
    }
    leaf module {
      type string;
      description
        "Module";
    }
    leaf revision {
      type string;
      description
        "Revision";
    }
    leaf deviation {
      type string;
      description
        "Deviation";
    }
  }

  grouping NC-CAPABILITIES-B {
    description
      "Netconf capabilities bag";
    list capability {
      description
        "Capability list";
      uses NC-CAPABILITY-B;
    }
  }

  grouping NC-RATELIMIT-STATS-B {
    description
      "Netconf rate-limit statistics bag";
    leaf total-data-dropped {
      type uint64;
      units "byte";
      description
        "Total Bytes dropped";
    }
  }

  grouping NC-SESSION-B {
    description
      "Netconf client session bag";
    leaf version {
      type string;
      description
        "Netconf version";
    }
    leaf connect-time {
      type uint64;
      units "millisecond";
      description
        "How long has a client been connected in
         milliseconds since the system started";
    }
    leaf last-op-time {
      type uint64;
      units "second";
      description
        "Last operation time in seconds since the system
         started";
    }
    leaf last-op-type {
      type string;
      description
        "Last operation type";
    }
    leaf locked {
      type string;
      description
        "Session locked";
    }
  }
}

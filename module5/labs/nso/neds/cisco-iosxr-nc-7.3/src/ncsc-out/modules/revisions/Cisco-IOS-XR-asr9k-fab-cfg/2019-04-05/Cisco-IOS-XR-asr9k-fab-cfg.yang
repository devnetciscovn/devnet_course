module Cisco-IOS-XR-asr9k-fab-cfg {
  // Generated by yanger -t ncs
  tailf:mount-id "cisco-iosxr-nc-7.3:cisco-iosxr-nc-7.3";
  tailf:ncs-device-type "netconf";

  namespace "http://cisco.com/ns/yang/Cisco-IOS-XR-asr9k-fab-cfg";
  prefix asr9k-fab-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-fab package configuration.

     This module contains definitions
     for the following management objects:
       fab-vqi-config: Configure Fabric Operation Mode

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Asr9k-fab-mode {
    type string;
    description
      "Asr9k fab mode";
  }

  typedef ncs_rpc_notif_Asr9k-fab-mode {
    type enumeration {
      enum "highbandwidth" {
        value 1;
        description
          "High bandwidth mode";
      }
      enum "a99-highbandwidth" {
        value 2;
        description
          "A99 High bandwidth mode";
      }
    }
    description
      "Asr9k fab mode";
  }

  typedef live_ncs_Asr9k-fab-mode {
    type enumeration {
      enum "highbandwidth" {
        value 1;
        description
          "High bandwidth mode";
      }
      enum "a99-highbandwidth" {
        value 2;
        description
          "A99 High bandwidth mode";
      }
    }
    description
      "Asr9k fab mode";
  }

  typedef Asr9k-fab-mode {
    type enumeration {
      enum "highbandwidth" {
        value 1;
        description
          "High bandwidth mode";
      }
      enum "a99-highbandwidth" {
        value 2;
        description
          "A99 High bandwidth mode";
      }
    }
    description
      "Asr9k fab mode";
  }

  augment "/ncs:devices/ncs:device/ncs:config" {
    container fab-vqi-config {
      tailf:ncs-device-type "netconf";
      tailf:display-when "not(../../ncs:module) or ../../ncs:module[ncs:name='Cisco-IOS-XR-asr9k-fab-cfg']";
      description
        "Configure Fabric Operation Mode";
      container mode {
        description
          "Mode Type";
        leaf fab-mode-type-xr {
          type Asr9k-fab-mode;
          description
            "Mode Type";
        }
        leaf fab-mode-type {
          type Asr9k-fab-mode;
          description
            "Mode Type";
        }
      }
    }
  }
  augment "/ncs:devices/ncs:device/ncs:live-status" {
    container fab-vqi-config {
      tailf:ncs-device-type "netconf";
      tailf:display-when "not(../../ncs:module) or ../../ncs:module[ncs:name='Cisco-IOS-XR-asr9k-fab-cfg'] or (../../ncs:live-status-protocol[not(ncs:capability)]) or (../../ncs:live-status-protocol/ncs:capability/ncs:module[.='Cisco-IOS-XR-asr9k-fab-cfg'])";
      description
        "Configure Fabric Operation Mode";
      container mode {
        description
          "Mode Type";
        leaf fab-mode-type-xr {
          type live_ncs_Asr9k-fab-mode;
          description
            "Mode Type";
        }
        leaf fab-mode-type {
          type live_ncs_Asr9k-fab-mode;
          description
            "Mode Type";
        }
      }
    }
  }
  augment "/ncs:devices/ncs:template/ncs:ned-id/ncs:config" {
    container fab-vqi-config {
      description
        "Configure Fabric Operation Mode";
      container mode {
        description
          "Mode Type";
        leaf fab-mode-type-xr {
          type ncs_template_Asr9k-fab-mode;
          description
            "Mode Type";
        }
        leaf fab-mode-type {
          type ncs_template_Asr9k-fab-mode;
          description
            "Mode Type";
        }
      }
    }
  }
}

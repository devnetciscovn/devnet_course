module Cisco-IOS-XR-install-augmented-oper {
  // Generated by yanger -t ncs
  tailf:mount-id "cisco-iosxr-nc-7.3:cisco-iosxr-nc-7.3";
  tailf:ncs-device-type "netconf";

  namespace "http://cisco.com/ns/yang/Cisco-IOS-XR-install-augmented-oper";
  prefix install-augmented-oper;

  import Cisco-IOS-XR-types {
    prefix xr;
  }
  import cisco-semver {
    prefix semver;
  }
  include Cisco-IOS-XR-install-augmented-oper-sub2 {
    revision-date 2020-09-30;
  }
  include Cisco-IOS-XR-install-augmented-oper-sub1 {
    revision-date 2020-09-30;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR install-augmented package operational data.

     This module contains definitions
     for the following management objects:
       install: Install operational data

     Copyright (c) 2013-2020 by Cisco Systems, Inc.
     All rights reserved.";

  revision 2020-09-30 {
    description
      "7.3.1 release features.";
    semver:module-version "2.1.0";
  }
  revision 2020-05-12 {
    description
      "Removal of compound from enum naming conventions to avoid confusion.
       2019-12-11
       Obsoleted the nodes list for history items.
       2019-10-14
       Combined platform updates including updates to show install rollback list-ids";
    semver:module-version "2.0.0";
  }
  revision 2019-10-13 {
    description
      "NCS540L 7.1.1 release
       2019-10-12
       8000 series 7.0.11 release";
    semver:module-version "1.1.0";
  }
  revision 2019-04-05 {
    description
      "Establish semantic version baseline.";
    semver:module-version "1.0.0";
  }
  revision 2015-11-09 {
    description
      "IOS XR 6.0 revision.";
  }

  grouping ncs_template_ATOMIC-CHANGE-TABLE {
    description
      "Common node of transaction, latest-transaction";
    container atomic-changes {
      description
        "Table for atomic software change specific
         operational data";
      list atomic-change {
        // NCS patched for predictable order
        ordered-by user;
        key "index";
        description
          "Information about a particular atomic change";
        leaf index {
          type string;
          description
            "Index";
        }
        uses ncs_template_PACKAGING-OPERATION-TABLE;
        uses ncs_template_ATOMIC-CHANGE-INFO;
        uses ncs_template_ATOMIC-CHANGE-INFO-NODE-TABLE;
      }
    }
  }

  grouping ncs_template_TRANSACTION-INFO-NODE-TABLE {
    description
      "Common node of transaction, latest-transaction";
    container transaction-info-nodes {
      description
        "Table for per-node information when carrying out
         a transaction";
      list transaction-info-node {
        // NCS patched for predictable order
        ordered-by user;
        key "node";
        description
          "Node specific information when carrying out a
           transaction";
        leaf node {
          type xr:ncs_template_Node-id;
          description
            "Node name";
        }
        uses ncs_template_INST-TRANS-NODE-BAG;
      }
    }
  }

  grouping ncs_template_TRANSACTION-INFO {
    description
      "Common node of transaction, latest-transaction";
    container transaction-info {
      description
        "Summary information about the transaction";
      uses ncs_template_INST-TRANS-BAG;
    }
  }

  grouping ncs_template_ATOMIC-CHANGE-INFO {
    description
      "Common node of atomic-change,
       latest-atomic-change";
    container atomic-change-info {
      description
        "Summary information about the atomic change";
      uses ncs_template_INST-ATOMIC-CHANGE-BAG;
    }
  }

  grouping ncs_template_PACKAGING-OPERATION-INFO-NODE-TABLE {
    description
      "Common node of latest-packaging-operation,
       packaging-operation";
    container packaging-operation-info-nodes {
      description
        "Table for per-node information when carrying out
         a packaging operation";
      list packaging-operation-info-node {
        // NCS patched for predictable order
        ordered-by user;
        key "node";
        description
          "Node specific information when carrying out a
           packaging operation";
        leaf node {
          type xr:ncs_template_Node-id;
          description
            "Node name";
        }
        uses ncs_template_INST-PKG-OP-NODE-BAG;
      }
    }
  }

  grouping ncs_template_PACKAGING-OPERATION-TABLE {
    description
      "Common node of atomic-change,
       latest-atomic-change";
    container packaging-operations {
      description
        "Table for packaging operation specific
         operational data";
      list packaging-operation {
        // NCS patched for predictable order
        ordered-by user;
        key "index";
        description
          "Data about a particular packaging operation";
        leaf index {
          type string;
          description
            "Index";
        }
        uses ncs_template_PACKAGING-OPERATION-ERRORS-NODE-TABLE;
        uses ncs_template_PACKAGING-OPERATION-INFO-NODE-TABLE;
        uses ncs_template_PACKAGING-OPERATION-INFO;
      }
    }
  }

  grouping ncs_template_PACKAGING-OPERATION-ERRORS-NODE-TABLE {
    description
      "Common node of latest-packaging-operation,
       packaging-operation";
    container packaging-operation-errors-nodes {
      description
        "Table for per-node DNF errors when carrying out
         a packaging operation";
      list packaging-operation-errors-node {
        // NCS patched for predictable order
        ordered-by user;
        key "node";
        description
          "Node specific DNF errors when carrying out a
           packaging operation";
        leaf node {
          type xr:ncs_template_Node-id;
          description
            "Node name";
        }
        uses ncs_template_INST-PKG-OP-ERRORS-BAG;
      }
    }
  }

  grouping ncs_template_PACKAGING-OPERATION-INFO {
    description
      "Common node of latest-packaging-operation,
       packaging-operation";
    container packaging-operation-info {
      description
        "Information about a packaging operation";
      uses ncs_template_INST-PKG-OP-BAG;
    }
  }

  grouping ncs_template_ATOMIC-CHANGE-INFO-NODE-TABLE {
    description
      "Common node of atomic-change,
       latest-atomic-change";
    container atomic-change-info-nodes {
      description
        "Table for per-node information when carrying out
         an atomic change";
      list atomic-change-info-node {
        // NCS patched for predictable order
        ordered-by user;
        key "node";
        description
          "Node specific information when carrying out an
           atomic change";
        leaf node {
          type xr:ncs_template_Node-id;
          description
            "Node name";
        }
        uses ncs_template_INST-ATOMIC-CHANGE-NODE-BAG;
      }
    }
  }

  grouping ncs_rpc_notif_ATOMIC-CHANGE-TABLE {
    description
      "Common node of transaction, latest-transaction";
    container atomic-changes {
      description
        "Table for atomic software change specific
         operational data";
      list atomic-change {
        key "index";
        description
          "Information about a particular atomic change";
        leaf index {
          type uint32;
          description
            "Index";
        }
        uses ncs_rpc_notif_PACKAGING-OPERATION-TABLE;
        uses ncs_rpc_notif_ATOMIC-CHANGE-INFO;
        uses ncs_rpc_notif_ATOMIC-CHANGE-INFO-NODE-TABLE;
      }
    }
  }

  grouping ncs_rpc_notif_TRANSACTION-INFO-NODE-TABLE {
    description
      "Common node of transaction, latest-transaction";
    container transaction-info-nodes {
      description
        "Table for per-node information when carrying out
         a transaction";
      list transaction-info-node {
        key "node";
        description
          "Node specific information when carrying out a
           transaction";
        leaf node {
          type xr:ncs_rpc_notif_Node-id;
          description
            "Node name";
        }
        uses ncs_rpc_notif_INST-TRANS-NODE-BAG;
      }
    }
  }

  grouping ncs_rpc_notif_TRANSACTION-INFO {
    description
      "Common node of transaction, latest-transaction";
    container transaction-info {
      description
        "Summary information about the transaction";
      uses ncs_rpc_notif_INST-TRANS-BAG;
    }
  }

  grouping ncs_rpc_notif_ATOMIC-CHANGE-INFO {
    description
      "Common node of atomic-change,
       latest-atomic-change";
    container atomic-change-info {
      description
        "Summary information about the atomic change";
      uses ncs_rpc_notif_INST-ATOMIC-CHANGE-BAG;
    }
  }

  grouping ncs_rpc_notif_PACKAGING-OPERATION-INFO-NODE-TABLE {
    description
      "Common node of latest-packaging-operation,
       packaging-operation";
    container packaging-operation-info-nodes {
      description
        "Table for per-node information when carrying out
         a packaging operation";
      list packaging-operation-info-node {
        key "node";
        description
          "Node specific information when carrying out a
           packaging operation";
        leaf node {
          type xr:ncs_rpc_notif_Node-id;
          description
            "Node name";
        }
        uses ncs_rpc_notif_INST-PKG-OP-NODE-BAG;
      }
    }
  }

  grouping ncs_rpc_notif_PACKAGING-OPERATION-TABLE {
    description
      "Common node of atomic-change,
       latest-atomic-change";
    container packaging-operations {
      description
        "Table for packaging operation specific
         operational data";
      list packaging-operation {
        key "index";
        description
          "Data about a particular packaging operation";
        leaf index {
          type uint32;
          description
            "Index";
        }
        uses ncs_rpc_notif_PACKAGING-OPERATION-ERRORS-NODE-TABLE;
        uses ncs_rpc_notif_PACKAGING-OPERATION-INFO-NODE-TABLE;
        uses ncs_rpc_notif_PACKAGING-OPERATION-INFO;
      }
    }
  }

  grouping ncs_rpc_notif_PACKAGING-OPERATION-ERRORS-NODE-TABLE {
    description
      "Common node of latest-packaging-operation,
       packaging-operation";
    container packaging-operation-errors-nodes {
      description
        "Table for per-node DNF errors when carrying out
         a packaging operation";
      list packaging-operation-errors-node {
        key "node";
        description
          "Node specific DNF errors when carrying out a
           packaging operation";
        leaf node {
          type xr:ncs_rpc_notif_Node-id;
          description
            "Node name";
        }
        uses ncs_rpc_notif_INST-PKG-OP-ERRORS-BAG;
      }
    }
  }

  grouping ncs_rpc_notif_PACKAGING-OPERATION-INFO {
    description
      "Common node of latest-packaging-operation,
       packaging-operation";
    container packaging-operation-info {
      description
        "Information about a packaging operation";
      uses ncs_rpc_notif_INST-PKG-OP-BAG;
    }
  }

  grouping ncs_rpc_notif_ATOMIC-CHANGE-INFO-NODE-TABLE {
    description
      "Common node of atomic-change,
       latest-atomic-change";
    container atomic-change-info-nodes {
      description
        "Table for per-node information when carrying out
         an atomic change";
      list atomic-change-info-node {
        key "node";
        description
          "Node specific information when carrying out an
           atomic change";
        leaf node {
          type xr:ncs_rpc_notif_Node-id;
          description
            "Node name";
        }
        uses ncs_rpc_notif_INST-ATOMIC-CHANGE-NODE-BAG;
      }
    }
  }

  grouping live_ncs_ATOMIC-CHANGE-TABLE {
    description
      "Common node of transaction, latest-transaction";
    container atomic-changes {
      description
        "Table for atomic software change specific
         operational data";
      list atomic-change {
        key "index";
        description
          "Information about a particular atomic change";
        leaf index {
          type uint32;
          description
            "Index";
        }
        uses live_ncs_PACKAGING-OPERATION-TABLE;
        uses live_ncs_ATOMIC-CHANGE-INFO;
        uses live_ncs_ATOMIC-CHANGE-INFO-NODE-TABLE;
      }
    }
  }

  grouping live_ncs_TRANSACTION-INFO-NODE-TABLE {
    description
      "Common node of transaction, latest-transaction";
    container transaction-info-nodes {
      description
        "Table for per-node information when carrying out
         a transaction";
      list transaction-info-node {
        key "node";
        description
          "Node specific information when carrying out a
           transaction";
        leaf node {
          type xr:live_ncs_Node-id;
          description
            "Node name";
        }
        uses live_ncs_INST-TRANS-NODE-BAG;
      }
    }
  }

  grouping live_ncs_TRANSACTION-INFO {
    description
      "Common node of transaction, latest-transaction";
    container transaction-info {
      description
        "Summary information about the transaction";
      uses live_ncs_INST-TRANS-BAG;
    }
  }

  grouping live_ncs_ATOMIC-CHANGE-INFO {
    description
      "Common node of atomic-change,
       latest-atomic-change";
    container atomic-change-info {
      description
        "Summary information about the atomic change";
      uses live_ncs_INST-ATOMIC-CHANGE-BAG;
    }
  }

  grouping live_ncs_PACKAGING-OPERATION-INFO-NODE-TABLE {
    description
      "Common node of latest-packaging-operation,
       packaging-operation";
    container packaging-operation-info-nodes {
      description
        "Table for per-node information when carrying out
         a packaging operation";
      list packaging-operation-info-node {
        key "node";
        description
          "Node specific information when carrying out a
           packaging operation";
        leaf node {
          type xr:live_ncs_Node-id;
          description
            "Node name";
        }
        uses live_ncs_INST-PKG-OP-NODE-BAG;
      }
    }
  }

  grouping live_ncs_PACKAGING-OPERATION-TABLE {
    description
      "Common node of atomic-change,
       latest-atomic-change";
    container packaging-operations {
      description
        "Table for packaging operation specific
         operational data";
      list packaging-operation {
        key "index";
        description
          "Data about a particular packaging operation";
        leaf index {
          type uint32;
          description
            "Index";
        }
        uses live_ncs_PACKAGING-OPERATION-ERRORS-NODE-TABLE;
        uses live_ncs_PACKAGING-OPERATION-INFO-NODE-TABLE;
        uses live_ncs_PACKAGING-OPERATION-INFO;
      }
    }
  }

  grouping live_ncs_PACKAGING-OPERATION-ERRORS-NODE-TABLE {
    description
      "Common node of latest-packaging-operation,
       packaging-operation";
    container packaging-operation-errors-nodes {
      description
        "Table for per-node DNF errors when carrying out
         a packaging operation";
      list packaging-operation-errors-node {
        key "node";
        description
          "Node specific DNF errors when carrying out a
           packaging operation";
        leaf node {
          type xr:live_ncs_Node-id;
          description
            "Node name";
        }
        uses live_ncs_INST-PKG-OP-ERRORS-BAG;
      }
    }
  }

  grouping live_ncs_PACKAGING-OPERATION-INFO {
    description
      "Common node of latest-packaging-operation,
       packaging-operation";
    container packaging-operation-info {
      description
        "Information about a packaging operation";
      uses live_ncs_INST-PKG-OP-BAG;
    }
  }

  grouping live_ncs_ATOMIC-CHANGE-INFO-NODE-TABLE {
    description
      "Common node of atomic-change,
       latest-atomic-change";
    container atomic-change-info-nodes {
      description
        "Table for per-node information when carrying out
         an atomic change";
      list atomic-change-info-node {
        key "node";
        description
          "Node specific information when carrying out an
           atomic change";
        leaf node {
          type xr:live_ncs_Node-id;
          description
            "Node name";
        }
        uses live_ncs_INST-ATOMIC-CHANGE-NODE-BAG;
      }
    }
  }

  grouping ATOMIC-CHANGE-TABLE {
    description
      "Common node of transaction, latest-transaction";
    container atomic-changes {
      description
        "Table for atomic software change specific
         operational data";
      list atomic-change {
        key "index";
        description
          "Information about a particular atomic change";
        leaf index {
          type uint32;
          description
            "Index";
        }
        uses PACKAGING-OPERATION-TABLE;
        uses ATOMIC-CHANGE-INFO;
        uses ATOMIC-CHANGE-INFO-NODE-TABLE;
      }
    }
  }

  grouping TRANSACTION-INFO-NODE-TABLE {
    description
      "Common node of transaction, latest-transaction";
    container transaction-info-nodes {
      description
        "Table for per-node information when carrying out
         a transaction";
      list transaction-info-node {
        key "node";
        description
          "Node specific information when carrying out a
           transaction";
        leaf node {
          type xr:Node-id;
          description
            "Node name";
        }
        uses INST-TRANS-NODE-BAG;
      }
    }
  }

  grouping TRANSACTION-INFO {
    description
      "Common node of transaction, latest-transaction";
    container transaction-info {
      description
        "Summary information about the transaction";
      uses INST-TRANS-BAG;
    }
  }

  grouping ATOMIC-CHANGE-INFO {
    description
      "Common node of atomic-change,
       latest-atomic-change";
    container atomic-change-info {
      description
        "Summary information about the atomic change";
      uses INST-ATOMIC-CHANGE-BAG;
    }
  }

  grouping PACKAGING-OPERATION-INFO-NODE-TABLE {
    description
      "Common node of latest-packaging-operation,
       packaging-operation";
    container packaging-operation-info-nodes {
      description
        "Table for per-node information when carrying out
         a packaging operation";
      list packaging-operation-info-node {
        key "node";
        description
          "Node specific information when carrying out a
           packaging operation";
        leaf node {
          type xr:Node-id;
          description
            "Node name";
        }
        uses INST-PKG-OP-NODE-BAG;
      }
    }
  }

  grouping PACKAGING-OPERATION-TABLE {
    description
      "Common node of atomic-change,
       latest-atomic-change";
    container packaging-operations {
      description
        "Table for packaging operation specific
         operational data";
      list packaging-operation {
        key "index";
        description
          "Data about a particular packaging operation";
        leaf index {
          type uint32;
          description
            "Index";
        }
        uses PACKAGING-OPERATION-ERRORS-NODE-TABLE;
        uses PACKAGING-OPERATION-INFO-NODE-TABLE;
        uses PACKAGING-OPERATION-INFO;
      }
    }
  }

  grouping PACKAGING-OPERATION-ERRORS-NODE-TABLE {
    description
      "Common node of latest-packaging-operation,
       packaging-operation";
    container packaging-operation-errors-nodes {
      description
        "Table for per-node DNF errors when carrying out
         a packaging operation";
      list packaging-operation-errors-node {
        key "node";
        description
          "Node specific DNF errors when carrying out a
           packaging operation";
        leaf node {
          type xr:Node-id;
          description
            "Node name";
        }
        uses INST-PKG-OP-ERRORS-BAG;
      }
    }
  }

  grouping PACKAGING-OPERATION-INFO {
    description
      "Common node of latest-packaging-operation,
       packaging-operation";
    container packaging-operation-info {
      description
        "Information about a packaging operation";
      uses INST-PKG-OP-BAG;
    }
  }

  grouping ATOMIC-CHANGE-INFO-NODE-TABLE {
    description
      "Common node of atomic-change,
       latest-atomic-change";
    container atomic-change-info-nodes {
      description
        "Table for per-node information when carrying out
         an atomic change";
      list atomic-change-info-node {
        key "node";
        description
          "Node specific information when carrying out an
           atomic change";
        leaf node {
          type xr:Node-id;
          description
            "Node name";
        }
        uses INST-ATOMIC-CHANGE-NODE-BAG;
      }
    }
  }

  augment "/ncs:devices/ncs:device/ncs:config" {
    // NCS drop config false container install
  }
  augment "/ncs:devices/ncs:device/ncs:live-status" {
    container install {
      tailf:ncs-device-type "netconf";
      tailf:display-when "not(../../ncs:module) or ../../ncs:module[ncs:name='Cisco-IOS-XR-install-augmented-oper'] or (../../ncs:live-status-protocol[not(ncs:capability)]) or (../../ncs:live-status-protocol/ncs:capability/ncs:module[.='Cisco-IOS-XR-install-augmented-oper'])";
      description
        "Install operational data";
      container platform-support {
        description
          "Information about what features are supported on
           this platform";
        container platform-support-info {
          description
            "Information about what features are supported
             on this platform";
          uses live_ncs_INST-PLATFORM-SUPPORT-BAG;
        }
      }
      container history {
        description
          "Operation history";
        container latest-transaction {
          description
            "Latest transaction data";
          uses live_ncs_TRANSACTION-INFO-NODE-TABLE;
          uses live_ncs_TRANSACTION-INFO;
          uses live_ncs_ATOMIC-CHANGE-TABLE;
        }
        container latest-packaging-operation {
          description
            "Information about the latest packaging
             operation";
          uses live_ncs_PACKAGING-OPERATION-ERRORS-NODE-TABLE;
          uses live_ncs_PACKAGING-OPERATION-INFO-NODE-TABLE;
          uses live_ncs_PACKAGING-OPERATION-INFO;
        }
        container latest-atomic-change {
          description
            "Latest atomic software change";
          uses live_ncs_PACKAGING-OPERATION-TABLE;
          uses live_ncs_ATOMIC-CHANGE-INFO;
          uses live_ncs_ATOMIC-CHANGE-INFO-NODE-TABLE;
        }
        container transactions {
          description
            "Table for transaction-specific operational data";
          list transaction {
            key "transaction-id";
            description
              "Information about a particular transaction";
            leaf transaction-id {
              type uint32;
              description
                "Install Transaction ID";
            }
            uses live_ncs_TRANSACTION-INFO-NODE-TABLE;
            uses live_ncs_TRANSACTION-INFO;
            uses live_ncs_ATOMIC-CHANGE-TABLE;
          }
        }
      }
      container packages {
        description
          "Package information";
        container cached {
          description
            "Information about cached packages";
          container summary {
            description
              "Summary packages";
            uses live_ncs_INST-PACKAGES-BAG;
          }
          container all {
            description
              "All packages including card-specific
               dependencies";
            uses live_ncs_INST-PACKAGES-BAG;
          }
        }
        container available {
          description
            "Information about available packages";
          container internal {
            description
              "All packages including card-specific
               dependencies";
            uses live_ncs_INST-AVAILABLE-PACKAGES-BAG;
          }
          container all {
            description
              "All user-installable packages";
            uses live_ncs_INST-AVAILABLE-PACKAGES-BAG;
          }
        }
      }
      container internal {
        description
          "Internal debug information";
        container fixes {
          description
            "Information about fixes that are available";
          container available-group-fixes {
            description
              "Groups of fixes";
            list available-group-fixe {
              key "ddts";
              description
                "Information about groups of fixes that are
                 available";
              leaf ddts {
                type xr:live_ncs_Cisco-ios-xr-string;
                description
                  "First DDTS Id in list";
              }
              uses live_ncs_INST-AVAILABLE-GROUP-FIXES-BAG;
            }
          }
        }
        container packages {
          description
            "Package information";
          container pkgmgr {
            description
              "Information about package-manager installed
               packages. During an atomic change, this is the
               full set of packages that will be active after
               the atomic change is applied";
            container nodes {
              description
                "Table for node level data";
              list node {
                key "node";
                description
                  "Per-node packages";
                leaf node {
                  type xr:live_ncs_Node-id;
                  description
                    "Node name";
                }
                uses live_ncs_INST-PACKAGES-BAG;
              }
            }
            container summary {
              description
                "Summary packages";
              uses live_ncs_INST-PACKAGES-BAG;
            }
          }
        }
      }
      container request {
        description
          "Information about the latest user request";
        container verbose {
          description
            "Verbose information about the status of current
             install operation";
          uses live_ncs_INST-REQUEST-VERBOSE-BAG;
        }
      }
      container version {
        description
          "Install version information";
        container detail {
          description
            "Install version detailed information";
          uses live_ncs_INST-VERSION-BAG;
        }
        container brief {
          description
            "Install version brief information";
          uses live_ncs_INST-VERSION-BAG;
        }
      }
      container rollback {
        description
          "Information about software rollback options";
        container rollback-points {
          description
            "Table for rollback points";
          list rollback-point {
            key "id";
            description
              "Rollback point information";
            container summary {
              description
                "Summary of changes when rolling back to a a
                 rollback point";
              uses live_ncs_INST-ROLLBACK-SUMMARY-BAG;
            }
            container installed-packages {
              description
                "Installed packages";
              container user-installable {
                description
                  "User-installable packages associated with
                   rollback point";
                uses live_ncs_INST-PACKAGES-BAG;
              }
              container changes {
                description
                  "Changes in packages if rolling back";
                uses live_ncs_INST-CHANGES-BAG;
              }
            }
            leaf id {
              type uint32;
              description
                "Rollback point ID";
            }
          }
        }
      }
      container fixes {
        description
          "Information about DDTS fixes";
        container deactivate-fixes {
          description
            "Deactivate one or more fixes";
          list deactivate-fixe {
            key "ddt-ss";
            description
              "Information about groups of fixes that are
               available";
            leaf ddt-ss {
              type xr:live_ncs_Cisco-ios-xr-string;
              description
                "Comma separated DDTS list of DDTSs to
                 deactivate";
            }
            uses live_ncs_INST-DEACTIVATE-DDTS-IDS-BAG;
          }
        }
        container available {
          description
            "Information about fixes that are available";
          uses live_ncs_INST-AVAILABLE-FIXES-BAG;
        }
      }
    }
  }
  augment "/ncs:devices/ncs:template/ncs:ned-id/ncs:config" {
    // NCS drop config false container install
  }
}

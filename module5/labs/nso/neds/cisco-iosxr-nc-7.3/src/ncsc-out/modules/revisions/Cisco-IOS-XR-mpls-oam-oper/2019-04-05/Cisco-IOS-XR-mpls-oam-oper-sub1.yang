submodule Cisco-IOS-XR-mpls-oam-oper-sub1 {
  // Generated by yanger -t ncs
  tailf:mount-id "cisco-iosxr-nc-7.3:cisco-iosxr-nc-7.3";

  belongs-to Cisco-IOS-XR-mpls-oam-oper {
    prefix Cisco-IOS-XR-mpls-oam-oper;
  }

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-oam package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Lspv-dpm-igp {
    type string;
    description
      "Lspv dpm igp";
  }

  typedef ncs_template_Lspv-dpm-fault-code {
    type string;
    description
      "Lspv dpm fault code";
  }

  typedef ncs_template_Lspv-dpm-pfx-validation-status {
    type string;
    description
      "Lspv dpm pfx validation status";
  }

  typedef ncs_template_Static-ipv6-address {
    type string;
    description
      "Static ipv6 address";
  }

  typedef ncs_template_Lspv-dpm-addr {
    type string;
    description
      "Lspv dpm addr";
  }

  typedef ncs_rpc_notif_Lspv-dpm-igp {
    type enumeration {
      enum "ospf" {
        description
          "OSPF";
      }
      enum "isis" {
        description
          "ISIS";
      }
    }
    description
      "Lspv dpm igp";
  }

  typedef ncs_rpc_notif_Lspv-dpm-fault-code {
    type enumeration {
      enum "lspv-dpm-fault-na" {
        value 0;
        description
          "Unset Code";
      }
      enum "lspv-dpm-fault-success" {
        value 33;
        description
          "Success";
      }
      enum "lspv-dpm-fault-timeout" {
        value 46;
        description
          "Timeout";
      }
      enum "lspv-dpm-fault-unlbl-out-intf" {
        value 66;
        description
          "Unlabeled output interface";
      }
      enum "lspv-dpm-fault-ds-mismatch" {
        value 68;
        description
          "DS Map mismatch";
      }
      enum "lspv-dpm-fault-no-fec" {
        value 70;
        description
          "No FEC mapping";
      }
      enum "lspv-dpm-fault-unknown-up-idx" {
        value 73;
        description
          "Unknown upstream index";
      }
      enum "lspv-dpm-fault-lbl-out-intf" {
        value 76;
        description
          "Labeled output interface";
      }
      enum "lspv-dpm-fault-mal" {
        value 77;
        description
          "Malformed request";
      }
      enum "lspv-dpm-fault-no-rx-lbl" {
        value 78;
        description
          "No rx label";
      }
      enum "lspv-dpm-fault-no-rx-intf-lbl-prot" {
        value 80;
        description
          "No rx intf label prot";
      }
      enum "lspv-dpm-fault-un-sent" {
        value 81;
        description
          "Request not sent";
      }
      enum "lspv-dpm-fault-transit" {
        value 82;
        description
          "Transit router";
      }
      enum "lspv-dpm-fault-x" {
        value 88;
        description
          "Unknown return code";
      }
      enum "lspv-dpm-fault-dd-map" {
        value 100;
        description
          "DDMAP";
      }
      enum "lspv-dpm-fault-fec-mismatch" {
        value 102;
        description
          "FEC mismatch";
      }
      enum "lspv-dpm-fault-bad-tlv" {
        value 109;
        description
          "Unsupported TLV";
      }
      enum "lspv-dpm-fault-pre-lsp" {
        value 112;
        description
          "Premature termination of LSP";
      }
      enum "lspv-dpm-fault-rt-0t" {
        value 120;
        description
          "return code 0t";
      }
    }
    description
      "Lspv dpm fault code";
  }

  typedef ncs_rpc_notif_Lspv-dpm-pfx-validation-status {
    type enumeration {
      enum "never" {
        description
          "Never";
      }
      enum "complete" {
        description
          "Complete";
      }
      enum "in-progress" {
        description
          "In Progress";
      }
      enum "scheduled" {
        description
          "Scheduled";
      }
      enum "stale" {
        description
          "Stale";
      }
      enum "no-upstreams" {
        description
          "No Upstreams";
      }
    }
    description
      "Lspv dpm pfx validation status";
  }

  typedef ncs_rpc_notif_Static-ipv6-address {
    type inet:ipv6-address;
    description
      "Static ipv6 address";
  }

  typedef ncs_rpc_notif_Lspv-dpm-addr {
    type enumeration {
      enum "ipv4" {
        description
          "IPv4";
      }
      enum "ipv6" {
        description
          "IPv6";
      }
    }
    description
      "Lspv dpm addr";
  }

  typedef live_ncs_Lspv-dpm-igp {
    type enumeration {
      enum "ospf" {
        description
          "OSPF";
      }
      enum "isis" {
        description
          "ISIS";
      }
    }
    description
      "Lspv dpm igp";
  }

  typedef live_ncs_Lspv-dpm-fault-code {
    type enumeration {
      enum "lspv-dpm-fault-na" {
        value 0;
        description
          "Unset Code";
      }
      enum "lspv-dpm-fault-success" {
        value 33;
        description
          "Success";
      }
      enum "lspv-dpm-fault-timeout" {
        value 46;
        description
          "Timeout";
      }
      enum "lspv-dpm-fault-unlbl-out-intf" {
        value 66;
        description
          "Unlabeled output interface";
      }
      enum "lspv-dpm-fault-ds-mismatch" {
        value 68;
        description
          "DS Map mismatch";
      }
      enum "lspv-dpm-fault-no-fec" {
        value 70;
        description
          "No FEC mapping";
      }
      enum "lspv-dpm-fault-unknown-up-idx" {
        value 73;
        description
          "Unknown upstream index";
      }
      enum "lspv-dpm-fault-lbl-out-intf" {
        value 76;
        description
          "Labeled output interface";
      }
      enum "lspv-dpm-fault-mal" {
        value 77;
        description
          "Malformed request";
      }
      enum "lspv-dpm-fault-no-rx-lbl" {
        value 78;
        description
          "No rx label";
      }
      enum "lspv-dpm-fault-no-rx-intf-lbl-prot" {
        value 80;
        description
          "No rx intf label prot";
      }
      enum "lspv-dpm-fault-un-sent" {
        value 81;
        description
          "Request not sent";
      }
      enum "lspv-dpm-fault-transit" {
        value 82;
        description
          "Transit router";
      }
      enum "lspv-dpm-fault-x" {
        value 88;
        description
          "Unknown return code";
      }
      enum "lspv-dpm-fault-dd-map" {
        value 100;
        description
          "DDMAP";
      }
      enum "lspv-dpm-fault-fec-mismatch" {
        value 102;
        description
          "FEC mismatch";
      }
      enum "lspv-dpm-fault-bad-tlv" {
        value 109;
        description
          "Unsupported TLV";
      }
      enum "lspv-dpm-fault-pre-lsp" {
        value 112;
        description
          "Premature termination of LSP";
      }
      enum "lspv-dpm-fault-rt-0t" {
        value 120;
        description
          "return code 0t";
      }
    }
    description
      "Lspv dpm fault code";
  }

  typedef live_ncs_Lspv-dpm-pfx-validation-status {
    type enumeration {
      enum "never" {
        description
          "Never";
      }
      enum "complete" {
        description
          "Complete";
      }
      enum "in-progress" {
        description
          "In Progress";
      }
      enum "scheduled" {
        description
          "Scheduled";
      }
      enum "stale" {
        description
          "Stale";
      }
      enum "no-upstreams" {
        description
          "No Upstreams";
      }
    }
    description
      "Lspv dpm pfx validation status";
  }

  typedef live_ncs_Static-ipv6-address {
    type inet:ipv6-address;
    description
      "Static ipv6 address";
  }

  typedef live_ncs_Lspv-dpm-addr {
    type enumeration {
      enum "ipv4" {
        description
          "IPv4";
      }
      enum "ipv6" {
        description
          "IPv6";
      }
    }
    description
      "Lspv dpm addr";
  }

  typedef Lspv-dpm-igp {
    type enumeration {
      enum "ospf" {
        description
          "OSPF";
      }
      enum "isis" {
        description
          "ISIS";
      }
    }
    description
      "Lspv dpm igp";
  }

  typedef Lspv-dpm-fault-code {
    type enumeration {
      enum "lspv-dpm-fault-na" {
        value 0;
        description
          "Unset Code";
      }
      enum "lspv-dpm-fault-success" {
        value 33;
        description
          "Success";
      }
      enum "lspv-dpm-fault-timeout" {
        value 46;
        description
          "Timeout";
      }
      enum "lspv-dpm-fault-unlbl-out-intf" {
        value 66;
        description
          "Unlabeled output interface";
      }
      enum "lspv-dpm-fault-ds-mismatch" {
        value 68;
        description
          "DS Map mismatch";
      }
      enum "lspv-dpm-fault-no-fec" {
        value 70;
        description
          "No FEC mapping";
      }
      enum "lspv-dpm-fault-unknown-up-idx" {
        value 73;
        description
          "Unknown upstream index";
      }
      enum "lspv-dpm-fault-lbl-out-intf" {
        value 76;
        description
          "Labeled output interface";
      }
      enum "lspv-dpm-fault-mal" {
        value 77;
        description
          "Malformed request";
      }
      enum "lspv-dpm-fault-no-rx-lbl" {
        value 78;
        description
          "No rx label";
      }
      enum "lspv-dpm-fault-no-rx-intf-lbl-prot" {
        value 80;
        description
          "No rx intf label prot";
      }
      enum "lspv-dpm-fault-un-sent" {
        value 81;
        description
          "Request not sent";
      }
      enum "lspv-dpm-fault-transit" {
        value 82;
        description
          "Transit router";
      }
      enum "lspv-dpm-fault-x" {
        value 88;
        description
          "Unknown return code";
      }
      enum "lspv-dpm-fault-dd-map" {
        value 100;
        description
          "DDMAP";
      }
      enum "lspv-dpm-fault-fec-mismatch" {
        value 102;
        description
          "FEC mismatch";
      }
      enum "lspv-dpm-fault-bad-tlv" {
        value 109;
        description
          "Unsupported TLV";
      }
      enum "lspv-dpm-fault-pre-lsp" {
        value 112;
        description
          "Premature termination of LSP";
      }
      enum "lspv-dpm-fault-rt-0t" {
        value 120;
        description
          "return code 0t";
      }
    }
    description
      "Lspv dpm fault code";
  }

  typedef Lspv-dpm-pfx-validation-status {
    type enumeration {
      enum "never" {
        description
          "Never";
      }
      enum "complete" {
        description
          "Complete";
      }
      enum "in-progress" {
        description
          "In Progress";
      }
      enum "scheduled" {
        description
          "Scheduled";
      }
      enum "stale" {
        description
          "Stale";
      }
      enum "no-upstreams" {
        description
          "No Upstreams";
      }
    }
    description
      "Lspv dpm pfx validation status";
  }

  typedef Static-ipv6-address {
    type inet:ipv6-address;
    description
      "Static ipv6 address";
  }

  typedef Lspv-dpm-addr {
    type enumeration {
      enum "ipv4" {
        description
          "IPv4";
      }
      enum "ipv6" {
        description
          "IPv6";
      }
    }
    description
      "Lspv dpm addr";
  }

  grouping ncs_template_LSPV-DPM-PFX-DB-SUMMARY {
    description
      "LSPV DPM Prefix DB summary";
    leaf pfx-db-size {
      type string;
      description
        "Size of Prefix DB";
    }
    leaf validated-prefixes {
      type string;
      description
        "Number of Validated Prefixes";
    }
    leaf requests-sent {
      type string;
      description
        "Number of Echo Requests Sent";
    }
    leaf requests-rcvd {
      type string;
      description
        "Number of Echo Requests Received";
    }
    leaf validation-errors {
      type string;
      description
        "Validation Errors";
    }
    leaf validation-start-time {
      type string;
      description
        "DPM Start Time";
    }
    leaf validation-end-time {
      type string;
      description
        "DPM End Time";
    }
  }

  grouping ncs_template_LSPV-DPM-ADJ-INFO {
    description
      "Adjacency Information";
    leaf local-label {
      type string;
      description
        "Label";
    }
    leaf flags {
      type string;
      description
        "Flags";
    }
    leaf protected {
      type string;
      description
        "Protected";
    }
    leaf static-adj {
      type string;
      description
        "Static Adj";
    }
    leaf group {
      type string;
      description
        "Group";
    }
    leaf isis-l1 {
      type string;
      description
        "ISIS Level 1";
    }
    leaf isis-l2 {
      type string;
      description
        "ISIS Level 2";
    }
    leaf success {
      type string;
      description
        "Sucess";
    }
  }

  grouping ncs_template_LSPV-DPM-ADJ {
    description
      "LSPV DPM Adjacency";
    container local-address {
      description
        "Local Address";
      uses ncs_template_LSPV-DPM-PREFIX-BAG;
    }
    container remote-address {
      description
        "Remote Address";
      uses ncs_template_LSPV-DPM-PREFIX-BAG;
    }
    leaf interface-name-xr {
      type string;
      description
        "Interface name";
    }
    leaf local-interface-id {
      type string;
      description
        "Local Interface Id";
    }
    leaf unprotected-local-label {
      type string;
      description
        "Unprotected Local Label";
    }
    leaf remote-interface-id {
      type string;
      description
        "Remote Interface Id";
    }
    leaf unprotected-remote-label {
      type string;
      description
        "Unprotected Remote Label";
    }
    leaf valid-adj {
      type string;
      description
        "Valid Adjacencies";
    }
    leaf total-adj {
      type string;
      description
        "Total Adjacencies";
    }
    leaf is-isis {
      type string;
      description
        "ISIS enabled";
    }
    leaf is-ipv4 {
      type string;
      description
        "IPv4 enabled";
    }
    leaf is-excluded {
      type string;
      description
        "Skipped for the current run";
    }
    leaf last-fault-time {
      type string;
      description
        "Last Fault Time";
    }
    list local-adj {
      // NCS patched for predictable order
      ordered-by user;
      description
        "Local Adjacencies";
      uses ncs_template_LSPV-DPM-ADJ-INFO;
    }
    list remote-adj {
      // NCS patched for predictable order
      ordered-by user;
      description
        "Remote Adjacencies";
      uses ncs_template_LSPV-DPM-ADJ-INFO;
    }
  }

  grouping ncs_template_LSPV-DPM-ADJ-FAULT {
    description
      "LSPV DPM ADJ fault";
    container ip {
      description
        "IP Address";
      xr:event-telemetry "Subscribe Telemetry Event";
      uses ncs_template_LSPV-DPM-PREFIX-BAG;
    }
    leaf interface-name-xr {
      type string;
      description
        "Interface name";
    }
    leaf igp {
      type ncs_template_Lspv-dpm-igp;
      description
        "IGP";
      xr:event-telemetry "Subscribe Telemetry Event";
    }
    leaf local-adj-sid {
      type string;
      description
        "Local Adj SID";
      xr:event-telemetry "Subscribe Telemetry Event";
    }
    leaf error-code {
      type ncs_template_Lspv-dpm-fault-code;
      description
        "DPM Error code";
      xr:event-telemetry "Subscribe Telemetry Event";
    }
  }

  grouping ncs_template_LSPV-DPM-SUMMARY {
    description
      "LSPV DPM summary";
    leaf v4rib-reg {
      type string;
      description
        "Registration to IPv4 RIB";
      xr:event-telemetry "Subscribe Telemetry Event";
    }
    leaf v4rib-con {
      type string;
      description
        "Connection to IPv4 RIB";
      xr:event-telemetry "Subscribe Telemetry Event";
    }
    leaf sysdb-reg {
      type string;
      description
        "Registration to SYSDB";
      xr:event-telemetry "Subscribe Telemetry Event";
    }
    leaf sysdb-con {
      type string;
      description
        "Connection to SYSDB";
      xr:event-telemetry "Subscribe Telemetry Event";
    }
    leaf im-reg {
      type string;
      description
        "Registration to IM";
      xr:event-telemetry "Subscribe Telemetry Event";
    }
    leaf im-con {
      type string;
      description
        "Connection to IM";
      xr:event-telemetry "Subscribe Telemetry Event";
    }
    leaf lspv-con {
      type string;
      description
        "Connection to LSPV";
      xr:event-telemetry "Subscribe Telemetry Event";
    }
    leaf num-of-adj {
      type string;
      description
        "Number of Adjacencies in DB";
      xr:event-telemetry "Subscribe Telemetry Event";
    }
    leaf validated-adjs {
      type string;
      description
        "Number of Validated Adjacencies";
      xr:event-telemetry "Subscribe Telemetry Event";
    }
    leaf dpm-eligible-intfs {
      type string;
      description
        "Number of DPM allowed interfaces";
    }
    leaf error-adjs {
      type string;
      description
        "Errored Adjacencies";
      xr:event-telemetry "Subscribe Telemetry Event";
    }
    leaf num-of-pfx {
      type string;
      description
        "Number of Prefixes in DB";
      xr:event-telemetry "Subscribe Telemetry Event";
    }
    leaf validated-pfxs {
      type string;
      description
        "Number of Validated Prefixes";
      xr:event-telemetry "Subscribe Telemetry Event";
    }
    leaf error-pfxs {
      type string;
      description
        "Errored Prefixes";
      xr:event-telemetry "Subscribe Telemetry Event";
    }
    leaf total-requests {
      type string;
      description
        "Total Requests";
      xr:event-telemetry "Subscribe Telemetry Event";
    }
    leaf total-responses {
      type string;
      description
        "Total Responses";
      xr:event-telemetry "Subscribe Telemetry Event";
    }
    leaf total-prop-req {
      type string;
      description
        "Total Property Requests";
    }
    leaf total-prop-errs {
      type string;
      description
        "Total Property Errors";
    }
    leaf total-prop-resp {
      type string;
      description
        "Total Property Responses";
    }
    leaf dpm-interval {
      type string;
      description
        "DPM Run Interval";
      xr:event-telemetry "Subscribe Telemetry Event";
    }
    leaf dpm-packets-per-second {
      type string;
      units "packet/s";
      description
        "DPM Packets Per Second";
      xr:event-telemetry "Subscribe Telemetry Event";
    }
    leaf total-retries {
      type string;
      description
        "Total Retries";
    }
    leaf validation-complete {
      type string;
      description
        "DPM Validation Complete";
      xr:event-telemetry "Subscribe Telemetry Event";
    }
    leaf last-dpm-run-time {
      type string;
      description
        "Last DPM interation time in nanosec";
      xr:event-telemetry "Subscribe Telemetry Event";
    }
    leaf last-dpm-fault-time {
      type string;
      description
        "Last DPM fault time in nanosec";
      xr:event-telemetry "Subscribe Telemetry Event";
    }
    leaf last-dpm-fault-time-ever {
      type string;
      description
        "Last Ever DPM fault time in nanosec";
      xr:event-telemetry "Subscribe Telemetry Event";
    }
  }

  grouping ncs_template_LSPV-DPM-FAULT {
    description
      "LSPV DPM Pfx NH fault";
    container prefix-xr {
      description
        "Prefix";
      uses ncs_template_LSPV-DPM-PREFIX-INFO;
    }
    container downlink-fault {
      description
        "Downlink associated with the fault";
      xr:event-telemetry "Subscribe Telemetry Event";
      uses ncs_template_LSPV-DPM-PREFIX-BAG;
    }
    container uplink-fault {
      description
        "Uplink associated with the fault";
      xr:event-telemetry "Subscribe Telemetry Event";
      uses ncs_template_LSPV-DPM-PREFIX-BAG;
    }
    leaf prefix-sid {
      type string;
      description
        "Prefix SID";
    }
    leaf error-code {
      type ncs_template_Lspv-dpm-fault-code;
      description
        "DPM Error code";
      xr:event-telemetry "Subscribe Telemetry Event";
    }
  }

  grouping ncs_template_LSPV-DPM-COUNTERS {
    description
      "LSPV DPM Counters";
    leaf requests-sent {
      type string;
      description
        "Requests Last Sent";
    }
    leaf requests-last-pending {
      type string;
      description
        "Requests Last Pending";
    }
    leaf requests-last-returned {
      type string;
      description
        "Requests Last Returned";
    }
    leaf requests-unsent {
      type string;
      description
        "Requests Unsent";
    }
    leaf requests-retry-unsent {
      type string;
      description
        "Requests Retry Unsent";
    }
    leaf requests-pending {
      type string;
      description
        "Requests Pending";
    }
  }

  grouping ncs_template_LSPV-DPM-PFX-ADJ {
    description
      "LSPV DPM Prefix Adj";
    container next-hop {
      description
        "NextHop";
      uses ncs_template_LSPV-DPM-PREFIX-BAG;
    }
    leaf requests-sent {
      type string;
      description
        "Requests Sent";
    }
    leaf errors {
      type string;
      description
        "Errors";
    }
    leaf last-fault-time {
      type string;
      description
        "Last Fault Time";
    }
    leaf status {
      type ncs_template_Lspv-dpm-pfx-validation-status;
      description
        "Status";
    }
    leaf stale {
      type string;
      description
        "Stale";
    }
  }

  grouping ncs_template_LSPV-DPM-PREFIX-BAG {
    description
      "LSPV DPM PREFIX BAG";
    leaf af-name {
      type ncs_template_Lspv-dpm-addr;
      description
        "AFName";
    }
    leaf ipv4-prefix {
      // NCS drop when statement
      type string;
      description
        "IPv4 prefix";
    }
    leaf ipv6-prefix {
      // NCS drop when statement
      type ncs_template_Static-ipv6-address;
      description
        "IPv6 prefix";
    }
  }

  grouping ncs_template_LSPV-DPM-PREFIX-INFO {
    description
      "Prefix Information";
    container prefix {
      description
        "Prefix";
      uses ncs_template_LSPV-DPM-PREFIX-BAG;
    }
    leaf prefix-length {
      type string;
      description
        "Prefix length";
    }
  }

  grouping ncs_template_LSPV-DPM-PFX {
    description
      "LSPV DPM Prefix";
    container prefix-xr {
      description
        "Prefix";
      xr:event-telemetry "Subscribe Telemetry Event";
      uses ncs_template_LSPV-DPM-PREFIX-INFO;
    }
    leaf pfx-sid {
      type string;
      description
        "Prefix SID";
      xr:event-telemetry "Subscribe Telemetry Event";
    }
    leaf requests-sent {
      type string;
      description
        "Requests Sent";
    }
    leaf requests-rcvd {
      type string;
      description
        "Requests Rcvd";
    }
    leaf errors {
      type string;
      description
        "Errors";
    }
    leaf last-fault-time {
      type string;
      description
        "Last Fault Time";
    }
    leaf status {
      type ncs_template_Lspv-dpm-pfx-validation-status;
      description
        "Status";
    }
    list upstream-adj {
      // NCS patched for predictable order
      ordered-by user;
      description
        "Upstream Adjacency";
      uses ncs_template_LSPV-DPM-PREFIX-BAG;
    }
    list downstream-adj-info {
      // NCS patched for predictable order
      ordered-by user;
      description
        "Downstream Adjacency Info";
      uses ncs_template_LSPV-DPM-PFX-ADJ;
    }
  }

  grouping ncs_template_LSPV-DPM-ADJ-DB-SUMMARY {
    description
      "LSPV DPM Adjacency DB summary";
    leaf adj-db-size {
      type string;
      description
        "Size of Adjacency DB";
    }
    leaf dpm-eligible-intfs {
      type string;
      description
        "Number of DPM allowed interfaces";
    }
    leaf err-intfs {
      type string;
      description
        "Number of Interfaces with Errors";
    }
    leaf validation-start-time {
      type string;
      description
        "Validation Start Time";
    }
    leaf validation-end-time {
      type string;
      description
        "Validation End Time";
    }
  }

  grouping ncs_rpc_notif_LSPV-DPM-PFX-DB-SUMMARY {
    description
      "LSPV DPM Prefix DB summary";
    leaf pfx-db-size {
      type uint32;
      description
        "Size of Prefix DB";
    }
    leaf validated-prefixes {
      type uint32;
      description
        "Number of Validated Prefixes";
    }
    leaf requests-sent {
      type uint32;
      description
        "Number of Echo Requests Sent";
    }
    leaf requests-rcvd {
      type uint32;
      description
        "Number of Echo Requests Received";
    }
    leaf validation-errors {
      type uint32;
      description
        "Validation Errors";
    }
    leaf validation-start-time {
      type uint64;
      description
        "DPM Start Time";
    }
    leaf validation-end-time {
      type uint64;
      description
        "DPM End Time";
    }
  }

  grouping ncs_rpc_notif_LSPV-DPM-ADJ-INFO {
    description
      "Adjacency Information";
    leaf local-label {
      type uint32;
      description
        "Label";
    }
    leaf flags {
      type uint32;
      description
        "Flags";
    }
    leaf protected {
      type boolean;
      description
        "Protected";
    }
    leaf static-adj {
      type boolean;
      description
        "Static Adj";
    }
    leaf group {
      type boolean;
      description
        "Group";
    }
    leaf isis-l1 {
      type boolean;
      description
        "ISIS Level 1";
    }
    leaf isis-l2 {
      type boolean;
      description
        "ISIS Level 2";
    }
    leaf success {
      type boolean;
      description
        "Sucess";
    }
  }

  grouping ncs_rpc_notif_LSPV-DPM-ADJ {
    description
      "LSPV DPM Adjacency";
    container local-address {
      description
        "Local Address";
      uses ncs_rpc_notif_LSPV-DPM-PREFIX-BAG;
    }
    container remote-address {
      description
        "Remote Address";
      uses ncs_rpc_notif_LSPV-DPM-PREFIX-BAG;
    }
    leaf interface-name-xr {
      type string;
      description
        "Interface name";
    }
    leaf local-interface-id {
      type uint32;
      description
        "Local Interface Id";
    }
    leaf unprotected-local-label {
      type uint32;
      description
        "Unprotected Local Label";
    }
    leaf remote-interface-id {
      type uint32;
      description
        "Remote Interface Id";
    }
    leaf unprotected-remote-label {
      type uint32;
      description
        "Unprotected Remote Label";
    }
    leaf valid-adj {
      type uint32;
      description
        "Valid Adjacencies";
    }
    leaf total-adj {
      type uint32;
      description
        "Total Adjacencies";
    }
    leaf is-isis {
      type boolean;
      description
        "ISIS enabled";
    }
    leaf is-ipv4 {
      type boolean;
      description
        "IPv4 enabled";
    }
    leaf is-excluded {
      type boolean;
      description
        "Skipped for the current run";
    }
    leaf last-fault-time {
      type uint64;
      description
        "Last Fault Time";
    }
    list local-adj {
      description
        "Local Adjacencies";
      uses ncs_rpc_notif_LSPV-DPM-ADJ-INFO;
    }
    list remote-adj {
      description
        "Remote Adjacencies";
      uses ncs_rpc_notif_LSPV-DPM-ADJ-INFO;
    }
  }

  grouping ncs_rpc_notif_LSPV-DPM-ADJ-FAULT {
    description
      "LSPV DPM ADJ fault";
    container ip {
      description
        "IP Address";
      xr:event-telemetry "Subscribe Telemetry Event";
      uses ncs_rpc_notif_LSPV-DPM-PREFIX-BAG;
    }
    leaf interface-name-xr {
      type string;
      description
        "Interface name";
    }
    leaf igp {
      type ncs_rpc_notif_Lspv-dpm-igp;
      description
        "IGP";
      xr:event-telemetry "Subscribe Telemetry Event";
    }
    leaf local-adj-sid {
      type uint32;
      description
        "Local Adj SID";
      xr:event-telemetry "Subscribe Telemetry Event";
    }
    leaf error-code {
      type ncs_rpc_notif_Lspv-dpm-fault-code;
      description
        "DPM Error code";
      xr:event-telemetry "Subscribe Telemetry Event";
    }
  }

  grouping ncs_rpc_notif_LSPV-DPM-SUMMARY {
    description
      "LSPV DPM summary";
    leaf v4rib-reg {
      type boolean;
      description
        "Registration to IPv4 RIB";
      xr:event-telemetry "Subscribe Telemetry Event";
    }
    leaf v4rib-con {
      type boolean;
      description
        "Connection to IPv4 RIB";
      xr:event-telemetry "Subscribe Telemetry Event";
    }
    leaf sysdb-reg {
      type boolean;
      description
        "Registration to SYSDB";
      xr:event-telemetry "Subscribe Telemetry Event";
    }
    leaf sysdb-con {
      type boolean;
      description
        "Connection to SYSDB";
      xr:event-telemetry "Subscribe Telemetry Event";
    }
    leaf im-reg {
      type boolean;
      description
        "Registration to IM";
      xr:event-telemetry "Subscribe Telemetry Event";
    }
    leaf im-con {
      type boolean;
      description
        "Connection to IM";
      xr:event-telemetry "Subscribe Telemetry Event";
    }
    leaf lspv-con {
      type boolean;
      description
        "Connection to LSPV";
      xr:event-telemetry "Subscribe Telemetry Event";
    }
    leaf num-of-adj {
      type uint32;
      description
        "Number of Adjacencies in DB";
      xr:event-telemetry "Subscribe Telemetry Event";
    }
    leaf validated-adjs {
      type uint32;
      description
        "Number of Validated Adjacencies";
      xr:event-telemetry "Subscribe Telemetry Event";
    }
    leaf dpm-eligible-intfs {
      type uint32;
      description
        "Number of DPM allowed interfaces";
    }
    leaf error-adjs {
      type uint32;
      description
        "Errored Adjacencies";
      xr:event-telemetry "Subscribe Telemetry Event";
    }
    leaf num-of-pfx {
      type uint32;
      description
        "Number of Prefixes in DB";
      xr:event-telemetry "Subscribe Telemetry Event";
    }
    leaf validated-pfxs {
      type uint32;
      description
        "Number of Validated Prefixes";
      xr:event-telemetry "Subscribe Telemetry Event";
    }
    leaf error-pfxs {
      type uint32;
      description
        "Errored Prefixes";
      xr:event-telemetry "Subscribe Telemetry Event";
    }
    leaf total-requests {
      type uint32;
      description
        "Total Requests";
      xr:event-telemetry "Subscribe Telemetry Event";
    }
    leaf total-responses {
      type uint32;
      description
        "Total Responses";
      xr:event-telemetry "Subscribe Telemetry Event";
    }
    leaf total-prop-req {
      type uint32;
      description
        "Total Property Requests";
    }
    leaf total-prop-errs {
      type uint32;
      description
        "Total Property Errors";
    }
    leaf total-prop-resp {
      type uint32;
      description
        "Total Property Responses";
    }
    leaf dpm-interval {
      type uint32;
      description
        "DPM Run Interval";
      xr:event-telemetry "Subscribe Telemetry Event";
    }
    leaf dpm-packets-per-second {
      type uint32;
      units "packet/s";
      description
        "DPM Packets Per Second";
      xr:event-telemetry "Subscribe Telemetry Event";
    }
    leaf total-retries {
      type uint32;
      description
        "Total Retries";
    }
    leaf validation-complete {
      type boolean;
      description
        "DPM Validation Complete";
      xr:event-telemetry "Subscribe Telemetry Event";
    }
    leaf last-dpm-run-time {
      type uint64;
      description
        "Last DPM interation time in nanosec";
      xr:event-telemetry "Subscribe Telemetry Event";
    }
    leaf last-dpm-fault-time {
      type uint64;
      description
        "Last DPM fault time in nanosec";
      xr:event-telemetry "Subscribe Telemetry Event";
    }
    leaf last-dpm-fault-time-ever {
      type uint64;
      description
        "Last Ever DPM fault time in nanosec";
      xr:event-telemetry "Subscribe Telemetry Event";
    }
  }

  grouping ncs_rpc_notif_LSPV-DPM-FAULT {
    description
      "LSPV DPM Pfx NH fault";
    container prefix-xr {
      description
        "Prefix";
      uses ncs_rpc_notif_LSPV-DPM-PREFIX-INFO;
    }
    container downlink-fault {
      description
        "Downlink associated with the fault";
      xr:event-telemetry "Subscribe Telemetry Event";
      uses ncs_rpc_notif_LSPV-DPM-PREFIX-BAG;
    }
    container uplink-fault {
      description
        "Uplink associated with the fault";
      xr:event-telemetry "Subscribe Telemetry Event";
      uses ncs_rpc_notif_LSPV-DPM-PREFIX-BAG;
    }
    leaf prefix-sid {
      type uint32;
      description
        "Prefix SID";
    }
    leaf error-code {
      type ncs_rpc_notif_Lspv-dpm-fault-code;
      description
        "DPM Error code";
      xr:event-telemetry "Subscribe Telemetry Event";
    }
  }

  grouping ncs_rpc_notif_LSPV-DPM-COUNTERS {
    description
      "LSPV DPM Counters";
    leaf requests-sent {
      type uint32;
      description
        "Requests Last Sent";
    }
    leaf requests-last-pending {
      type uint32;
      description
        "Requests Last Pending";
    }
    leaf requests-last-returned {
      type uint32;
      description
        "Requests Last Returned";
    }
    leaf requests-unsent {
      type uint32;
      description
        "Requests Unsent";
    }
    leaf requests-retry-unsent {
      type uint32;
      description
        "Requests Retry Unsent";
    }
    leaf requests-pending {
      type uint32;
      description
        "Requests Pending";
    }
  }

  grouping ncs_rpc_notif_LSPV-DPM-PFX-ADJ {
    description
      "LSPV DPM Prefix Adj";
    container next-hop {
      description
        "NextHop";
      uses ncs_rpc_notif_LSPV-DPM-PREFIX-BAG;
    }
    leaf requests-sent {
      type uint32;
      description
        "Requests Sent";
    }
    leaf errors {
      type uint32;
      description
        "Errors";
    }
    leaf last-fault-time {
      type uint64;
      description
        "Last Fault Time";
    }
    leaf status {
      type ncs_rpc_notif_Lspv-dpm-pfx-validation-status;
      description
        "Status";
    }
    leaf stale {
      type boolean;
      description
        "Stale";
    }
  }

  grouping ncs_rpc_notif_LSPV-DPM-PREFIX-BAG {
    description
      "LSPV DPM PREFIX BAG";
    leaf af-name {
      type ncs_rpc_notif_Lspv-dpm-addr;
      description
        "AFName";
    }
    leaf ipv4-prefix {
      when "../af-name = 'ipv4'" {
        tailf:xpath-root 3;
        description
          "../AFName = 'IPv4'";
      }
      type inet:ipv4-address;
      description
        "IPv4 prefix";
    }
    leaf ipv6-prefix {
      when "../af-name = 'ipv6'" {
        tailf:xpath-root 3;
        description
          "../AFName = 'IPv6'";
      }
      type ncs_rpc_notif_Static-ipv6-address;
      description
        "IPv6 prefix";
    }
  }

  grouping ncs_rpc_notif_LSPV-DPM-PREFIX-INFO {
    description
      "Prefix Information";
    container prefix {
      description
        "Prefix";
      uses ncs_rpc_notif_LSPV-DPM-PREFIX-BAG;
    }
    leaf prefix-length {
      type uint8;
      description
        "Prefix length";
    }
  }

  grouping ncs_rpc_notif_LSPV-DPM-PFX {
    description
      "LSPV DPM Prefix";
    container prefix-xr {
      description
        "Prefix";
      xr:event-telemetry "Subscribe Telemetry Event";
      uses ncs_rpc_notif_LSPV-DPM-PREFIX-INFO;
    }
    leaf pfx-sid {
      type uint32;
      description
        "Prefix SID";
      xr:event-telemetry "Subscribe Telemetry Event";
    }
    leaf requests-sent {
      type uint32;
      description
        "Requests Sent";
    }
    leaf requests-rcvd {
      type uint32;
      description
        "Requests Rcvd";
    }
    leaf errors {
      type uint32;
      description
        "Errors";
    }
    leaf last-fault-time {
      type uint64;
      description
        "Last Fault Time";
    }
    leaf status {
      type ncs_rpc_notif_Lspv-dpm-pfx-validation-status;
      description
        "Status";
    }
    list upstream-adj {
      description
        "Upstream Adjacency";
      uses ncs_rpc_notif_LSPV-DPM-PREFIX-BAG;
    }
    list downstream-adj-info {
      description
        "Downstream Adjacency Info";
      uses ncs_rpc_notif_LSPV-DPM-PFX-ADJ;
    }
  }

  grouping ncs_rpc_notif_LSPV-DPM-ADJ-DB-SUMMARY {
    description
      "LSPV DPM Adjacency DB summary";
    leaf adj-db-size {
      type uint32;
      description
        "Size of Adjacency DB";
    }
    leaf dpm-eligible-intfs {
      type uint32;
      description
        "Number of DPM allowed interfaces";
    }
    leaf err-intfs {
      type uint32;
      description
        "Number of Interfaces with Errors";
    }
    leaf validation-start-time {
      type uint64;
      description
        "Validation Start Time";
    }
    leaf validation-end-time {
      type uint64;
      description
        "Validation End Time";
    }
  }

  grouping live_ncs_LSPV-DPM-PFX-DB-SUMMARY {
    description
      "LSPV DPM Prefix DB summary";
    leaf pfx-db-size {
      type uint32;
      description
        "Size of Prefix DB";
    }
    leaf validated-prefixes {
      type uint32;
      description
        "Number of Validated Prefixes";
    }
    leaf requests-sent {
      type uint32;
      description
        "Number of Echo Requests Sent";
    }
    leaf requests-rcvd {
      type uint32;
      description
        "Number of Echo Requests Received";
    }
    leaf validation-errors {
      type uint32;
      description
        "Validation Errors";
    }
    leaf validation-start-time {
      type uint64;
      description
        "DPM Start Time";
    }
    leaf validation-end-time {
      type uint64;
      description
        "DPM End Time";
    }
  }

  grouping live_ncs_LSPV-DPM-ADJ-INFO {
    description
      "Adjacency Information";
    leaf local-label {
      type uint32;
      description
        "Label";
    }
    leaf flags {
      type uint32;
      description
        "Flags";
    }
    leaf protected {
      type boolean;
      description
        "Protected";
    }
    leaf static-adj {
      type boolean;
      description
        "Static Adj";
    }
    leaf group {
      type boolean;
      description
        "Group";
    }
    leaf isis-l1 {
      type boolean;
      description
        "ISIS Level 1";
    }
    leaf isis-l2 {
      type boolean;
      description
        "ISIS Level 2";
    }
    leaf success {
      type boolean;
      description
        "Sucess";
    }
  }

  grouping live_ncs_LSPV-DPM-ADJ {
    description
      "LSPV DPM Adjacency";
    container local-address {
      description
        "Local Address";
      uses live_ncs_LSPV-DPM-PREFIX-BAG;
    }
    container remote-address {
      description
        "Remote Address";
      uses live_ncs_LSPV-DPM-PREFIX-BAG;
    }
    leaf interface-name-xr {
      type string;
      description
        "Interface name";
    }
    leaf local-interface-id {
      type uint32;
      description
        "Local Interface Id";
    }
    leaf unprotected-local-label {
      type uint32;
      description
        "Unprotected Local Label";
    }
    leaf remote-interface-id {
      type uint32;
      description
        "Remote Interface Id";
    }
    leaf unprotected-remote-label {
      type uint32;
      description
        "Unprotected Remote Label";
    }
    leaf valid-adj {
      type uint32;
      description
        "Valid Adjacencies";
    }
    leaf total-adj {
      type uint32;
      description
        "Total Adjacencies";
    }
    leaf is-isis {
      type boolean;
      description
        "ISIS enabled";
    }
    leaf is-ipv4 {
      type boolean;
      description
        "IPv4 enabled";
    }
    leaf is-excluded {
      type boolean;
      description
        "Skipped for the current run";
    }
    leaf last-fault-time {
      type uint64;
      description
        "Last Fault Time";
    }
    list local-adj {
      description
        "Local Adjacencies";
      uses live_ncs_LSPV-DPM-ADJ-INFO;
    }
    list remote-adj {
      description
        "Remote Adjacencies";
      uses live_ncs_LSPV-DPM-ADJ-INFO;
    }
  }

  grouping live_ncs_LSPV-DPM-ADJ-FAULT {
    description
      "LSPV DPM ADJ fault";
    container ip {
      description
        "IP Address";
      xr:event-telemetry "Subscribe Telemetry Event";
      uses live_ncs_LSPV-DPM-PREFIX-BAG;
    }
    leaf interface-name-xr {
      type string;
      description
        "Interface name";
    }
    leaf igp {
      type live_ncs_Lspv-dpm-igp;
      description
        "IGP";
      xr:event-telemetry "Subscribe Telemetry Event";
    }
    leaf local-adj-sid {
      type uint32;
      description
        "Local Adj SID";
      xr:event-telemetry "Subscribe Telemetry Event";
    }
    leaf error-code {
      type live_ncs_Lspv-dpm-fault-code;
      description
        "DPM Error code";
      xr:event-telemetry "Subscribe Telemetry Event";
    }
  }

  grouping live_ncs_LSPV-DPM-SUMMARY {
    description
      "LSPV DPM summary";
    leaf v4rib-reg {
      type boolean;
      description
        "Registration to IPv4 RIB";
      xr:event-telemetry "Subscribe Telemetry Event";
    }
    leaf v4rib-con {
      type boolean;
      description
        "Connection to IPv4 RIB";
      xr:event-telemetry "Subscribe Telemetry Event";
    }
    leaf sysdb-reg {
      type boolean;
      description
        "Registration to SYSDB";
      xr:event-telemetry "Subscribe Telemetry Event";
    }
    leaf sysdb-con {
      type boolean;
      description
        "Connection to SYSDB";
      xr:event-telemetry "Subscribe Telemetry Event";
    }
    leaf im-reg {
      type boolean;
      description
        "Registration to IM";
      xr:event-telemetry "Subscribe Telemetry Event";
    }
    leaf im-con {
      type boolean;
      description
        "Connection to IM";
      xr:event-telemetry "Subscribe Telemetry Event";
    }
    leaf lspv-con {
      type boolean;
      description
        "Connection to LSPV";
      xr:event-telemetry "Subscribe Telemetry Event";
    }
    leaf num-of-adj {
      type uint32;
      description
        "Number of Adjacencies in DB";
      xr:event-telemetry "Subscribe Telemetry Event";
    }
    leaf validated-adjs {
      type uint32;
      description
        "Number of Validated Adjacencies";
      xr:event-telemetry "Subscribe Telemetry Event";
    }
    leaf dpm-eligible-intfs {
      type uint32;
      description
        "Number of DPM allowed interfaces";
    }
    leaf error-adjs {
      type uint32;
      description
        "Errored Adjacencies";
      xr:event-telemetry "Subscribe Telemetry Event";
    }
    leaf num-of-pfx {
      type uint32;
      description
        "Number of Prefixes in DB";
      xr:event-telemetry "Subscribe Telemetry Event";
    }
    leaf validated-pfxs {
      type uint32;
      description
        "Number of Validated Prefixes";
      xr:event-telemetry "Subscribe Telemetry Event";
    }
    leaf error-pfxs {
      type uint32;
      description
        "Errored Prefixes";
      xr:event-telemetry "Subscribe Telemetry Event";
    }
    leaf total-requests {
      type uint32;
      description
        "Total Requests";
      xr:event-telemetry "Subscribe Telemetry Event";
    }
    leaf total-responses {
      type uint32;
      description
        "Total Responses";
      xr:event-telemetry "Subscribe Telemetry Event";
    }
    leaf total-prop-req {
      type uint32;
      description
        "Total Property Requests";
    }
    leaf total-prop-errs {
      type uint32;
      description
        "Total Property Errors";
    }
    leaf total-prop-resp {
      type uint32;
      description
        "Total Property Responses";
    }
    leaf dpm-interval {
      type uint32;
      description
        "DPM Run Interval";
      xr:event-telemetry "Subscribe Telemetry Event";
    }
    leaf dpm-packets-per-second {
      type uint32;
      units "packet/s";
      description
        "DPM Packets Per Second";
      xr:event-telemetry "Subscribe Telemetry Event";
    }
    leaf total-retries {
      type uint32;
      description
        "Total Retries";
    }
    leaf validation-complete {
      type boolean;
      description
        "DPM Validation Complete";
      xr:event-telemetry "Subscribe Telemetry Event";
    }
    leaf last-dpm-run-time {
      type uint64;
      description
        "Last DPM interation time in nanosec";
      xr:event-telemetry "Subscribe Telemetry Event";
    }
    leaf last-dpm-fault-time {
      type uint64;
      description
        "Last DPM fault time in nanosec";
      xr:event-telemetry "Subscribe Telemetry Event";
    }
    leaf last-dpm-fault-time-ever {
      type uint64;
      description
        "Last Ever DPM fault time in nanosec";
      xr:event-telemetry "Subscribe Telemetry Event";
    }
  }

  grouping live_ncs_LSPV-DPM-FAULT {
    description
      "LSPV DPM Pfx NH fault";
    container prefix-xr {
      description
        "Prefix";
      uses live_ncs_LSPV-DPM-PREFIX-INFO;
    }
    container downlink-fault {
      description
        "Downlink associated with the fault";
      xr:event-telemetry "Subscribe Telemetry Event";
      uses live_ncs_LSPV-DPM-PREFIX-BAG;
    }
    container uplink-fault {
      description
        "Uplink associated with the fault";
      xr:event-telemetry "Subscribe Telemetry Event";
      uses live_ncs_LSPV-DPM-PREFIX-BAG;
    }
    leaf prefix-sid {
      type uint32;
      description
        "Prefix SID";
    }
    leaf error-code {
      type live_ncs_Lspv-dpm-fault-code;
      description
        "DPM Error code";
      xr:event-telemetry "Subscribe Telemetry Event";
    }
  }

  grouping live_ncs_LSPV-DPM-COUNTERS {
    description
      "LSPV DPM Counters";
    leaf requests-sent {
      type uint32;
      description
        "Requests Last Sent";
    }
    leaf requests-last-pending {
      type uint32;
      description
        "Requests Last Pending";
    }
    leaf requests-last-returned {
      type uint32;
      description
        "Requests Last Returned";
    }
    leaf requests-unsent {
      type uint32;
      description
        "Requests Unsent";
    }
    leaf requests-retry-unsent {
      type uint32;
      description
        "Requests Retry Unsent";
    }
    leaf requests-pending {
      type uint32;
      description
        "Requests Pending";
    }
  }

  grouping live_ncs_LSPV-DPM-PFX-ADJ {
    description
      "LSPV DPM Prefix Adj";
    container next-hop {
      description
        "NextHop";
      uses live_ncs_LSPV-DPM-PREFIX-BAG;
    }
    leaf requests-sent {
      type uint32;
      description
        "Requests Sent";
    }
    leaf errors {
      type uint32;
      description
        "Errors";
    }
    leaf last-fault-time {
      type uint64;
      description
        "Last Fault Time";
    }
    leaf status {
      type live_ncs_Lspv-dpm-pfx-validation-status;
      description
        "Status";
    }
    leaf stale {
      type boolean;
      description
        "Stale";
    }
  }

  grouping live_ncs_LSPV-DPM-PREFIX-BAG {
    description
      "LSPV DPM PREFIX BAG";
    leaf af-name {
      type live_ncs_Lspv-dpm-addr;
      description
        "AFName";
    }
    leaf ipv4-prefix {
      // NCS drop when statement
      type inet:ipv4-address;
      description
        "IPv4 prefix";
    }
    leaf ipv6-prefix {
      // NCS drop when statement
      type live_ncs_Static-ipv6-address;
      description
        "IPv6 prefix";
    }
  }

  grouping live_ncs_LSPV-DPM-PREFIX-INFO {
    description
      "Prefix Information";
    container prefix {
      description
        "Prefix";
      uses live_ncs_LSPV-DPM-PREFIX-BAG;
    }
    leaf prefix-length {
      type uint8;
      description
        "Prefix length";
    }
  }

  grouping live_ncs_LSPV-DPM-PFX {
    description
      "LSPV DPM Prefix";
    container prefix-xr {
      description
        "Prefix";
      xr:event-telemetry "Subscribe Telemetry Event";
      uses live_ncs_LSPV-DPM-PREFIX-INFO;
    }
    leaf pfx-sid {
      type uint32;
      description
        "Prefix SID";
      xr:event-telemetry "Subscribe Telemetry Event";
    }
    leaf requests-sent {
      type uint32;
      description
        "Requests Sent";
    }
    leaf requests-rcvd {
      type uint32;
      description
        "Requests Rcvd";
    }
    leaf errors {
      type uint32;
      description
        "Errors";
    }
    leaf last-fault-time {
      type uint64;
      description
        "Last Fault Time";
    }
    leaf status {
      type live_ncs_Lspv-dpm-pfx-validation-status;
      description
        "Status";
    }
    list upstream-adj {
      description
        "Upstream Adjacency";
      uses live_ncs_LSPV-DPM-PREFIX-BAG;
    }
    list downstream-adj-info {
      description
        "Downstream Adjacency Info";
      uses live_ncs_LSPV-DPM-PFX-ADJ;
    }
  }

  grouping live_ncs_LSPV-DPM-ADJ-DB-SUMMARY {
    description
      "LSPV DPM Adjacency DB summary";
    leaf adj-db-size {
      type uint32;
      description
        "Size of Adjacency DB";
    }
    leaf dpm-eligible-intfs {
      type uint32;
      description
        "Number of DPM allowed interfaces";
    }
    leaf err-intfs {
      type uint32;
      description
        "Number of Interfaces with Errors";
    }
    leaf validation-start-time {
      type uint64;
      description
        "Validation Start Time";
    }
    leaf validation-end-time {
      type uint64;
      description
        "Validation End Time";
    }
  }

  grouping LSPV-DPM-PFX-DB-SUMMARY {
    description
      "LSPV DPM Prefix DB summary";
    leaf pfx-db-size {
      type uint32;
      description
        "Size of Prefix DB";
    }
    leaf validated-prefixes {
      type uint32;
      description
        "Number of Validated Prefixes";
    }
    leaf requests-sent {
      type uint32;
      description
        "Number of Echo Requests Sent";
    }
    leaf requests-rcvd {
      type uint32;
      description
        "Number of Echo Requests Received";
    }
    leaf validation-errors {
      type uint32;
      description
        "Validation Errors";
    }
    leaf validation-start-time {
      type uint64;
      description
        "DPM Start Time";
    }
    leaf validation-end-time {
      type uint64;
      description
        "DPM End Time";
    }
  }

  grouping LSPV-DPM-ADJ-INFO {
    description
      "Adjacency Information";
    leaf local-label {
      type uint32;
      description
        "Label";
    }
    leaf flags {
      type uint32;
      description
        "Flags";
    }
    leaf protected {
      type boolean;
      description
        "Protected";
    }
    leaf static-adj {
      type boolean;
      description
        "Static Adj";
    }
    leaf group {
      type boolean;
      description
        "Group";
    }
    leaf isis-l1 {
      type boolean;
      description
        "ISIS Level 1";
    }
    leaf isis-l2 {
      type boolean;
      description
        "ISIS Level 2";
    }
    leaf success {
      type boolean;
      description
        "Sucess";
    }
  }

  grouping LSPV-DPM-ADJ {
    description
      "LSPV DPM Adjacency";
    container local-address {
      description
        "Local Address";
      uses LSPV-DPM-PREFIX-BAG;
    }
    container remote-address {
      description
        "Remote Address";
      uses LSPV-DPM-PREFIX-BAG;
    }
    leaf interface-name-xr {
      type string;
      description
        "Interface name";
    }
    leaf local-interface-id {
      type uint32;
      description
        "Local Interface Id";
    }
    leaf unprotected-local-label {
      type uint32;
      description
        "Unprotected Local Label";
    }
    leaf remote-interface-id {
      type uint32;
      description
        "Remote Interface Id";
    }
    leaf unprotected-remote-label {
      type uint32;
      description
        "Unprotected Remote Label";
    }
    leaf valid-adj {
      type uint32;
      description
        "Valid Adjacencies";
    }
    leaf total-adj {
      type uint32;
      description
        "Total Adjacencies";
    }
    leaf is-isis {
      type boolean;
      description
        "ISIS enabled";
    }
    leaf is-ipv4 {
      type boolean;
      description
        "IPv4 enabled";
    }
    leaf is-excluded {
      type boolean;
      description
        "Skipped for the current run";
    }
    leaf last-fault-time {
      type uint64;
      description
        "Last Fault Time";
    }
    list local-adj {
      description
        "Local Adjacencies";
      uses LSPV-DPM-ADJ-INFO;
    }
    list remote-adj {
      description
        "Remote Adjacencies";
      uses LSPV-DPM-ADJ-INFO;
    }
  }

  grouping LSPV-DPM-ADJ-FAULT {
    description
      "LSPV DPM ADJ fault";
    container ip {
      description
        "IP Address";
      xr:event-telemetry "Subscribe Telemetry Event";
      uses LSPV-DPM-PREFIX-BAG;
    }
    leaf interface-name-xr {
      type string;
      description
        "Interface name";
    }
    leaf igp {
      type Lspv-dpm-igp;
      description
        "IGP";
      xr:event-telemetry "Subscribe Telemetry Event";
    }
    leaf local-adj-sid {
      type uint32;
      description
        "Local Adj SID";
      xr:event-telemetry "Subscribe Telemetry Event";
    }
    leaf error-code {
      type Lspv-dpm-fault-code;
      description
        "DPM Error code";
      xr:event-telemetry "Subscribe Telemetry Event";
    }
  }

  grouping LSPV-DPM-SUMMARY {
    description
      "LSPV DPM summary";
    leaf v4rib-reg {
      type boolean;
      description
        "Registration to IPv4 RIB";
      xr:event-telemetry "Subscribe Telemetry Event";
    }
    leaf v4rib-con {
      type boolean;
      description
        "Connection to IPv4 RIB";
      xr:event-telemetry "Subscribe Telemetry Event";
    }
    leaf sysdb-reg {
      type boolean;
      description
        "Registration to SYSDB";
      xr:event-telemetry "Subscribe Telemetry Event";
    }
    leaf sysdb-con {
      type boolean;
      description
        "Connection to SYSDB";
      xr:event-telemetry "Subscribe Telemetry Event";
    }
    leaf im-reg {
      type boolean;
      description
        "Registration to IM";
      xr:event-telemetry "Subscribe Telemetry Event";
    }
    leaf im-con {
      type boolean;
      description
        "Connection to IM";
      xr:event-telemetry "Subscribe Telemetry Event";
    }
    leaf lspv-con {
      type boolean;
      description
        "Connection to LSPV";
      xr:event-telemetry "Subscribe Telemetry Event";
    }
    leaf num-of-adj {
      type uint32;
      description
        "Number of Adjacencies in DB";
      xr:event-telemetry "Subscribe Telemetry Event";
    }
    leaf validated-adjs {
      type uint32;
      description
        "Number of Validated Adjacencies";
      xr:event-telemetry "Subscribe Telemetry Event";
    }
    leaf dpm-eligible-intfs {
      type uint32;
      description
        "Number of DPM allowed interfaces";
    }
    leaf error-adjs {
      type uint32;
      description
        "Errored Adjacencies";
      xr:event-telemetry "Subscribe Telemetry Event";
    }
    leaf num-of-pfx {
      type uint32;
      description
        "Number of Prefixes in DB";
      xr:event-telemetry "Subscribe Telemetry Event";
    }
    leaf validated-pfxs {
      type uint32;
      description
        "Number of Validated Prefixes";
      xr:event-telemetry "Subscribe Telemetry Event";
    }
    leaf error-pfxs {
      type uint32;
      description
        "Errored Prefixes";
      xr:event-telemetry "Subscribe Telemetry Event";
    }
    leaf total-requests {
      type uint32;
      description
        "Total Requests";
      xr:event-telemetry "Subscribe Telemetry Event";
    }
    leaf total-responses {
      type uint32;
      description
        "Total Responses";
      xr:event-telemetry "Subscribe Telemetry Event";
    }
    leaf total-prop-req {
      type uint32;
      description
        "Total Property Requests";
    }
    leaf total-prop-errs {
      type uint32;
      description
        "Total Property Errors";
    }
    leaf total-prop-resp {
      type uint32;
      description
        "Total Property Responses";
    }
    leaf dpm-interval {
      type uint32;
      description
        "DPM Run Interval";
      xr:event-telemetry "Subscribe Telemetry Event";
    }
    leaf dpm-packets-per-second {
      type uint32;
      units "packet/s";
      description
        "DPM Packets Per Second";
      xr:event-telemetry "Subscribe Telemetry Event";
    }
    leaf total-retries {
      type uint32;
      description
        "Total Retries";
    }
    leaf validation-complete {
      type boolean;
      description
        "DPM Validation Complete";
      xr:event-telemetry "Subscribe Telemetry Event";
    }
    leaf last-dpm-run-time {
      type uint64;
      description
        "Last DPM interation time in nanosec";
      xr:event-telemetry "Subscribe Telemetry Event";
    }
    leaf last-dpm-fault-time {
      type uint64;
      description
        "Last DPM fault time in nanosec";
      xr:event-telemetry "Subscribe Telemetry Event";
    }
    leaf last-dpm-fault-time-ever {
      type uint64;
      description
        "Last Ever DPM fault time in nanosec";
      xr:event-telemetry "Subscribe Telemetry Event";
    }
  }

  grouping LSPV-DPM-FAULT {
    description
      "LSPV DPM Pfx NH fault";
    container prefix-xr {
      description
        "Prefix";
      uses LSPV-DPM-PREFIX-INFO;
    }
    container downlink-fault {
      description
        "Downlink associated with the fault";
      xr:event-telemetry "Subscribe Telemetry Event";
      uses LSPV-DPM-PREFIX-BAG;
    }
    container uplink-fault {
      description
        "Uplink associated with the fault";
      xr:event-telemetry "Subscribe Telemetry Event";
      uses LSPV-DPM-PREFIX-BAG;
    }
    leaf prefix-sid {
      type uint32;
      description
        "Prefix SID";
    }
    leaf error-code {
      type Lspv-dpm-fault-code;
      description
        "DPM Error code";
      xr:event-telemetry "Subscribe Telemetry Event";
    }
  }

  grouping LSPV-DPM-COUNTERS {
    description
      "LSPV DPM Counters";
    leaf requests-sent {
      type uint32;
      description
        "Requests Last Sent";
    }
    leaf requests-last-pending {
      type uint32;
      description
        "Requests Last Pending";
    }
    leaf requests-last-returned {
      type uint32;
      description
        "Requests Last Returned";
    }
    leaf requests-unsent {
      type uint32;
      description
        "Requests Unsent";
    }
    leaf requests-retry-unsent {
      type uint32;
      description
        "Requests Retry Unsent";
    }
    leaf requests-pending {
      type uint32;
      description
        "Requests Pending";
    }
  }

  grouping LSPV-DPM-PFX-ADJ {
    description
      "LSPV DPM Prefix Adj";
    container next-hop {
      description
        "NextHop";
      uses LSPV-DPM-PREFIX-BAG;
    }
    leaf requests-sent {
      type uint32;
      description
        "Requests Sent";
    }
    leaf errors {
      type uint32;
      description
        "Errors";
    }
    leaf last-fault-time {
      type uint64;
      description
        "Last Fault Time";
    }
    leaf status {
      type Lspv-dpm-pfx-validation-status;
      description
        "Status";
    }
    leaf stale {
      type boolean;
      description
        "Stale";
    }
  }

  grouping LSPV-DPM-PREFIX-BAG {
    description
      "LSPV DPM PREFIX BAG";
    leaf af-name {
      type Lspv-dpm-addr;
      description
        "AFName";
    }
    leaf ipv4-prefix {
      when "../af-name = 'ipv4'" {
        tailf:xpath-root 3;
        description
          "../AFName = 'IPv4'";
      }
      type inet:ipv4-address;
      description
        "IPv4 prefix";
    }
    leaf ipv6-prefix {
      when "../af-name = 'ipv6'" {
        tailf:xpath-root 3;
        description
          "../AFName = 'IPv6'";
      }
      type Static-ipv6-address;
      description
        "IPv6 prefix";
    }
  }

  grouping LSPV-DPM-PREFIX-INFO {
    description
      "Prefix Information";
    container prefix {
      description
        "Prefix";
      uses LSPV-DPM-PREFIX-BAG;
    }
    leaf prefix-length {
      type uint8;
      description
        "Prefix length";
    }
  }

  grouping LSPV-DPM-PFX {
    description
      "LSPV DPM Prefix";
    container prefix-xr {
      description
        "Prefix";
      xr:event-telemetry "Subscribe Telemetry Event";
      uses LSPV-DPM-PREFIX-INFO;
    }
    leaf pfx-sid {
      type uint32;
      description
        "Prefix SID";
      xr:event-telemetry "Subscribe Telemetry Event";
    }
    leaf requests-sent {
      type uint32;
      description
        "Requests Sent";
    }
    leaf requests-rcvd {
      type uint32;
      description
        "Requests Rcvd";
    }
    leaf errors {
      type uint32;
      description
        "Errors";
    }
    leaf last-fault-time {
      type uint64;
      description
        "Last Fault Time";
    }
    leaf status {
      type Lspv-dpm-pfx-validation-status;
      description
        "Status";
    }
    list upstream-adj {
      description
        "Upstream Adjacency";
      uses LSPV-DPM-PREFIX-BAG;
    }
    list downstream-adj-info {
      description
        "Downstream Adjacency Info";
      uses LSPV-DPM-PFX-ADJ;
    }
  }

  grouping LSPV-DPM-ADJ-DB-SUMMARY {
    description
      "LSPV DPM Adjacency DB summary";
    leaf adj-db-size {
      type uint32;
      description
        "Size of Adjacency DB";
    }
    leaf dpm-eligible-intfs {
      type uint32;
      description
        "Number of DPM allowed interfaces";
    }
    leaf err-intfs {
      type uint32;
      description
        "Number of Interfaces with Errors";
    }
    leaf validation-start-time {
      type uint64;
      description
        "Validation Start Time";
    }
    leaf validation-end-time {
      type uint64;
      description
        "Validation End Time";
    }
  }
}

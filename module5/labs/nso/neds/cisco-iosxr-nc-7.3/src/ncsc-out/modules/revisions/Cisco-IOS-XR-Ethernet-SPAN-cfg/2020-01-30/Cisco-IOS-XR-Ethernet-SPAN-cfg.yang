module Cisco-IOS-XR-Ethernet-SPAN-cfg {
  // Generated by yanger -t ncs
  tailf:mount-id "cisco-iosxr-nc-7.3:cisco-iosxr-nc-7.3";
  tailf:ncs-device-type "netconf";

  namespace "http://cisco.com/ns/yang/Cisco-IOS-XR-Ethernet-SPAN-cfg";
  prefix ethernet-span-cfg;

  import ietf-inet-types {
    prefix inet;
  }
  import Cisco-IOS-XR-types {
    prefix xr;
  }
  import cisco-semver {
    prefix semver;
  }
  import Cisco-IOS-XR-Ethernet-SPAN-datatypes {
    prefix dt1;
  }
  import Cisco-IOS-XR-ifmgr-cfg {
    prefix a1;
  }
  import Cisco-IOS-XR-l2vpn-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN package configuration.

     This module contains definitions
     for the following management objects:
       span-monitor-session: none

     This YANG module augments the
       Cisco-IOS-XR-ifmgr-cfg,
       Cisco-IOS-XR-l2vpn-cfg
     modules with configuration data.

     Copyright (c) 2013-2020 by Cisco Systems, Inc.
     All rights reserved.";

  revision 2020-01-30 {
    description
      "Added support for L3 IPv4 and IPv6 ACLs on a L2 ethernet SPAN session";
    semver:module-version "3.0.0";
  }
  revision 2019-10-31 {
    description
      "Added mandatory nodes.
       2019-05-12
       Added support for file destinations.";
    semver:module-version "2.0.0";
  }
  revision 2019-04-05 {
    description
      "Establish semantic version baseline.";
    semver:module-version "1.0.0";
  }
  revision 2015-11-09 {
    description
      "IOS XR 6.0 revision.";
  }

  typedef ncs_template_Span-traffic-direction {
    type string;
    description
      "Span traffic direction";
  }

  typedef ncs_template_Span-mirror-interval {
    type string;
    description
      "Span mirror interval";
  }

  typedef ncs_template_Span-destination {
    type string;
    description
      "Span destination";
  }

  typedef ncs_template_Span-buffer {
    type string;
    description
      "Span buffer";
  }

  typedef ncs_template_Span-file-format {
    type string;
    description
      "Span file format";
  }

  typedef ncs_template_Span-buffer-size {
    type string;
    description
      "Span buffer size";
  }

  typedef ncs_rpc_notif_Span-traffic-direction {
    type enumeration {
      enum "rx-only" {
        value 1;
        description
          "Replicate only received (ingress) traffic";
      }
      enum "tx-only" {
        value 2;
        description
          "Replicate only transmitted (egress) traffic";
      }
    }
    description
      "Span traffic direction";
  }

  typedef ncs_rpc_notif_Span-mirror-interval {
    type enumeration {
      enum "512" {
        value 1;
        description
          "Mirror 1 in every 512 packets";
      }
      enum "1k" {
        value 2;
        description
          "Mirror 1 in every 1024 packets";
      }
      enum "2k" {
        value 3;
        description
          "Mirror 1 in every 2048 packets";
      }
      enum "4k" {
        value 4;
        description
          "Mirror 1 in every 4096 packets";
      }
      enum "8k" {
        value 5;
        description
          "Mirror 1 in every 8192 packets";
      }
      enum "16k" {
        value 6;
        description
          "Mirror 1 in every 16384 packets";
      }
    }
    description
      "Span mirror interval";
  }

  typedef ncs_rpc_notif_Span-destination {
    type enumeration {
      enum "interface" {
        value 0;
        description
          "Destination Interface";
      }
      enum "pseudowire" {
        value 1;
        description
          "Destination Pseudowire";
      }
      enum "ipv4-address" {
        value 2;
        description
          "Destination next-hop IPv4 address";
      }
      enum "ipv6-address" {
        value 3;
        description
          "Destination next-hop IPv6 address";
      }
      enum "file" {
        value 5;
        description
          "Destination File";
      }
      enum "udp" {
        value 6;
        description
          "Destination IP address over UDP";
      }
    }
    description
      "Span destination";
  }

  typedef ncs_rpc_notif_Span-buffer {
    type enumeration {
      enum "circular" {
        value 1;
        description
          "File buffer circular";
      }
      enum "linear" {
        value 2;
        description
          "File buffer linear";
      }
    }
    description
      "Span buffer";
  }

  typedef ncs_rpc_notif_Span-file-format {
    type enumeration {
      enum "pcapng" {
        value 2;
        description
          "File format pcapng";
      }
    }
    description
      "Span file format";
  }

  typedef ncs_rpc_notif_Span-buffer-size {
    type uint32;
    description
      "Span buffer size";
  }

  typedef live_ncs_Span-traffic-direction {
    type enumeration {
      enum "rx-only" {
        value 1;
        description
          "Replicate only received (ingress) traffic";
      }
      enum "tx-only" {
        value 2;
        description
          "Replicate only transmitted (egress) traffic";
      }
    }
    description
      "Span traffic direction";
  }

  typedef live_ncs_Span-mirror-interval {
    type enumeration {
      enum "512" {
        value 1;
        description
          "Mirror 1 in every 512 packets";
      }
      enum "1k" {
        value 2;
        description
          "Mirror 1 in every 1024 packets";
      }
      enum "2k" {
        value 3;
        description
          "Mirror 1 in every 2048 packets";
      }
      enum "4k" {
        value 4;
        description
          "Mirror 1 in every 4096 packets";
      }
      enum "8k" {
        value 5;
        description
          "Mirror 1 in every 8192 packets";
      }
      enum "16k" {
        value 6;
        description
          "Mirror 1 in every 16384 packets";
      }
    }
    description
      "Span mirror interval";
  }

  typedef live_ncs_Span-destination {
    type enumeration {
      enum "interface" {
        value 0;
        description
          "Destination Interface";
      }
      enum "pseudowire" {
        value 1;
        description
          "Destination Pseudowire";
      }
      enum "ipv4-address" {
        value 2;
        description
          "Destination next-hop IPv4 address";
      }
      enum "ipv6-address" {
        value 3;
        description
          "Destination next-hop IPv6 address";
      }
      enum "file" {
        value 5;
        description
          "Destination File";
      }
      enum "udp" {
        value 6;
        description
          "Destination IP address over UDP";
      }
    }
    description
      "Span destination";
  }

  typedef live_ncs_Span-buffer {
    type enumeration {
      enum "circular" {
        value 1;
        description
          "File buffer circular";
      }
      enum "linear" {
        value 2;
        description
          "File buffer linear";
      }
    }
    description
      "Span buffer";
  }

  typedef live_ncs_Span-file-format {
    type enumeration {
      enum "pcapng" {
        value 2;
        description
          "File format pcapng";
      }
    }
    description
      "Span file format";
  }

  typedef live_ncs_Span-buffer-size {
    type uint32;
    description
      "Span buffer size";
  }

  typedef Span-traffic-direction {
    type enumeration {
      enum "rx-only" {
        value 1;
        description
          "Replicate only received (ingress) traffic";
      }
      enum "tx-only" {
        value 2;
        description
          "Replicate only transmitted (egress) traffic";
      }
    }
    description
      "Span traffic direction";
  }

  typedef Span-mirror-interval {
    type enumeration {
      enum "512" {
        value 1;
        description
          "Mirror 1 in every 512 packets";
      }
      enum "1k" {
        value 2;
        description
          "Mirror 1 in every 1024 packets";
      }
      enum "2k" {
        value 3;
        description
          "Mirror 1 in every 2048 packets";
      }
      enum "4k" {
        value 4;
        description
          "Mirror 1 in every 4096 packets";
      }
      enum "8k" {
        value 5;
        description
          "Mirror 1 in every 8192 packets";
      }
      enum "16k" {
        value 6;
        description
          "Mirror 1 in every 16384 packets";
      }
    }
    description
      "Span mirror interval";
  }

  typedef Span-destination {
    type enumeration {
      enum "interface" {
        value 0;
        description
          "Destination Interface";
      }
      enum "pseudowire" {
        value 1;
        description
          "Destination Pseudowire";
      }
      enum "ipv4-address" {
        value 2;
        description
          "Destination next-hop IPv4 address";
      }
      enum "ipv6-address" {
        value 3;
        description
          "Destination next-hop IPv6 address";
      }
      enum "file" {
        value 5;
        description
          "Destination File";
      }
      enum "udp" {
        value 6;
        description
          "Destination IP address over UDP";
      }
    }
    description
      "Span destination";
  }

  typedef Span-buffer {
    type enumeration {
      enum "circular" {
        value 1;
        description
          "File buffer circular";
      }
      enum "linear" {
        value 2;
        description
          "File buffer linear";
      }
    }
    description
      "Span buffer";
  }

  typedef Span-file-format {
    type enumeration {
      enum "pcapng" {
        value 2;
        description
          "File format pcapng";
      }
    }
    description
      "Span file format";
  }

  typedef Span-buffer-size {
    type uint32;
    description
      "Span buffer size";
  }

  grouping ncs_template_IPV6ACL {
    description
      "Common node of span-monitor-session,
       span-monitor-session";
    container ipv6acl {
      presence "Indicates a ipv6acl node is configured.";
      description
        "Enable IPv6 ACL matching for traffic mirroring";
      leaf acl-enable {
        type empty;
        // NCS drop mandatory statement
        description
          "Enable ACL";
      }
      leaf acl-name {
        type dt1:ncs_template_Span-acl-name;
        description
          "ACL Name";
      }
    }
  }

  grouping ncs_template_MIRROR-INTERVAL {
    description
      "Common node of span-monitor-session,
       span-monitor-session";
    leaf mirror-interval {
      type ncs_template_Span-mirror-interval;
      description
        "Specify the mirror interval";
    }
  }

  grouping ncs_template_DROPS {
    description
      "Common node of span-monitor-session,
       span-monitor-session";
    leaf drops {
      type string;
      description
        "Specify whether or not to mirror dropped packets";
    }
  }

  grouping ncs_template_MIRROR-FIRST {
    description
      "Common node of span-monitor-session,
       span-monitor-session";
    leaf mirror-first {
      type string;
      units "byte";
      description
        "Mirror a specified number of bytes from start of
         packet";
    }
  }

  grouping ncs_template_SPAN-MONITOR-SESSION-TABLE {
    description
      "Common node of ip-subscriber, ppp,
       subscriber-service";
    container span-monitor-sessions {
      description
        "Monitor Session container for this template";
      list span-monitor-session {
        // NCS patched for predictable order
        ordered-by user;
        key "session-class";
        description
          "Configuration for a particular class of Monitor
           Session";
        leaf session-class {
          type dt1:ncs_template_Span-session-class;
          description
            "Session Class";
        }
        uses ncs_template_MIRROR-FIRST;
        uses ncs_template_ATTACHMENT;
        uses ncs_template_MIRROR-INTERVAL;
        uses ncs_template_ACL;
        uses ncs_template_DROPS;
        uses ncs_template_IPV4ACL;
        uses ncs_template_IPV6ACL;
      }
    }
  }

  grouping ncs_template_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        // NCS patched for predictable order
        ordered-by user;
        key "session-class";
        description
          "Configuration for a particular class of Monitor
           Session";
        leaf session-class {
          type dt1:ncs_template_Span-session-class;
          description
            "Session Class";
        }
        uses ncs_template_MIRROR-FIRST;
        uses ncs_template_ATTACHMENT;
        uses ncs_template_MIRROR-INTERVAL;
        uses ncs_template_ACL;
        uses ncs_template_DROPS;
        uses ncs_template_IPV4ACL;
        uses ncs_template_IPV6ACL;
      }
    }
  }

  grouping ncs_template_ACL {
    description
      "Common node of span-monitor-session,
       span-monitor-session";
    container acl {
      presence "Indicates a acl node is configured.";
      description
        "Enable ACL matching for traffic mirroring";
      leaf acl-enable {
        type empty;
        // NCS drop mandatory statement
        description
          "Enable ACL";
      }
      leaf acl-name {
        type dt1:ncs_template_Span-acl-name;
        description
          "ACL Name";
      }
    }
  }

  grouping ncs_template_IPV4ACL {
    description
      "Common node of span-monitor-session,
       span-monitor-session";
    container ipv4acl {
      presence "Indicates a ipv4acl node is configured.";
      description
        "Enable IPv4 ACL matching for traffic mirroring";
      leaf acl-enable {
        type empty;
        // NCS drop mandatory statement
        description
          "Enable ACL";
      }
      leaf acl-name {
        type dt1:ncs_template_Span-acl-name;
        description
          "ACL Name";
      }
    }
  }

  grouping ncs_template_ATTACHMENT {
    description
      "Common node of span-monitor-session,
       span-monitor-session";
    container attachment {
      presence "Indicates a attachment node is configured.";
      description
        "Attach the interface to a Monitor Session";
      leaf session-name {
        type dt1:ncs_template_Span-session-name;
        // NCS drop mandatory statement
        description
          "Session Name";
      }
      leaf direction {
        type ncs_template_Span-traffic-direction;
        description
          "Specify the direction of traffic to replicate
           (optional)";
      }
      leaf port-level-enable {
        type empty;
        description
          "Enable port level traffic mirroring";
      }
    }
  }

  grouping ncs_rpc_notif_IPV6ACL {
    description
      "Common node of span-monitor-session,
       span-monitor-session";
    container ipv6acl {
      presence "Indicates a ipv6acl node is configured.";
      description
        "Enable IPv6 ACL matching for traffic mirroring";
      leaf acl-enable {
        type empty;
        mandatory true;
        description
          "Enable ACL";
      }
      leaf acl-name {
        type dt1:ncs_rpc_notif_Span-acl-name;
        description
          "ACL Name";
      }
    }
  }

  grouping ncs_rpc_notif_MIRROR-INTERVAL {
    description
      "Common node of span-monitor-session,
       span-monitor-session";
    leaf mirror-interval {
      type ncs_rpc_notif_Span-mirror-interval;
      description
        "Specify the mirror interval";
    }
  }

  grouping ncs_rpc_notif_DROPS {
    description
      "Common node of span-monitor-session,
       span-monitor-session";
    leaf drops {
      type boolean;
      description
        "Specify whether or not to mirror dropped packets";
    }
  }

  grouping ncs_rpc_notif_MIRROR-FIRST {
    description
      "Common node of span-monitor-session,
       span-monitor-session";
    leaf mirror-first {
      type uint32 {
        range "1..10000";
      }
      units "byte";
      description
        "Mirror a specified number of bytes from start of
         packet";
    }
  }

  grouping ncs_rpc_notif_SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:ncs_rpc_notif_Span-session-class;
          description
            "Session Class";
        }
        uses ncs_rpc_notif_MIRROR-FIRST;
        uses ncs_rpc_notif_ATTACHMENT;
        uses ncs_rpc_notif_MIRROR-INTERVAL;
        uses ncs_rpc_notif_ACL;
        uses ncs_rpc_notif_DROPS;
        uses ncs_rpc_notif_IPV4ACL;
        uses ncs_rpc_notif_IPV6ACL;
      }
    }
  }

  grouping ncs_rpc_notif_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:ncs_rpc_notif_Span-session-class;
          description
            "Session Class";
        }
        uses ncs_rpc_notif_MIRROR-FIRST;
        uses ncs_rpc_notif_ATTACHMENT;
        uses ncs_rpc_notif_MIRROR-INTERVAL;
        uses ncs_rpc_notif_ACL;
        uses ncs_rpc_notif_DROPS;
        uses ncs_rpc_notif_IPV4ACL;
        uses ncs_rpc_notif_IPV6ACL;
      }
    }
  }

  grouping ncs_rpc_notif_ACL {
    description
      "Common node of span-monitor-session,
       span-monitor-session";
    container acl {
      presence "Indicates a acl node is configured.";
      description
        "Enable ACL matching for traffic mirroring";
      leaf acl-enable {
        type empty;
        mandatory true;
        description
          "Enable ACL";
      }
      leaf acl-name {
        type dt1:ncs_rpc_notif_Span-acl-name;
        description
          "ACL Name";
      }
    }
  }

  grouping ncs_rpc_notif_IPV4ACL {
    description
      "Common node of span-monitor-session,
       span-monitor-session";
    container ipv4acl {
      presence "Indicates a ipv4acl node is configured.";
      description
        "Enable IPv4 ACL matching for traffic mirroring";
      leaf acl-enable {
        type empty;
        mandatory true;
        description
          "Enable ACL";
      }
      leaf acl-name {
        type dt1:ncs_rpc_notif_Span-acl-name;
        description
          "ACL Name";
      }
    }
  }

  grouping ncs_rpc_notif_ATTACHMENT {
    description
      "Common node of span-monitor-session,
       span-monitor-session";
    container attachment {
      presence "Indicates a attachment node is configured.";
      description
        "Attach the interface to a Monitor Session";
      leaf session-name {
        type dt1:ncs_rpc_notif_Span-session-name;
        mandatory true;
        description
          "Session Name";
      }
      leaf direction {
        type ncs_rpc_notif_Span-traffic-direction;
        description
          "Specify the direction of traffic to replicate
           (optional)";
      }
      leaf port-level-enable {
        type empty;
        description
          "Enable port level traffic mirroring";
      }
    }
  }

  grouping live_ncs_IPV6ACL {
    description
      "Common node of span-monitor-session,
       span-monitor-session";
    container ipv6acl {
      presence "Indicates a ipv6acl node is configured.";
      description
        "Enable IPv6 ACL matching for traffic mirroring";
      leaf acl-enable {
        type empty;
        // NCS drop mandatory statement
        description
          "Enable ACL";
      }
      leaf acl-name {
        type dt1:live_ncs_Span-acl-name;
        description
          "ACL Name";
      }
    }
  }

  grouping live_ncs_MIRROR-INTERVAL {
    description
      "Common node of span-monitor-session,
       span-monitor-session";
    leaf mirror-interval {
      type live_ncs_Span-mirror-interval;
      description
        "Specify the mirror interval";
    }
  }

  grouping live_ncs_DROPS {
    description
      "Common node of span-monitor-session,
       span-monitor-session";
    leaf drops {
      type boolean;
      description
        "Specify whether or not to mirror dropped packets";
    }
  }

  grouping live_ncs_MIRROR-FIRST {
    description
      "Common node of span-monitor-session,
       span-monitor-session";
    leaf mirror-first {
      type uint32 {
        range "1..10000";
      }
      units "byte";
      description
        "Mirror a specified number of bytes from start of
         packet";
    }
  }

  grouping live_ncs_SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:live_ncs_Span-session-class;
          description
            "Session Class";
        }
        uses live_ncs_MIRROR-FIRST;
        uses live_ncs_ATTACHMENT;
        uses live_ncs_MIRROR-INTERVAL;
        uses live_ncs_ACL;
        uses live_ncs_DROPS;
        uses live_ncs_IPV4ACL;
        uses live_ncs_IPV6ACL;
      }
    }
  }

  grouping live_ncs_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:live_ncs_Span-session-class;
          description
            "Session Class";
        }
        uses live_ncs_MIRROR-FIRST;
        uses live_ncs_ATTACHMENT;
        uses live_ncs_MIRROR-INTERVAL;
        uses live_ncs_ACL;
        uses live_ncs_DROPS;
        uses live_ncs_IPV4ACL;
        uses live_ncs_IPV6ACL;
      }
    }
  }

  grouping live_ncs_ACL {
    description
      "Common node of span-monitor-session,
       span-monitor-session";
    container acl {
      presence "Indicates a acl node is configured.";
      description
        "Enable ACL matching for traffic mirroring";
      leaf acl-enable {
        type empty;
        // NCS drop mandatory statement
        description
          "Enable ACL";
      }
      leaf acl-name {
        type dt1:live_ncs_Span-acl-name;
        description
          "ACL Name";
      }
    }
  }

  grouping live_ncs_IPV4ACL {
    description
      "Common node of span-monitor-session,
       span-monitor-session";
    container ipv4acl {
      presence "Indicates a ipv4acl node is configured.";
      description
        "Enable IPv4 ACL matching for traffic mirroring";
      leaf acl-enable {
        type empty;
        // NCS drop mandatory statement
        description
          "Enable ACL";
      }
      leaf acl-name {
        type dt1:live_ncs_Span-acl-name;
        description
          "ACL Name";
      }
    }
  }

  grouping live_ncs_ATTACHMENT {
    description
      "Common node of span-monitor-session,
       span-monitor-session";
    container attachment {
      presence "Indicates a attachment node is configured.";
      description
        "Attach the interface to a Monitor Session";
      leaf session-name {
        type dt1:live_ncs_Span-session-name;
        // NCS drop mandatory statement
        description
          "Session Name";
      }
      leaf direction {
        type live_ncs_Span-traffic-direction;
        description
          "Specify the direction of traffic to replicate
           (optional)";
      }
      leaf port-level-enable {
        type empty;
        description
          "Enable port level traffic mirroring";
      }
    }
  }

  grouping IPV6ACL {
    description
      "Common node of span-monitor-session,
       span-monitor-session";
    container ipv6acl {
      presence "Indicates a ipv6acl node is configured.";
      description
        "Enable IPv6 ACL matching for traffic mirroring";
      leaf acl-enable {
        type empty;
        mandatory true;
        description
          "Enable ACL";
      }
      leaf acl-name {
        type dt1:Span-acl-name;
        description
          "ACL Name";
      }
    }
  }

  grouping MIRROR-INTERVAL {
    description
      "Common node of span-monitor-session,
       span-monitor-session";
    leaf mirror-interval {
      type Span-mirror-interval;
      description
        "Specify the mirror interval";
    }
  }

  grouping DROPS {
    description
      "Common node of span-monitor-session,
       span-monitor-session";
    leaf drops {
      type boolean;
      description
        "Specify whether or not to mirror dropped packets";
    }
  }

  grouping MIRROR-FIRST {
    description
      "Common node of span-monitor-session,
       span-monitor-session";
    leaf mirror-first {
      type uint32 {
        range "1..10000";
      }
      units "byte";
      description
        "Mirror a specified number of bytes from start of
         packet";
    }
  }

  grouping SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:Span-session-class;
          description
            "Session Class";
        }
        uses MIRROR-FIRST;
        uses ATTACHMENT;
        uses MIRROR-INTERVAL;
        uses ACL;
        uses DROPS;
        uses IPV4ACL;
        uses IPV6ACL;
      }
    }
  }

  grouping ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:Span-session-class;
          description
            "Session Class";
        }
        uses MIRROR-FIRST;
        uses ATTACHMENT;
        uses MIRROR-INTERVAL;
        uses ACL;
        uses DROPS;
        uses IPV4ACL;
        uses IPV6ACL;
      }
    }
  }

  grouping ACL {
    description
      "Common node of span-monitor-session,
       span-monitor-session";
    container acl {
      presence "Indicates a acl node is configured.";
      description
        "Enable ACL matching for traffic mirroring";
      leaf acl-enable {
        type empty;
        mandatory true;
        description
          "Enable ACL";
      }
      leaf acl-name {
        type dt1:Span-acl-name;
        description
          "ACL Name";
      }
    }
  }

  grouping IPV4ACL {
    description
      "Common node of span-monitor-session,
       span-monitor-session";
    container ipv4acl {
      presence "Indicates a ipv4acl node is configured.";
      description
        "Enable IPv4 ACL matching for traffic mirroring";
      leaf acl-enable {
        type empty;
        mandatory true;
        description
          "Enable ACL";
      }
      leaf acl-name {
        type dt1:Span-acl-name;
        description
          "ACL Name";
      }
    }
  }

  grouping ATTACHMENT {
    description
      "Common node of span-monitor-session,
       span-monitor-session";
    container attachment {
      presence "Indicates a attachment node is configured.";
      description
        "Attach the interface to a Monitor Session";
      leaf session-name {
        type dt1:Span-session-name;
        mandatory true;
        description
          "Session Name";
      }
      leaf direction {
        type Span-traffic-direction;
        description
          "Specify the direction of traffic to replicate
           (optional)";
      }
      leaf port-level-enable {
        type empty;
        description
          "Enable port level traffic mirroring";
      }
    }
  }

  augment "/ncs:devices/ncs:device/ncs:config" {
    container span-monitor-session {
      tailf:ncs-device-type "netconf";
      tailf:display-when "not(../../ncs:module) or ../../ncs:module[ncs:name='Cisco-IOS-XR-Ethernet-SPAN-cfg']";
      description
        "none";
      container sessions {
        description
          "Monitor-session configuration commands";
        list session {
          key "session";
          description
            "Configuration for a particular Monitor Session";
          container cloud-span {
            description
              "CloudSPAN configuration options for this
               session";
            leaf cloud-span-enable {
              type empty;
              description
                "Enable CloudSPAN on this session";
            }
          }
          container destination {
            description
              "Specify a destination";
            leaf destination-type {
              type Span-destination;
              description
                "Specify the type of destination";
            }
            leaf destination-interface-name {
              when "../destination-type = 'interface' or ../destination-type = 'udp'" {
                tailf:xpath-root 3;
                description
                  "../DestinationType = Interface or .
                   ./DestinationType = UDP";
              }
              type xr:Interface-name;
              description
                "Specify the destination interface name";
            }
            leaf destination-ipv4-address {
              when "../destination-type = 'ipv4-address' or ../destination-type = 'udp'" {
                tailf:xpath-root 3;
                description
                  "../DestinationType = IPv4Address or .
                   ./DestinationType = UDP";
              }
              type inet:ipv4-address-no-zone;
              description
                "Specify the destination IPv4 address";
            }
            leaf destination-ipv6-address {
              when "../destination-type = 'ipv6-address' or ../destination-type = 'udp'" {
                tailf:xpath-root 3;
                description
                  "../DestinationType = IPv6Address or .
                   ./DestinationType = UDP";
              }
              type inet:ipv6-address-no-zone;
              description
                "Specify the destination IPv6 address";
            }
            leaf destination-buffer-size {
              when "../destination-type = 'file'" {
                tailf:xpath-root 3;
                description
                  "../DestinationType = File";
              }
              type Span-buffer-size;
              units "kilobyte";
              description
                "Specify buffer size in kilobytes for
                 destination file";
            }
            leaf destination-buffer-type {
              when "../destination-type = 'file'" {
                tailf:xpath-root 3;
                description
                  "../DestinationType = File";
              }
              type Span-buffer;
              description
                "Specify the buffer type for destination file";
            }
            leaf destination-port {
              when "../destination-type = 'udp'" {
                tailf:xpath-root 3;
                description
                  "../DestinationType = UDP";
              }
              type uint32;
              description
                "Specify the destination port";
            }
            leaf source-ipv4-address {
              when "../destination-type = 'udp'" {
                tailf:xpath-root 3;
                description
                  "../DestinationType = UDP";
              }
              type inet:ipv4-address-no-zone;
              description
                "Specify the source IPv4 address";
            }
            leaf source-ipv6-address {
              when "../destination-type = 'udp'" {
                tailf:xpath-root 3;
                description
                  "../DestinationType = UDP";
              }
              type inet:ipv6-address-no-zone;
              description
                "Specify the source  IPv6 address";
            }
            leaf source-port {
              when "../destination-type = 'udp'" {
                tailf:xpath-root 3;
                description
                  "../DestinationType = UDP";
              }
              type uint32;
              description
                "Specify the source port";
            }
            leaf vrf-name {
              when "../destination-type = 'udp'" {
                tailf:xpath-root 3;
                description
                  "../DestinationType = UDP";
              }
              type string;
              description
                "Specify the VRF name";
            }
            leaf destination-file-format {
              when "../destination-type = 'file'" {
                tailf:xpath-root 3;
                description
                  "../DestinationType = File";
              }
              type Span-file-format;
              description
                "Specify the file format";
            }
            leaf destination-pcap-filter {
              when "../destination-type = 'file'" {
                tailf:xpath-root 3;
                description
                  "../DestinationType = File";
              }
              type string;
              description
                "Specify a pcap filter";
            }
          }
          leaf class {
            type dt1:Span-session-class;
            mandatory true;
            description
              "Enable a Monitor Session.  Setting this item
               causes the Monitor Session to be created.";
          }
          leaf discard-class {
            type uint32 {
              range "0..7";
            }
            description
              "Specify the discard class value to be set on
               all traffic mirrored to the destination";
          }
          leaf inject-interface {
            type xr:Interface-name;
            description
              "Specify the inject interface name";
          }
          leaf traffic-class {
            type uint32 {
              range "0..7";
            }
            description
              "Specify the traffic class value to be set on
               all traffic mirrored to the destination";
          }
          leaf session {
            type dt1:Span-session-name;
            description
              "Session Name";
          }
        }
      }
    }
  }
  augment "/ncs:devices/ncs:device/ncs:live-status" {
    container span-monitor-session {
      tailf:ncs-device-type "netconf";
      tailf:display-when "not(../../ncs:module) or ../../ncs:module[ncs:name='Cisco-IOS-XR-Ethernet-SPAN-cfg'] or (../../ncs:live-status-protocol[not(ncs:capability)]) or (../../ncs:live-status-protocol/ncs:capability/ncs:module[.='Cisco-IOS-XR-Ethernet-SPAN-cfg'])";
      description
        "none";
      container sessions {
        description
          "Monitor-session configuration commands";
        list session {
          key "session";
          description
            "Configuration for a particular Monitor Session";
          container cloud-span {
            description
              "CloudSPAN configuration options for this
               session";
            leaf cloud-span-enable {
              type empty;
              description
                "Enable CloudSPAN on this session";
            }
          }
          container destination {
            description
              "Specify a destination";
            leaf destination-type {
              type live_ncs_Span-destination;
              description
                "Specify the type of destination";
            }
            leaf destination-interface-name {
              // NCS drop when statement
              type xr:live_ncs_Interface-name;
              description
                "Specify the destination interface name";
            }
            leaf destination-ipv4-address {
              // NCS drop when statement
              type inet:ipv4-address-no-zone;
              description
                "Specify the destination IPv4 address";
            }
            leaf destination-ipv6-address {
              // NCS drop when statement
              type inet:ipv6-address-no-zone;
              description
                "Specify the destination IPv6 address";
            }
            leaf destination-buffer-size {
              // NCS drop when statement
              type live_ncs_Span-buffer-size;
              units "kilobyte";
              description
                "Specify buffer size in kilobytes for
                 destination file";
            }
            leaf destination-buffer-type {
              // NCS drop when statement
              type live_ncs_Span-buffer;
              description
                "Specify the buffer type for destination file";
            }
            leaf destination-port {
              // NCS drop when statement
              type uint32;
              description
                "Specify the destination port";
            }
            leaf source-ipv4-address {
              // NCS drop when statement
              type inet:ipv4-address-no-zone;
              description
                "Specify the source IPv4 address";
            }
            leaf source-ipv6-address {
              // NCS drop when statement
              type inet:ipv6-address-no-zone;
              description
                "Specify the source  IPv6 address";
            }
            leaf source-port {
              // NCS drop when statement
              type uint32;
              description
                "Specify the source port";
            }
            leaf vrf-name {
              // NCS drop when statement
              type string;
              description
                "Specify the VRF name";
            }
            leaf destination-file-format {
              // NCS drop when statement
              type live_ncs_Span-file-format;
              description
                "Specify the file format";
            }
            leaf destination-pcap-filter {
              // NCS drop when statement
              type string;
              description
                "Specify a pcap filter";
            }
          }
          leaf class {
            type dt1:live_ncs_Span-session-class;
            // NCS drop mandatory statement
            description
              "Enable a Monitor Session.  Setting this item
               causes the Monitor Session to be created.";
          }
          leaf discard-class {
            type uint32 {
              range "0..7";
            }
            description
              "Specify the discard class value to be set on
               all traffic mirrored to the destination";
          }
          leaf inject-interface {
            type xr:live_ncs_Interface-name;
            description
              "Specify the inject interface name";
          }
          leaf traffic-class {
            type uint32 {
              range "0..7";
            }
            description
              "Specify the traffic class value to be set on
               all traffic mirrored to the destination";
          }
          leaf session {
            type dt1:live_ncs_Span-session-name;
            description
              "Session Name";
          }
        }
      }
    }
  }
  augment "/ncs:devices/ncs:template/ncs:ned-id/ncs:config" {
    container span-monitor-session {
      description
        "none";
      container sessions {
        description
          "Monitor-session configuration commands";
        list session {
          // NCS patched for predictable order
          ordered-by user;
          key "session";
          description
            "Configuration for a particular Monitor Session";
          container cloud-span {
            description
              "CloudSPAN configuration options for this
               session";
            leaf cloud-span-enable {
              type empty;
              description
                "Enable CloudSPAN on this session";
            }
          }
          container destination {
            description
              "Specify a destination";
            leaf destination-type {
              type ncs_template_Span-destination;
              description
                "Specify the type of destination";
            }
            leaf destination-interface-name {
              // NCS drop when statement
              type xr:ncs_template_Interface-name;
              description
                "Specify the destination interface name";
            }
            leaf destination-ipv4-address {
              // NCS drop when statement
              type string;
              description
                "Specify the destination IPv4 address";
            }
            leaf destination-ipv6-address {
              // NCS drop when statement
              type string;
              description
                "Specify the destination IPv6 address";
            }
            leaf destination-buffer-size {
              // NCS drop when statement
              type ncs_template_Span-buffer-size;
              units "kilobyte";
              description
                "Specify buffer size in kilobytes for
                 destination file";
            }
            leaf destination-buffer-type {
              // NCS drop when statement
              type ncs_template_Span-buffer;
              description
                "Specify the buffer type for destination file";
            }
            leaf destination-port {
              // NCS drop when statement
              type string;
              description
                "Specify the destination port";
            }
            leaf source-ipv4-address {
              // NCS drop when statement
              type string;
              description
                "Specify the source IPv4 address";
            }
            leaf source-ipv6-address {
              // NCS drop when statement
              type string;
              description
                "Specify the source  IPv6 address";
            }
            leaf source-port {
              // NCS drop when statement
              type string;
              description
                "Specify the source port";
            }
            leaf vrf-name {
              // NCS drop when statement
              type string;
              description
                "Specify the VRF name";
            }
            leaf destination-file-format {
              // NCS drop when statement
              type ncs_template_Span-file-format;
              description
                "Specify the file format";
            }
            leaf destination-pcap-filter {
              // NCS drop when statement
              type string;
              description
                "Specify a pcap filter";
            }
          }
          leaf class {
            type dt1:ncs_template_Span-session-class;
            // NCS drop mandatory statement
            description
              "Enable a Monitor Session.  Setting this item
               causes the Monitor Session to be created.";
          }
          leaf discard-class {
            type string;
            description
              "Specify the discard class value to be set on
               all traffic mirrored to the destination";
          }
          leaf inject-interface {
            type xr:ncs_template_Interface-name;
            description
              "Specify the inject interface name";
          }
          leaf traffic-class {
            type string;
            description
              "Specify the traffic class value to be set on
               all traffic mirrored to the destination";
          }
          leaf session {
            type dt1:ncs_template_Span-session-name;
            description
              "Session Name";
          }
        }
      }
    }
  }
  augment "/ncs:devices/ncs:template/ncs:ned-id/ncs:config/a1:interface-configurations/a1:interface-configuration/a2:l2-transport" {
    description
      "This augment extends the configuration data of
       'Cisco-IOS-XR-l2vpn-cfg'";
    uses ncs_template_ETHERNET-SPAN-INTERFACE-CFG-SPAN-MONITOR-SESSION-TABLE;
  }
  augment "/ncs:devices/ncs:device/ncs:live-status/a1:interface-configurations/a1:interface-configuration/a2:l2-transport" {
    description
      "This augment extends the configuration data of
       'Cisco-IOS-XR-l2vpn-cfg'";
    uses live_ncs_ETHERNET-SPAN-INTERFACE-CFG-SPAN-MONITOR-SESSION-TABLE {
      refine span-monitor-sessions {
        tailf:ncs-device-type "netconf";
        tailf:display-when "not(../../../../../ncs:module) or ../../../../../ncs:module[ncs:name='Cisco-IOS-XR-Ethernet-SPAN-cfg'] or (../../../../../ncs:live-status-protocol[not(ncs:capability)]) or (../../../../../ncs:live-status-protocol/ncs:capability/ncs:module[.='Cisco-IOS-XR-Ethernet-SPAN-cfg'])";
      }
    }
  }
  augment "/ncs:devices/ncs:device/ncs:config/a1:interface-configurations/a1:interface-configuration/a2:l2-transport" {
    description
      "This augment extends the configuration data of
       'Cisco-IOS-XR-l2vpn-cfg'";
    uses ETHERNET-SPAN-INTERFACE-CFG-SPAN-MONITOR-SESSION-TABLE {
      refine span-monitor-sessions {
        tailf:ncs-device-type "netconf";
        tailf:display-when "not(../../../../../ncs:module) or ../../../../../ncs:module[ncs:name='Cisco-IOS-XR-Ethernet-SPAN-cfg']";
      }
    }
  }
  augment "/ncs:devices/ncs:template/ncs:ned-id/ncs:config/a1:interface-configurations/a1:interface-configuration" {
    description
      "This augment extends the configuration data of
       'Cisco-IOS-XR-ifmgr-cfg'";
    uses ncs_template_ETHERNET-SPAN-INTERFACE-CFG-SPAN-MONITOR-SESSION-TABLE;
  }
  augment "/ncs:devices/ncs:device/ncs:live-status/a1:interface-configurations/a1:interface-configuration" {
    description
      "This augment extends the configuration data of
       'Cisco-IOS-XR-ifmgr-cfg'";
    uses live_ncs_ETHERNET-SPAN-INTERFACE-CFG-SPAN-MONITOR-SESSION-TABLE {
      refine span-monitor-sessions {
        tailf:ncs-device-type "netconf";
        tailf:display-when "not(../../../../ncs:module) or ../../../../ncs:module[ncs:name='Cisco-IOS-XR-Ethernet-SPAN-cfg'] or (../../../../ncs:live-status-protocol[not(ncs:capability)]) or (../../../../ncs:live-status-protocol/ncs:capability/ncs:module[.='Cisco-IOS-XR-Ethernet-SPAN-cfg'])";
      }
    }
  }
  augment "/ncs:devices/ncs:device/ncs:config/a1:interface-configurations/a1:interface-configuration" {
    description
      "This augment extends the configuration data of
       'Cisco-IOS-XR-ifmgr-cfg'";
    uses ETHERNET-SPAN-INTERFACE-CFG-SPAN-MONITOR-SESSION-TABLE {
      refine span-monitor-sessions {
        tailf:ncs-device-type "netconf";
        tailf:display-when "not(../../../../ncs:module) or ../../../../ncs:module[ncs:name='Cisco-IOS-XR-Ethernet-SPAN-cfg']";
      }
    }
  }
}

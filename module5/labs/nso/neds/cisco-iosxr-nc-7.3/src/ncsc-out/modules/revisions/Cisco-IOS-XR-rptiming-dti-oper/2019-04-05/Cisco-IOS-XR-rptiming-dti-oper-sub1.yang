submodule Cisco-IOS-XR-rptiming-dti-oper-sub1 {
  // Generated by yanger -t ncs
  tailf:mount-id "cisco-iosxr-nc-7.3:cisco-iosxr-nc-7.3";

  belongs-to Cisco-IOS-XR-rptiming-dti-oper {
    prefix Cisco-IOS-XR-rptiming-dti-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR rptiming-dti package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_DTI-TOD-INFO {
    description
      "DTI tod status";
    leaf port1-tod-message-mode {
      type string;
      description
        "port1 tod message mode";
    }
    leaf port1-tod-state {
      type string;
      description
        "port1 tod state";
    }
    leaf port1-tod-time-setting-mode {
      type string;
      description
        "port1 tod time setting mode";
    }
    leaf port1-gps-seconds {
      type string;
      units "second";
      description
        "port1 gps seconds";
    }
    leaf port1-leap-seconds {
      type string;
      units "second";
      description
        "port1 leap seconds";
    }
    leaf port1-calendar-time-valid {
      type string;
      description
        "port1 calendar time valid";
    }
    leaf port1-modified-julian-date {
      type string;
      description
        "port1 modified julian date";
    }
    leaf port1-date {
      type string;
      description
        "port1 date";
    }
    leaf port1-time {
      type string;
      description
        "port1 time";
    }
    leaf port1-time-zone-offset {
      type string;
      description
        "port1 time zone offset";
    }
    leaf port1-leap-second-indicator {
      type string;
      description
        "port1 leap second indicator";
    }
    leaf port2-tod-message-mode {
      type string;
      description
        "port2 tod message mode";
    }
    leaf port2-tod-state {
      type string;
      description
        "port2 tod state";
    }
    leaf port2-tod-time-setting-mode {
      type string;
      description
        "port2 tod time setting mode";
    }
    leaf port2-gps-seconds {
      type string;
      units "second";
      description
        "port2 gps seconds";
    }
    leaf port2-leap-seconds {
      type string;
      units "second";
      description
        "port2 leap seconds";
    }
    leaf port2-calendar-time-valid {
      type string;
      description
        "port2 calendar time valid";
    }
    leaf port2-modified-julian-date {
      type string;
      description
        "port2 modified julian date";
    }
    leaf port2-date {
      type string;
      description
        "port2 date";
    }
    leaf port2-time {
      type string;
      description
        "port2 time";
    }
    leaf port2-time-zone-offset {
      type string;
      description
        "port2 time zone offset";
    }
    leaf port2-leap-second-indicator {
      type string;
      description
        "port2 leap second indicator";
    }
  }

  grouping ncs_template_DTI-PORT-INFO {
    description
      "DTI port status";
    leaf port1-fr-err-rate-greater5-per {
      type string;
      units "percentage";
      description
        "port1 frame error rate greater than 5 percent";
    }
    leaf port1-fr-err-rate-greater2-per {
      type string;
      units "percentage";
      description
        "port1 frame error rate greater than 2 percent";
    }
    leaf port1-dti-signal-detected {
      type string;
      description
        "port1 DTI signal detected";
    }
    leaf port1-server-timing-source {
      type string;
      description
        "port1 server timing source";
    }
    leaf port1-server-type {
      type string;
      description
        "port1 server type";
    }
    leaf port1-server-clock-type {
      type string;
      description
        "port1 server clock type";
    }
    leaf port1-server-state {
      type string;
      description
        "port1 server state";
    }
    leaf port1-client-perf-stable {
      type string;
      description
        "port1 client performance stable";
    }
    leaf port1-cable-advance-valid {
      type string;
      description
        "port1 cable advance valid";
    }
    leaf port2-fr-err-rate-greater5-per {
      type string;
      units "percentage";
      description
        "port2 frame error rate greater than 5 percent";
    }
    leaf port2-fr-err-rate-greater2-per {
      type string;
      units "percentage";
      description
        "port2 frame error rate greater than 2 percent";
    }
    leaf port2-dti-signal-detected {
      type string;
      description
        "port2 DTI signal detected";
    }
    leaf port2-server-timing-source {
      type string;
      description
        "port2 server timing source";
    }
    leaf port2-server-type {
      type string;
      description
        "port2 server type";
    }
    leaf port2-server-clock-type {
      type string;
      description
        "port2 server clock type";
    }
    leaf port2-server-state {
      type string;
      description
        "port2 server state";
    }
    leaf port2-client-perf-stable {
      type string;
      description
        "port2 client performance stable";
    }
    leaf port2-cable-advance-valid {
      type string;
      description
        "port2 cable advance valid";
    }
  }

  grouping ncs_template_DTI-CLIENT-INFO {
    description
      "DTI client status";
    leaf timestamp-comparator-enable {
      type string;
      description
        "timestamp comparator enable";
    }
    leaf register-write-enable {
      type string;
      description
        "register write enable";
    }
    leaf revertive-mode-enable {
      type string;
      description
        "revertive mode enable";
    }
    leaf port-mode-select {
      type string;
      description
        "port mode select";
    }
    leaf force-freerun {
      type string;
      description
        "force freerun";
    }
    leaf reference-select-port {
      type string;
      description
        "reference select port";
    }
    leaf timestamp-sync-detected {
      type string;
      description
        "timestamp sync detected";
    }
    leaf reference10mhz-detected {
      type string;
      description
        "10Mhz reference detected";
    }
    leaf active-input-port {
      type string;
      description
        "active input port";
    }
    leaf client-state {
      type string;
      description
        "client state";
    }
  }

  grouping ncs_rpc_notif_DTI-TOD-INFO {
    description
      "DTI tod status";
    leaf port1-tod-message-mode {
      type string {
        length "0..50";
      }
      description
        "port1 tod message mode";
    }
    leaf port1-tod-state {
      type string {
        length "0..50";
      }
      description
        "port1 tod state";
    }
    leaf port1-tod-time-setting-mode {
      type string {
        length "0..50";
      }
      description
        "port1 tod time setting mode";
    }
    leaf port1-gps-seconds {
      type uint32;
      units "second";
      description
        "port1 gps seconds";
    }
    leaf port1-leap-seconds {
      type uint8;
      units "second";
      description
        "port1 leap seconds";
    }
    leaf port1-calendar-time-valid {
      type string {
        length "0..50";
      }
      description
        "port1 calendar time valid";
    }
    leaf port1-modified-julian-date {
      type string {
        length "0..50";
      }
      description
        "port1 modified julian date";
    }
    leaf port1-date {
      type string {
        length "0..50";
      }
      description
        "port1 date";
    }
    leaf port1-time {
      type string {
        length "0..50";
      }
      description
        "port1 time";
    }
    leaf port1-time-zone-offset {
      type string {
        length "0..50";
      }
      description
        "port1 time zone offset";
    }
    leaf port1-leap-second-indicator {
      type uint8;
      description
        "port1 leap second indicator";
    }
    leaf port2-tod-message-mode {
      type string {
        length "0..50";
      }
      description
        "port2 tod message mode";
    }
    leaf port2-tod-state {
      type string {
        length "0..50";
      }
      description
        "port2 tod state";
    }
    leaf port2-tod-time-setting-mode {
      type string {
        length "0..50";
      }
      description
        "port2 tod time setting mode";
    }
    leaf port2-gps-seconds {
      type uint32;
      units "second";
      description
        "port2 gps seconds";
    }
    leaf port2-leap-seconds {
      type uint8;
      units "second";
      description
        "port2 leap seconds";
    }
    leaf port2-calendar-time-valid {
      type string {
        length "0..50";
      }
      description
        "port2 calendar time valid";
    }
    leaf port2-modified-julian-date {
      type string {
        length "0..50";
      }
      description
        "port2 modified julian date";
    }
    leaf port2-date {
      type string {
        length "0..50";
      }
      description
        "port2 date";
    }
    leaf port2-time {
      type string {
        length "0..50";
      }
      description
        "port2 time";
    }
    leaf port2-time-zone-offset {
      type string {
        length "0..50";
      }
      description
        "port2 time zone offset";
    }
    leaf port2-leap-second-indicator {
      type uint8;
      description
        "port2 leap second indicator";
    }
  }

  grouping ncs_rpc_notif_DTI-PORT-INFO {
    description
      "DTI port status";
    leaf port1-fr-err-rate-greater5-per {
      type string {
        length "0..50";
      }
      units "percentage";
      description
        "port1 frame error rate greater than 5 percent";
    }
    leaf port1-fr-err-rate-greater2-per {
      type string {
        length "0..50";
      }
      units "percentage";
      description
        "port1 frame error rate greater than 2 percent";
    }
    leaf port1-dti-signal-detected {
      type string {
        length "0..50";
      }
      description
        "port1 DTI signal detected";
    }
    leaf port1-server-timing-source {
      type string {
        length "0..50";
      }
      description
        "port1 server timing source";
    }
    leaf port1-server-type {
      type string {
        length "0..50";
      }
      description
        "port1 server type";
    }
    leaf port1-server-clock-type {
      type string {
        length "0..50";
      }
      description
        "port1 server clock type";
    }
    leaf port1-server-state {
      type string {
        length "0..50";
      }
      description
        "port1 server state";
    }
    leaf port1-client-perf-stable {
      type string {
        length "0..50";
      }
      description
        "port1 client performance stable";
    }
    leaf port1-cable-advance-valid {
      type string {
        length "0..50";
      }
      description
        "port1 cable advance valid";
    }
    leaf port2-fr-err-rate-greater5-per {
      type string {
        length "0..50";
      }
      units "percentage";
      description
        "port2 frame error rate greater than 5 percent";
    }
    leaf port2-fr-err-rate-greater2-per {
      type string {
        length "0..50";
      }
      units "percentage";
      description
        "port2 frame error rate greater than 2 percent";
    }
    leaf port2-dti-signal-detected {
      type string {
        length "0..50";
      }
      description
        "port2 DTI signal detected";
    }
    leaf port2-server-timing-source {
      type string {
        length "0..50";
      }
      description
        "port2 server timing source";
    }
    leaf port2-server-type {
      type string {
        length "0..50";
      }
      description
        "port2 server type";
    }
    leaf port2-server-clock-type {
      type string {
        length "0..50";
      }
      description
        "port2 server clock type";
    }
    leaf port2-server-state {
      type string {
        length "0..50";
      }
      description
        "port2 server state";
    }
    leaf port2-client-perf-stable {
      type string {
        length "0..50";
      }
      description
        "port2 client performance stable";
    }
    leaf port2-cable-advance-valid {
      type string {
        length "0..50";
      }
      description
        "port2 cable advance valid";
    }
  }

  grouping ncs_rpc_notif_DTI-CLIENT-INFO {
    description
      "DTI client status";
    leaf timestamp-comparator-enable {
      type string {
        length "0..50";
      }
      description
        "timestamp comparator enable";
    }
    leaf register-write-enable {
      type string {
        length "0..50";
      }
      description
        "register write enable";
    }
    leaf revertive-mode-enable {
      type string {
        length "0..50";
      }
      description
        "revertive mode enable";
    }
    leaf port-mode-select {
      type string {
        length "0..50";
      }
      description
        "port mode select";
    }
    leaf force-freerun {
      type string {
        length "0..50";
      }
      description
        "force freerun";
    }
    leaf reference-select-port {
      type string {
        length "0..50";
      }
      description
        "reference select port";
    }
    leaf timestamp-sync-detected {
      type string {
        length "0..50";
      }
      description
        "timestamp sync detected";
    }
    leaf reference10mhz-detected {
      type string {
        length "0..50";
      }
      description
        "10Mhz reference detected";
    }
    leaf active-input-port {
      type string {
        length "0..50";
      }
      description
        "active input port";
    }
    leaf client-state {
      type string {
        length "0..50";
      }
      description
        "client state";
    }
  }

  grouping live_ncs_DTI-TOD-INFO {
    description
      "DTI tod status";
    leaf port1-tod-message-mode {
      type string {
        length "0..50";
      }
      description
        "port1 tod message mode";
    }
    leaf port1-tod-state {
      type string {
        length "0..50";
      }
      description
        "port1 tod state";
    }
    leaf port1-tod-time-setting-mode {
      type string {
        length "0..50";
      }
      description
        "port1 tod time setting mode";
    }
    leaf port1-gps-seconds {
      type uint32;
      units "second";
      description
        "port1 gps seconds";
    }
    leaf port1-leap-seconds {
      type uint8;
      units "second";
      description
        "port1 leap seconds";
    }
    leaf port1-calendar-time-valid {
      type string {
        length "0..50";
      }
      description
        "port1 calendar time valid";
    }
    leaf port1-modified-julian-date {
      type string {
        length "0..50";
      }
      description
        "port1 modified julian date";
    }
    leaf port1-date {
      type string {
        length "0..50";
      }
      description
        "port1 date";
    }
    leaf port1-time {
      type string {
        length "0..50";
      }
      description
        "port1 time";
    }
    leaf port1-time-zone-offset {
      type string {
        length "0..50";
      }
      description
        "port1 time zone offset";
    }
    leaf port1-leap-second-indicator {
      type uint8;
      description
        "port1 leap second indicator";
    }
    leaf port2-tod-message-mode {
      type string {
        length "0..50";
      }
      description
        "port2 tod message mode";
    }
    leaf port2-tod-state {
      type string {
        length "0..50";
      }
      description
        "port2 tod state";
    }
    leaf port2-tod-time-setting-mode {
      type string {
        length "0..50";
      }
      description
        "port2 tod time setting mode";
    }
    leaf port2-gps-seconds {
      type uint32;
      units "second";
      description
        "port2 gps seconds";
    }
    leaf port2-leap-seconds {
      type uint8;
      units "second";
      description
        "port2 leap seconds";
    }
    leaf port2-calendar-time-valid {
      type string {
        length "0..50";
      }
      description
        "port2 calendar time valid";
    }
    leaf port2-modified-julian-date {
      type string {
        length "0..50";
      }
      description
        "port2 modified julian date";
    }
    leaf port2-date {
      type string {
        length "0..50";
      }
      description
        "port2 date";
    }
    leaf port2-time {
      type string {
        length "0..50";
      }
      description
        "port2 time";
    }
    leaf port2-time-zone-offset {
      type string {
        length "0..50";
      }
      description
        "port2 time zone offset";
    }
    leaf port2-leap-second-indicator {
      type uint8;
      description
        "port2 leap second indicator";
    }
  }

  grouping live_ncs_DTI-PORT-INFO {
    description
      "DTI port status";
    leaf port1-fr-err-rate-greater5-per {
      type string {
        length "0..50";
      }
      units "percentage";
      description
        "port1 frame error rate greater than 5 percent";
    }
    leaf port1-fr-err-rate-greater2-per {
      type string {
        length "0..50";
      }
      units "percentage";
      description
        "port1 frame error rate greater than 2 percent";
    }
    leaf port1-dti-signal-detected {
      type string {
        length "0..50";
      }
      description
        "port1 DTI signal detected";
    }
    leaf port1-server-timing-source {
      type string {
        length "0..50";
      }
      description
        "port1 server timing source";
    }
    leaf port1-server-type {
      type string {
        length "0..50";
      }
      description
        "port1 server type";
    }
    leaf port1-server-clock-type {
      type string {
        length "0..50";
      }
      description
        "port1 server clock type";
    }
    leaf port1-server-state {
      type string {
        length "0..50";
      }
      description
        "port1 server state";
    }
    leaf port1-client-perf-stable {
      type string {
        length "0..50";
      }
      description
        "port1 client performance stable";
    }
    leaf port1-cable-advance-valid {
      type string {
        length "0..50";
      }
      description
        "port1 cable advance valid";
    }
    leaf port2-fr-err-rate-greater5-per {
      type string {
        length "0..50";
      }
      units "percentage";
      description
        "port2 frame error rate greater than 5 percent";
    }
    leaf port2-fr-err-rate-greater2-per {
      type string {
        length "0..50";
      }
      units "percentage";
      description
        "port2 frame error rate greater than 2 percent";
    }
    leaf port2-dti-signal-detected {
      type string {
        length "0..50";
      }
      description
        "port2 DTI signal detected";
    }
    leaf port2-server-timing-source {
      type string {
        length "0..50";
      }
      description
        "port2 server timing source";
    }
    leaf port2-server-type {
      type string {
        length "0..50";
      }
      description
        "port2 server type";
    }
    leaf port2-server-clock-type {
      type string {
        length "0..50";
      }
      description
        "port2 server clock type";
    }
    leaf port2-server-state {
      type string {
        length "0..50";
      }
      description
        "port2 server state";
    }
    leaf port2-client-perf-stable {
      type string {
        length "0..50";
      }
      description
        "port2 client performance stable";
    }
    leaf port2-cable-advance-valid {
      type string {
        length "0..50";
      }
      description
        "port2 cable advance valid";
    }
  }

  grouping live_ncs_DTI-CLIENT-INFO {
    description
      "DTI client status";
    leaf timestamp-comparator-enable {
      type string {
        length "0..50";
      }
      description
        "timestamp comparator enable";
    }
    leaf register-write-enable {
      type string {
        length "0..50";
      }
      description
        "register write enable";
    }
    leaf revertive-mode-enable {
      type string {
        length "0..50";
      }
      description
        "revertive mode enable";
    }
    leaf port-mode-select {
      type string {
        length "0..50";
      }
      description
        "port mode select";
    }
    leaf force-freerun {
      type string {
        length "0..50";
      }
      description
        "force freerun";
    }
    leaf reference-select-port {
      type string {
        length "0..50";
      }
      description
        "reference select port";
    }
    leaf timestamp-sync-detected {
      type string {
        length "0..50";
      }
      description
        "timestamp sync detected";
    }
    leaf reference10mhz-detected {
      type string {
        length "0..50";
      }
      description
        "10Mhz reference detected";
    }
    leaf active-input-port {
      type string {
        length "0..50";
      }
      description
        "active input port";
    }
    leaf client-state {
      type string {
        length "0..50";
      }
      description
        "client state";
    }
  }

  grouping DTI-TOD-INFO {
    description
      "DTI tod status";
    leaf port1-tod-message-mode {
      type string {
        length "0..50";
      }
      description
        "port1 tod message mode";
    }
    leaf port1-tod-state {
      type string {
        length "0..50";
      }
      description
        "port1 tod state";
    }
    leaf port1-tod-time-setting-mode {
      type string {
        length "0..50";
      }
      description
        "port1 tod time setting mode";
    }
    leaf port1-gps-seconds {
      type uint32;
      units "second";
      description
        "port1 gps seconds";
    }
    leaf port1-leap-seconds {
      type uint8;
      units "second";
      description
        "port1 leap seconds";
    }
    leaf port1-calendar-time-valid {
      type string {
        length "0..50";
      }
      description
        "port1 calendar time valid";
    }
    leaf port1-modified-julian-date {
      type string {
        length "0..50";
      }
      description
        "port1 modified julian date";
    }
    leaf port1-date {
      type string {
        length "0..50";
      }
      description
        "port1 date";
    }
    leaf port1-time {
      type string {
        length "0..50";
      }
      description
        "port1 time";
    }
    leaf port1-time-zone-offset {
      type string {
        length "0..50";
      }
      description
        "port1 time zone offset";
    }
    leaf port1-leap-second-indicator {
      type uint8;
      description
        "port1 leap second indicator";
    }
    leaf port2-tod-message-mode {
      type string {
        length "0..50";
      }
      description
        "port2 tod message mode";
    }
    leaf port2-tod-state {
      type string {
        length "0..50";
      }
      description
        "port2 tod state";
    }
    leaf port2-tod-time-setting-mode {
      type string {
        length "0..50";
      }
      description
        "port2 tod time setting mode";
    }
    leaf port2-gps-seconds {
      type uint32;
      units "second";
      description
        "port2 gps seconds";
    }
    leaf port2-leap-seconds {
      type uint8;
      units "second";
      description
        "port2 leap seconds";
    }
    leaf port2-calendar-time-valid {
      type string {
        length "0..50";
      }
      description
        "port2 calendar time valid";
    }
    leaf port2-modified-julian-date {
      type string {
        length "0..50";
      }
      description
        "port2 modified julian date";
    }
    leaf port2-date {
      type string {
        length "0..50";
      }
      description
        "port2 date";
    }
    leaf port2-time {
      type string {
        length "0..50";
      }
      description
        "port2 time";
    }
    leaf port2-time-zone-offset {
      type string {
        length "0..50";
      }
      description
        "port2 time zone offset";
    }
    leaf port2-leap-second-indicator {
      type uint8;
      description
        "port2 leap second indicator";
    }
  }

  grouping DTI-PORT-INFO {
    description
      "DTI port status";
    leaf port1-fr-err-rate-greater5-per {
      type string {
        length "0..50";
      }
      units "percentage";
      description
        "port1 frame error rate greater than 5 percent";
    }
    leaf port1-fr-err-rate-greater2-per {
      type string {
        length "0..50";
      }
      units "percentage";
      description
        "port1 frame error rate greater than 2 percent";
    }
    leaf port1-dti-signal-detected {
      type string {
        length "0..50";
      }
      description
        "port1 DTI signal detected";
    }
    leaf port1-server-timing-source {
      type string {
        length "0..50";
      }
      description
        "port1 server timing source";
    }
    leaf port1-server-type {
      type string {
        length "0..50";
      }
      description
        "port1 server type";
    }
    leaf port1-server-clock-type {
      type string {
        length "0..50";
      }
      description
        "port1 server clock type";
    }
    leaf port1-server-state {
      type string {
        length "0..50";
      }
      description
        "port1 server state";
    }
    leaf port1-client-perf-stable {
      type string {
        length "0..50";
      }
      description
        "port1 client performance stable";
    }
    leaf port1-cable-advance-valid {
      type string {
        length "0..50";
      }
      description
        "port1 cable advance valid";
    }
    leaf port2-fr-err-rate-greater5-per {
      type string {
        length "0..50";
      }
      units "percentage";
      description
        "port2 frame error rate greater than 5 percent";
    }
    leaf port2-fr-err-rate-greater2-per {
      type string {
        length "0..50";
      }
      units "percentage";
      description
        "port2 frame error rate greater than 2 percent";
    }
    leaf port2-dti-signal-detected {
      type string {
        length "0..50";
      }
      description
        "port2 DTI signal detected";
    }
    leaf port2-server-timing-source {
      type string {
        length "0..50";
      }
      description
        "port2 server timing source";
    }
    leaf port2-server-type {
      type string {
        length "0..50";
      }
      description
        "port2 server type";
    }
    leaf port2-server-clock-type {
      type string {
        length "0..50";
      }
      description
        "port2 server clock type";
    }
    leaf port2-server-state {
      type string {
        length "0..50";
      }
      description
        "port2 server state";
    }
    leaf port2-client-perf-stable {
      type string {
        length "0..50";
      }
      description
        "port2 client performance stable";
    }
    leaf port2-cable-advance-valid {
      type string {
        length "0..50";
      }
      description
        "port2 cable advance valid";
    }
  }

  grouping DTI-CLIENT-INFO {
    description
      "DTI client status";
    leaf timestamp-comparator-enable {
      type string {
        length "0..50";
      }
      description
        "timestamp comparator enable";
    }
    leaf register-write-enable {
      type string {
        length "0..50";
      }
      description
        "register write enable";
    }
    leaf revertive-mode-enable {
      type string {
        length "0..50";
      }
      description
        "revertive mode enable";
    }
    leaf port-mode-select {
      type string {
        length "0..50";
      }
      description
        "port mode select";
    }
    leaf force-freerun {
      type string {
        length "0..50";
      }
      description
        "force freerun";
    }
    leaf reference-select-port {
      type string {
        length "0..50";
      }
      description
        "reference select port";
    }
    leaf timestamp-sync-detected {
      type string {
        length "0..50";
      }
      description
        "timestamp sync detected";
    }
    leaf reference10mhz-detected {
      type string {
        length "0..50";
      }
      description
        "10Mhz reference detected";
    }
    leaf active-input-port {
      type string {
        length "0..50";
      }
      description
        "active input port";
    }
    leaf client-state {
      type string {
        length "0..50";
      }
      description
        "client state";
    }
  }
}

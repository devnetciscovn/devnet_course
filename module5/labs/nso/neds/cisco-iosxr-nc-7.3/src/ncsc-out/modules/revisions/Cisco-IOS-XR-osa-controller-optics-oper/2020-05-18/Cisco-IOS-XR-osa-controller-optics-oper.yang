module Cisco-IOS-XR-osa-controller-optics-oper {
  // Generated by yanger -t ncs
  tailf:mount-id "cisco-iosxr-nc-7.3:cisco-iosxr-nc-7.3";
  tailf:ncs-device-type "netconf";

  namespace "http://cisco.com/ns/yang/Cisco-IOS-XR-osa-controller-optics-oper";
  prefix osa-controller-optics-oper;

  import Cisco-IOS-XR-types {
    prefix xr;
  }
  import cisco-semver {
    prefix semver;
  }
  include Cisco-IOS-XR-osa-controller-optics-oper-sub1 {
    revision-date 2020-05-18;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR osa-controller-optics package operational data.

     This module contains definitions
     for the following management objects:
       osa-controller-operational-info: OSA controller Operational
         Information

     Copyright (c) 2013-2020 by Cisco Systems, Inc.
     All rights reserved.";

  revision 2020-05-18 {
    description
      "Initial Revision.";
    semver:module-version "1.1.0";
  }
  revision 2019-04-05 {
    description
      "Establish semantic version baseline.";
    semver:module-version "1.1.0";
  }
  revision 2019-02-16 {
    description
      "Initial Revision.";
  }
  revision 2015-11-09 {
    description
      "IOS XR 6.0 revision.";
  }

  augment "/ncs:devices/ncs:device/ncs:config" {
    // NCS drop config false container 'osa-controller-operational-info'
  }
  augment "/ncs:devices/ncs:device/ncs:live-status" {
    container osa-controller-operational-info {
      tailf:ncs-device-type "netconf";
      tailf:display-when "not(../../ncs:module) or ../../ncs:module[ncs:name='Cisco-IOS-XR-osa-controller-optics-oper'] or (../../ncs:live-status-protocol[not(ncs:capability)]) or (../../ncs:live-status-protocol/ncs:capability/ncs:module[.='Cisco-IOS-XR-osa-controller-optics-oper'])";
      description
        "OSA controller Operational Information";
      container osa-optics-controller {
        description
          "Optics Controller";
        container controller-names {
          description
            "OSA optics controller Table";
          list controller-name {
            key "name";
            description
              "Controller Name";
            container bps-baud-rate-info {
              description
                "Fetch all BPS-GBD Capability Info";
              uses live_ncs_OSA-OPTICS-BPS-GBD-CAPAB-B;
            }
            leaf name {
              type xr:live_ncs_Interface-name;
              description
                "Controller name";
            }
          }
        }
      }
    }
  }
  augment "/ncs:devices/ncs:template/ncs:ned-id/ncs:config" {
    // NCS drop config false container 'osa-controller-operational-info'
  }
}

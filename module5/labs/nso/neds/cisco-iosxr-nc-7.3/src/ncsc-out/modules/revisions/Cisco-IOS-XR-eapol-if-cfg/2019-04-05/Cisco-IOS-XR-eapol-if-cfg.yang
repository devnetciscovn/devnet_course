module Cisco-IOS-XR-eapol-if-cfg {
  // Generated by yanger -t ncs
  tailf:mount-id "cisco-iosxr-nc-7.3:cisco-iosxr-nc-7.3";
  tailf:ncs-device-type "netconf";

  namespace "http://cisco.com/ns/yang/Cisco-IOS-XR-eapol-if-cfg";
  prefix eapol-if-cfg;

  import ietf-yang-types {
    prefix yang;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR eapol-if package configuration.

     This YANG module augments the
       Cisco-IOS-XR-ifmgr-cfg
     module with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Eapol-ether {
    type string;
    description
      "Eapol ether";
  }

  typedef ncs_rpc_notif_Eapol-ether {
    type enumeration {
      enum "eapol-ether-type-876f" {
        value 34671;
        description
          "EAPOL ETHER TYPE 876F";
      }
    }
    description
      "Eapol ether";
  }

  typedef live_ncs_Eapol-ether {
    type enumeration {
      enum "eapol-ether-type-876f" {
        value 34671;
        description
          "EAPOL ETHER TYPE 876F";
      }
    }
    description
      "Eapol ether";
  }

  typedef Eapol-ether {
    type enumeration {
      enum "eapol-ether-type-876f" {
        value 34671;
        description
          "EAPOL ETHER TYPE 876F";
      }
    }
    description
      "Eapol ether";
  }

  augment "/ncs:devices/ncs:template/ncs:ned-id/ncs:config/a1:interface-configurations/a1:interface-configuration" {
    description
      "This augment extends the configuration data of
       'Cisco-IOS-XR-ifmgr-cfg'";
    container eapol {
      description
        "Interface Specific Dot1x Configuration";
      leaf eapol-ether-type {
        type ncs_template_Eapol-ether;
        description
          "EAPoL ethertype for EAPoL frames transmission";
      }
      leaf eapol-dest-addr {
        type string;
        description
          "Destination address for EAPoL frames
           transmission";
      }
    }
  }
  augment "/ncs:devices/ncs:device/ncs:live-status/a1:interface-configurations/a1:interface-configuration" {
    description
      "This augment extends the configuration data of
       'Cisco-IOS-XR-ifmgr-cfg'";
    container eapol {
      tailf:ncs-device-type "netconf";
      tailf:display-when "not(../../../../ncs:module) or ../../../../ncs:module[ncs:name='Cisco-IOS-XR-eapol-if-cfg'] or (../../../../ncs:live-status-protocol[not(ncs:capability)]) or (../../../../ncs:live-status-protocol/ncs:capability/ncs:module[.='Cisco-IOS-XR-eapol-if-cfg'])";
      description
        "Interface Specific Dot1x Configuration";
      leaf eapol-ether-type {
        type live_ncs_Eapol-ether;
        description
          "EAPoL ethertype for EAPoL frames transmission";
      }
      leaf eapol-dest-addr {
        type yang:mac-address;
        description
          "Destination address for EAPoL frames
           transmission";
      }
    }
  }
  augment "/ncs:devices/ncs:device/ncs:config/a1:interface-configurations/a1:interface-configuration" {
    description
      "This augment extends the configuration data of
       'Cisco-IOS-XR-ifmgr-cfg'";
    container eapol {
      tailf:ncs-device-type "netconf";
      tailf:display-when "not(../../../../ncs:module) or ../../../../ncs:module[ncs:name='Cisco-IOS-XR-eapol-if-cfg']";
      description
        "Interface Specific Dot1x Configuration";
      leaf eapol-ether-type {
        type Eapol-ether;
        description
          "EAPoL ethertype for EAPoL frames transmission";
      }
      leaf eapol-dest-addr {
        type yang:mac-address;
        description
          "Destination address for EAPoL frames
           transmission";
      }
    }
  }
}

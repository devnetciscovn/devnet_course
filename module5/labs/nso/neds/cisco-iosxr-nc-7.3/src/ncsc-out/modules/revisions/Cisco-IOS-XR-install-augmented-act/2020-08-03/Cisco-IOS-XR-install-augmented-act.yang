module Cisco-IOS-XR-install-augmented-act {
  // Generated by yanger -t ncs
  tailf:mount-id "cisco-iosxr-nc-7.3:cisco-iosxr-nc-7.3";
  tailf:ncs-device-type "netconf";

  namespace "http://cisco.com/ns/yang/Cisco-IOS-XR-install-augmented-act";
  prefix install-augmented-act;

  import cisco-semver {
    prefix semver;
  }
  import Cisco-IOS-XR-types {
    prefix csc;
  }
  import Cisco-IOS-XR-install-act {
    prefix install-act;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a augmented collection of YANG definitions for Cisco
     IOS-XR install actions, and should be used along with
     Cisco-IOS-XR-install-act.yang

     Copyright (c) 2016-2020 by Cisco Systems, Inc.
     All rights reserved.";

  revision 2020-08-03 {
    description
      "Modified tasks for the RPC operations.";
    semver:module-version "3.1.0";
  }
  revision 2020-03-06 {
    description
      "Removal of the install-reload-failed-nodes RPC
       2019-11-05
       Addition of INST-AUGMENTED-OP-ID-TYPE for the return type of action RPCs";
    semver:module-version "3.0.0";
  }
  revision 2019-10-03 {
    description
      "Move apply type enum to Cisco-IOS-XR-install-act.yang
       2019-10-01
       Made changes to be RFC6087 compliant
       2019-09-19
       Allow user to indicate apply-type at the beginning of an operation.";
    semver:module-version "2.0.0";
  }
  revision 2019-04-05 {
    description
      "Establish semantic version baseline.";
    semver:module-version "1.0.0";
  }
  revision 2018-10-05 {
    description
      "IOS XR 7.0.1 revision.";
  }

  typedef ncs_template_abort-type {
    type string;
    description
      "abort type";
  }

  typedef ncs_rpc_notif_abort-type {
    type enumeration {
      enum "latest" {
        description
          "Abort the latest packaging operation";
      }
      enum "all-since-apply" {
        description
          "Abort all packaging operations since the last apply";
      }
    }
    description
      "abort type";
  }

  typedef live_ncs_abort-type {
    type enumeration {
      enum "latest" {
        description
          "Abort the latest packaging operation";
      }
      enum "all-since-apply" {
        description
          "Abort all packaging operations since the last apply";
      }
    }
    description
      "abort type";
  }

  typedef abort-type {
    type enumeration {
      enum "latest" {
        description
          "Abort the latest packaging operation";
      }
      enum "all-since-apply" {
        description
          "Abort all packaging operations since the last apply";
      }
    }
    description
      "abort type";
  }

  grouping ncs_template_INST-AUGMENTED-OP-ID-TYPE {
    leaf op-id {
      type string;
      description
        "operation id of the triggered action";
    }
  }

  grouping ncs_rpc_notif_INST-AUGMENTED-OP-ID-TYPE {
    leaf op-id {
      type string;
      description
        "operation id of the triggered action";
    }
  }

  grouping live_ncs_INST-AUGMENTED-OP-ID-TYPE {
    leaf op-id {
      type string;
      description
        "operation id of the triggered action";
    }
  }

  grouping INST-AUGMENTED-OP-ID-TYPE {
    leaf op-id {
      type string;
      description
        "operation id of the triggered action";
    }
  }

  augment "/ncs:devices/ncs:device/ncs:rpc" {
    container rpc-install-clear-rollback {
      tailf:ncs-device-type "netconf";
      tailf:display-when "not(../../ncs:module) or ../../ncs:module[ncs:name='Cisco-IOS-XR-install-augmented-act']";
      tailf:action install-clear-rollback {
        tailf:actionpoint ncsproxy {
          tailf:internal;
        }
        description
          "Remove specified rollback points to save disk space";
        input {
          leaf transaction-id {
            type uint32;
            mandatory true;
            description
              "Transaction ID corresponding to the rollback point to be removed";
          }
        }
        csc:xr-task "pkg-mgmt";
      }
    }
  }
  augment "/ncs:devices/ncs:device-group/ncs:ned-id/ncs:rpc" {
    container rpc-install-clear-rollback {
      tailf:ncs-device-type "netconf";
      tailf:display-when "/ncs:devices/ncs:device[ncs:name=current()/../../../ncs:member]/ncs:module[ncs:name='Cisco-IOS-XR-install-augmented-act']";
      tailf:action install-clear-rollback {
        tailf:actionpoint ncsproxy {
          tailf:internal;
        }
        description
          "Remove specified rollback points to save disk space";
        input {
          leaf transaction-id {
            type uint32;
            mandatory true;
            description
              "Transaction ID corresponding to the rollback point to be removed";
          }
        }
        csc:xr-task "pkg-mgmt";
      }
    }
  }
  augment "/ncs:devices/ncs:device/ncs:rpc" {
    container rpc-install-package-abort {
      tailf:ncs-device-type "netconf";
      tailf:display-when "not(../../ncs:module) or ../../ncs:module[ncs:name='Cisco-IOS-XR-install-augmented-act']";
      tailf:action install-package-abort {
        tailf:actionpoint ncsproxy {
          tailf:internal;
        }
        description
          "Abort the specified packaging operation(s)";
        input {
          leaf abort-type {
            type ncs_rpc_notif_abort-type;
            mandatory true;
            description
              "Which packaging operations to abort";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-package-abort {
      tailf:ncs-device-type "netconf";
      tailf:display-when "/ncs:devices/ncs:device[ncs:name=current()/../../../ncs:member]/ncs:module[ncs:name='Cisco-IOS-XR-install-augmented-act']";
      tailf:action install-package-abort {
        tailf:actionpoint ncsproxy {
          tailf:internal;
        }
        description
          "Abort the specified packaging operation(s)";
        input {
          leaf abort-type {
            type ncs_rpc_notif_abort-type;
            mandatory true;
            description
              "Which packaging operations to abort";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-apply {
      tailf:ncs-device-type "netconf";
      tailf:display-when "not(../../ncs:module) or ../../ncs:module[ncs:name='Cisco-IOS-XR-install-augmented-act']";
      tailf:action install-apply {
        tailf:actionpoint ncsproxy {
          tailf:internal;
        }
        description
          "Apply atomic operation by restarting processes or reloading";
        input {
          leaf apply-method {
            type install-act:ncs_rpc_notif_apply-type;
            mandatory true;
            description
              "Method of applying atomic operation";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-apply {
      tailf:ncs-device-type "netconf";
      tailf:display-when "/ncs:devices/ncs:device[ncs:name=current()/../../../ncs:member]/ncs:module[ncs:name='Cisco-IOS-XR-install-augmented-act']";
      tailf:action install-apply {
        tailf:actionpoint ncsproxy {
          tailf:internal;
        }
        description
          "Apply atomic operation by restarting processes or reloading";
        input {
          leaf apply-method {
            type install-act:ncs_rpc_notif_apply-type;
            mandatory true;
            description
              "Method of applying atomic operation";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-rollback {
      tailf:ncs-device-type "netconf";
      tailf:display-when "not(../../ncs:module) or ../../ncs:module[ncs:name='Cisco-IOS-XR-install-augmented-act']";
      tailf:action install-rollback {
        tailf:actionpoint ncsproxy {
          tailf:internal;
        }
        description
          "Rollback the installed software to a previous revision and apply the change";
        input {
          leaf transaction-id {
            type uint32;
            mandatory true;
            description
              "Transaction ID to rollback to";
          }
          leaf commit {
            type boolean;
            default "false";
            description
              "Commit at the end of the rollback operation, if the
               software is successfully applied";
          }
          leaf activation-type {
            type install-act:ncs_rpc_notif_apply-type;
            default "least-impactful";
            description
              "Activate the software using the specified apply type";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-rollback {
      tailf:ncs-device-type "netconf";
      tailf:display-when "/ncs:devices/ncs:device[ncs:name=current()/../../../ncs:member]/ncs:module[ncs:name='Cisco-IOS-XR-install-augmented-act']";
      tailf:action install-rollback {
        tailf:actionpoint ncsproxy {
          tailf:internal;
        }
        description
          "Rollback the installed software to a previous revision and apply the change";
        input {
          leaf transaction-id {
            type uint32;
            mandatory true;
            description
              "Transaction ID to rollback to";
          }
          leaf commit {
            type boolean;
            default "false";
            description
              "Commit at the end of the rollback operation, if the
               software is successfully applied";
          }
          leaf activation-type {
            type install-act:ncs_rpc_notif_apply-type;
            default "least-impactful";
            description
              "Activate the software using the specified apply type";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-package-rollback {
      tailf:ncs-device-type "netconf";
      tailf:display-when "not(../../ncs:module) or ../../ncs:module[ncs:name='Cisco-IOS-XR-install-augmented-act']";
      tailf:action install-package-rollback {
        tailf:actionpoint ncsproxy {
          tailf:internal;
        }
        description
          "Rollback the installed software to a previous revision";
        input {
          leaf transaction-id {
            type uint32;
            mandatory true;
            description
              "Transaction ID to rollback to";
          }
        }
        output {
          uses ncs_rpc_notif_INST-AUGMENTED-OP-ID-TYPE;
        }
        csc:xr-task "pkg-mgmt";
        csc:cli-command "install package rollback <transaction-id>";
      }
    }
  }
  augment "/ncs:devices/ncs:device-group/ncs:ned-id/ncs:rpc" {
    container rpc-install-package-rollback {
      tailf:ncs-device-type "netconf";
      tailf:display-when "/ncs:devices/ncs:device[ncs:name=current()/../../../ncs:member]/ncs:module[ncs:name='Cisco-IOS-XR-install-augmented-act']";
      tailf:action install-package-rollback {
        tailf:actionpoint ncsproxy {
          tailf:internal;
        }
        description
          "Rollback the installed software to a previous revision";
        input {
          leaf transaction-id {
            type uint32;
            mandatory true;
            description
              "Transaction ID to rollback to";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
        csc:cli-command "install package rollback <transaction-id>";
      }
    }
  }
  augment "/ncs:devices/ncs:device/ncs:rpc" {
    container rpc-install-package-replace {
      tailf:ncs-device-type "netconf";
      tailf:display-when "not(../../ncs:module) or ../../ncs:module[ncs:name='Cisco-IOS-XR-install-augmented-act']";
      tailf:action install-package-replace {
        tailf:actionpoint ncsproxy {
          tailf:internal;
        }
        description
          "Replace the current installed software";
        input {
          leaf source-type {
            type install-act:ncs_rpc_notif_replace-source-type;
            default "local";
            description
              "Type of source used to obtain the ISO";
          }
          leaf source {
            type string;
            mandatory true;
            description
              "Path to the location of the ISO";
          }
          leaf file {
            type string;
            mandatory true;
            description
              "Name of the ISO to install";
          }
        }
        output {
          uses ncs_rpc_notif_INST-AUGMENTED-OP-ID-TYPE;
        }
        csc:xr-task "pkg-mgmt";
        csc:cli-command "install package replace <iso>";
      }
    }
  }
  augment "/ncs:devices/ncs:device-group/ncs:ned-id/ncs:rpc" {
    container rpc-install-package-replace {
      tailf:ncs-device-type "netconf";
      tailf:display-when "/ncs:devices/ncs:device[ncs:name=current()/../../../ncs:member]/ncs:module[ncs:name='Cisco-IOS-XR-install-augmented-act']";
      tailf:action install-package-replace {
        tailf:actionpoint ncsproxy {
          tailf:internal;
        }
        description
          "Replace the current installed software";
        input {
          leaf source-type {
            type install-act:ncs_rpc_notif_replace-source-type;
            default "local";
            description
              "Type of source used to obtain the ISO";
          }
          leaf source {
            type string;
            mandatory true;
            description
              "Path to the location of the ISO";
          }
          leaf file {
            type string;
            mandatory true;
            description
              "Name of the ISO to install";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
        csc:cli-command "install package replace <iso>";
      }
    }
  }
  augment "/ncs:devices/ncs:device/ncs:rpc" {
    container rpc-install-package-downgrade {
      tailf:ncs-device-type "netconf";
      tailf:display-when "not(../../ncs:module) or ../../ncs:module[ncs:name='Cisco-IOS-XR-install-augmented-act']";
      tailf:action install-package-downgrade {
        tailf:actionpoint ncsproxy {
          tailf:internal;
        }
        description
          "Downgrade all packages in a specified source, or the given list of
           packages";
        input {
          container packages {
            description
              "List of packages to downgrade, or empty to downgrade all packages
               in a specified source";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-package-downgrade {
      tailf:ncs-device-type "netconf";
      tailf:display-when "/ncs:devices/ncs:device[ncs:name=current()/../../../ncs:member]/ncs:module[ncs:name='Cisco-IOS-XR-install-augmented-act']";
      tailf:action install-package-downgrade {
        tailf:actionpoint ncsproxy {
          tailf:internal;
        }
        description
          "Downgrade all packages in a specified source, or the given list of
           packages";
        input {
          container packages {
            description
              "List of packages to downgrade, or empty to downgrade all packages
               in a specified source";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-package-upgrade {
      tailf:ncs-device-type "netconf";
      tailf:display-when "not(../../ncs:module) or ../../ncs:module[ncs:name='Cisco-IOS-XR-install-augmented-act']";
      tailf:action install-package-upgrade {
        tailf:actionpoint ncsproxy {
          tailf:internal;
        }
        description
          "Upgrade all packages, or the given list of packages";
        input {
          container packages {
            description
              "List of packages to upgrade, or empty to upgrade all packages";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-package-upgrade {
      tailf:ncs-device-type "netconf";
      tailf:display-when "/ncs:devices/ncs:device[ncs:name=current()/../../../ncs:member]/ncs:module[ncs:name='Cisco-IOS-XR-install-augmented-act']";
      tailf:action install-package-upgrade {
        tailf:actionpoint ncsproxy {
          tailf:internal;
        }
        description
          "Upgrade all packages, or the given list of packages";
        input {
          container packages {
            description
              "List of packages to upgrade, or empty to upgrade all packages";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-package-remove {
      tailf:ncs-device-type "netconf";
      tailf:display-when "not(../../ncs:module) or ../../ncs:module[ncs:name='Cisco-IOS-XR-install-augmented-act']";
      tailf:action install-package-remove {
        tailf:actionpoint ncsproxy {
          tailf:internal;
        }
        description
          "Remove the given list of packages";
        input {
          container packages {
            description
              "List of packages to remove";
            leaf-list packagename {
              type string;
              description
                "package name";
            }
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-package-remove {
      tailf:ncs-device-type "netconf";
      tailf:display-when "/ncs:devices/ncs:device[ncs:name=current()/../../../ncs:member]/ncs:module[ncs:name='Cisco-IOS-XR-install-augmented-act']";
      tailf:action install-package-remove {
        tailf:actionpoint ncsproxy {
          tailf:internal;
        }
        description
          "Remove the given list of packages";
        input {
          container packages {
            description
              "List of packages to remove";
            leaf-list packagename {
              type string;
              description
                "package name";
            }
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
  augment "/ncs:devices/ncs:device/ncs:rpc" {
    container rpc-install-package-add {
      tailf:ncs-device-type "netconf";
      tailf:display-when "not(../../ncs:module) or ../../ncs:module[ncs:name='Cisco-IOS-XR-install-augmented-act']";
      tailf:action install-package-add {
        tailf:actionpoint ncsproxy {
          tailf:internal;
        }
        description
          "Add all packages in a specified source, or the given list of packages";
        input {
          container packages {
            description
              "List of packages to add, or empty to add all packages";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          uses ncs_rpc_notif_INST-AUGMENTED-OP-ID-TYPE;
        }
        csc:xr-task "pkg-mgmt";
      }
    }
  }
  augment "/ncs:devices/ncs:device-group/ncs:ned-id/ncs:rpc" {
    container rpc-install-package-add {
      tailf:ncs-device-type "netconf";
      tailf:display-when "/ncs:devices/ncs:device[ncs:name=current()/../../../ncs:member]/ncs:module[ncs:name='Cisco-IOS-XR-install-augmented-act']";
      tailf:action install-package-add {
        tailf:actionpoint ncsproxy {
          tailf:internal;
        }
        description
          "Add all packages in a specified source, or the given list of packages";
        input {
          container packages {
            description
              "List of packages to add, or empty to add all packages";
            leaf-list packagename {
              type string;
              description
                "package name";
            }
          }
          leaf source-type {
            type install-act:ncs_rpc_notif_packages-source-type;
            default "any-configured-repository";
            description
              "Type of source used to obtain the packages";
          }
          leaf source {
            type string;
            description
              "Path to the location of the packages.  If source-type is
               'any-configured-repository' this field is unused, and if
               source-type is 'configured-repository' this should be the
               name of the repository to use.";
          }
        }
        output {
          container "device" {
            leaf "name" {
              type string;
            }
            leaf "info" {
              type string;
            }
            container "result" {
              uses ncs_rpc_notif_INST-AUGMENTED-OP-ID-TYPE;
            }
          }
        }
        csc:xr-task "pkg-mgmt";
      }
    }
  }
}

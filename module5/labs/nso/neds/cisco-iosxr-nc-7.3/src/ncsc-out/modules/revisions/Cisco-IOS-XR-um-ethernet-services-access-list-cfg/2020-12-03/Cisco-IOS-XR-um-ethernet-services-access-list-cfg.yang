module Cisco-IOS-XR-um-ethernet-services-access-list-cfg {
  // Generated by yanger -t ncs
  tailf:mount-id "cisco-iosxr-nc-7.3:cisco-iosxr-nc-7.3";
  tailf:ncs-device-type "netconf";

  namespace "http://cisco.com/ns/yang/Cisco-IOS-XR-um-ethernet-services-access-list-cfg";
  prefix um-es-acl-cfg;

  import cisco-semver {
    prefix semver;
  }
  import ietf-yang-types {
    prefix yang;
  }
  import Cisco-IOS-XR-types {
    prefix xr2;
  }
  import Cisco-IOS-XR-um-access-list-datatypes {
    prefix um-acl-types;
  }
  import tailf-common {
    prefix tailf;
  }
  import tailf-ncs {
    prefix ncs;
  }

  organization
    "Cisco Systems, Inc.";
  contact
    "
     Cisco Systems, Inc.
     Customer Service

     Postal: 170 W Tasman Drive
     San Jose, CA 95134

     Tel: +1 1800 553-NETS

     E-mail: cs-yang@cisco.com
    ";
  description
    "
     This module contains a collection of IOS-XR YANG model derived from CLI.

     Copyright (c) 2019-2020 by Cisco Systems, Inc.
     All rights reserved.
    ";

  revision 2020-12-03 {
    description
      "Limit length of remark string";
    semver:module-version "1.0.0";
  }
  revision 2019-06-10 {
    description
      "Establish semantic version baseline.";
    semver:module-version "1.0.0";
  }
  revision 2019-04-01 {
    description
      "Initial version";
  }

  grouping ncs_template_source-address {
    leaf mac-address {
      type string;
      description
        "48-bit source MAC address";
    }
    leaf mac-address-mask {
      type string;
      description
        "48-bit source wildcard bits";
    }
    container any {
      presence "Any source host";
      description
        "Any host";
    }
    leaf host {
      type string;
      description
        "A single source host";
    }
  }

  grouping ncs_template_destination-address {
    leaf mac-address {
      type string;
      description
        "48-bit destination MAC address";
    }
    leaf mac-address-mask {
      type string;
      description
        "48-bit destination wildcard bits";
    }
    container any {
      presence "Any destination host";
      description
        "Any host";
    }
    leaf host {
      type string;
      description
        "A single destination host";
    }
  }

  grouping ncs_template_ethertype {
    leaf ethernet-type {
      type xr2:ncs_template_Hex-integer-16;
      description
        "An Ethertype Number";
    }
  }

  grouping ncs_template_match-option-common {
    container capture {
      // NCS drop if-feature statement
      presence "Capture matched packet";
      description
        "Capture matched packet";
    }
    container log {
      // NCS drop if-feature statement
      presence "Log matches against this entry";
      description
        "Log matches against this entry";
    }
  }

  grouping ncs_template_ace-common {
    container source {
      // NCS drop must statement
      uses ncs_template_source-address;
    }
    container destination {
      // NCS drop must statement
      uses ncs_template_destination-address;
    }
    leaf vlan {
      type um-acl-types:ncs_template_vlan-id;
      description
        "a vlan id or range of vlan ids";
    }
    leaf inner-vlan {
      type um-acl-types:ncs_template_vlan-id;
      description
        "A vlan id or range of vlan ids of the Inner Header";
    }
    leaf cos {
      type string;
      description
        "Class of Service";
    }
    leaf inner-cos {
      type string;
      description
        "Class of Service of Inner Header";
    }
    container dei {
      presence "Discard Eligibility Indication";
      description
        "Discard Eligibility Indication";
    }
    container inner-dei {
      presence "Discard Eligibility Indication for Inner Header";
      description
        "Discard Eligibility Indication for Inner Header";
    }
  }

  grouping ncs_rpc_notif_source-address {
    leaf mac-address {
      type yang:mac-address;
      description
        "48-bit source MAC address";
    }
    leaf mac-address-mask {
      type yang:mac-address;
      description
        "48-bit source wildcard bits";
    }
    container any {
      presence "Any source host";
      description
        "Any host";
    }
    leaf host {
      type yang:mac-address;
      description
        "A single source host";
    }
  }

  grouping ncs_rpc_notif_destination-address {
    leaf mac-address {
      type yang:mac-address;
      description
        "48-bit destination MAC address";
    }
    leaf mac-address-mask {
      type yang:mac-address;
      description
        "48-bit destination wildcard bits";
    }
    container any {
      presence "Any destination host";
      description
        "Any host";
    }
    leaf host {
      type yang:mac-address;
      description
        "A single destination host";
    }
  }

  grouping ncs_rpc_notif_ethertype {
    leaf ethernet-type {
      type xr2:ncs_rpc_notif_Hex-integer-16;
      description
        "An Ethertype Number";
    }
  }

  grouping ncs_rpc_notif_match-option-common {
    container capture {
      tailf:display-when "not(../ncs:module) or boolean(/ncs:devices/ncs:device[ncs:name=current()/../ncs:name]/capability/feature='es_acl_capture_implemented')";
      presence "Capture matched packet";
      description
        "Capture matched packet";
    }
    container log {
      tailf:display-when "not(../ncs:module) or boolean(/ncs:devices/ncs:device[ncs:name=current()/../ncs:name]/capability/feature='es_acl_log_option_supported')";
      presence "Log matches against this entry";
      description
        "Log matches against this entry";
    }
  }

  grouping ncs_rpc_notif_ace-common {
    container source {
      must '(mac-address and mac-address-mask) or any or host' {
        tailf:xpath-root 3;
      }
      uses ncs_rpc_notif_source-address;
    }
    container destination {
      must '(mac-address and mac-address-mask) or any or host' {
        tailf:xpath-root 3;
      }
      uses ncs_rpc_notif_destination-address;
    }
    leaf vlan {
      type um-acl-types:ncs_rpc_notif_vlan-id;
      description
        "a vlan id or range of vlan ids";
    }
    leaf inner-vlan {
      type um-acl-types:ncs_rpc_notif_vlan-id;
      description
        "A vlan id or range of vlan ids of the Inner Header";
    }
    leaf cos {
      type uint8 {
        range "0..7" {
          description
            "CoS value for this entry";
        }
      }
      description
        "Class of Service";
    }
    leaf inner-cos {
      type uint8 {
        range "0..7" {
          description
            "CoS value for the Inner Header";
        }
      }
      description
        "Class of Service of Inner Header";
    }
    container dei {
      presence "Discard Eligibility Indication";
      description
        "Discard Eligibility Indication";
    }
    container inner-dei {
      presence "Discard Eligibility Indication for Inner Header";
      description
        "Discard Eligibility Indication for Inner Header";
    }
  }

  grouping live_ncs_source-address {
    leaf mac-address {
      type yang:mac-address;
      description
        "48-bit source MAC address";
    }
    leaf mac-address-mask {
      type yang:mac-address;
      description
        "48-bit source wildcard bits";
    }
    container any {
      presence "Any source host";
      description
        "Any host";
    }
    leaf host {
      type yang:mac-address;
      description
        "A single source host";
    }
  }

  grouping live_ncs_destination-address {
    leaf mac-address {
      type yang:mac-address;
      description
        "48-bit destination MAC address";
    }
    leaf mac-address-mask {
      type yang:mac-address;
      description
        "48-bit destination wildcard bits";
    }
    container any {
      presence "Any destination host";
      description
        "Any host";
    }
    leaf host {
      type yang:mac-address;
      description
        "A single destination host";
    }
  }

  grouping live_ncs_ethertype {
    leaf ethernet-type {
      type xr2:live_ncs_Hex-integer-16;
      description
        "An Ethertype Number";
    }
  }

  grouping live_ncs_match-option-common {
    container capture {
      // NCS drop if-feature statement
      presence "Capture matched packet";
      description
        "Capture matched packet";
    }
    container log {
      // NCS drop if-feature statement
      presence "Log matches against this entry";
      description
        "Log matches against this entry";
    }
  }

  grouping live_ncs_ace-common {
    container source {
      // NCS drop must statement
      uses live_ncs_source-address;
    }
    container destination {
      // NCS drop must statement
      uses live_ncs_destination-address;
    }
    leaf vlan {
      type um-acl-types:live_ncs_vlan-id;
      description
        "a vlan id or range of vlan ids";
    }
    leaf inner-vlan {
      type um-acl-types:live_ncs_vlan-id;
      description
        "A vlan id or range of vlan ids of the Inner Header";
    }
    leaf cos {
      type uint8 {
        range "0..7" {
          description
            "CoS value for this entry";
        }
      }
      description
        "Class of Service";
    }
    leaf inner-cos {
      type uint8 {
        range "0..7" {
          description
            "CoS value for the Inner Header";
        }
      }
      description
        "Class of Service of Inner Header";
    }
    container dei {
      presence "Discard Eligibility Indication";
      description
        "Discard Eligibility Indication";
    }
    container inner-dei {
      presence "Discard Eligibility Indication for Inner Header";
      description
        "Discard Eligibility Indication for Inner Header";
    }
  }

  grouping source-address {
    leaf mac-address {
      type yang:mac-address;
      description
        "48-bit source MAC address";
    }
    leaf mac-address-mask {
      type yang:mac-address;
      description
        "48-bit source wildcard bits";
    }
    container any {
      presence "Any source host";
      description
        "Any host";
    }
    leaf host {
      type yang:mac-address;
      description
        "A single source host";
    }
  }

  grouping destination-address {
    leaf mac-address {
      type yang:mac-address;
      description
        "48-bit destination MAC address";
    }
    leaf mac-address-mask {
      type yang:mac-address;
      description
        "48-bit destination wildcard bits";
    }
    container any {
      presence "Any destination host";
      description
        "Any host";
    }
    leaf host {
      type yang:mac-address;
      description
        "A single destination host";
    }
  }

  grouping ethertype {
    leaf ethernet-type {
      type xr2:Hex-integer-16;
      description
        "An Ethertype Number";
    }
  }

  grouping match-option-common {
    container capture {
      tailf:display-when "not(../ncs:module) or boolean(/ncs:devices/ncs:device[ncs:name=current()/../ncs:name]/capability/feature='es_acl_capture_implemented')";
      presence "Capture matched packet";
      description
        "Capture matched packet";
    }
    container log {
      tailf:display-when "not(../ncs:module) or boolean(/ncs:devices/ncs:device[ncs:name=current()/../ncs:name]/capability/feature='es_acl_log_option_supported')";
      presence "Log matches against this entry";
      description
        "Log matches against this entry";
    }
  }

  grouping ace-common {
    container source {
      must '(mac-address and mac-address-mask) or any or host' {
        tailf:xpath-root 3;
      }
      uses source-address;
    }
    container destination {
      must '(mac-address and mac-address-mask) or any or host' {
        tailf:xpath-root 3;
      }
      uses destination-address;
    }
    leaf vlan {
      type um-acl-types:vlan-id;
      description
        "a vlan id or range of vlan ids";
    }
    leaf inner-vlan {
      type um-acl-types:vlan-id;
      description
        "A vlan id or range of vlan ids of the Inner Header";
    }
    leaf cos {
      type uint8 {
        range "0..7" {
          description
            "CoS value for this entry";
        }
      }
      description
        "Class of Service";
    }
    leaf inner-cos {
      type uint8 {
        range "0..7" {
          description
            "CoS value for the Inner Header";
        }
      }
      description
        "Class of Service of Inner Header";
    }
    container dei {
      presence "Discard Eligibility Indication";
      description
        "Discard Eligibility Indication";
    }
    container inner-dei {
      presence "Discard Eligibility Indication for Inner Header";
      description
        "Discard Eligibility Indication for Inner Header";
    }
  }

  augment "/ncs:devices/ncs:device/ncs:config" {
    container ethernet-services {
      tailf:ncs-device-type "netconf";
      tailf:display-when "not(../../ncs:module) or ../../ncs:module[ncs:name='Cisco-IOS-XR-um-ethernet-services-access-list-cfg']";
      tailf:display-when "not(../ncs:module) or boolean(/ncs:devices/ncs:device[ncs:name=current()/../ncs:name]/capability/feature='es_acl_supported')";
      description
        "Configure ethernet-services access-list";
      container access-list-options {
        container log-update {
          description
            "Control access lists log updates";
          leaf threshold {
            type uint32 {
              range "1..2147483647" {
                description
                  "Log update threshold (number of hits)";
              }
            }
            description
              "Set access-list logging threshold";
          }
        }
      }
      container access-lists {
        description
          "Access-lists";
        list access-list {
          key "access-list-name";
          description
            "Access-list configuration";
          leaf access-list-name {
            type string {
              length "1..64";
            }
            description
              "Access list name - maximum 64 characters";
          }
          container sequences {
            description
              "Access list entries";
            list sequence {
              must 'deny or permit or remark' {
                tailf:xpath-root 3;
              }
              key "sequence-number";
              description
                "access list entry";
              leaf sequence-number {
                type uint32 {
                  range "1..2147483643";
                }
                description
                  "Sequence number for this entry";
              }
              container deny {
                must 'source and destination' {
                  tailf:xpath-root 3;
                }
                presence "Grant type Deny";
                uses ace-common;
                uses match-option-common;
              }
              container permit {
                must 'source and destination' {
                  tailf:xpath-root 3;
                }
                presence "Grant type Permit";
                uses ace-common;
                uses match-option-common;
              }
              leaf remark {
                type string {
                  length "0..255";
                }
                description
                  "Comment for access list";
              }
            }
          }
        }
      }
    }
  }
  augment "/ncs:devices/ncs:device/ncs:live-status" {
    container ethernet-services {
      tailf:ncs-device-type "netconf";
      tailf:display-when "not(../../ncs:module) or ../../ncs:module[ncs:name='Cisco-IOS-XR-um-ethernet-services-access-list-cfg'] or (../../ncs:live-status-protocol[not(ncs:capability)]) or (../../ncs:live-status-protocol/ncs:capability/ncs:module[.='Cisco-IOS-XR-um-ethernet-services-access-list-cfg'])";
      // NCS drop if-feature statement
      description
        "Configure ethernet-services access-list";
      container access-list-options {
        container log-update {
          description
            "Control access lists log updates";
          leaf threshold {
            type uint32 {
              range "1..2147483647" {
                description
                  "Log update threshold (number of hits)";
              }
            }
            description
              "Set access-list logging threshold";
          }
        }
      }
      container access-lists {
        description
          "Access-lists";
        list access-list {
          key "access-list-name";
          description
            "Access-list configuration";
          leaf access-list-name {
            type string {
              length "1..64";
            }
            description
              "Access list name - maximum 64 characters";
          }
          container sequences {
            description
              "Access list entries";
            list sequence {
              // NCS drop must statement
              key "sequence-number";
              description
                "access list entry";
              leaf sequence-number {
                type uint32 {
                  range "1..2147483643";
                }
                description
                  "Sequence number for this entry";
              }
              container deny {
                // NCS drop must statement
                presence "Grant type Deny";
                uses live_ncs_ace-common;
                uses live_ncs_match-option-common;
              }
              container permit {
                // NCS drop must statement
                presence "Grant type Permit";
                uses live_ncs_ace-common;
                uses live_ncs_match-option-common;
              }
              leaf remark {
                type string {
                  length "0..255";
                }
                description
                  "Comment for access list";
              }
            }
          }
        }
      }
    }
  }
  augment "/ncs:devices/ncs:template/ncs:ned-id/ncs:config" {
    container ethernet-services {
      // NCS drop if-feature statement
      description
        "Configure ethernet-services access-list";
      container access-list-options {
        container log-update {
          description
            "Control access lists log updates";
          leaf threshold {
            type string;
            description
              "Set access-list logging threshold";
          }
        }
      }
      container access-lists {
        description
          "Access-lists";
        list access-list {
          // NCS patched for predictable order
          ordered-by user;
          key "access-list-name";
          description
            "Access-list configuration";
          leaf access-list-name {
            type string;
            description
              "Access list name - maximum 64 characters";
          }
          container sequences {
            description
              "Access list entries";
            list sequence {
              // NCS patched for predictable order
              ordered-by user;
              // NCS drop must statement
              key "sequence-number";
              description
                "access list entry";
              leaf sequence-number {
                type string;
                description
                  "Sequence number for this entry";
              }
              container deny {
                // NCS drop must statement
                presence "Grant type Deny";
                uses ncs_template_ace-common;
                uses ncs_template_match-option-common;
              }
              container permit {
                // NCS drop must statement
                presence "Grant type Permit";
                uses ncs_template_ace-common;
                uses ncs_template_match-option-common;
              }
              leaf remark {
                type string;
                description
                  "Comment for access list";
              }
            }
          }
        }
      }
    }
  }

  feature es_acl_log_option_supported {
    description
      "Log matches against access-list entry";
  }

  feature es_acl_capture_implemented {
    description
      "Capture matched packet";
  }

  feature es_acl_supported {
    description
      "Access list for ethernet services";
  }
}

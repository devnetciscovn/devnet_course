module Cisco-IOS-XR-man-http-lighttpd-yang-cfg {
  // Generated by yanger -t ncs
  tailf:mount-id "cisco-iosxr-nc-7.3:cisco-iosxr-nc-7.3";
  tailf:ncs-device-type "netconf";

  namespace "http://cisco.com/ns/yang/Cisco-IOS-XR-man-http-lighttpd-yang-cfg";
  prefix man-http-lighttpd-yang-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-http-lighttpd-yang package configuration.

     This module contains definitions
     for the following management objects:
       web: Webserver configuration commands

     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2015-11-09 {
    description
      "IOS XR 6.0 revision.";
  }

  augment "/ncs:devices/ncs:device/ncs:config" {
    container web {
      tailf:ncs-device-type "netconf";
      tailf:display-when "not(../../ncs:module) or ../../ncs:module[ncs:name='Cisco-IOS-XR-man-http-lighttpd-yang-cfg']";
      description
        "Webserver configuration commands";
      container server {
        description
          "Webserver configuration commands";
        container service {
          description
            "Web Service that needs to be activated";
          container restconf {
            presence "Indicates a restconf node is configured.";
            description
              "Restconf specific configurations";
            leaf http-port {
              type uint32;
              description
                "Port number http server is listening on";
            }
            leaf http-enable {
              type empty;
              description
                "Enable http connection in addition to https";
            }
            leaf https-port {
              type uint32;
              description
                "Port number https server is listening on";
            }
            leaf enable {
              type empty;
              mandatory true;
              description
                "Enable RESTCONF Service";
            }
          }
        }
      }
    }
  }
  augment "/ncs:devices/ncs:device/ncs:live-status" {
    container web {
      tailf:ncs-device-type "netconf";
      tailf:display-when "not(../../ncs:module) or ../../ncs:module[ncs:name='Cisco-IOS-XR-man-http-lighttpd-yang-cfg'] or (../../ncs:live-status-protocol[not(ncs:capability)]) or (../../ncs:live-status-protocol/ncs:capability/ncs:module[.='Cisco-IOS-XR-man-http-lighttpd-yang-cfg'])";
      description
        "Webserver configuration commands";
      container server {
        description
          "Webserver configuration commands";
        container service {
          description
            "Web Service that needs to be activated";
          container restconf {
            presence "Indicates a restconf node is configured.";
            description
              "Restconf specific configurations";
            leaf http-port {
              type uint32;
              description
                "Port number http server is listening on";
            }
            leaf http-enable {
              type empty;
              description
                "Enable http connection in addition to https";
            }
            leaf https-port {
              type uint32;
              description
                "Port number https server is listening on";
            }
            leaf enable {
              type empty;
              // NCS drop mandatory statement
              description
                "Enable RESTCONF Service";
            }
          }
        }
      }
    }
  }
  augment "/ncs:devices/ncs:template/ncs:ned-id/ncs:config" {
    container web {
      description
        "Webserver configuration commands";
      container server {
        description
          "Webserver configuration commands";
        container service {
          description
            "Web Service that needs to be activated";
          container restconf {
            presence "Indicates a restconf node is configured.";
            description
              "Restconf specific configurations";
            leaf http-port {
              type string;
              description
                "Port number http server is listening on";
            }
            leaf http-enable {
              type empty;
              description
                "Enable http connection in addition to https";
            }
            leaf https-port {
              type string;
              description
                "Port number https server is listening on";
            }
            leaf enable {
              type empty;
              // NCS drop mandatory statement
              description
                "Enable RESTCONF Service";
            }
          }
        }
      }
    }
  }
}

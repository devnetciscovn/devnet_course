module Cisco-IOS-XR-controller-optics-oper {
  // Generated by yanger -t ncs
  tailf:mount-id "cisco-iosxr-nc-7.3:cisco-iosxr-nc-7.3";
  tailf:ncs-device-type "netconf";

  namespace "http://cisco.com/ns/yang/Cisco-IOS-XR-controller-optics-oper";
  prefix controller-optics-oper;

  import Cisco-IOS-XR-types {
    prefix xr;
  }
  import cisco-semver {
    prefix semver;
  }
  include Cisco-IOS-XR-controller-optics-oper-sub1 {
    revision-date 2021-06-22;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-optics package operational data.

     This module contains definitions
     for the following management objects:
       optics-oper: Optics operational data

     Copyright (c) 2013-2021 by Cisco Systems, Inc.
     All rights reserved.";

  revision 2021-06-22 {
    description
      "New Enum added for QSFP 100G 4W10I
       2021-05-27
         DAC rate and Laser temperature and laser age Added for Optics Controller
       2021-04-14
         New Enums added for Multirate Optics Phy type
       2021-02-23
         enum added for new Optics Phy Type for 400G LR4 module
       2021-02-19
         enum added for 1 new Optics Phy Type and new value added to enum EthernetPmdType
       2021-02-17
         New OPTICS_ETH_100GBASE_DR_S added to enum EthernetPmdType";
    semver:module-version "5.0.0";
  }
  revision 2020-12-23 {
    description
      "New value added to enum EthernetPmdType
       2020-11-18
       Enum value in optics_modulation_type is changed from MODE_16QAM_32QAM to MOD_16QAM_32QAM
       2020-11-10
       enum added for 1 new Optics Phy Type for 100G DR-S optics module
       2020-09-10
       removed optics_edm_fastpoll_info and added new bag optics_edm_fastpoll_data
       2020-08-02
       New values added to enum FiberConnectorType
       2020-07-24
       New value added in optics yang for FastPollInfo
       2020-07-14
       New value added to enum EthernetPmdType";
    semver:module-version "4.0.0";
  }
  revision 2020-04-26 {
    description
      "New value added to enum EthernetPmdType
       2020-02-24
       enum added for OTN Application code.
       2020-02-19
       enum added for 1 new Optics Phy Type
       2020-01-31
       enum added for 1 new Optics Phy Type
       2020-01-27
       Added new parameters in optics bag to display parameters which are not configurable
       2019-12-05
       enum added for 2 new OTN Application codes.
       2019-11-30
       Back Reflection data field is added in bag.
       2019-09-30
       chan_num data field is added to support L-Band frequency range.";
    semver:module-version "3.0.0";
  }
  revision 2019-04-05 {
    description
      "Establish semantic version baseline.";
    semver:module-version "2.0.0";
  }
  revision 2017-09-07 {
    description
      "Fixed type translation error.";
  }
  revision 2017-05-01 {
    description
      "Fixing backward compatibility error in module.";
  }
  revision 2015-11-09 {
    description
      "IOS XR 6.0 revision.";
  }

  augment "/ncs:devices/ncs:device/ncs:config" {
    // NCS drop config false container 'optics-oper'
  }
  augment "/ncs:devices/ncs:device/ncs:live-status" {
    container optics-oper {
      tailf:ncs-device-type "netconf";
      tailf:display-when "not(../../ncs:module) or ../../ncs:module[ncs:name='Cisco-IOS-XR-controller-optics-oper'] or (../../ncs:live-status-protocol[not(ncs:capability)]) or (../../ncs:live-status-protocol/ncs:capability/ncs:module[.='Cisco-IOS-XR-controller-optics-oper'])";
      description
        "Optics operational data";
      container optics-ports {
        description
          "All Optics Port operational data";
        list optics-port {
          key "name";
          description
            "Optics operational data";
          container optics-dwdm-carrier-channel-map {
            description
              "Optics operational data";
            uses live_ncs_OPTICS-EDM-WAVE-INFO;
          }
          container ots-spectrum-info {
            description
              "Ots Spectrum Operational data";
            uses live_ncs_OPTICS-EDM-SPECTRUM-INFO;
          }
          container optics-dwdm-carrier-channel-map-flexi {
            description
              "Optics operational data";
            uses live_ncs_OPTICS-EDM-WAVE-INFO;
          }
          container optics-info {
            description
              "Optics operational data";
            uses live_ncs_OPTICS-EDM-INFO;
          }
          container optics-fastpolls {
            description
              "All Optics Fastpoll operational data";
            list optics-fastpoll {
              key "unique-id";
              description
                "Fastpoll Information";
              leaf unique-id {
                type uint32;
                description
                  "Fastpoll Index";
              }
              uses live_ncs_OPTICS-EDM-FASTPOLL-DATA;
            }
          }
          container optics-lanes {
            description
              "All Optics Port operational data";
            list optics-lane {
              key "number";
              description
                "Lane Information";
              leaf number {
                type uint32;
                description
                  "Lane Index";
              }
              uses live_ncs_OPTICS-EDM-LANE-DATA;
            }
          }
          container optics-db-info {
            description
              "Optics operational data";
            uses live_ncs_OPTICS-DB-INFO;
          }
          leaf name {
            type xr:live_ncs_Interface-name;
            description
              "Port name";
          }
        }
      }
    }
  }
  augment "/ncs:devices/ncs:template/ncs:ned-id/ncs:config" {
    // NCS drop config false container 'optics-oper'
  }
}

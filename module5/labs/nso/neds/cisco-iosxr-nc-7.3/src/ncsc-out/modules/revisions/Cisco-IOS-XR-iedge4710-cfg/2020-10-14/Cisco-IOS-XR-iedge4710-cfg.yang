module Cisco-IOS-XR-iedge4710-cfg {
  // Generated by yanger -t ncs
  tailf:mount-id "cisco-iosxr-nc-7.3:cisco-iosxr-nc-7.3";
  tailf:ncs-device-type "netconf";

  namespace "http://cisco.com/ns/yang/Cisco-IOS-XR-iedge4710-cfg";
  prefix iedge4710-cfg;

  import Cisco-IOS-XR-types {
    prefix xr;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR iedge4710 package configuration.

     This module contains definitions
     for the following management objects:
       subscriber-manager: iEdge subscriber manager configuration
       subscriber-featurette: iEdge subscriber featurette
         configuration
       iedge-license-manager: Session License Manager Configuration
       sub-manager: iEdge subscriber manager configuration

     This YANG module augments the
       Cisco-IOS-XR-ifmgr-cfg
     module with configuration data.

     Copyright (c) 2013-2020 by Cisco Systems, Inc.
     All rights reserved.";

  revision 2020-10-14 {
    description
      "added srg acct start time.";
    semver:module-version "1.1.0";
  }
  revision 2019-04-05 {
    description
      "Establish semantic version baseline.";
    semver:module-version "1.0.1";
  }
  revision 2017-09-07 {
    description
      "Fixed type translation error.";
  }
  revision 2015-11-09 {
    description
      "IOS XR 6.0 revision.";
  }

  augment "/ncs:devices/ncs:device/ncs:config" {
    container subscriber-manager {
      tailf:ncs-device-type "netconf";
      tailf:display-when "not(../../ncs:module) or ../../ncs:module[ncs:name='Cisco-IOS-XR-iedge4710-cfg']";
      description
        "iEdge subscriber manager configuration";
      container accounting {
        description
          "iEdge accounting feature";
        container send-stop {
          description
            "Accounting send stop feature";
          container setup-failure {
            description
              "Setup failure feature";
            leaf method-list-name {
              type string;
              description
                "AAA List name either default or preconfigured";
            }
          }
        }
        container interim {
          description
            "interim accounting related";
          container variation {
            description
              "variation of first session or service interim
               record from configured timeout";
            leaf maximum-percentage-variation {
              type uint32 {
                range "0..50";
              }
              units "percentage";
              description
                "maximum percentage variation (maximum
                 absolute variation is 15 minutes)";
            }
          }
        }
      }
      container srg {
        description
          "SRG specific config";
        leaf account-start-time {
          type empty;
          description
            "acct start time ref to srg role change slave to
             master";
        }
        leaf sync-account-session-id {
          type empty;
          description
            "sync account session id from master to slave";
        }
      }
    }
    container subscriber-featurette {
      tailf:ncs-device-type "netconf";
      tailf:display-when "not(../../ncs:module) or ../../ncs:module[ncs:name='Cisco-IOS-XR-iedge4710-cfg']";
      description
        "iEdge subscriber featurette configuration";
      list featurette-name {
        key "featurette";
        description
          "enable featurette processing";
        leaf enable {
          type uint32;
          description
            "instance of featurette";
        }
        leaf featurette {
          type xr:Cisco-ios-xr-string;
          description
            "subscriber feature";
        }
      }
    }
    container iedge-license-manager {
      tailf:ncs-device-type "netconf";
      tailf:display-when "not(../../ncs:module) or ../../ncs:module[ncs:name='Cisco-IOS-XR-iedge4710-cfg']";
      description
        "Session License Manager Configuration";
      leaf session-limit {
        type uint32 {
          range "1..200000";
        }
        description
          "Session limit configured on linecard";
      }
    }
    container sub-manager {
      tailf:ncs-device-type "netconf";
      tailf:display-when "not(../../ncs:module) or ../../ncs:module[ncs:name='Cisco-IOS-XR-iedge4710-cfg']";
      description
        "iEdge subscriber manager configuration";
      list location {
        key "location1";
        description
          "Select location";
        container trace {
          description
            "Subscriber manager trace";
          leaf trace-level {
            type uint32;
            description
              "Subscriber manager trace level";
          }
        }
        leaf history {
          type empty;
          description
            "Disable history for subscriber manager";
        }
        leaf location1 {
          type xr:Cisco-ios-xr-string;
          description
            "Specify location";
        }
      }
    }
  }
  augment "/ncs:devices/ncs:device/ncs:live-status" {
    container subscriber-manager {
      tailf:ncs-device-type "netconf";
      tailf:display-when "not(../../ncs:module) or ../../ncs:module[ncs:name='Cisco-IOS-XR-iedge4710-cfg'] or (../../ncs:live-status-protocol[not(ncs:capability)]) or (../../ncs:live-status-protocol/ncs:capability/ncs:module[.='Cisco-IOS-XR-iedge4710-cfg'])";
      description
        "iEdge subscriber manager configuration";
      container accounting {
        description
          "iEdge accounting feature";
        container send-stop {
          description
            "Accounting send stop feature";
          container setup-failure {
            description
              "Setup failure feature";
            leaf method-list-name {
              type string;
              description
                "AAA List name either default or preconfigured";
            }
          }
        }
        container interim {
          description
            "interim accounting related";
          container variation {
            description
              "variation of first session or service interim
               record from configured timeout";
            leaf maximum-percentage-variation {
              type uint32 {
                range "0..50";
              }
              units "percentage";
              description
                "maximum percentage variation (maximum
                 absolute variation is 15 minutes)";
            }
          }
        }
      }
      container srg {
        description
          "SRG specific config";
        leaf account-start-time {
          type empty;
          description
            "acct start time ref to srg role change slave to
             master";
        }
        leaf sync-account-session-id {
          type empty;
          description
            "sync account session id from master to slave";
        }
      }
    }
    container subscriber-featurette {
      tailf:ncs-device-type "netconf";
      tailf:display-when "not(../../ncs:module) or ../../ncs:module[ncs:name='Cisco-IOS-XR-iedge4710-cfg'] or (../../ncs:live-status-protocol[not(ncs:capability)]) or (../../ncs:live-status-protocol/ncs:capability/ncs:module[.='Cisco-IOS-XR-iedge4710-cfg'])";
      description
        "iEdge subscriber featurette configuration";
      list featurette-name {
        key "featurette";
        description
          "enable featurette processing";
        leaf enable {
          type uint32;
          description
            "instance of featurette";
        }
        leaf featurette {
          type xr:live_ncs_Cisco-ios-xr-string;
          description
            "subscriber feature";
        }
      }
    }
    container iedge-license-manager {
      tailf:ncs-device-type "netconf";
      tailf:display-when "not(../../ncs:module) or ../../ncs:module[ncs:name='Cisco-IOS-XR-iedge4710-cfg'] or (../../ncs:live-status-protocol[not(ncs:capability)]) or (../../ncs:live-status-protocol/ncs:capability/ncs:module[.='Cisco-IOS-XR-iedge4710-cfg'])";
      description
        "Session License Manager Configuration";
      leaf session-limit {
        type uint32 {
          range "1..200000";
        }
        description
          "Session limit configured on linecard";
      }
    }
    container sub-manager {
      tailf:ncs-device-type "netconf";
      tailf:display-when "not(../../ncs:module) or ../../ncs:module[ncs:name='Cisco-IOS-XR-iedge4710-cfg'] or (../../ncs:live-status-protocol[not(ncs:capability)]) or (../../ncs:live-status-protocol/ncs:capability/ncs:module[.='Cisco-IOS-XR-iedge4710-cfg'])";
      description
        "iEdge subscriber manager configuration";
      list location {
        key "location1";
        description
          "Select location";
        container trace {
          description
            "Subscriber manager trace";
          leaf trace-level {
            type uint32;
            description
              "Subscriber manager trace level";
          }
        }
        leaf history {
          type empty;
          description
            "Disable history for subscriber manager";
        }
        leaf location1 {
          type xr:live_ncs_Cisco-ios-xr-string;
          description
            "Specify location";
        }
      }
    }
  }
  augment "/ncs:devices/ncs:template/ncs:ned-id/ncs:config" {
    container subscriber-manager {
      description
        "iEdge subscriber manager configuration";
      container accounting {
        description
          "iEdge accounting feature";
        container send-stop {
          description
            "Accounting send stop feature";
          container setup-failure {
            description
              "Setup failure feature";
            leaf method-list-name {
              type string;
              description
                "AAA List name either default or preconfigured";
            }
          }
        }
        container interim {
          description
            "interim accounting related";
          container variation {
            description
              "variation of first session or service interim
               record from configured timeout";
            leaf maximum-percentage-variation {
              type string;
              units "percentage";
              description
                "maximum percentage variation (maximum
                 absolute variation is 15 minutes)";
            }
          }
        }
      }
      container srg {
        description
          "SRG specific config";
        leaf account-start-time {
          type empty;
          description
            "acct start time ref to srg role change slave to
             master";
        }
        leaf sync-account-session-id {
          type empty;
          description
            "sync account session id from master to slave";
        }
      }
    }
    container subscriber-featurette {
      description
        "iEdge subscriber featurette configuration";
      list featurette-name {
        // NCS patched for predictable order
        ordered-by user;
        key "featurette";
        description
          "enable featurette processing";
        leaf enable {
          type string;
          description
            "instance of featurette";
        }
        leaf featurette {
          type xr:ncs_template_Cisco-ios-xr-string;
          description
            "subscriber feature";
        }
      }
    }
    container iedge-license-manager {
      description
        "Session License Manager Configuration";
      leaf session-limit {
        type string;
        description
          "Session limit configured on linecard";
      }
    }
    container sub-manager {
      description
        "iEdge subscriber manager configuration";
      list location {
        // NCS patched for predictable order
        ordered-by user;
        key "location1";
        description
          "Select location";
        container trace {
          description
            "Subscriber manager trace";
          leaf trace-level {
            type string;
            description
              "Subscriber manager trace level";
          }
        }
        leaf history {
          type empty;
          description
            "Disable history for subscriber manager";
        }
        leaf location1 {
          type xr:ncs_template_Cisco-ios-xr-string;
          description
            "Specify location";
        }
      }
    }
  }
  augment "/ncs:devices/ncs:template/ncs:ned-id/ncs:config/a1:interface-configurations/a1:interface-configuration" {
    description
      "This augment extends the configuration data of
       'Cisco-IOS-XR-ifmgr-cfg'";
    container service-policies {
      description
        "Interface control subscriber policy
         configuration";
      list service-policy {
        // NCS patched for predictable order
        ordered-by user;
        key "service-policy-name";
        description
          "Service policy to be applied to access
           interface  for subscribers";
        leaf service-policy-name {
          type string;
          description
            "Name of policy-map";
        }
      }
    }
  }
  augment "/ncs:devices/ncs:device/ncs:live-status/a1:interface-configurations/a1:interface-configuration" {
    description
      "This augment extends the configuration data of
       'Cisco-IOS-XR-ifmgr-cfg'";
    container service-policies {
      tailf:ncs-device-type "netconf";
      tailf:display-when "not(../../../../ncs:module) or ../../../../ncs:module[ncs:name='Cisco-IOS-XR-iedge4710-cfg'] or (../../../../ncs:live-status-protocol[not(ncs:capability)]) or (../../../../ncs:live-status-protocol/ncs:capability/ncs:module[.='Cisco-IOS-XR-iedge4710-cfg'])";
      description
        "Interface control subscriber policy
         configuration";
      list service-policy {
        key "service-policy-name";
        description
          "Service policy to be applied to access
           interface  for subscribers";
        leaf service-policy-name {
          type string {
            length "1..63";
          }
          description
            "Name of policy-map";
        }
      }
    }
  }
  augment "/ncs:devices/ncs:device/ncs:config/a1:interface-configurations/a1:interface-configuration" {
    description
      "This augment extends the configuration data of
       'Cisco-IOS-XR-ifmgr-cfg'";
    container service-policies {
      tailf:ncs-device-type "netconf";
      tailf:display-when "not(../../../../ncs:module) or ../../../../ncs:module[ncs:name='Cisco-IOS-XR-iedge4710-cfg']";
      description
        "Interface control subscriber policy
         configuration";
      list service-policy {
        key "service-policy-name";
        description
          "Service policy to be applied to access
           interface  for subscribers";
        leaf service-policy-name {
          type string {
            length "1..63";
          }
          description
            "Name of policy-map";
        }
      }
    }
  }
}

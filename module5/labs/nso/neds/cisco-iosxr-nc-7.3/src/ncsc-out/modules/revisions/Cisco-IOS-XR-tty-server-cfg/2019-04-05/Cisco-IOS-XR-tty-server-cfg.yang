module Cisco-IOS-XR-tty-server-cfg {
  // Generated by yanger -t ncs
  tailf:mount-id "cisco-iosxr-nc-7.3:cisco-iosxr-nc-7.3";
  tailf:ncs-device-type "netconf";

  namespace "http://cisco.com/ns/yang/Cisco-IOS-XR-tty-server-cfg";
  prefix tty-server-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tty-server package configuration.

     This module contains definitions
     for the following management objects:
       tty: TTY Line Configuration

     Copyright (c) 2013-2019 by Cisco Systems, Inc.
     All rights reserved.";

  revision 2019-04-05 {
    description
      "Establish semantic version baseline.";
    semver:module-version "1.0.1";
  }
  revision 2015-07-30 {
    description
      "Descriptions updated.";
  }
  revision 2015-01-07 {
    description
      "IOS XR 5.3.1 revision.";
  }

  augment "/ncs:devices/ncs:device/ncs:config" {
    container tty {
      tailf:ncs-device-type "netconf";
      tailf:display-when "not(../../ncs:module) or ../../ncs:module[ncs:name='Cisco-IOS-XR-tty-server-cfg']";
      description
        "TTY Line Configuration";
      container tty-lines {
        description
          "TTY templates";
        list tty-line {
          key "name";
          description
            "TTY Line,Use string 'console' to configure a
             console line,Use string 'default' to configure
             a default line,Use any string to configure a
             user defined template";
          container general {
            description
              "TTY line general configuration";
            leaf length {
              type uint32 {
                range "0..512";
              }
              default "24";
              description
                "Number of lines on a screen.";
            }
            leaf absolute-timeout {
              type uint32 {
                range "0..10000";
              }
              units "minute";
              default "0";
              description
                "Absolute timeout for line disconnection";
            }
            leaf width {
              type uint32 {
                range "0..512";
              }
              default "80";
              description
                "Number of characters on a screen line.";
            }
          }
          container telnet {
            description
              "Telnet protocol-specific configuration";
            leaf transparent {
              type empty;
              description
                "Send a CR as a CR followed by a NULL instead
                 of a CRfollowed by a LF";
            }
          }
          container aaa {
            description
              "Container class for AAA related TTY
               configuration";
            container user-groups {
              description
                "Users characteristics";
              list user-group {
                key "name";
                description
                  "Group to which the user will belong";
                leaf name {
                  type xr:Cisco-ios-xr-string;
                  description
                    "Name of the group";
                }
                leaf category {
                  type string;
                  mandatory true;
                  description
                    "Specify as 'root-system' for root-system
                     group and 'other' for remaining groups";
                }
              }
            }
            container authorization {
              description
                "Authorization parameters";
              leaf exec {
                type string;
                description
                  "For starting an exec (shell)";
              }
              leaf event-manager {
                type string;
                description
                  "Specify 'default' or use an authorization
                   list with this name";
              }
              leaf commands {
                type string;
                description
                  "For exec (shell) configuration";
              }
            }
            container authentication {
              description
                "Authentication parameters";
              leaf login {
                type string;
                description
                  "Authentication list name";
              }
            }
            container accounting {
              description
                "Accounting parameters";
              leaf exec {
                type string;
                description
                  "For starting an exec (shell)";
              }
              leaf commands {
                type string;
                description
                  "For exec (shell) configuration";
              }
            }
            leaf login-timeout {
              type uint32 {
                range "0..300";
              }
              units "second";
              default "30";
              description
                "Timeouts for any user input during login
                 sequence";
            }
            leaf secret {
              type xr:Md5-password;
              description
                "Configure a secure one way encrypted password";
            }
            leaf password {
              type xr:Md5-password;
              description
                "Configure the password for the user";
            }
          }
          container exec {
            description
              "EXEC timeout and timestamp configurtion";
            container timeout {
              presence "Indicates a timeout node is configured.";
              description
                "EXEC Timeout";
              leaf minutes {
                type uint32 {
                  range "0..35791";
                }
                units "minute";
                mandatory true;
                description
                  "Timeout in minutes";
              }
              leaf seconds {
                type uint32 {
                  range "0..2147483";
                }
                units "second";
                mandatory true;
                description
                  "Timeout in seconds";
              }
            }
            leaf time-stamp {
              type boolean;
              description
                "'True' to Enable & 'False' to Disable time
                 stamp";
            }
          }
          leaf name {
            type xr:Cisco-ios-xr-string;
            description
              "Name of the template";
          }
        }
      }
    }
  }
  augment "/ncs:devices/ncs:device/ncs:live-status" {
    container tty {
      tailf:ncs-device-type "netconf";
      tailf:display-when "not(../../ncs:module) or ../../ncs:module[ncs:name='Cisco-IOS-XR-tty-server-cfg'] or (../../ncs:live-status-protocol[not(ncs:capability)]) or (../../ncs:live-status-protocol/ncs:capability/ncs:module[.='Cisco-IOS-XR-tty-server-cfg'])";
      description
        "TTY Line Configuration";
      container tty-lines {
        description
          "TTY templates";
        list tty-line {
          key "name";
          description
            "TTY Line,Use string 'console' to configure a
             console line,Use string 'default' to configure
             a default line,Use any string to configure a
             user defined template";
          container general {
            description
              "TTY line general configuration";
            leaf length {
              type uint32 {
                range "0..512";
              }
              // NCS drop default statement
              description
                "Number of lines on a screen.";
            }
            leaf absolute-timeout {
              type uint32 {
                range "0..10000";
              }
              units "minute";
              // NCS drop default statement
              description
                "Absolute timeout for line disconnection";
            }
            leaf width {
              type uint32 {
                range "0..512";
              }
              // NCS drop default statement
              description
                "Number of characters on a screen line.";
            }
          }
          container telnet {
            description
              "Telnet protocol-specific configuration";
            leaf transparent {
              type empty;
              description
                "Send a CR as a CR followed by a NULL instead
                 of a CRfollowed by a LF";
            }
          }
          container aaa {
            description
              "Container class for AAA related TTY
               configuration";
            container user-groups {
              description
                "Users characteristics";
              list user-group {
                key "name";
                description
                  "Group to which the user will belong";
                leaf name {
                  type xr:live_ncs_Cisco-ios-xr-string;
                  description
                    "Name of the group";
                }
                leaf category {
                  type string;
                  // NCS drop mandatory statement
                  description
                    "Specify as 'root-system' for root-system
                     group and 'other' for remaining groups";
                }
              }
            }
            container authorization {
              description
                "Authorization parameters";
              leaf exec {
                type string;
                description
                  "For starting an exec (shell)";
              }
              leaf event-manager {
                type string;
                description
                  "Specify 'default' or use an authorization
                   list with this name";
              }
              leaf commands {
                type string;
                description
                  "For exec (shell) configuration";
              }
            }
            container authentication {
              description
                "Authentication parameters";
              leaf login {
                type string;
                description
                  "Authentication list name";
              }
            }
            container accounting {
              description
                "Accounting parameters";
              leaf exec {
                type string;
                description
                  "For starting an exec (shell)";
              }
              leaf commands {
                type string;
                description
                  "For exec (shell) configuration";
              }
            }
            leaf login-timeout {
              type uint32 {
                range "0..300";
              }
              units "second";
              // NCS drop default statement
              description
                "Timeouts for any user input during login
                 sequence";
            }
            leaf secret {
              type xr:live_ncs_Md5-password;
              description
                "Configure a secure one way encrypted password";
            }
            leaf password {
              type xr:live_ncs_Md5-password;
              description
                "Configure the password for the user";
            }
          }
          container exec {
            description
              "EXEC timeout and timestamp configurtion";
            container timeout {
              presence "Indicates a timeout node is configured.";
              description
                "EXEC Timeout";
              leaf minutes {
                type uint32 {
                  range "0..35791";
                }
                units "minute";
                // NCS drop mandatory statement
                description
                  "Timeout in minutes";
              }
              leaf seconds {
                type uint32 {
                  range "0..2147483";
                }
                units "second";
                // NCS drop mandatory statement
                description
                  "Timeout in seconds";
              }
            }
            leaf time-stamp {
              type boolean;
              description
                "'True' to Enable & 'False' to Disable time
                 stamp";
            }
          }
          leaf name {
            type xr:live_ncs_Cisco-ios-xr-string;
            description
              "Name of the template";
          }
        }
      }
    }
  }
  augment "/ncs:devices/ncs:template/ncs:ned-id/ncs:config" {
    container tty {
      description
        "TTY Line Configuration";
      container tty-lines {
        description
          "TTY templates";
        list tty-line {
          // NCS patched for predictable order
          ordered-by user;
          key "name";
          description
            "TTY Line,Use string 'console' to configure a
             console line,Use string 'default' to configure
             a default line,Use any string to configure a
             user defined template";
          container general {
            description
              "TTY line general configuration";
            leaf length {
              type string;
              // NCS drop default statement
              description
                "Number of lines on a screen.";
            }
            leaf absolute-timeout {
              type string;
              units "minute";
              // NCS drop default statement
              description
                "Absolute timeout for line disconnection";
            }
            leaf width {
              type string;
              // NCS drop default statement
              description
                "Number of characters on a screen line.";
            }
          }
          container telnet {
            description
              "Telnet protocol-specific configuration";
            leaf transparent {
              type empty;
              description
                "Send a CR as a CR followed by a NULL instead
                 of a CRfollowed by a LF";
            }
          }
          container aaa {
            description
              "Container class for AAA related TTY
               configuration";
            container user-groups {
              description
                "Users characteristics";
              list user-group {
                // NCS patched for predictable order
                ordered-by user;
                key "name";
                description
                  "Group to which the user will belong";
                leaf name {
                  type xr:ncs_template_Cisco-ios-xr-string;
                  description
                    "Name of the group";
                }
                leaf category {
                  type string;
                  // NCS drop mandatory statement
                  description
                    "Specify as 'root-system' for root-system
                     group and 'other' for remaining groups";
                }
              }
            }
            container authorization {
              description
                "Authorization parameters";
              leaf exec {
                type string;
                description
                  "For starting an exec (shell)";
              }
              leaf event-manager {
                type string;
                description
                  "Specify 'default' or use an authorization
                   list with this name";
              }
              leaf commands {
                type string;
                description
                  "For exec (shell) configuration";
              }
            }
            container authentication {
              description
                "Authentication parameters";
              leaf login {
                type string;
                description
                  "Authentication list name";
              }
            }
            container accounting {
              description
                "Accounting parameters";
              leaf exec {
                type string;
                description
                  "For starting an exec (shell)";
              }
              leaf commands {
                type string;
                description
                  "For exec (shell) configuration";
              }
            }
            leaf login-timeout {
              type string;
              units "second";
              // NCS drop default statement
              description
                "Timeouts for any user input during login
                 sequence";
            }
            leaf secret {
              type xr:ncs_template_Md5-password;
              description
                "Configure a secure one way encrypted password";
            }
            leaf password {
              type xr:ncs_template_Md5-password;
              description
                "Configure the password for the user";
            }
          }
          container exec {
            description
              "EXEC timeout and timestamp configurtion";
            container timeout {
              presence "Indicates a timeout node is configured.";
              description
                "EXEC Timeout";
              leaf minutes {
                type string;
                units "minute";
                // NCS drop mandatory statement
                description
                  "Timeout in minutes";
              }
              leaf seconds {
                type string;
                units "second";
                // NCS drop mandatory statement
                description
                  "Timeout in seconds";
              }
            }
            leaf time-stamp {
              type string;
              description
                "'True' to Enable & 'False' to Disable time
                 stamp";
            }
          }
          leaf name {
            type xr:ncs_template_Cisco-ios-xr-string;
            description
              "Name of the template";
          }
        }
      }
    }
  }
}

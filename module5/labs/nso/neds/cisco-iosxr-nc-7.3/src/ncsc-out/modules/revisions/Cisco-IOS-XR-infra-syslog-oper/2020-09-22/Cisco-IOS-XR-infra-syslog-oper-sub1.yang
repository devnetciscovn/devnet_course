submodule Cisco-IOS-XR-infra-syslog-oper-sub1 {
  // Generated by yanger -t ncs
  tailf:mount-id "cisco-iosxr-nc-7.3:cisco-iosxr-nc-7.3";

  belongs-to Cisco-IOS-XR-infra-syslog-oper {
    prefix Cisco-IOS-XR-infra-syslog-oper;
  }

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR infra-syslog package operational data.

     Copyright (c) 2013-2020 by Cisco Systems, Inc.
     All rights reserved.";

  revision 2020-09-22 {
    description
      "Marking Sensor Paths for Event Driven Telemetry";
    semver:module-version "1.1.0";
  }
  revision 2019-04-05 {
    description
      "Establish semantic version baseline.";
    semver:module-version "1.0.1";
  }
  revision 2018-02-23 {
    description
      "Added a new rpc statement.";
  }
  revision 2018-02-22 {
    description
      "Fixed syslog message filter.";
  }
  revision 2017-09-07 {
    description
      "Fixed type translation error.";
  }
  revision 2016-06-24 {
    description
      "Schema added for Show logging files CLI";
  }
  revision 2015-01-07 {
    description
      "IOS XR 5.3.1 revision.";
  }

  typedef ncs_template_System-message-severity {
    type string;
    description
      "System message severity";
  }

  typedef ncs_rpc_notif_System-message-severity {
    type enumeration {
      enum "message-severity-unknown" {
        value -1;
        description
          "Unknown";
      }
      enum "message-severity-emergency" {
        value 0;
        description
          "Emergency";
      }
      enum "message-severity-alert" {
        value 1;
        description
          "Alert";
      }
      enum "message-severity-critical" {
        value 2;
        description
          "Critical";
      }
      enum "message-severity-error" {
        value 3;
        description
          "Error";
      }
      enum "message-severity-warning" {
        value 4;
        description
          "Warning";
      }
      enum "message-severity-notice" {
        value 5;
        description
          "Notice";
      }
      enum "message-severity-informational" {
        value 6;
        description
          "Informational";
      }
      enum "message-severity-debug" {
        value 7;
        description
          "Debug";
      }
    }
    description
      "System message severity";
  }

  typedef live_ncs_System-message-severity {
    type enumeration {
      enum "message-severity-unknown" {
        value -1;
        description
          "Unknown";
      }
      enum "message-severity-emergency" {
        value 0;
        description
          "Emergency";
      }
      enum "message-severity-alert" {
        value 1;
        description
          "Alert";
      }
      enum "message-severity-critical" {
        value 2;
        description
          "Critical";
      }
      enum "message-severity-error" {
        value 3;
        description
          "Error";
      }
      enum "message-severity-warning" {
        value 4;
        description
          "Warning";
      }
      enum "message-severity-notice" {
        value 5;
        description
          "Notice";
      }
      enum "message-severity-informational" {
        value 6;
        description
          "Informational";
      }
      enum "message-severity-debug" {
        value 7;
        description
          "Debug";
      }
    }
    description
      "System message severity";
  }

  typedef System-message-severity {
    type enumeration {
      enum "message-severity-unknown" {
        value -1;
        description
          "Unknown";
      }
      enum "message-severity-emergency" {
        value 0;
        description
          "Emergency";
      }
      enum "message-severity-alert" {
        value 1;
        description
          "Alert";
      }
      enum "message-severity-critical" {
        value 2;
        description
          "Critical";
      }
      enum "message-severity-error" {
        value 3;
        description
          "Error";
      }
      enum "message-severity-warning" {
        value 4;
        description
          "Warning";
      }
      enum "message-severity-notice" {
        value 5;
        description
          "Notice";
      }
      enum "message-severity-informational" {
        value 6;
        description
          "Informational";
      }
      enum "message-severity-debug" {
        value 7;
        description
          "Debug";
      }
    }
    description
      "System message severity";
  }

  grouping ncs_template_FILE-LOG-STATS {
    description
      "System log file destination statistics";
    leaf file-name {
      type string;
      description
        "File name for logging messages";
    }
    leaf message-count {
      type string;
      description
        "Message count";
    }
  }

  grouping ncs_template_TLS-REMOTE-LOG-STATS {
    description
      "System log tls remote statistics";
    leaf remote-host-name {
      type string;
      description
        "TLS Remote hostname";
    }
    leaf message-count {
      type string;
      description
        "Message count";
    }
  }

  grouping ncs_template_REMOTE-LOG-STATS {
    description
      "System log remote statistics";
    leaf remote-host-name {
      type string;
      description
        "Remote hostname";
    }
    leaf message-count {
      type string;
      description
        "Message count";
    }
  }

  grouping ncs_template_LOG-DEST-STATS {
    description
      "System log statistics";
    leaf is-log-enabled {
      type string;
      description
        "Is log enabled";
    }
    leaf severity {
      type ncs_template_System-message-severity;
      description
        "Configured severity";
    }
    leaf message-count {
      type string;
      description
        "Message count";
    }
    leaf buffer-size {
      type string;
      units "byte";
      description
        "Buffer size in bytes if logging buffer isenabled";
    }
  }

  grouping ncs_template_LOG-ENABLE-STATS {
    description
      "System log discard statistics";
    leaf is-log-enabled {
      type string;
      description
        "Is log enabled";
    }
    leaf drop-count {
      type string;
      description
        "Number of messages dropped";
    }
    leaf flush-count {
      type string;
      description
        "Number of messages flushed";
    }
    leaf overrun-count {
      type string;
      description
        "Number of messages overrun";
    }
  }

  grouping ncs_template_SYSTEM-MESSAGE-STATISTICS {
    description
      "System message statistics";
    container logging-stats {
      description
        "Logging statistics";
      uses ncs_template_LOG-ENABLE-STATS;
    }
    container console-logging-stats {
      description
        "Console logging statistics";
      uses ncs_template_LOG-DEST-STATS;
    }
    container monitor-logging-stats {
      description
        "Monitor loggingstatistics";
      uses ncs_template_LOG-DEST-STATS;
    }
    container trap-logging-stats {
      description
        "Trap logging statistics";
      uses ncs_template_LOG-DEST-STATS;
    }
    container buffer-logging-stats {
      description
        "Buffer logging statistics";
      uses ncs_template_LOG-DEST-STATS;
    }
    list remote-logging-stat {
      // NCS patched for predictable order
      ordered-by user;
      description
        "Remote logging statistics";
      uses ncs_template_REMOTE-LOG-STATS;
    }
    list tls-remote-logging-stat {
      // NCS patched for predictable order
      ordered-by user;
      description
        "TLS Remote logging statistics";
      uses ncs_template_TLS-REMOTE-LOG-STATS;
    }
    list file-logging-stat {
      // NCS patched for predictable order
      ordered-by user;
      description
        "File logging statistics";
      uses ncs_template_FILE-LOG-STATS;
    }
  }

  grouping ncs_template_SYSTEM-MESSAGE {
    description
      "System message";
    leaf card-type {
      type string;
      description
        "Message card location: 'RP', 'DRP', 'LC', 'SC',
         'SP' or 'UNK' ";
      xr:event-telemetry "Subscribe Telemetry Event";
    }
    leaf node-name {
      type xr:ncs_template_Node-id;
      description
        "Message source location";
      xr:event-telemetry "Subscribe Telemetry Event";
    }
    leaf time-stamp {
      type string;
      units "millisecond";
      description
        "Time in milliseconds since 00:00:00 UTC, January
         11970 of when message was generated";
      xr:event-telemetry "Subscribe Telemetry Event";
    }
    leaf time-of-day {
      type string;
      description
        "Time of day of event in DDD MMM DD  YYYY HH:MM
         :SS format, e.g Wed Apr 01 2009  15:50:26";
      xr:event-telemetry "Subscribe Telemetry Event";
    }
    leaf time-zone {
      type string;
      description
        "Time Zone in UTC+/-HH:MM format,  e.g UTC+5:30,
         UTC-6";
      xr:event-telemetry "Subscribe Telemetry Event";
    }
    leaf process-name {
      type string;
      description
        "Process name";
      xr:event-telemetry "Subscribe Telemetry Event";
    }
    leaf category {
      type string;
      description
        "Message category";
      xr:event-telemetry "Subscribe Telemetry Event";
    }
    leaf group {
      type string;
      description
        "Message group";
      xr:event-telemetry "Subscribe Telemetry Event";
    }
    leaf message-name {
      type string;
      description
        "Message name";
      xr:event-telemetry "Subscribe Telemetry Event";
    }
    leaf severity {
      type ncs_template_System-message-severity;
      description
        "Message severity";
      xr:event-telemetry "Subscribe Telemetry Event";
    }
    leaf text {
      type string;
      description
        "Additional message text";
      xr:event-telemetry "Subscribe Telemetry Event";
    }
  }

  grouping ncs_template_AN-REMOTE-LOG-SERVER {
    description
      "A System log AN remote log server structure";
    leaf ip-address {
      type string;
      description
        "IP Address";
    }
    leaf vrf-name {
      type string;
      description
        "VRF Name";
    }
    leaf vrf-severity {
      type string;
      description
        "VRF Severity";
    }
    leaf rh-discriminator {
      type string;
      description
        "Remote-Host Discriminator";
    }
  }

  grouping ncs_template_AN-REMOTE-LOG-SERVERS {
    description
      "System log All AN remote servers";
    list an-remote-log-server {
      // NCS patched for predictable order
      ordered-by user;
      description
        "AN Remote Log Servers";
      uses ncs_template_AN-REMOTE-LOG-SERVER;
    }
  }

  grouping ncs_template_FILE-LOG-DETAILS {
    description
      "System log file details";
    leaf file-path {
      type string;
      description
        "File path for logging messages";
    }
    leaf file-name {
      type string;
      description
        "File name for logging messages";
    }
  }

  grouping ncs_template_FILE-LOG-LIST-PATH {
    description
      "System log files list and path";
    list file-log-detail {
      // NCS patched for predictable order
      ordered-by user;
      description
        "Logging Files";
      uses ncs_template_FILE-LOG-DETAILS;
    }
  }

  grouping ncs_rpc_notif_FILE-LOG-STATS {
    description
      "System log file destination statistics";
    leaf file-name {
      type string;
      description
        "File name for logging messages";
    }
    leaf message-count {
      type uint32;
      description
        "Message count";
    }
  }

  grouping ncs_rpc_notif_TLS-REMOTE-LOG-STATS {
    description
      "System log tls remote statistics";
    leaf remote-host-name {
      type string;
      description
        "TLS Remote hostname";
    }
    leaf message-count {
      type uint32;
      description
        "Message count";
    }
  }

  grouping ncs_rpc_notif_REMOTE-LOG-STATS {
    description
      "System log remote statistics";
    leaf remote-host-name {
      type string;
      description
        "Remote hostname";
    }
    leaf message-count {
      type uint32;
      description
        "Message count";
    }
  }

  grouping ncs_rpc_notif_LOG-DEST-STATS {
    description
      "System log statistics";
    leaf is-log-enabled {
      type boolean;
      description
        "Is log enabled";
    }
    leaf severity {
      type ncs_rpc_notif_System-message-severity;
      description
        "Configured severity";
    }
    leaf message-count {
      type uint32;
      description
        "Message count";
    }
    leaf buffer-size {
      type uint32;
      units "byte";
      description
        "Buffer size in bytes if logging buffer isenabled";
    }
  }

  grouping ncs_rpc_notif_LOG-ENABLE-STATS {
    description
      "System log discard statistics";
    leaf is-log-enabled {
      type boolean;
      description
        "Is log enabled";
    }
    leaf drop-count {
      type uint32;
      description
        "Number of messages dropped";
    }
    leaf flush-count {
      type uint32;
      description
        "Number of messages flushed";
    }
    leaf overrun-count {
      type uint32;
      description
        "Number of messages overrun";
    }
  }

  grouping ncs_rpc_notif_SYSTEM-MESSAGE-STATISTICS {
    description
      "System message statistics";
    container logging-stats {
      description
        "Logging statistics";
      uses ncs_rpc_notif_LOG-ENABLE-STATS;
    }
    container console-logging-stats {
      description
        "Console logging statistics";
      uses ncs_rpc_notif_LOG-DEST-STATS;
    }
    container monitor-logging-stats {
      description
        "Monitor loggingstatistics";
      uses ncs_rpc_notif_LOG-DEST-STATS;
    }
    container trap-logging-stats {
      description
        "Trap logging statistics";
      uses ncs_rpc_notif_LOG-DEST-STATS;
    }
    container buffer-logging-stats {
      description
        "Buffer logging statistics";
      uses ncs_rpc_notif_LOG-DEST-STATS;
    }
    list remote-logging-stat {
      description
        "Remote logging statistics";
      uses ncs_rpc_notif_REMOTE-LOG-STATS;
    }
    list tls-remote-logging-stat {
      description
        "TLS Remote logging statistics";
      uses ncs_rpc_notif_TLS-REMOTE-LOG-STATS;
    }
    list file-logging-stat {
      description
        "File logging statistics";
      uses ncs_rpc_notif_FILE-LOG-STATS;
    }
  }

  grouping ncs_rpc_notif_SYSTEM-MESSAGE {
    description
      "System message";
    leaf card-type {
      type string;
      description
        "Message card location: 'RP', 'DRP', 'LC', 'SC',
         'SP' or 'UNK' ";
      xr:event-telemetry "Subscribe Telemetry Event";
    }
    leaf node-name {
      type xr:ncs_rpc_notif_Node-id;
      description
        "Message source location";
      xr:event-telemetry "Subscribe Telemetry Event";
    }
    leaf time-stamp {
      type uint64;
      units "millisecond";
      description
        "Time in milliseconds since 00:00:00 UTC, January
         11970 of when message was generated";
      xr:event-telemetry "Subscribe Telemetry Event";
    }
    leaf time-of-day {
      type string;
      description
        "Time of day of event in DDD MMM DD  YYYY HH:MM
         :SS format, e.g Wed Apr 01 2009  15:50:26";
      xr:event-telemetry "Subscribe Telemetry Event";
    }
    leaf time-zone {
      type string;
      description
        "Time Zone in UTC+/-HH:MM format,  e.g UTC+5:30,
         UTC-6";
      xr:event-telemetry "Subscribe Telemetry Event";
    }
    leaf process-name {
      type string;
      description
        "Process name";
      xr:event-telemetry "Subscribe Telemetry Event";
    }
    leaf category {
      type string;
      description
        "Message category";
      xr:event-telemetry "Subscribe Telemetry Event";
    }
    leaf group {
      type string;
      description
        "Message group";
      xr:event-telemetry "Subscribe Telemetry Event";
    }
    leaf message-name {
      type string;
      description
        "Message name";
      xr:event-telemetry "Subscribe Telemetry Event";
    }
    leaf severity {
      type ncs_rpc_notif_System-message-severity;
      description
        "Message severity";
      xr:event-telemetry "Subscribe Telemetry Event";
    }
    leaf text {
      type string;
      description
        "Additional message text";
      xr:event-telemetry "Subscribe Telemetry Event";
    }
  }

  grouping ncs_rpc_notif_AN-REMOTE-LOG-SERVER {
    description
      "A System log AN remote log server structure";
    leaf ip-address {
      type string;
      description
        "IP Address";
    }
    leaf vrf-name {
      type string;
      description
        "VRF Name";
    }
    leaf vrf-severity {
      type string;
      description
        "VRF Severity";
    }
    leaf rh-discriminator {
      type string;
      description
        "Remote-Host Discriminator";
    }
  }

  grouping ncs_rpc_notif_AN-REMOTE-LOG-SERVERS {
    description
      "System log All AN remote servers";
    list an-remote-log-server {
      description
        "AN Remote Log Servers";
      uses ncs_rpc_notif_AN-REMOTE-LOG-SERVER;
    }
  }

  grouping ncs_rpc_notif_FILE-LOG-DETAILS {
    description
      "System log file details";
    leaf file-path {
      type string;
      description
        "File path for logging messages";
    }
    leaf file-name {
      type string;
      description
        "File name for logging messages";
    }
  }

  grouping ncs_rpc_notif_FILE-LOG-LIST-PATH {
    description
      "System log files list and path";
    list file-log-detail {
      description
        "Logging Files";
      uses ncs_rpc_notif_FILE-LOG-DETAILS;
    }
  }

  grouping live_ncs_FILE-LOG-STATS {
    description
      "System log file destination statistics";
    leaf file-name {
      type string;
      description
        "File name for logging messages";
    }
    leaf message-count {
      type uint32;
      description
        "Message count";
    }
  }

  grouping live_ncs_TLS-REMOTE-LOG-STATS {
    description
      "System log tls remote statistics";
    leaf remote-host-name {
      type string;
      description
        "TLS Remote hostname";
    }
    leaf message-count {
      type uint32;
      description
        "Message count";
    }
  }

  grouping live_ncs_REMOTE-LOG-STATS {
    description
      "System log remote statistics";
    leaf remote-host-name {
      type string;
      description
        "Remote hostname";
    }
    leaf message-count {
      type uint32;
      description
        "Message count";
    }
  }

  grouping live_ncs_LOG-DEST-STATS {
    description
      "System log statistics";
    leaf is-log-enabled {
      type boolean;
      description
        "Is log enabled";
    }
    leaf severity {
      type live_ncs_System-message-severity;
      description
        "Configured severity";
    }
    leaf message-count {
      type uint32;
      description
        "Message count";
    }
    leaf buffer-size {
      type uint32;
      units "byte";
      description
        "Buffer size in bytes if logging buffer isenabled";
    }
  }

  grouping live_ncs_LOG-ENABLE-STATS {
    description
      "System log discard statistics";
    leaf is-log-enabled {
      type boolean;
      description
        "Is log enabled";
    }
    leaf drop-count {
      type uint32;
      description
        "Number of messages dropped";
    }
    leaf flush-count {
      type uint32;
      description
        "Number of messages flushed";
    }
    leaf overrun-count {
      type uint32;
      description
        "Number of messages overrun";
    }
  }

  grouping live_ncs_SYSTEM-MESSAGE-STATISTICS {
    description
      "System message statistics";
    container logging-stats {
      description
        "Logging statistics";
      uses live_ncs_LOG-ENABLE-STATS;
    }
    container console-logging-stats {
      description
        "Console logging statistics";
      uses live_ncs_LOG-DEST-STATS;
    }
    container monitor-logging-stats {
      description
        "Monitor loggingstatistics";
      uses live_ncs_LOG-DEST-STATS;
    }
    container trap-logging-stats {
      description
        "Trap logging statistics";
      uses live_ncs_LOG-DEST-STATS;
    }
    container buffer-logging-stats {
      description
        "Buffer logging statistics";
      uses live_ncs_LOG-DEST-STATS;
    }
    list remote-logging-stat {
      description
        "Remote logging statistics";
      uses live_ncs_REMOTE-LOG-STATS;
    }
    list tls-remote-logging-stat {
      description
        "TLS Remote logging statistics";
      uses live_ncs_TLS-REMOTE-LOG-STATS;
    }
    list file-logging-stat {
      description
        "File logging statistics";
      uses live_ncs_FILE-LOG-STATS;
    }
  }

  grouping live_ncs_SYSTEM-MESSAGE {
    description
      "System message";
    leaf card-type {
      type string;
      description
        "Message card location: 'RP', 'DRP', 'LC', 'SC',
         'SP' or 'UNK' ";
      xr:event-telemetry "Subscribe Telemetry Event";
    }
    leaf node-name {
      type xr:live_ncs_Node-id;
      description
        "Message source location";
      xr:event-telemetry "Subscribe Telemetry Event";
    }
    leaf time-stamp {
      type uint64;
      units "millisecond";
      description
        "Time in milliseconds since 00:00:00 UTC, January
         11970 of when message was generated";
      xr:event-telemetry "Subscribe Telemetry Event";
    }
    leaf time-of-day {
      type string;
      description
        "Time of day of event in DDD MMM DD  YYYY HH:MM
         :SS format, e.g Wed Apr 01 2009  15:50:26";
      xr:event-telemetry "Subscribe Telemetry Event";
    }
    leaf time-zone {
      type string;
      description
        "Time Zone in UTC+/-HH:MM format,  e.g UTC+5:30,
         UTC-6";
      xr:event-telemetry "Subscribe Telemetry Event";
    }
    leaf process-name {
      type string;
      description
        "Process name";
      xr:event-telemetry "Subscribe Telemetry Event";
    }
    leaf category {
      type string;
      description
        "Message category";
      xr:event-telemetry "Subscribe Telemetry Event";
    }
    leaf group {
      type string;
      description
        "Message group";
      xr:event-telemetry "Subscribe Telemetry Event";
    }
    leaf message-name {
      type string;
      description
        "Message name";
      xr:event-telemetry "Subscribe Telemetry Event";
    }
    leaf severity {
      type live_ncs_System-message-severity;
      description
        "Message severity";
      xr:event-telemetry "Subscribe Telemetry Event";
    }
    leaf text {
      type string;
      description
        "Additional message text";
      xr:event-telemetry "Subscribe Telemetry Event";
    }
  }

  grouping live_ncs_AN-REMOTE-LOG-SERVER {
    description
      "A System log AN remote log server structure";
    leaf ip-address {
      type string;
      description
        "IP Address";
    }
    leaf vrf-name {
      type string;
      description
        "VRF Name";
    }
    leaf vrf-severity {
      type string;
      description
        "VRF Severity";
    }
    leaf rh-discriminator {
      type string;
      description
        "Remote-Host Discriminator";
    }
  }

  grouping live_ncs_AN-REMOTE-LOG-SERVERS {
    description
      "System log All AN remote servers";
    list an-remote-log-server {
      description
        "AN Remote Log Servers";
      uses live_ncs_AN-REMOTE-LOG-SERVER;
    }
  }

  grouping live_ncs_FILE-LOG-DETAILS {
    description
      "System log file details";
    leaf file-path {
      type string;
      description
        "File path for logging messages";
    }
    leaf file-name {
      type string;
      description
        "File name for logging messages";
    }
  }

  grouping live_ncs_FILE-LOG-LIST-PATH {
    description
      "System log files list and path";
    list file-log-detail {
      description
        "Logging Files";
      uses live_ncs_FILE-LOG-DETAILS;
    }
  }

  grouping FILE-LOG-STATS {
    description
      "System log file destination statistics";
    leaf file-name {
      type string;
      description
        "File name for logging messages";
    }
    leaf message-count {
      type uint32;
      description
        "Message count";
    }
  }

  grouping TLS-REMOTE-LOG-STATS {
    description
      "System log tls remote statistics";
    leaf remote-host-name {
      type string;
      description
        "TLS Remote hostname";
    }
    leaf message-count {
      type uint32;
      description
        "Message count";
    }
  }

  grouping REMOTE-LOG-STATS {
    description
      "System log remote statistics";
    leaf remote-host-name {
      type string;
      description
        "Remote hostname";
    }
    leaf message-count {
      type uint32;
      description
        "Message count";
    }
  }

  grouping LOG-DEST-STATS {
    description
      "System log statistics";
    leaf is-log-enabled {
      type boolean;
      description
        "Is log enabled";
    }
    leaf severity {
      type System-message-severity;
      description
        "Configured severity";
    }
    leaf message-count {
      type uint32;
      description
        "Message count";
    }
    leaf buffer-size {
      type uint32;
      units "byte";
      description
        "Buffer size in bytes if logging buffer isenabled";
    }
  }

  grouping LOG-ENABLE-STATS {
    description
      "System log discard statistics";
    leaf is-log-enabled {
      type boolean;
      description
        "Is log enabled";
    }
    leaf drop-count {
      type uint32;
      description
        "Number of messages dropped";
    }
    leaf flush-count {
      type uint32;
      description
        "Number of messages flushed";
    }
    leaf overrun-count {
      type uint32;
      description
        "Number of messages overrun";
    }
  }

  grouping SYSTEM-MESSAGE-STATISTICS {
    description
      "System message statistics";
    container logging-stats {
      description
        "Logging statistics";
      uses LOG-ENABLE-STATS;
    }
    container console-logging-stats {
      description
        "Console logging statistics";
      uses LOG-DEST-STATS;
    }
    container monitor-logging-stats {
      description
        "Monitor loggingstatistics";
      uses LOG-DEST-STATS;
    }
    container trap-logging-stats {
      description
        "Trap logging statistics";
      uses LOG-DEST-STATS;
    }
    container buffer-logging-stats {
      description
        "Buffer logging statistics";
      uses LOG-DEST-STATS;
    }
    list remote-logging-stat {
      description
        "Remote logging statistics";
      uses REMOTE-LOG-STATS;
    }
    list tls-remote-logging-stat {
      description
        "TLS Remote logging statistics";
      uses TLS-REMOTE-LOG-STATS;
    }
    list file-logging-stat {
      description
        "File logging statistics";
      uses FILE-LOG-STATS;
    }
  }

  grouping SYSTEM-MESSAGE {
    description
      "System message";
    leaf card-type {
      type string;
      description
        "Message card location: 'RP', 'DRP', 'LC', 'SC',
         'SP' or 'UNK' ";
      xr:event-telemetry "Subscribe Telemetry Event";
    }
    leaf node-name {
      type xr:Node-id;
      description
        "Message source location";
      xr:event-telemetry "Subscribe Telemetry Event";
    }
    leaf time-stamp {
      type uint64;
      units "millisecond";
      description
        "Time in milliseconds since 00:00:00 UTC, January
         11970 of when message was generated";
      xr:event-telemetry "Subscribe Telemetry Event";
    }
    leaf time-of-day {
      type string;
      description
        "Time of day of event in DDD MMM DD  YYYY HH:MM
         :SS format, e.g Wed Apr 01 2009  15:50:26";
      xr:event-telemetry "Subscribe Telemetry Event";
    }
    leaf time-zone {
      type string;
      description
        "Time Zone in UTC+/-HH:MM format,  e.g UTC+5:30,
         UTC-6";
      xr:event-telemetry "Subscribe Telemetry Event";
    }
    leaf process-name {
      type string;
      description
        "Process name";
      xr:event-telemetry "Subscribe Telemetry Event";
    }
    leaf category {
      type string;
      description
        "Message category";
      xr:event-telemetry "Subscribe Telemetry Event";
    }
    leaf group {
      type string;
      description
        "Message group";
      xr:event-telemetry "Subscribe Telemetry Event";
    }
    leaf message-name {
      type string;
      description
        "Message name";
      xr:event-telemetry "Subscribe Telemetry Event";
    }
    leaf severity {
      type System-message-severity;
      description
        "Message severity";
      xr:event-telemetry "Subscribe Telemetry Event";
    }
    leaf text {
      type string;
      description
        "Additional message text";
      xr:event-telemetry "Subscribe Telemetry Event";
    }
  }

  grouping AN-REMOTE-LOG-SERVER {
    description
      "A System log AN remote log server structure";
    leaf ip-address {
      type string;
      description
        "IP Address";
    }
    leaf vrf-name {
      type string;
      description
        "VRF Name";
    }
    leaf vrf-severity {
      type string;
      description
        "VRF Severity";
    }
    leaf rh-discriminator {
      type string;
      description
        "Remote-Host Discriminator";
    }
  }

  grouping AN-REMOTE-LOG-SERVERS {
    description
      "System log All AN remote servers";
    list an-remote-log-server {
      description
        "AN Remote Log Servers";
      uses AN-REMOTE-LOG-SERVER;
    }
  }

  grouping FILE-LOG-DETAILS {
    description
      "System log file details";
    leaf file-path {
      type string;
      description
        "File path for logging messages";
    }
    leaf file-name {
      type string;
      description
        "File name for logging messages";
    }
  }

  grouping FILE-LOG-LIST-PATH {
    description
      "System log files list and path";
    list file-log-detail {
      description
        "Logging Files";
      uses FILE-LOG-DETAILS;
    }
  }
}

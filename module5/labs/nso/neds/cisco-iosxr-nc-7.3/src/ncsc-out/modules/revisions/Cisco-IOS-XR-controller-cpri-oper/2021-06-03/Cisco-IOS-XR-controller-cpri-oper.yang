module Cisco-IOS-XR-controller-cpri-oper {
  // Generated by yanger -t ncs
  tailf:mount-id "cisco-iosxr-nc-7.3:cisco-iosxr-nc-7.3";
  tailf:ncs-device-type "netconf";

  namespace "http://cisco.com/ns/yang/Cisco-IOS-XR-controller-cpri-oper";
  prefix controller-cpri-oper;

  import Cisco-IOS-XR-types {
    prefix xr;
  }
  import cisco-semver {
    prefix semver;
  }
  include Cisco-IOS-XR-controller-cpri-oper-sub1 {
    revision-date 2021-06-03;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-cpri package operational data.

     This module contains definitions
     for the following management objects:
       cpri: CPRI operational data

     Copyright (c) 2013-2021 by Cisco Systems, Inc.
     All rights reserved.";

  revision 2021-06-03 {
    description
      "Added leaf cpri-hfn-sync-event to container stats.
       2021-05-10
         Added leaf hfn-sync-disable to grouping CPRI-PORT-ROE-PARAMS
       2021-05-03
         Added mapper,demapper roe-profile parameters presync-match-threshold, resync-match-threshold, resync-mismatch-threshold, sync-threshold, drain-threshold, presync-match-count, resync-match-count, resync-mismatch-count.
       2021-04-30
         Added roe-pkt-len-in-use to container info.
       2020-11-04
         Added auto-neg-status, auto-neg-fail-reason, hfn-sync-time, roe-sync-time and auto-neg-completion-time to container info. Added rx-cpri-hyper-frames and tx-cpri-hyper-frames to container stats.";
    semver:module-version "2.1.0";
  }
  revision 2020-08-03 {
    description
      "Changed leaf packet-len type to uint16. Renamed leaf errored-packets to errored-length-packets. Added leaves receive-good-packets and receive-roe-lcv-count.";
    semver:module-version "2.0.0";
  }
  revision 2019-12-02 {
    description
      "Show command subtype added for CPRI controller";
    semver:module-version "1.1.0";
  }
  revision 2019-04-05 {
    description
      "Establish semantic version baseline.";
    semver:module-version "1.0.0";
  }
  revision 2015-11-09 {
    description
      "IOS XR 6.0 revision.";
  }

  augment "/ncs:devices/ncs:device/ncs:config" {
    // NCS drop config false container cpri
  }
  augment "/ncs:devices/ncs:device/ncs:live-status" {
    container cpri {
      tailf:ncs-device-type "netconf";
      tailf:display-when "not(../../ncs:module) or ../../ncs:module[ncs:name='Cisco-IOS-XR-controller-cpri-oper'] or (../../ncs:live-status-protocol[not(ncs:capability)]) or (../../ncs:live-status-protocol/ncs:capability/ncs:module[.='Cisco-IOS-XR-controller-cpri-oper'])";
      description
        "CPRI operational data";
      container controllers {
        description
          "All CPRI controller operational data";
        list controller {
          key "controller-name";
          description
            "CPRI controller operational data";
          container detail {
            description
              "CPRI controller detailed data including ROE
               stats";
            uses live_ncs_CPRI-PORT-DETAIL;
          }
          container stats {
            description
              "CPRI controller operational data statistics";
            uses live_ncs_CPRI-PORT-STATS;
          }
          container info {
            description
              "CPRI controller operational data";
            uses live_ncs_CPRI-PORT-INFO;
          }
          container roe-stats {
            description
              "ROE statistics w.r.t CPRI controller";
            uses live_ncs_CPRI-PORT-ROE-STATS;
          }
          container roe-profile {
            description
              "ROE profile params associated with CPRI
               controller";
            uses live_ncs_CPRI-PORT-ROE-PROFILE;
          }
          leaf controller-name {
            type xr:live_ncs_Interface-name;
            description
              "Interface name";
          }
        }
      }
    }
  }
  augment "/ncs:devices/ncs:template/ncs:ned-id/ncs:config" {
    // NCS drop config false container cpri
  }
}

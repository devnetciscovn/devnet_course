module Cisco-IOS-XR-config-cfgmgr-exec-augmented-oper {
  // Generated by yanger -t ncs
  tailf:mount-id "cisco-iosxr-nc-7.3:cisco-iosxr-nc-7.3";
  tailf:ncs-device-type "netconf";

  namespace "http://cisco.com/ns/yang/Cisco-IOS-XR-config-cfgmgr-exec-augmented-oper";
  prefix config-cfgmgr-exec-augmented-oper;

  import cisco-semver {
    prefix semver;
  }
  import Cisco-IOS-XR-config-cfgmgr-exec-oper {
    prefix cfgmgr-exec;
  }
  import tailf-common {
    prefix tailf;
  }
  import tailf-ncs {
    prefix ncs;
  }

  organization
    "Cisco Systems, Inc.";
  contact
    "
     Cisco Systems, Inc.
     Customer Service

     Postal: 170 W Tasman Drive
     San Jose, CA 95134

     Tel: +1 1800 553-NETS

     E-mail: cs-yang@cisco.com";
  description
    "This module contains a collection of YANG definitions
     for Cisco IOS-XR config-cfgmgr-exec-oper package operational data.

     Copyright (c) 2020 by Cisco Systems, Inc.
     All rights reserved.";

  revision 2020-06-02 {
    description
      "Initial revision to augment Cisco-IOS-XR-config-cfgmgr-exec-oper.yang model.";
    semver:module-version "1.0.0";
  }

  augment "/ncs:devices/ncs:device/ncs:live-status/cfgmgr-exec:config-manager/cfgmgr-exec:global/cfgmgr-exec:config-commit" {
    description
      "Augmenting Cisco-IOS-XR-config-cfgmgr-exec-oper model with
       last-commit-id.";
    leaf last-commit-id {
      tailf:ncs-device-type "netconf";
      tailf:display-when "not(../../../../../ncs:module) or ../../../../../ncs:module[ncs:name='Cisco-IOS-XR-config-cfgmgr-exec-augmented-oper'] or (../../../../../ncs:live-status-protocol[not(ncs:capability)]) or (../../../../../ncs:live-status-protocol/ncs:capability/ncs:module[.='Cisco-IOS-XR-config-cfgmgr-exec-augmented-oper'])";
      type string;
      description
        "Identifier for the last commit in devices with a system admin console.
         A client can use this to detect if the config datastore is modified in
         either the XR or the system admin VMs.";
    }
  }
}

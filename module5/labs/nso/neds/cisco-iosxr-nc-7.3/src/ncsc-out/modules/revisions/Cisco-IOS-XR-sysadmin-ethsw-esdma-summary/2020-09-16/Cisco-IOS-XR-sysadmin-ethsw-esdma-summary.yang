module Cisco-IOS-XR-sysadmin-ethsw-esdma-summary {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-summary";
  prefix esdma_summary;

  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch summary' commands.

     Copyright (c) 2011-2020 by Cisco Systems, Inc.
     All rights reserved.";

  revision 2020-09-16 {
    description
      "Addition of new groupings for iosxrwbd";
    semver:module-version "1.1.0";
  }
  revision 2019-04-15 {
    description
      "Establish semantic version baseline.";
    semver:module-version "1.0.0";
  }
  revision 2017-05-01 {
    description
      "Namespace change to comply with Cisco guidelines on namespace";
  }
  revision 2016-07-06 {
    description
      "Initial revision with content extracted from esdma_cli.yang.";
  }

  grouping ncs_template_switch-summary-group {
    container summary {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest";
        }
        leaf switch-id {
          type esdma_types:ncs_template_esdma-switch-type-enum;
          description
            "Switch type";
        }
        leaf serial-num {
          type string;
          description
            "Rack serial number";
        }
        list port-iter {
          // NCS patched for predictable order
          ordered-by user;
          key "port";
          leaf port {
            type esdma_types:ncs_template_esdma-switch-port-type;
            description
              "Switch port";
          }
          leaf phys-state {
            type esdma_types:ncs_template_esdma-switch-port-state;
            description
              "Physical port state";
          }
          leaf admin-state {
            type esdma_types:ncs_template_esdma-switch-port-state;
            description
              "Administrative port state";
          }
          leaf port-speed {
            type string;
            description
              "Indicates the port speed in bits per second";
          }
          leaf protocol-state {
            type esdma_types:ncs_template_mlap-state-enum;
            description
              "Protocol invoked port state";
          }
          leaf forwarding {
            type esdma_types:ncs_template_switch-forwarding-state;
            description
              "Indicates whether this port is allowed to forward traffic";
          }
          leaf connects-to {
            type string;
            description
              "Indicates what this port connects to";
          }
        }
      }
    }
  }

  grouping ncs_template_switch-summary-group-iosxrwbd {
    container summary {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest";
        }
        leaf switch-id {
          type esdma_types:ncs_template_esdma-switch-type-enum;
          description
            "Switch type";
        }
        leaf serial-num {
          type string;
          description
            "Rack serial number";
        }
        list port-iter {
          // NCS patched for predictable order
          ordered-by user;
          key "port";
          leaf port {
            type esdma_types:ncs_template_esdma-switch-port-type;
            description
              "Switch port";
          }
          leaf phys-state {
            type esdma_types:ncs_template_esdma-switch-port-state;
            description
              "Physical port state";
          }
          leaf admin-state {
            type esdma_types:ncs_template_esdma-switch-port-state;
            description
              "Administrative port state";
          }
          leaf port-speed {
            type string;
            description
              "Indicates the port speed in bits per second";
          }
          leaf protocol-state {
            type esdma_types:ncs_template_mlap-state-enum;
            description
              "Protocol invoked port state";
          }
          leaf forwarding {
            type esdma_types:ncs_template_switch-forwarding-state;
            description
              "Indicates whether this port is allowed to forward traffic";
          }
        }
      }
    }
  }

  grouping ncs_rpc_notif_switch-summary-group {
    container summary {
      list location {
        key "rack card switch-id";
        leaf rack {
          type esdma_types:ncs_rpc_notif_esdma-rack-num-enum;
        }
        leaf card {
          type esdma_types:ncs_rpc_notif_esdma-cpu;
          description
            "Card that owns a switch of interest";
        }
        leaf switch-id {
          type esdma_types:ncs_rpc_notif_esdma-switch-type-enum;
          description
            "Switch type";
        }
        leaf serial-num {
          type string;
          description
            "Rack serial number";
        }
        list port-iter {
          key "port";
          leaf port {
            type esdma_types:ncs_rpc_notif_esdma-switch-port-type;
            description
              "Switch port";
          }
          leaf phys-state {
            type esdma_types:ncs_rpc_notif_esdma-switch-port-state;
            description
              "Physical port state";
          }
          leaf admin-state {
            type esdma_types:ncs_rpc_notif_esdma-switch-port-state;
            description
              "Administrative port state";
          }
          leaf port-speed {
            type string;
            description
              "Indicates the port speed in bits per second";
          }
          leaf protocol-state {
            type esdma_types:ncs_rpc_notif_mlap-state-enum;
            description
              "Protocol invoked port state";
          }
          leaf forwarding {
            type esdma_types:ncs_rpc_notif_switch-forwarding-state;
            description
              "Indicates whether this port is allowed to forward traffic";
          }
          leaf connects-to {
            type string;
            description
              "Indicates what this port connects to";
          }
        }
      }
    }
  }

  grouping ncs_rpc_notif_switch-summary-group-iosxrwbd {
    container summary {
      list location {
        key "rack card switch-id";
        leaf rack {
          type esdma_types:ncs_rpc_notif_esdma-rack-num-enum;
        }
        leaf card {
          type esdma_types:ncs_rpc_notif_esdma-cpu;
          description
            "Card that owns a switch of interest";
        }
        leaf switch-id {
          type esdma_types:ncs_rpc_notif_esdma-switch-type-enum;
          description
            "Switch type";
        }
        leaf serial-num {
          type string;
          description
            "Rack serial number";
        }
        list port-iter {
          key "port";
          leaf port {
            type esdma_types:ncs_rpc_notif_esdma-switch-port-type;
            description
              "Switch port";
          }
          leaf phys-state {
            type esdma_types:ncs_rpc_notif_esdma-switch-port-state;
            description
              "Physical port state";
          }
          leaf admin-state {
            type esdma_types:ncs_rpc_notif_esdma-switch-port-state;
            description
              "Administrative port state";
          }
          leaf port-speed {
            type string;
            description
              "Indicates the port speed in bits per second";
          }
          leaf protocol-state {
            type esdma_types:ncs_rpc_notif_mlap-state-enum;
            description
              "Protocol invoked port state";
          }
          leaf forwarding {
            type esdma_types:ncs_rpc_notif_switch-forwarding-state;
            description
              "Indicates whether this port is allowed to forward traffic";
          }
        }
      }
    }
  }

  grouping live_ncs_switch-summary-group {
    container summary {
      list location {
        key "rack card switch-id";
        leaf rack {
          type esdma_types:live_ncs_esdma-rack-num-enum;
        }
        leaf card {
          type esdma_types:live_ncs_esdma-cpu;
          description
            "Card that owns a switch of interest";
        }
        leaf switch-id {
          type esdma_types:live_ncs_esdma-switch-type-enum;
          description
            "Switch type";
        }
        leaf serial-num {
          type string;
          description
            "Rack serial number";
        }
        list port-iter {
          key "port";
          leaf port {
            type esdma_types:live_ncs_esdma-switch-port-type;
            description
              "Switch port";
          }
          leaf phys-state {
            type esdma_types:live_ncs_esdma-switch-port-state;
            description
              "Physical port state";
          }
          leaf admin-state {
            type esdma_types:live_ncs_esdma-switch-port-state;
            description
              "Administrative port state";
          }
          leaf port-speed {
            type string;
            description
              "Indicates the port speed in bits per second";
          }
          leaf protocol-state {
            type esdma_types:live_ncs_mlap-state-enum;
            description
              "Protocol invoked port state";
          }
          leaf forwarding {
            type esdma_types:live_ncs_switch-forwarding-state;
            description
              "Indicates whether this port is allowed to forward traffic";
          }
          leaf connects-to {
            type string;
            description
              "Indicates what this port connects to";
          }
        }
      }
    }
  }

  grouping live_ncs_switch-summary-group-iosxrwbd {
    container summary {
      list location {
        key "rack card switch-id";
        leaf rack {
          type esdma_types:live_ncs_esdma-rack-num-enum;
        }
        leaf card {
          type esdma_types:live_ncs_esdma-cpu;
          description
            "Card that owns a switch of interest";
        }
        leaf switch-id {
          type esdma_types:live_ncs_esdma-switch-type-enum;
          description
            "Switch type";
        }
        leaf serial-num {
          type string;
          description
            "Rack serial number";
        }
        list port-iter {
          key "port";
          leaf port {
            type esdma_types:live_ncs_esdma-switch-port-type;
            description
              "Switch port";
          }
          leaf phys-state {
            type esdma_types:live_ncs_esdma-switch-port-state;
            description
              "Physical port state";
          }
          leaf admin-state {
            type esdma_types:live_ncs_esdma-switch-port-state;
            description
              "Administrative port state";
          }
          leaf port-speed {
            type string;
            description
              "Indicates the port speed in bits per second";
          }
          leaf protocol-state {
            type esdma_types:live_ncs_mlap-state-enum;
            description
              "Protocol invoked port state";
          }
          leaf forwarding {
            type esdma_types:live_ncs_switch-forwarding-state;
            description
              "Indicates whether this port is allowed to forward traffic";
          }
        }
      }
    }
  }

  grouping switch-summary-group {
    container summary {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter {
          key "port";
          leaf port {
            type esdma_types:esdma-switch-port-type;
            description
              "Switch port";
          }
          leaf phys-state {
            type esdma_types:esdma-switch-port-state;
            description
              "Physical port state";
          }
          leaf admin-state {
            type esdma_types:esdma-switch-port-state;
            description
              "Administrative port state";
          }
          leaf port-speed {
            type string;
            description
              "Indicates the port speed in bits per second";
          }
          leaf protocol-state {
            type esdma_types:mlap-state-enum;
            description
              "Protocol invoked port state";
          }
          leaf forwarding {
            type esdma_types:switch-forwarding-state;
            description
              "Indicates whether this port is allowed to forward traffic";
          }
          leaf connects-to {
            type string;
            description
              "Indicates what this port connects to";
          }
        }
      }
    }
  }

  grouping switch-summary-group-iosxrwbd {
    container summary {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter {
          key "port";
          leaf port {
            type esdma_types:esdma-switch-port-type;
            description
              "Switch port";
          }
          leaf phys-state {
            type esdma_types:esdma-switch-port-state;
            description
              "Physical port state";
          }
          leaf admin-state {
            type esdma_types:esdma-switch-port-state;
            description
              "Administrative port state";
          }
          leaf port-speed {
            type string;
            description
              "Indicates the port speed in bits per second";
          }
          leaf protocol-state {
            type esdma_types:mlap-state-enum;
            description
              "Protocol invoked port state";
          }
          leaf forwarding {
            type esdma_types:switch-forwarding-state;
            description
              "Indicates whether this port is allowed to forward traffic";
          }
        }
      }
    }
  }
}

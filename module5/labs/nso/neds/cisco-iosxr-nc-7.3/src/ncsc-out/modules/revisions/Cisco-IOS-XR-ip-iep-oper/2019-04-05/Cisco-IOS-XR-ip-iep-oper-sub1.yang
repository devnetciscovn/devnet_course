submodule Cisco-IOS-XR-ip-iep-oper-sub1 {
  // Generated by yanger -t ncs
  tailf:mount-id "cisco-iosxr-nc-7.3:cisco-iosxr-nc-7.3";

  belongs-to Cisco-IOS-XR-ip-iep-oper {
    prefix Cisco-IOS-XR-ip-iep-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-iep package operational data.

     Copyright (c) 2013-2019 by Cisco Systems, Inc.
     All rights reserved.";

  revision 2019-04-05 {
    description
      "Establish semantic version baseline.";
    semver:module-version "1.0.1";
  }
  revision 2017-09-07 {
    description
      "Fixed type translation error.";
  }
  revision 2015-11-09 {
    description
      "IOS XR 6.0 revision.";
  }

  typedef ncs_template_Iep-hop {
    type string;
    description
      "Hop types of the next-address configured";
  }

  typedef ncs_template_Iep-address {
    type string;
    description
      "Address types";
  }

  typedef ncs_template_Iep-status {
    type string;
    description
      "Status of the path";
  }

  typedef ncs_rpc_notif_Iep-hop {
    type enumeration {
      enum "strict" {
        description
          "Hop type is strict";
      }
      enum "loose" {
        description
          "Hop type is loose";
      }
    }
    description
      "Hop types of the next-address configured";
  }

  typedef ncs_rpc_notif_Iep-address {
    type enumeration {
      enum "next" {
        description
          "Address type is next";
      }
      enum "exclude" {
        description
          "Address type is exclude";
      }
      enum "exclude-srlg" {
        description
          "Address type is exclude SRLG";
      }
    }
    description
      "Address types";
  }

  typedef ncs_rpc_notif_Iep-status {
    type enumeration {
      enum "enabled" {
        description
          "Status is enabled";
      }
      enum "disabled" {
        description
          "Status is disabled";
      }
    }
    description
      "Status of the path";
  }

  typedef live_ncs_Iep-hop {
    type enumeration {
      enum "strict" {
        description
          "Hop type is strict";
      }
      enum "loose" {
        description
          "Hop type is loose";
      }
    }
    description
      "Hop types of the next-address configured";
  }

  typedef live_ncs_Iep-address {
    type enumeration {
      enum "next" {
        description
          "Address type is next";
      }
      enum "exclude" {
        description
          "Address type is exclude";
      }
      enum "exclude-srlg" {
        description
          "Address type is exclude SRLG";
      }
    }
    description
      "Address types";
  }

  typedef live_ncs_Iep-status {
    type enumeration {
      enum "enabled" {
        description
          "Status is enabled";
      }
      enum "disabled" {
        description
          "Status is disabled";
      }
    }
    description
      "Status of the path";
  }

  typedef Iep-hop {
    type enumeration {
      enum "strict" {
        description
          "Hop type is strict";
      }
      enum "loose" {
        description
          "Hop type is loose";
      }
    }
    description
      "Hop types of the next-address configured";
  }

  typedef Iep-address {
    type enumeration {
      enum "next" {
        description
          "Address type is next";
      }
      enum "exclude" {
        description
          "Address type is exclude";
      }
      enum "exclude-srlg" {
        description
          "Address type is exclude SRLG";
      }
    }
    description
      "Address types";
  }

  typedef Iep-status {
    type enumeration {
      enum "enabled" {
        description
          "Status is enabled";
      }
      enum "disabled" {
        description
          "Status is disabled";
      }
    }
    description
      "Status of the path";
  }

  grouping ncs_template_IEP-IP-ADDRESS-ENTRY {
    description
      "IP address configured in the explicit path";
    leaf index {
      type string;
      description
        "Index number at which the path entry is inserted
         or modified";
    }
    leaf if-index {
      type string;
      description
        "Interface Index of the path";
    }
    leaf address-type {
      type ncs_template_Iep-address;
      description
        "Specifies the address type";
    }
    leaf hop-type {
      type ncs_template_Iep-hop;
      description
        "Specifies the next unicast address in the path
         as a strict or loose hop";
    }
    leaf address {
      type string;
      description
        "IPv4 unicast address";
    }
    leaf mpls-label {
      type string;
      description
        "MPLS label";
    }
  }

  grouping ncs_template_IEP-EXPLICIT-PATH {
    description
      "Explicit path details";
    leaf status {
      type ncs_template_Iep-status;
      description
        "Status of the path";
    }
    list address {
      // NCS patched for predictable order
      ordered-by user;
      description
        "List of IP addresses configured in the explicit
         path";
      uses ncs_template_IEP-IP-ADDRESS-ENTRY;
    }
  }

  grouping ncs_rpc_notif_IEP-IP-ADDRESS-ENTRY {
    description
      "IP address configured in the explicit path";
    leaf index {
      type uint32;
      description
        "Index number at which the path entry is inserted
         or modified";
    }
    leaf if-index {
      type uint32;
      description
        "Interface Index of the path";
    }
    leaf address-type {
      type ncs_rpc_notif_Iep-address;
      description
        "Specifies the address type";
    }
    leaf hop-type {
      type ncs_rpc_notif_Iep-hop;
      description
        "Specifies the next unicast address in the path
         as a strict or loose hop";
    }
    leaf address {
      type inet:ipv4-address;
      description
        "IPv4 unicast address";
    }
    leaf mpls-label {
      type uint32;
      description
        "MPLS label";
    }
  }

  grouping ncs_rpc_notif_IEP-EXPLICIT-PATH {
    description
      "Explicit path details";
    leaf status {
      type ncs_rpc_notif_Iep-status;
      description
        "Status of the path";
    }
    list address {
      description
        "List of IP addresses configured in the explicit
         path";
      uses ncs_rpc_notif_IEP-IP-ADDRESS-ENTRY;
    }
  }

  grouping live_ncs_IEP-IP-ADDRESS-ENTRY {
    description
      "IP address configured in the explicit path";
    leaf index {
      type uint32;
      description
        "Index number at which the path entry is inserted
         or modified";
    }
    leaf if-index {
      type uint32;
      description
        "Interface Index of the path";
    }
    leaf address-type {
      type live_ncs_Iep-address;
      description
        "Specifies the address type";
    }
    leaf hop-type {
      type live_ncs_Iep-hop;
      description
        "Specifies the next unicast address in the path
         as a strict or loose hop";
    }
    leaf address {
      type inet:ipv4-address;
      description
        "IPv4 unicast address";
    }
    leaf mpls-label {
      type uint32;
      description
        "MPLS label";
    }
  }

  grouping live_ncs_IEP-EXPLICIT-PATH {
    description
      "Explicit path details";
    leaf status {
      type live_ncs_Iep-status;
      description
        "Status of the path";
    }
    list address {
      description
        "List of IP addresses configured in the explicit
         path";
      uses live_ncs_IEP-IP-ADDRESS-ENTRY;
    }
  }

  grouping IEP-IP-ADDRESS-ENTRY {
    description
      "IP address configured in the explicit path";
    leaf index {
      type uint32;
      description
        "Index number at which the path entry is inserted
         or modified";
    }
    leaf if-index {
      type uint32;
      description
        "Interface Index of the path";
    }
    leaf address-type {
      type Iep-address;
      description
        "Specifies the address type";
    }
    leaf hop-type {
      type Iep-hop;
      description
        "Specifies the next unicast address in the path
         as a strict or loose hop";
    }
    leaf address {
      type inet:ipv4-address;
      description
        "IPv4 unicast address";
    }
    leaf mpls-label {
      type uint32;
      description
        "MPLS label";
    }
  }

  grouping IEP-EXPLICIT-PATH {
    description
      "Explicit path details";
    leaf status {
      type Iep-status;
      description
        "Status of the path";
    }
    list address {
      description
        "List of IP addresses configured in the explicit
         path";
      uses IEP-IP-ADDRESS-ENTRY;
    }
  }
}

module Cisco-IOS-XR-asr9k-apm-src-flexr-cfg {
  // Generated by yanger -t ncs
  tailf:mount-id "cisco-iosxr-nc-7.3:cisco-iosxr-nc-7.3";
  tailf:ncs-device-type "netconf";

  namespace "http://cisco.com/ns/yang/Cisco-IOS-XR-asr9k-apm-src-flexr-cfg";
  prefix asr9k-apm-src-flexr-cfg;

  import Cisco-IOS-XR-types {
    prefix xr;
  }
  import cisco-semver {
    prefix semver;
  }
  import Cisco-IOS-XR-config-mda-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-apm-src-flexr package configuration.

     This module contains definitions
     for the following management objects:
       hw-module-slice-config: Advanced power management

     Copyright (c) 2013-2021 by Cisco Systems, Inc.
     All rights reserved.";

  revision 2021-03-01 {
    description
      "IOS XR 7.4.1 revision.";
    semver:module-version "1.0.0";
  }
  revision 2019-04-05 {
    description
      "Establish semantic version baseline.";
  }
  revision 2015-11-09 {
    description
      "IOS XR 6.0 revision.";
  }

  typedef ncs_template_Slice-power-management-mode {
    type string;
    description
      "Slice power management mode";
  }

  typedef ncs_rpc_notif_Slice-power-management-mode {
    type enumeration {
      enum "power-savings" {
        value 1;
        description
          "Shutdown the slice";
      }
      enum "power-down" {
        value 2;
        description
          "Power down the slice";
      }
    }
    description
      "Slice power management mode";
  }

  typedef live_ncs_Slice-power-management-mode {
    type enumeration {
      enum "power-savings" {
        value 1;
        description
          "Shutdown the slice";
      }
      enum "power-down" {
        value 2;
        description
          "Power down the slice";
      }
    }
    description
      "Slice power management mode";
  }

  typedef Slice-power-management-mode {
    type enumeration {
      enum "power-savings" {
        value 1;
        description
          "Shutdown the slice";
      }
      enum "power-down" {
        value 2;
        description
          "Power down the slice";
      }
    }
    description
      "Slice power management mode";
  }

  augment "/ncs:devices/ncs:device/ncs:config" {
    container hw-module-slice-config {
      tailf:ncs-device-type "netconf";
      tailf:display-when "not(../../ncs:module) or ../../ncs:module[ncs:name='Cisco-IOS-XR-asr9k-apm-src-flexr-cfg']";
      description
        "Advanced power management";
      container apm {
        description
          "Advanced power management";
        container nodes {
          description
            "line-card node location";
          list node {
            key "node-name";
            description
              "line-card node location";
            container slices {
              description
                "Slice Table";
              list slice {
                key "slice-number";
                description
                  "Slice";
                leaf power-management-mode {
                  type Slice-power-management-mode;
                  description
                    "Slice power management mode";
                }
                leaf slice-number {
                  type uint32 {
                    range "0..9";
                  }
                  description
                    "Slice number";
                }
              }
            }
            leaf node-name {
              type xr:Node-id;
              description
                "Fully qualified line card specification";
            }
          }
        }
      }
    }
  }
  augment "/ncs:devices/ncs:device/ncs:live-status" {
    container hw-module-slice-config {
      tailf:ncs-device-type "netconf";
      tailf:display-when "not(../../ncs:module) or ../../ncs:module[ncs:name='Cisco-IOS-XR-asr9k-apm-src-flexr-cfg'] or (../../ncs:live-status-protocol[not(ncs:capability)]) or (../../ncs:live-status-protocol/ncs:capability/ncs:module[.='Cisco-IOS-XR-asr9k-apm-src-flexr-cfg'])";
      description
        "Advanced power management";
      container apm {
        description
          "Advanced power management";
        container nodes {
          description
            "line-card node location";
          list node {
            key "node-name";
            description
              "line-card node location";
            container slices {
              description
                "Slice Table";
              list slice {
                key "slice-number";
                description
                  "Slice";
                leaf power-management-mode {
                  type live_ncs_Slice-power-management-mode;
                  description
                    "Slice power management mode";
                }
                leaf slice-number {
                  type uint32 {
                    range "0..9";
                  }
                  description
                    "Slice number";
                }
              }
            }
            leaf node-name {
              type xr:live_ncs_Node-id;
              description
                "Fully qualified line card specification";
            }
          }
        }
      }
    }
  }
  augment "/ncs:devices/ncs:template/ncs:ned-id/ncs:config" {
    container hw-module-slice-config {
      description
        "Advanced power management";
      container apm {
        description
          "Advanced power management";
        container nodes {
          description
            "line-card node location";
          list node {
            // NCS patched for predictable order
            ordered-by user;
            key "node-name";
            description
              "line-card node location";
            container slices {
              description
                "Slice Table";
              list slice {
                // NCS patched for predictable order
                ordered-by user;
                key "slice-number";
                description
                  "Slice";
                leaf power-management-mode {
                  type ncs_template_Slice-power-management-mode;
                  description
                    "Slice power management mode";
                }
                leaf slice-number {
                  type string;
                  description
                    "Slice number";
                }
              }
            }
            leaf node-name {
              type xr:ncs_template_Node-id;
              description
                "Fully qualified line card specification";
            }
          }
        }
      }
    }
  }
}

module Cisco-IOS-XR-platform-inventory-oper {
  // Generated by yanger -t ncs
  tailf:mount-id "cisco-iosxr-nc-7.3:cisco-iosxr-nc-7.3";
  tailf:ncs-device-type "netconf";

  namespace "http://cisco.com/ns/yang/Cisco-IOS-XR-platform-inventory-oper";
  prefix platform-inventory-oper;

  import Cisco-IOS-XR-types {
    prefix xr;
  }
  import cisco-semver {
    prefix semver;
  }
  include Cisco-IOS-XR-platform-inventory-oper-sub1 {
    revision-date 2020-05-14;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platform-inventory package operational data.

     This module contains definitions
     for the following management objects:
       platform-inventory: Inventory operational data

     Copyright (c) 2013-2020 by Cisco Systems, Inc.
     All rights reserved.";

  revision 2020-05-14 {
    description
      "New model, replaces Cisco-IOS-XR-plat-chas-invmgr-ng-oper";
    semver:module-version "1.0.0";
  }
  revision 2019-04-05 {
    description
      "Establish semantic version baseline.";
  }
  revision 2015-11-09 {
    description
      "IOS XR 6.0 revision.";
  }

  grouping ncs_template_PORT-SLOT-TABLE {
    description
      "Common node of card, module";
    container port-slots {
      description
        "Table of port slots";
      list port-slot {
        // NCS patched for predictable order
        ordered-by user;
        key "name";
        description
          "Port slot number";
        leaf name {
          type xr:ncs_template_Cisco-ios-xr-string;
          description
            "Port slot name";
        }
        uses ncs_template_PORT-TABLE;
        uses ncs_template_INVENTORY-COMMON-SENSOR-TABLE;
        uses ncs_template_INVENTORY-COMMON-ATTRIBUTES;
      }
    }
  }

  grouping ncs_template_SLOT-TABLE {
    description
      "Common node of rack, rack";
    container slots {
      description
        "Table of slots";
      list slot {
        // NCS patched for predictable order
        ordered-by user;
        key "name";
        description
          "Slot name";
        container cards {
          description
            "Table of cards";
          list card {
            // NCS patched for predictable order
            ordered-by user;
            key "name";
            description
              "Card number";
            container hardware-information {
              description
                "HardwareInformationDir";
              container processor-information {
                description
                  "ProcesorInformation";
                uses ncs_template_INV-PROCESSOR;
              }
              container motherboard-information {
                description
                  "MotherboardInformation";
                uses ncs_template_INV-XML-MOTHERBOARD-INFO;
              }
              container bootflash-information {
                description
                  "BootflashInformation";
                uses ncs_template_INV-BOOTFLASH;
              }
              container disk-information {
                description
                  "DiskInformation";
                uses ncs_template_INV-XML-DISK-INFO;
              }
            }
            container sub-slots {
              description
                "Table of subslots";
              list sub-slot {
                // NCS patched for predictable order
                ordered-by user;
                key "name";
                description
                  "Subslot number";
                container module {
                  description
                    "Module of a subslot";
                  uses ncs_template_PORT-SLOT-TABLE;
                  uses ncs_template_INVENTORY-COMMON-SENSOR-TABLE;
                  uses ncs_template_INVENTORY-COMMON-ATTRIBUTES;
                }
                leaf name {
                  type xr:ncs_template_Cisco-ios-xr-string;
                  description
                    "Subslot name";
                }
                uses ncs_template_INVENTORY-COMMON-ATTRIBUTES;
              }
            }
            container modules {
              description
                "Table of modules";
              list module {
                // NCS patched for predictable order
                ordered-by user;
                key "module-name";
                description
                  "A module";
                container sub-modules {
                  description
                    "Table of Sub Module components ";
                  list sub-module {
                    // NCS patched for predictable order
                    ordered-by user;
                    key "name";
                    description
                      "Sub Module component number";
                    container sub-module-l2s {
                      description
                        "Table of Sub Module components ";
                      list sub-module-l2 {
                        // NCS patched for predictable order
                        ordered-by user;
                        key "name";
                        description
                          "Sub Module component number";
                        container sub-module-l3s {
                          description
                            "Table of Sub Module components ";
                          list sub-module-l3 {
                            // NCS patched for predictable order
                            ordered-by user;
                            key "name";
                            description
                              "Sub Module component number";
                            container sub-module-l4s {
                              description
                                "Table of Sub Module components ";
                              list sub-module-l4 {
                                // NCS patched for predictable order
                                ordered-by user;
                                key "name";
                                description
                                  "Sub Module component number";
                                container sub-module-l5s {
                                  description
                                    "Table of Sub Module components ";
                                  list sub-module-l5 {
                                    // NCS patched for predictable order
                                    ordered-by user;
                                    key "name";
                                    description
                                      "Sub Module component number";
                                    leaf name {
                                      type xr:ncs_template_Cisco-ios-xr-string;
                                      description
                                        "HW component name";
                                    }
                                    uses ncs_template_INVENTORY-EXT2-OPER-SENSOR-TABLE;
                                    uses ncs_template_INVENTORY-EXT2-OPER-ATTRIBUTES;
                                    uses ncs_template_INVENTORY-EXT2-OPER-HW-COMPONENT-TABLE;
                                  }
                                }
                                leaf name {
                                  type xr:ncs_template_Cisco-ios-xr-string;
                                  description
                                    "HW component name";
                                }
                                uses ncs_template_INVENTORY-EXT2-OPER-SENSOR-TABLE;
                                uses ncs_template_INVENTORY-EXT2-OPER-ATTRIBUTES;
                                uses ncs_template_INVENTORY-EXT2-OPER-HW-COMPONENT-TABLE;
                              }
                            }
                            container ports {
                              description
                                "Table of spirit port slots";
                              list port {
                                // NCS patched for predictable order
                                ordered-by user;
                                key "name";
                                description
                                  "Port number";
                                leaf name {
                                  type xr:ncs_template_Cisco-ios-xr-string;
                                  description
                                    "Port name";
                                }
                                uses ncs_template_INVENTORY-EXT2-OPER-ATTRIBUTES;
                              }
                            }
                            leaf name {
                              type xr:ncs_template_Cisco-ios-xr-string;
                              description
                                "HW component name";
                            }
                            uses ncs_template_INVENTORY-EXT2-OPER-SENSOR-TABLE;
                            uses ncs_template_INVENTORY-EXT2-OPER-ATTRIBUTES;
                            uses ncs_template_INVENTORY-EXT2-OPER-HW-COMPONENT-TABLE;
                          }
                        }
                        leaf name {
                          type xr:ncs_template_Cisco-ios-xr-string;
                          description
                            "HW component name";
                        }
                        uses ncs_template_INVENTORY-EXT2-OPER-SENSOR-TABLE;
                        uses ncs_template_INVENTORY-EXT2-OPER-ATTRIBUTES;
                        uses ncs_template_INVENTORY-EXT2-OPER-HW-COMPONENT-TABLE;
                      }
                    }
                    container ports {
                      description
                        "Table of spirit port slots";
                      list port {
                        // NCS patched for predictable order
                        ordered-by user;
                        key "name";
                        description
                          "Port number";
                        container port-modules {
                          description
                            "Table of Module components ";
                          list port-module {
                            // NCS patched for predictable order
                            ordered-by user;
                            key "name";
                            description
                              "POrt Module component number";
                            leaf name {
                              type xr:ncs_template_Cisco-ios-xr-string;
                              description
                                "module name";
                            }
                            uses ncs_template_ATTRIBUTES;
                          }
                        }
                        leaf name {
                          type xr:ncs_template_Cisco-ios-xr-string;
                          description
                            "Port name";
                        }
                        uses ncs_template_ATTRIBUTES;
                        uses ncs_template_INVENTORY-EXT1-OPER-HW-COMPONENT-TABLE;
                      }
                    }
                    leaf name {
                      type xr:ncs_template_Cisco-ios-xr-string;
                      description
                        "HW component name";
                    }
                    uses ncs_template_SENSOR-TABLE;
                    uses ncs_template_ATTRIBUTES;
                    uses ncs_template_INVENTORY-EXT1-OPER-HW-COMPONENT-TABLE;
                  }
                }
                leaf module-name {
                  type xr:ncs_template_Cisco-ios-xr-string;
                  description
                    "Module name";
                }
                uses ncs_template_SENSOR-TABLE;
                uses ncs_template_ATTRIBUTES;
                uses ncs_template_INVENTORY-EXT1-OPER-HW-COMPONENT-TABLE;
              }
            }
            leaf name {
              type xr:ncs_template_Cisco-ios-xr-string;
              description
                "Card name";
            }
            uses ncs_template_PORT-TABLE;
            uses ncs_template_PORT-SLOT-TABLE;
            uses ncs_template_HW-COMPONENT-TABLE;
            uses ncs_template_INVENTORY-COMMON-SENSOR-TABLE;
            uses ncs_template_INVENTORY-COMMON-ATTRIBUTES;
          }
        }
        leaf name {
          type xr:ncs_template_Cisco-ios-xr-string;
          description
            "Slot name";
        }
        uses ncs_template_INVENTORY-COMMON-ATTRIBUTES;
      }
    }
  }

  grouping ncs_template_SENSOR-TABLE {
    description
      "Common node of module, sub-module, hw-component";
    container sensors {
      description
        "Table of sensors";
      list sensor {
        // NCS patched for predictable order
        ordered-by user;
        key "name";
        description
          "Sensor number";
        leaf name {
          type xr:ncs_template_Cisco-ios-xr-string;
          description
            "Sensor name";
        }
        uses ncs_template_ATTRIBUTES;
      }
    }
  }

  grouping ncs_template_INVENTORY-EXT2-OPER-SENSOR-TABLE {
    description
      "Common node of module, sub-module,
       hw-componentCommon node of hw-component,
       sub-module-l2, sub-module-l3, sub-module-l4,
       sub-module-l5";
    container sensors {
      description
        "Table of sensors";
      list sensor {
        // NCS patched for predictable order
        ordered-by user;
        key "name";
        description
          "Sensor number";
        leaf name {
          type xr:ncs_template_Cisco-ios-xr-string;
          description
            "Sensor name";
        }
        uses ncs_template_INVENTORY-EXT2-OPER-ATTRIBUTES;
      }
    }
  }

  grouping ncs_template_INVENTORY-COMMON-SENSOR-TABLE {
    description
      "Common node of module, sub-module,
       hw-componentCommon node of hw-component,
       sub-module-l2, sub-module-l3, sub-module-l4,
       sub-module-l5Common node of card, module,
       hw-component, port-slot, ports";
    container sensors {
      description
        "Table of sensors";
      list sensor {
        // NCS patched for predictable order
        ordered-by user;
        key "name";
        description
          "Sensor number";
        leaf name {
          type xr:ncs_template_Cisco-ios-xr-string;
          description
            "Sensor name";
        }
        uses ncs_template_INVENTORY-COMMON-ATTRIBUTES;
      }
    }
  }

  grouping ncs_template_PORT-TABLE {
    description
      "Common node of port-slot, card";
    container portses {
      description
        "Table of port slots";
      list ports {
        // NCS patched for predictable order
        ordered-by user;
        key "name";
        description
          "Port number";
        leaf name {
          type xr:ncs_template_Cisco-ios-xr-string;
          description
            "Port name";
        }
        uses ncs_template_HW-COMPONENT-TABLE;
        uses ncs_template_INVENTORY-COMMON-SENSOR-TABLE;
        uses ncs_template_INVENTORY-COMMON-ATTRIBUTES;
      }
    }
  }

  grouping ncs_template_HW-COMPONENT-TABLE {
    description
      "Common node of card, ports";
    container hw-components {
      description
        "Table of  HW components ";
      list hw-component {
        // NCS patched for predictable order
        ordered-by user;
        key "name";
        description
          "HW component number";
        leaf name {
          type xr:ncs_template_Cisco-ios-xr-string;
          description
            "HW component name";
        }
        uses ncs_template_INVENTORY-COMMON-SENSOR-TABLE;
        uses ncs_template_INVENTORY-COMMON-ATTRIBUTES;
      }
    }
  }

  grouping ncs_template_INVENTORY-EXT1-OPER-HW-COMPONENT-TABLE {
    description
      "Common node of card, portsCommon node of module,
       sub-module, port";
    container hw-components {
      description
        "Table of HW components ";
      list hw-component {
        // NCS patched for predictable order
        ordered-by user;
        key "name";
        description
          "HW component number";
        leaf name {
          type xr:ncs_template_Cisco-ios-xr-string;
          description
            "HW component name";
        }
        uses ncs_template_SENSOR-TABLE;
        uses ncs_template_ATTRIBUTES;
      }
    }
  }

  grouping ncs_template_INVENTORY-EXT2-OPER-HW-COMPONENT-TABLE {
    description
      "Common node of card, portsCommon node of module,
       sub-module, portCommon node of sub-module-l2,
       sub-module-l3, sub-module-l4, sub-module-l5";
    container hw-components {
      description
        "Table of HW components ";
      list hw-component {
        // NCS patched for predictable order
        ordered-by user;
        key "name";
        description
          "HW component number";
        leaf name {
          type xr:ncs_template_Cisco-ios-xr-string;
          description
            "HW component name";
        }
        uses ncs_template_INVENTORY-EXT2-OPER-SENSOR-TABLE;
        uses ncs_template_INVENTORY-EXT2-OPER-ATTRIBUTES;
      }
    }
  }

  grouping ncs_template_INVENTORY-EXT3-OPER-HW-COMPONENT-TABLE {
    description
      "Common node of card, portsCommon node of module,
       sub-module, portCommon node of sub-module-l2,
       sub-module-l3, sub-module-l4, sub-module-l5Common
       node of backplane, module";
    container hw-components {
      description
        "Table of  HW components ";
      list hw-component {
        // NCS patched for predictable order
        ordered-by user;
        key "name";
        description
          "HW component number";
        leaf name {
          type xr:ncs_template_Cisco-ios-xr-string;
          description
            "HW component name";
        }
        uses ncs_template_INVENTORY-EXT3-OPER-ATTRIBUTES;
      }
    }
  }

  grouping ncs_template_ATTRIBUTES {
    description
      "Common node of module, sub-module, sensor,
       hw-component, port, port-module";
    container attributes {
      description
        "Attributes";
      container basic-info {
        description
          "Entity attributes";
        uses ncs_template_INV-XML-ENTITY-BASIC-INFO;
      }
      container fru-info {
        description
          "Field Replaceable Unit (FRU) attributes";
        uses ncs_template_INV-XML-FRU-INFO;
      }
    }
  }

  grouping ncs_template_INVENTORY-EXT2-OPER-ATTRIBUTES {
    description
      "Common node of module, sub-module, sensor,
       hw-component, port, port-moduleCommon node of
       sub-module-l2, sub-module-l3, sub-module-l4,
       sub-module-l5, sensor, hw-component, port";
    container attributes {
      description
        "Attributes";
      container basic-info {
        description
          "Entity attributes";
        uses ncs_template_INV-XML-ENTITY-BASIC-INFO;
      }
      container fru-info {
        description
          "Field Replaceable Unit (FRU) attributes";
        uses ncs_template_INV-XML-FRU-INFO;
      }
    }
  }

  grouping ncs_template_INVENTORY-EXT3-OPER-ATTRIBUTES {
    description
      "Common node of module, sub-module, sensor,
       hw-component, port, port-moduleCommon node of
       sub-module-l2, sub-module-l3, sub-module-l4,
       sub-module-l5, sensor, hw-component, portCommon
       node of backplane, module, hw-component";
    container attributes {
      description
        "Attributes";
      container basic-info {
        description
          "Entity attributes";
        uses ncs_template_INV-XML-ENTITY-BASIC-INFO;
      }
      container fru-info {
        description
          "Field Replaceable Unit (FRU) attributes";
        uses ncs_template_INV-XML-FRU-INFO;
      }
    }
  }

  grouping ncs_template_INVENTORY-COMMON-ATTRIBUTES {
    description
      "Common node of module, sub-module, sensor,
       hw-component, port, port-moduleCommon node of
       sub-module-l2, sub-module-l3, sub-module-l4,
       sub-module-l5, sensor, hw-component, portCommon
       node of backplane, module, hw-componentCommon
       node of rack, rack, slot, card, sub-slot, module,
       port-slot, hw-component, sensor, ports";
    container attributes {
      description
        "Attributes";
      container basic-info {
        description
          "Entity attributes";
        uses ncs_template_INV-XML-ENTITY-BASIC-INFO;
      }
      container fru-info {
        description
          "Field Replaceable Unit (FRU) attributes";
        uses ncs_template_INV-XML-FRU-INFO;
      }
    }
  }

  grouping ncs_template_BACKPLANE-TABLE {
    description
      "Common node of rack, rack";
    container backplanes {
      description
        "Table of backplane";
      list backplane {
        // NCS patched for predictable order
        ordered-by user;
        key "name";
        description
          "Backplane name";
        container modules {
          description
            "Table of modules";
          list module {
            // NCS patched for predictable order
            ordered-by user;
            key "module-name";
            description
              "A module";
            leaf module-name {
              type xr:ncs_template_Cisco-ios-xr-string;
              description
                "Module name";
            }
            uses ncs_template_INVENTORY-EXT3-OPER-ATTRIBUTES;
            uses ncs_template_INVENTORY-EXT3-OPER-HW-COMPONENT-TABLE;
          }
        }
        leaf name {
          type xr:ncs_template_Cisco-ios-xr-string;
          description
            "Backplane name";
        }
        uses ncs_template_INVENTORY-EXT3-OPER-ATTRIBUTES;
        uses ncs_template_INVENTORY-EXT3-OPER-HW-COMPONENT-TABLE;
      }
    }
  }

  grouping ncs_rpc_notif_PORT-SLOT-TABLE {
    description
      "Common node of card, module";
    container port-slots {
      description
        "Table of port slots";
      list port-slot {
        key "name";
        description
          "Port slot number";
        leaf name {
          type xr:ncs_rpc_notif_Cisco-ios-xr-string;
          description
            "Port slot name";
        }
        uses ncs_rpc_notif_PORT-TABLE;
        uses ncs_rpc_notif_INVENTORY-COMMON-SENSOR-TABLE;
        uses ncs_rpc_notif_INVENTORY-COMMON-ATTRIBUTES;
      }
    }
  }

  grouping ncs_rpc_notif_SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses ncs_rpc_notif_INV-PROCESSOR;
              }
              container motherboard-information {
                description
                  "MotherboardInformation";
                uses ncs_rpc_notif_INV-XML-MOTHERBOARD-INFO;
              }
              container bootflash-information {
                description
                  "BootflashInformation";
                uses ncs_rpc_notif_INV-BOOTFLASH;
              }
              container disk-information {
                description
                  "DiskInformation";
                uses ncs_rpc_notif_INV-XML-DISK-INFO;
              }
            }
            container sub-slots {
              description
                "Table of subslots";
              list sub-slot {
                key "name";
                description
                  "Subslot number";
                container module {
                  description
                    "Module of a subslot";
                  uses ncs_rpc_notif_PORT-SLOT-TABLE;
                  uses ncs_rpc_notif_INVENTORY-COMMON-SENSOR-TABLE;
                  uses ncs_rpc_notif_INVENTORY-COMMON-ATTRIBUTES;
                }
                leaf name {
                  type xr:ncs_rpc_notif_Cisco-ios-xr-string;
                  description
                    "Subslot name";
                }
                uses ncs_rpc_notif_INVENTORY-COMMON-ATTRIBUTES;
              }
            }
            container modules {
              description
                "Table of modules";
              list module {
                key "module-name";
                description
                  "A module";
                container sub-modules {
                  description
                    "Table of Sub Module components ";
                  list sub-module {
                    key "name";
                    description
                      "Sub Module component number";
                    container sub-module-l2s {
                      description
                        "Table of Sub Module components ";
                      list sub-module-l2 {
                        key "name";
                        description
                          "Sub Module component number";
                        container sub-module-l3s {
                          description
                            "Table of Sub Module components ";
                          list sub-module-l3 {
                            key "name";
                            description
                              "Sub Module component number";
                            container sub-module-l4s {
                              description
                                "Table of Sub Module components ";
                              list sub-module-l4 {
                                key "name";
                                description
                                  "Sub Module component number";
                                container sub-module-l5s {
                                  description
                                    "Table of Sub Module components ";
                                  list sub-module-l5 {
                                    key "name";
                                    description
                                      "Sub Module component number";
                                    leaf name {
                                      type xr:ncs_rpc_notif_Cisco-ios-xr-string;
                                      description
                                        "HW component name";
                                    }
                                    uses ncs_rpc_notif_INVENTORY-EXT2-OPER-SENSOR-TABLE;
                                    uses ncs_rpc_notif_INVENTORY-EXT2-OPER-ATTRIBUTES;
                                    uses ncs_rpc_notif_INVENTORY-EXT2-OPER-HW-COMPONENT-TABLE;
                                  }
                                }
                                leaf name {
                                  type xr:ncs_rpc_notif_Cisco-ios-xr-string;
                                  description
                                    "HW component name";
                                }
                                uses ncs_rpc_notif_INVENTORY-EXT2-OPER-SENSOR-TABLE;
                                uses ncs_rpc_notif_INVENTORY-EXT2-OPER-ATTRIBUTES;
                                uses ncs_rpc_notif_INVENTORY-EXT2-OPER-HW-COMPONENT-TABLE;
                              }
                            }
                            container ports {
                              description
                                "Table of spirit port slots";
                              list port {
                                key "name";
                                description
                                  "Port number";
                                leaf name {
                                  type xr:ncs_rpc_notif_Cisco-ios-xr-string;
                                  description
                                    "Port name";
                                }
                                uses ncs_rpc_notif_INVENTORY-EXT2-OPER-ATTRIBUTES;
                              }
                            }
                            leaf name {
                              type xr:ncs_rpc_notif_Cisco-ios-xr-string;
                              description
                                "HW component name";
                            }
                            uses ncs_rpc_notif_INVENTORY-EXT2-OPER-SENSOR-TABLE;
                            uses ncs_rpc_notif_INVENTORY-EXT2-OPER-ATTRIBUTES;
                            uses ncs_rpc_notif_INVENTORY-EXT2-OPER-HW-COMPONENT-TABLE;
                          }
                        }
                        leaf name {
                          type xr:ncs_rpc_notif_Cisco-ios-xr-string;
                          description
                            "HW component name";
                        }
                        uses ncs_rpc_notif_INVENTORY-EXT2-OPER-SENSOR-TABLE;
                        uses ncs_rpc_notif_INVENTORY-EXT2-OPER-ATTRIBUTES;
                        uses ncs_rpc_notif_INVENTORY-EXT2-OPER-HW-COMPONENT-TABLE;
                      }
                    }
                    container ports {
                      description
                        "Table of spirit port slots";
                      list port {
                        key "name";
                        description
                          "Port number";
                        container port-modules {
                          description
                            "Table of Module components ";
                          list port-module {
                            key "name";
                            description
                              "POrt Module component number";
                            leaf name {
                              type xr:ncs_rpc_notif_Cisco-ios-xr-string;
                              description
                                "module name";
                            }
                            uses ncs_rpc_notif_ATTRIBUTES;
                          }
                        }
                        leaf name {
                          type xr:ncs_rpc_notif_Cisco-ios-xr-string;
                          description
                            "Port name";
                        }
                        uses ncs_rpc_notif_ATTRIBUTES;
                        uses ncs_rpc_notif_INVENTORY-EXT1-OPER-HW-COMPONENT-TABLE;
                      }
                    }
                    leaf name {
                      type xr:ncs_rpc_notif_Cisco-ios-xr-string;
                      description
                        "HW component name";
                    }
                    uses ncs_rpc_notif_SENSOR-TABLE;
                    uses ncs_rpc_notif_ATTRIBUTES;
                    uses ncs_rpc_notif_INVENTORY-EXT1-OPER-HW-COMPONENT-TABLE;
                  }
                }
                leaf module-name {
                  type xr:ncs_rpc_notif_Cisco-ios-xr-string;
                  description
                    "Module name";
                }
                uses ncs_rpc_notif_SENSOR-TABLE;
                uses ncs_rpc_notif_ATTRIBUTES;
                uses ncs_rpc_notif_INVENTORY-EXT1-OPER-HW-COMPONENT-TABLE;
              }
            }
            leaf name {
              type xr:ncs_rpc_notif_Cisco-ios-xr-string;
              description
                "Card name";
            }
            uses ncs_rpc_notif_PORT-TABLE;
            uses ncs_rpc_notif_PORT-SLOT-TABLE;
            uses ncs_rpc_notif_HW-COMPONENT-TABLE;
            uses ncs_rpc_notif_INVENTORY-COMMON-SENSOR-TABLE;
            uses ncs_rpc_notif_INVENTORY-COMMON-ATTRIBUTES;
          }
        }
        leaf name {
          type xr:ncs_rpc_notif_Cisco-ios-xr-string;
          description
            "Slot name";
        }
        uses ncs_rpc_notif_INVENTORY-COMMON-ATTRIBUTES;
      }
    }
  }

  grouping ncs_rpc_notif_SENSOR-TABLE {
    description
      "Common node of module, sub-module, hw-component";
    container sensors {
      description
        "Table of sensors";
      list sensor {
        key "name";
        description
          "Sensor number";
        leaf name {
          type xr:ncs_rpc_notif_Cisco-ios-xr-string;
          description
            "Sensor name";
        }
        uses ncs_rpc_notif_ATTRIBUTES;
      }
    }
  }

  grouping ncs_rpc_notif_INVENTORY-EXT2-OPER-SENSOR-TABLE {
    description
      "Common node of module, sub-module,
       hw-componentCommon node of hw-component,
       sub-module-l2, sub-module-l3, sub-module-l4,
       sub-module-l5";
    container sensors {
      description
        "Table of sensors";
      list sensor {
        key "name";
        description
          "Sensor number";
        leaf name {
          type xr:ncs_rpc_notif_Cisco-ios-xr-string;
          description
            "Sensor name";
        }
        uses ncs_rpc_notif_INVENTORY-EXT2-OPER-ATTRIBUTES;
      }
    }
  }

  grouping ncs_rpc_notif_INVENTORY-COMMON-SENSOR-TABLE {
    description
      "Common node of module, sub-module,
       hw-componentCommon node of hw-component,
       sub-module-l2, sub-module-l3, sub-module-l4,
       sub-module-l5Common node of card, module,
       hw-component, port-slot, ports";
    container sensors {
      description
        "Table of sensors";
      list sensor {
        key "name";
        description
          "Sensor number";
        leaf name {
          type xr:ncs_rpc_notif_Cisco-ios-xr-string;
          description
            "Sensor name";
        }
        uses ncs_rpc_notif_INVENTORY-COMMON-ATTRIBUTES;
      }
    }
  }

  grouping ncs_rpc_notif_PORT-TABLE {
    description
      "Common node of port-slot, card";
    container portses {
      description
        "Table of port slots";
      list ports {
        key "name";
        description
          "Port number";
        leaf name {
          type xr:ncs_rpc_notif_Cisco-ios-xr-string;
          description
            "Port name";
        }
        uses ncs_rpc_notif_HW-COMPONENT-TABLE;
        uses ncs_rpc_notif_INVENTORY-COMMON-SENSOR-TABLE;
        uses ncs_rpc_notif_INVENTORY-COMMON-ATTRIBUTES;
      }
    }
  }

  grouping ncs_rpc_notif_HW-COMPONENT-TABLE {
    description
      "Common node of card, ports";
    container hw-components {
      description
        "Table of  HW components ";
      list hw-component {
        key "name";
        description
          "HW component number";
        leaf name {
          type xr:ncs_rpc_notif_Cisco-ios-xr-string;
          description
            "HW component name";
        }
        uses ncs_rpc_notif_INVENTORY-COMMON-SENSOR-TABLE;
        uses ncs_rpc_notif_INVENTORY-COMMON-ATTRIBUTES;
      }
    }
  }

  grouping ncs_rpc_notif_INVENTORY-EXT1-OPER-HW-COMPONENT-TABLE {
    description
      "Common node of card, portsCommon node of module,
       sub-module, port";
    container hw-components {
      description
        "Table of HW components ";
      list hw-component {
        key "name";
        description
          "HW component number";
        leaf name {
          type xr:ncs_rpc_notif_Cisco-ios-xr-string;
          description
            "HW component name";
        }
        uses ncs_rpc_notif_SENSOR-TABLE;
        uses ncs_rpc_notif_ATTRIBUTES;
      }
    }
  }

  grouping ncs_rpc_notif_INVENTORY-EXT2-OPER-HW-COMPONENT-TABLE {
    description
      "Common node of card, portsCommon node of module,
       sub-module, portCommon node of sub-module-l2,
       sub-module-l3, sub-module-l4, sub-module-l5";
    container hw-components {
      description
        "Table of HW components ";
      list hw-component {
        key "name";
        description
          "HW component number";
        leaf name {
          type xr:ncs_rpc_notif_Cisco-ios-xr-string;
          description
            "HW component name";
        }
        uses ncs_rpc_notif_INVENTORY-EXT2-OPER-SENSOR-TABLE;
        uses ncs_rpc_notif_INVENTORY-EXT2-OPER-ATTRIBUTES;
      }
    }
  }

  grouping ncs_rpc_notif_INVENTORY-EXT3-OPER-HW-COMPONENT-TABLE {
    description
      "Common node of card, portsCommon node of module,
       sub-module, portCommon node of sub-module-l2,
       sub-module-l3, sub-module-l4, sub-module-l5Common
       node of backplane, module";
    container hw-components {
      description
        "Table of  HW components ";
      list hw-component {
        key "name";
        description
          "HW component number";
        leaf name {
          type xr:ncs_rpc_notif_Cisco-ios-xr-string;
          description
            "HW component name";
        }
        uses ncs_rpc_notif_INVENTORY-EXT3-OPER-ATTRIBUTES;
      }
    }
  }

  grouping ncs_rpc_notif_ATTRIBUTES {
    description
      "Common node of module, sub-module, sensor,
       hw-component, port, port-module";
    container attributes {
      description
        "Attributes";
      container basic-info {
        description
          "Entity attributes";
        uses ncs_rpc_notif_INV-XML-ENTITY-BASIC-INFO;
      }
      container fru-info {
        description
          "Field Replaceable Unit (FRU) attributes";
        uses ncs_rpc_notif_INV-XML-FRU-INFO;
      }
    }
  }

  grouping ncs_rpc_notif_INVENTORY-EXT2-OPER-ATTRIBUTES {
    description
      "Common node of module, sub-module, sensor,
       hw-component, port, port-moduleCommon node of
       sub-module-l2, sub-module-l3, sub-module-l4,
       sub-module-l5, sensor, hw-component, port";
    container attributes {
      description
        "Attributes";
      container basic-info {
        description
          "Entity attributes";
        uses ncs_rpc_notif_INV-XML-ENTITY-BASIC-INFO;
      }
      container fru-info {
        description
          "Field Replaceable Unit (FRU) attributes";
        uses ncs_rpc_notif_INV-XML-FRU-INFO;
      }
    }
  }

  grouping ncs_rpc_notif_INVENTORY-EXT3-OPER-ATTRIBUTES {
    description
      "Common node of module, sub-module, sensor,
       hw-component, port, port-moduleCommon node of
       sub-module-l2, sub-module-l3, sub-module-l4,
       sub-module-l5, sensor, hw-component, portCommon
       node of backplane, module, hw-component";
    container attributes {
      description
        "Attributes";
      container basic-info {
        description
          "Entity attributes";
        uses ncs_rpc_notif_INV-XML-ENTITY-BASIC-INFO;
      }
      container fru-info {
        description
          "Field Replaceable Unit (FRU) attributes";
        uses ncs_rpc_notif_INV-XML-FRU-INFO;
      }
    }
  }

  grouping ncs_rpc_notif_INVENTORY-COMMON-ATTRIBUTES {
    description
      "Common node of module, sub-module, sensor,
       hw-component, port, port-moduleCommon node of
       sub-module-l2, sub-module-l3, sub-module-l4,
       sub-module-l5, sensor, hw-component, portCommon
       node of backplane, module, hw-componentCommon
       node of rack, rack, slot, card, sub-slot, module,
       port-slot, hw-component, sensor, ports";
    container attributes {
      description
        "Attributes";
      container basic-info {
        description
          "Entity attributes";
        uses ncs_rpc_notif_INV-XML-ENTITY-BASIC-INFO;
      }
      container fru-info {
        description
          "Field Replaceable Unit (FRU) attributes";
        uses ncs_rpc_notif_INV-XML-FRU-INFO;
      }
    }
  }

  grouping ncs_rpc_notif_BACKPLANE-TABLE {
    description
      "Common node of rack, rack";
    container backplanes {
      description
        "Table of backplane";
      list backplane {
        key "name";
        description
          "Backplane name";
        container modules {
          description
            "Table of modules";
          list module {
            key "module-name";
            description
              "A module";
            leaf module-name {
              type xr:ncs_rpc_notif_Cisco-ios-xr-string;
              description
                "Module name";
            }
            uses ncs_rpc_notif_INVENTORY-EXT3-OPER-ATTRIBUTES;
            uses ncs_rpc_notif_INVENTORY-EXT3-OPER-HW-COMPONENT-TABLE;
          }
        }
        leaf name {
          type xr:ncs_rpc_notif_Cisco-ios-xr-string;
          description
            "Backplane name";
        }
        uses ncs_rpc_notif_INVENTORY-EXT3-OPER-ATTRIBUTES;
        uses ncs_rpc_notif_INVENTORY-EXT3-OPER-HW-COMPONENT-TABLE;
      }
    }
  }

  grouping live_ncs_PORT-SLOT-TABLE {
    description
      "Common node of card, module";
    container port-slots {
      description
        "Table of port slots";
      list port-slot {
        key "name";
        description
          "Port slot number";
        leaf name {
          type xr:live_ncs_Cisco-ios-xr-string;
          description
            "Port slot name";
        }
        uses live_ncs_PORT-TABLE;
        uses live_ncs_INVENTORY-COMMON-SENSOR-TABLE;
        uses live_ncs_INVENTORY-COMMON-ATTRIBUTES;
      }
    }
  }

  grouping live_ncs_SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses live_ncs_INV-PROCESSOR;
              }
              container motherboard-information {
                description
                  "MotherboardInformation";
                uses live_ncs_INV-XML-MOTHERBOARD-INFO;
              }
              container bootflash-information {
                description
                  "BootflashInformation";
                uses live_ncs_INV-BOOTFLASH;
              }
              container disk-information {
                description
                  "DiskInformation";
                uses live_ncs_INV-XML-DISK-INFO;
              }
            }
            container sub-slots {
              description
                "Table of subslots";
              list sub-slot {
                key "name";
                description
                  "Subslot number";
                container module {
                  description
                    "Module of a subslot";
                  uses live_ncs_PORT-SLOT-TABLE;
                  uses live_ncs_INVENTORY-COMMON-SENSOR-TABLE;
                  uses live_ncs_INVENTORY-COMMON-ATTRIBUTES;
                }
                leaf name {
                  type xr:live_ncs_Cisco-ios-xr-string;
                  description
                    "Subslot name";
                }
                uses live_ncs_INVENTORY-COMMON-ATTRIBUTES;
              }
            }
            container modules {
              description
                "Table of modules";
              list module {
                key "module-name";
                description
                  "A module";
                container sub-modules {
                  description
                    "Table of Sub Module components ";
                  list sub-module {
                    key "name";
                    description
                      "Sub Module component number";
                    container sub-module-l2s {
                      description
                        "Table of Sub Module components ";
                      list sub-module-l2 {
                        key "name";
                        description
                          "Sub Module component number";
                        container sub-module-l3s {
                          description
                            "Table of Sub Module components ";
                          list sub-module-l3 {
                            key "name";
                            description
                              "Sub Module component number";
                            container sub-module-l4s {
                              description
                                "Table of Sub Module components ";
                              list sub-module-l4 {
                                key "name";
                                description
                                  "Sub Module component number";
                                container sub-module-l5s {
                                  description
                                    "Table of Sub Module components ";
                                  list sub-module-l5 {
                                    key "name";
                                    description
                                      "Sub Module component number";
                                    leaf name {
                                      type xr:live_ncs_Cisco-ios-xr-string;
                                      description
                                        "HW component name";
                                    }
                                    uses live_ncs_INVENTORY-EXT2-OPER-SENSOR-TABLE;
                                    uses live_ncs_INVENTORY-EXT2-OPER-ATTRIBUTES;
                                    uses live_ncs_INVENTORY-EXT2-OPER-HW-COMPONENT-TABLE;
                                  }
                                }
                                leaf name {
                                  type xr:live_ncs_Cisco-ios-xr-string;
                                  description
                                    "HW component name";
                                }
                                uses live_ncs_INVENTORY-EXT2-OPER-SENSOR-TABLE;
                                uses live_ncs_INVENTORY-EXT2-OPER-ATTRIBUTES;
                                uses live_ncs_INVENTORY-EXT2-OPER-HW-COMPONENT-TABLE;
                              }
                            }
                            container ports {
                              description
                                "Table of spirit port slots";
                              list port {
                                key "name";
                                description
                                  "Port number";
                                leaf name {
                                  type xr:live_ncs_Cisco-ios-xr-string;
                                  description
                                    "Port name";
                                }
                                uses live_ncs_INVENTORY-EXT2-OPER-ATTRIBUTES;
                              }
                            }
                            leaf name {
                              type xr:live_ncs_Cisco-ios-xr-string;
                              description
                                "HW component name";
                            }
                            uses live_ncs_INVENTORY-EXT2-OPER-SENSOR-TABLE;
                            uses live_ncs_INVENTORY-EXT2-OPER-ATTRIBUTES;
                            uses live_ncs_INVENTORY-EXT2-OPER-HW-COMPONENT-TABLE;
                          }
                        }
                        leaf name {
                          type xr:live_ncs_Cisco-ios-xr-string;
                          description
                            "HW component name";
                        }
                        uses live_ncs_INVENTORY-EXT2-OPER-SENSOR-TABLE;
                        uses live_ncs_INVENTORY-EXT2-OPER-ATTRIBUTES;
                        uses live_ncs_INVENTORY-EXT2-OPER-HW-COMPONENT-TABLE;
                      }
                    }
                    container ports {
                      description
                        "Table of spirit port slots";
                      list port {
                        key "name";
                        description
                          "Port number";
                        container port-modules {
                          description
                            "Table of Module components ";
                          list port-module {
                            key "name";
                            description
                              "POrt Module component number";
                            leaf name {
                              type xr:live_ncs_Cisco-ios-xr-string;
                              description
                                "module name";
                            }
                            uses live_ncs_ATTRIBUTES;
                          }
                        }
                        leaf name {
                          type xr:live_ncs_Cisco-ios-xr-string;
                          description
                            "Port name";
                        }
                        uses live_ncs_ATTRIBUTES;
                        uses live_ncs_INVENTORY-EXT1-OPER-HW-COMPONENT-TABLE;
                      }
                    }
                    leaf name {
                      type xr:live_ncs_Cisco-ios-xr-string;
                      description
                        "HW component name";
                    }
                    uses live_ncs_SENSOR-TABLE;
                    uses live_ncs_ATTRIBUTES;
                    uses live_ncs_INVENTORY-EXT1-OPER-HW-COMPONENT-TABLE;
                  }
                }
                leaf module-name {
                  type xr:live_ncs_Cisco-ios-xr-string;
                  description
                    "Module name";
                }
                uses live_ncs_SENSOR-TABLE;
                uses live_ncs_ATTRIBUTES;
                uses live_ncs_INVENTORY-EXT1-OPER-HW-COMPONENT-TABLE;
              }
            }
            leaf name {
              type xr:live_ncs_Cisco-ios-xr-string;
              description
                "Card name";
            }
            uses live_ncs_PORT-TABLE;
            uses live_ncs_PORT-SLOT-TABLE;
            uses live_ncs_HW-COMPONENT-TABLE;
            uses live_ncs_INVENTORY-COMMON-SENSOR-TABLE;
            uses live_ncs_INVENTORY-COMMON-ATTRIBUTES;
          }
        }
        leaf name {
          type xr:live_ncs_Cisco-ios-xr-string;
          description
            "Slot name";
        }
        uses live_ncs_INVENTORY-COMMON-ATTRIBUTES;
      }
    }
  }

  grouping live_ncs_SENSOR-TABLE {
    description
      "Common node of module, sub-module, hw-component";
    container sensors {
      description
        "Table of sensors";
      list sensor {
        key "name";
        description
          "Sensor number";
        leaf name {
          type xr:live_ncs_Cisco-ios-xr-string;
          description
            "Sensor name";
        }
        uses live_ncs_ATTRIBUTES;
      }
    }
  }

  grouping live_ncs_INVENTORY-EXT2-OPER-SENSOR-TABLE {
    description
      "Common node of module, sub-module,
       hw-componentCommon node of hw-component,
       sub-module-l2, sub-module-l3, sub-module-l4,
       sub-module-l5";
    container sensors {
      description
        "Table of sensors";
      list sensor {
        key "name";
        description
          "Sensor number";
        leaf name {
          type xr:live_ncs_Cisco-ios-xr-string;
          description
            "Sensor name";
        }
        uses live_ncs_INVENTORY-EXT2-OPER-ATTRIBUTES;
      }
    }
  }

  grouping live_ncs_INVENTORY-COMMON-SENSOR-TABLE {
    description
      "Common node of module, sub-module,
       hw-componentCommon node of hw-component,
       sub-module-l2, sub-module-l3, sub-module-l4,
       sub-module-l5Common node of card, module,
       hw-component, port-slot, ports";
    container sensors {
      description
        "Table of sensors";
      list sensor {
        key "name";
        description
          "Sensor number";
        leaf name {
          type xr:live_ncs_Cisco-ios-xr-string;
          description
            "Sensor name";
        }
        uses live_ncs_INVENTORY-COMMON-ATTRIBUTES;
      }
    }
  }

  grouping live_ncs_PORT-TABLE {
    description
      "Common node of port-slot, card";
    container portses {
      description
        "Table of port slots";
      list ports {
        key "name";
        description
          "Port number";
        leaf name {
          type xr:live_ncs_Cisco-ios-xr-string;
          description
            "Port name";
        }
        uses live_ncs_HW-COMPONENT-TABLE;
        uses live_ncs_INVENTORY-COMMON-SENSOR-TABLE;
        uses live_ncs_INVENTORY-COMMON-ATTRIBUTES;
      }
    }
  }

  grouping live_ncs_HW-COMPONENT-TABLE {
    description
      "Common node of card, ports";
    container hw-components {
      description
        "Table of  HW components ";
      list hw-component {
        key "name";
        description
          "HW component number";
        leaf name {
          type xr:live_ncs_Cisco-ios-xr-string;
          description
            "HW component name";
        }
        uses live_ncs_INVENTORY-COMMON-SENSOR-TABLE;
        uses live_ncs_INVENTORY-COMMON-ATTRIBUTES;
      }
    }
  }

  grouping live_ncs_INVENTORY-EXT1-OPER-HW-COMPONENT-TABLE {
    description
      "Common node of card, portsCommon node of module,
       sub-module, port";
    container hw-components {
      description
        "Table of HW components ";
      list hw-component {
        key "name";
        description
          "HW component number";
        leaf name {
          type xr:live_ncs_Cisco-ios-xr-string;
          description
            "HW component name";
        }
        uses live_ncs_SENSOR-TABLE;
        uses live_ncs_ATTRIBUTES;
      }
    }
  }

  grouping live_ncs_INVENTORY-EXT2-OPER-HW-COMPONENT-TABLE {
    description
      "Common node of card, portsCommon node of module,
       sub-module, portCommon node of sub-module-l2,
       sub-module-l3, sub-module-l4, sub-module-l5";
    container hw-components {
      description
        "Table of HW components ";
      list hw-component {
        key "name";
        description
          "HW component number";
        leaf name {
          type xr:live_ncs_Cisco-ios-xr-string;
          description
            "HW component name";
        }
        uses live_ncs_INVENTORY-EXT2-OPER-SENSOR-TABLE;
        uses live_ncs_INVENTORY-EXT2-OPER-ATTRIBUTES;
      }
    }
  }

  grouping live_ncs_INVENTORY-EXT3-OPER-HW-COMPONENT-TABLE {
    description
      "Common node of card, portsCommon node of module,
       sub-module, portCommon node of sub-module-l2,
       sub-module-l3, sub-module-l4, sub-module-l5Common
       node of backplane, module";
    container hw-components {
      description
        "Table of  HW components ";
      list hw-component {
        key "name";
        description
          "HW component number";
        leaf name {
          type xr:live_ncs_Cisco-ios-xr-string;
          description
            "HW component name";
        }
        uses live_ncs_INVENTORY-EXT3-OPER-ATTRIBUTES;
      }
    }
  }

  grouping live_ncs_ATTRIBUTES {
    description
      "Common node of module, sub-module, sensor,
       hw-component, port, port-module";
    container attributes {
      description
        "Attributes";
      container basic-info {
        description
          "Entity attributes";
        uses live_ncs_INV-XML-ENTITY-BASIC-INFO;
      }
      container fru-info {
        description
          "Field Replaceable Unit (FRU) attributes";
        uses live_ncs_INV-XML-FRU-INFO;
      }
    }
  }

  grouping live_ncs_INVENTORY-EXT2-OPER-ATTRIBUTES {
    description
      "Common node of module, sub-module, sensor,
       hw-component, port, port-moduleCommon node of
       sub-module-l2, sub-module-l3, sub-module-l4,
       sub-module-l5, sensor, hw-component, port";
    container attributes {
      description
        "Attributes";
      container basic-info {
        description
          "Entity attributes";
        uses live_ncs_INV-XML-ENTITY-BASIC-INFO;
      }
      container fru-info {
        description
          "Field Replaceable Unit (FRU) attributes";
        uses live_ncs_INV-XML-FRU-INFO;
      }
    }
  }

  grouping live_ncs_INVENTORY-EXT3-OPER-ATTRIBUTES {
    description
      "Common node of module, sub-module, sensor,
       hw-component, port, port-moduleCommon node of
       sub-module-l2, sub-module-l3, sub-module-l4,
       sub-module-l5, sensor, hw-component, portCommon
       node of backplane, module, hw-component";
    container attributes {
      description
        "Attributes";
      container basic-info {
        description
          "Entity attributes";
        uses live_ncs_INV-XML-ENTITY-BASIC-INFO;
      }
      container fru-info {
        description
          "Field Replaceable Unit (FRU) attributes";
        uses live_ncs_INV-XML-FRU-INFO;
      }
    }
  }

  grouping live_ncs_INVENTORY-COMMON-ATTRIBUTES {
    description
      "Common node of module, sub-module, sensor,
       hw-component, port, port-moduleCommon node of
       sub-module-l2, sub-module-l3, sub-module-l4,
       sub-module-l5, sensor, hw-component, portCommon
       node of backplane, module, hw-componentCommon
       node of rack, rack, slot, card, sub-slot, module,
       port-slot, hw-component, sensor, ports";
    container attributes {
      description
        "Attributes";
      container basic-info {
        description
          "Entity attributes";
        uses live_ncs_INV-XML-ENTITY-BASIC-INFO;
      }
      container fru-info {
        description
          "Field Replaceable Unit (FRU) attributes";
        uses live_ncs_INV-XML-FRU-INFO;
      }
    }
  }

  grouping live_ncs_BACKPLANE-TABLE {
    description
      "Common node of rack, rack";
    container backplanes {
      description
        "Table of backplane";
      list backplane {
        key "name";
        description
          "Backplane name";
        container modules {
          description
            "Table of modules";
          list module {
            key "module-name";
            description
              "A module";
            leaf module-name {
              type xr:live_ncs_Cisco-ios-xr-string;
              description
                "Module name";
            }
            uses live_ncs_INVENTORY-EXT3-OPER-ATTRIBUTES;
            uses live_ncs_INVENTORY-EXT3-OPER-HW-COMPONENT-TABLE;
          }
        }
        leaf name {
          type xr:live_ncs_Cisco-ios-xr-string;
          description
            "Backplane name";
        }
        uses live_ncs_INVENTORY-EXT3-OPER-ATTRIBUTES;
        uses live_ncs_INVENTORY-EXT3-OPER-HW-COMPONENT-TABLE;
      }
    }
  }

  grouping PORT-SLOT-TABLE {
    description
      "Common node of card, module";
    container port-slots {
      description
        "Table of port slots";
      list port-slot {
        key "name";
        description
          "Port slot number";
        leaf name {
          type xr:Cisco-ios-xr-string;
          description
            "Port slot name";
        }
        uses PORT-TABLE;
        uses INVENTORY-COMMON-SENSOR-TABLE;
        uses INVENTORY-COMMON-ATTRIBUTES;
      }
    }
  }

  grouping SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses INV-PROCESSOR;
              }
              container motherboard-information {
                description
                  "MotherboardInformation";
                uses INV-XML-MOTHERBOARD-INFO;
              }
              container bootflash-information {
                description
                  "BootflashInformation";
                uses INV-BOOTFLASH;
              }
              container disk-information {
                description
                  "DiskInformation";
                uses INV-XML-DISK-INFO;
              }
            }
            container sub-slots {
              description
                "Table of subslots";
              list sub-slot {
                key "name";
                description
                  "Subslot number";
                container module {
                  description
                    "Module of a subslot";
                  uses PORT-SLOT-TABLE;
                  uses INVENTORY-COMMON-SENSOR-TABLE;
                  uses INVENTORY-COMMON-ATTRIBUTES;
                }
                leaf name {
                  type xr:Cisco-ios-xr-string;
                  description
                    "Subslot name";
                }
                uses INVENTORY-COMMON-ATTRIBUTES;
              }
            }
            container modules {
              description
                "Table of modules";
              list module {
                key "module-name";
                description
                  "A module";
                container sub-modules {
                  description
                    "Table of Sub Module components ";
                  list sub-module {
                    key "name";
                    description
                      "Sub Module component number";
                    container sub-module-l2s {
                      description
                        "Table of Sub Module components ";
                      list sub-module-l2 {
                        key "name";
                        description
                          "Sub Module component number";
                        container sub-module-l3s {
                          description
                            "Table of Sub Module components ";
                          list sub-module-l3 {
                            key "name";
                            description
                              "Sub Module component number";
                            container sub-module-l4s {
                              description
                                "Table of Sub Module components ";
                              list sub-module-l4 {
                                key "name";
                                description
                                  "Sub Module component number";
                                container sub-module-l5s {
                                  description
                                    "Table of Sub Module components ";
                                  list sub-module-l5 {
                                    key "name";
                                    description
                                      "Sub Module component number";
                                    leaf name {
                                      type xr:Cisco-ios-xr-string;
                                      description
                                        "HW component name";
                                    }
                                    uses INVENTORY-EXT2-OPER-SENSOR-TABLE;
                                    uses INVENTORY-EXT2-OPER-ATTRIBUTES;
                                    uses INVENTORY-EXT2-OPER-HW-COMPONENT-TABLE;
                                  }
                                }
                                leaf name {
                                  type xr:Cisco-ios-xr-string;
                                  description
                                    "HW component name";
                                }
                                uses INVENTORY-EXT2-OPER-SENSOR-TABLE;
                                uses INVENTORY-EXT2-OPER-ATTRIBUTES;
                                uses INVENTORY-EXT2-OPER-HW-COMPONENT-TABLE;
                              }
                            }
                            container ports {
                              description
                                "Table of spirit port slots";
                              list port {
                                key "name";
                                description
                                  "Port number";
                                leaf name {
                                  type xr:Cisco-ios-xr-string;
                                  description
                                    "Port name";
                                }
                                uses INVENTORY-EXT2-OPER-ATTRIBUTES;
                              }
                            }
                            leaf name {
                              type xr:Cisco-ios-xr-string;
                              description
                                "HW component name";
                            }
                            uses INVENTORY-EXT2-OPER-SENSOR-TABLE;
                            uses INVENTORY-EXT2-OPER-ATTRIBUTES;
                            uses INVENTORY-EXT2-OPER-HW-COMPONENT-TABLE;
                          }
                        }
                        leaf name {
                          type xr:Cisco-ios-xr-string;
                          description
                            "HW component name";
                        }
                        uses INVENTORY-EXT2-OPER-SENSOR-TABLE;
                        uses INVENTORY-EXT2-OPER-ATTRIBUTES;
                        uses INVENTORY-EXT2-OPER-HW-COMPONENT-TABLE;
                      }
                    }
                    container ports {
                      description
                        "Table of spirit port slots";
                      list port {
                        key "name";
                        description
                          "Port number";
                        container port-modules {
                          description
                            "Table of Module components ";
                          list port-module {
                            key "name";
                            description
                              "POrt Module component number";
                            leaf name {
                              type xr:Cisco-ios-xr-string;
                              description
                                "module name";
                            }
                            uses ATTRIBUTES;
                          }
                        }
                        leaf name {
                          type xr:Cisco-ios-xr-string;
                          description
                            "Port name";
                        }
                        uses ATTRIBUTES;
                        uses INVENTORY-EXT1-OPER-HW-COMPONENT-TABLE;
                      }
                    }
                    leaf name {
                      type xr:Cisco-ios-xr-string;
                      description
                        "HW component name";
                    }
                    uses SENSOR-TABLE;
                    uses ATTRIBUTES;
                    uses INVENTORY-EXT1-OPER-HW-COMPONENT-TABLE;
                  }
                }
                leaf module-name {
                  type xr:Cisco-ios-xr-string;
                  description
                    "Module name";
                }
                uses SENSOR-TABLE;
                uses ATTRIBUTES;
                uses INVENTORY-EXT1-OPER-HW-COMPONENT-TABLE;
              }
            }
            leaf name {
              type xr:Cisco-ios-xr-string;
              description
                "Card name";
            }
            uses PORT-TABLE;
            uses PORT-SLOT-TABLE;
            uses HW-COMPONENT-TABLE;
            uses INVENTORY-COMMON-SENSOR-TABLE;
            uses INVENTORY-COMMON-ATTRIBUTES;
          }
        }
        leaf name {
          type xr:Cisco-ios-xr-string;
          description
            "Slot name";
        }
        uses INVENTORY-COMMON-ATTRIBUTES;
      }
    }
  }

  grouping SENSOR-TABLE {
    description
      "Common node of module, sub-module, hw-component";
    container sensors {
      description
        "Table of sensors";
      list sensor {
        key "name";
        description
          "Sensor number";
        leaf name {
          type xr:Cisco-ios-xr-string;
          description
            "Sensor name";
        }
        uses ATTRIBUTES;
      }
    }
  }

  grouping INVENTORY-EXT2-OPER-SENSOR-TABLE {
    description
      "Common node of module, sub-module,
       hw-componentCommon node of hw-component,
       sub-module-l2, sub-module-l3, sub-module-l4,
       sub-module-l5";
    container sensors {
      description
        "Table of sensors";
      list sensor {
        key "name";
        description
          "Sensor number";
        leaf name {
          type xr:Cisco-ios-xr-string;
          description
            "Sensor name";
        }
        uses INVENTORY-EXT2-OPER-ATTRIBUTES;
      }
    }
  }

  grouping INVENTORY-COMMON-SENSOR-TABLE {
    description
      "Common node of module, sub-module,
       hw-componentCommon node of hw-component,
       sub-module-l2, sub-module-l3, sub-module-l4,
       sub-module-l5Common node of card, module,
       hw-component, port-slot, ports";
    container sensors {
      description
        "Table of sensors";
      list sensor {
        key "name";
        description
          "Sensor number";
        leaf name {
          type xr:Cisco-ios-xr-string;
          description
            "Sensor name";
        }
        uses INVENTORY-COMMON-ATTRIBUTES;
      }
    }
  }

  grouping PORT-TABLE {
    description
      "Common node of port-slot, card";
    container portses {
      description
        "Table of port slots";
      list ports {
        key "name";
        description
          "Port number";
        leaf name {
          type xr:Cisco-ios-xr-string;
          description
            "Port name";
        }
        uses HW-COMPONENT-TABLE;
        uses INVENTORY-COMMON-SENSOR-TABLE;
        uses INVENTORY-COMMON-ATTRIBUTES;
      }
    }
  }

  grouping HW-COMPONENT-TABLE {
    description
      "Common node of card, ports";
    container hw-components {
      description
        "Table of  HW components ";
      list hw-component {
        key "name";
        description
          "HW component number";
        leaf name {
          type xr:Cisco-ios-xr-string;
          description
            "HW component name";
        }
        uses INVENTORY-COMMON-SENSOR-TABLE;
        uses INVENTORY-COMMON-ATTRIBUTES;
      }
    }
  }

  grouping INVENTORY-EXT1-OPER-HW-COMPONENT-TABLE {
    description
      "Common node of card, portsCommon node of module,
       sub-module, port";
    container hw-components {
      description
        "Table of HW components ";
      list hw-component {
        key "name";
        description
          "HW component number";
        leaf name {
          type xr:Cisco-ios-xr-string;
          description
            "HW component name";
        }
        uses SENSOR-TABLE;
        uses ATTRIBUTES;
      }
    }
  }

  grouping INVENTORY-EXT2-OPER-HW-COMPONENT-TABLE {
    description
      "Common node of card, portsCommon node of module,
       sub-module, portCommon node of sub-module-l2,
       sub-module-l3, sub-module-l4, sub-module-l5";
    container hw-components {
      description
        "Table of HW components ";
      list hw-component {
        key "name";
        description
          "HW component number";
        leaf name {
          type xr:Cisco-ios-xr-string;
          description
            "HW component name";
        }
        uses INVENTORY-EXT2-OPER-SENSOR-TABLE;
        uses INVENTORY-EXT2-OPER-ATTRIBUTES;
      }
    }
  }

  grouping INVENTORY-EXT3-OPER-HW-COMPONENT-TABLE {
    description
      "Common node of card, portsCommon node of module,
       sub-module, portCommon node of sub-module-l2,
       sub-module-l3, sub-module-l4, sub-module-l5Common
       node of backplane, module";
    container hw-components {
      description
        "Table of  HW components ";
      list hw-component {
        key "name";
        description
          "HW component number";
        leaf name {
          type xr:Cisco-ios-xr-string;
          description
            "HW component name";
        }
        uses INVENTORY-EXT3-OPER-ATTRIBUTES;
      }
    }
  }

  grouping ATTRIBUTES {
    description
      "Common node of module, sub-module, sensor,
       hw-component, port, port-module";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-EXT2-OPER-ATTRIBUTES {
    description
      "Common node of module, sub-module, sensor,
       hw-component, port, port-moduleCommon node of
       sub-module-l2, sub-module-l3, sub-module-l4,
       sub-module-l5, sensor, hw-component, port";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-EXT3-OPER-ATTRIBUTES {
    description
      "Common node of module, sub-module, sensor,
       hw-component, port, port-moduleCommon node of
       sub-module-l2, sub-module-l3, sub-module-l4,
       sub-module-l5, sensor, hw-component, portCommon
       node of backplane, module, hw-component";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping INVENTORY-COMMON-ATTRIBUTES {
    description
      "Common node of module, sub-module, sensor,
       hw-component, port, port-moduleCommon node of
       sub-module-l2, sub-module-l3, sub-module-l4,
       sub-module-l5, sensor, hw-component, portCommon
       node of backplane, module, hw-componentCommon
       node of rack, rack, slot, card, sub-slot, module,
       port-slot, hw-component, sensor, ports";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  grouping BACKPLANE-TABLE {
    description
      "Common node of rack, rack";
    container backplanes {
      description
        "Table of backplane";
      list backplane {
        key "name";
        description
          "Backplane name";
        container modules {
          description
            "Table of modules";
          list module {
            key "module-name";
            description
              "A module";
            leaf module-name {
              type xr:Cisco-ios-xr-string;
              description
                "Module name";
            }
            uses INVENTORY-EXT3-OPER-ATTRIBUTES;
            uses INVENTORY-EXT3-OPER-HW-COMPONENT-TABLE;
          }
        }
        leaf name {
          type xr:Cisco-ios-xr-string;
          description
            "Backplane name";
        }
        uses INVENTORY-EXT3-OPER-ATTRIBUTES;
        uses INVENTORY-EXT3-OPER-HW-COMPONENT-TABLE;
      }
    }
  }

  augment "/ncs:devices/ncs:device/ncs:config" {
    // NCS drop config false container 'platform-inventory'
  }
  augment "/ncs:devices/ncs:device/ncs:live-status" {
    container platform-inventory {
      tailf:ncs-device-type "netconf";
      tailf:display-when "not(../../ncs:module) or ../../ncs:module[ncs:name='Cisco-IOS-XR-platform-inventory-oper'] or (../../ncs:live-status-protocol[not(ncs:capability)]) or (../../ncs:live-status-protocol/ncs:capability/ncs:module[.='Cisco-IOS-XR-platform-inventory-oper'])";
      description
        "Inventory operational data";
      container racks {
        description
          "Table of racks";
        list rack {
          key "name";
          description
            "Rack name";
          leaf name {
            type xr:live_ncs_Cisco-ios-xr-string;
            description
              "Rack name";
          }
          uses live_ncs_SLOT-TABLE;
          uses live_ncs_INVENTORY-COMMON-ATTRIBUTES;
          uses live_ncs_BACKPLANE-TABLE;
        }
      }
    }
  }
  augment "/ncs:devices/ncs:template/ncs:ned-id/ncs:config" {
    // NCS drop config false container 'platform-inventory'
  }
}

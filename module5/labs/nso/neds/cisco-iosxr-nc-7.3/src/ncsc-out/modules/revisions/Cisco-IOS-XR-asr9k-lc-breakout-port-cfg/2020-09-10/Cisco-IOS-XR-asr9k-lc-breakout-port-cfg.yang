module Cisco-IOS-XR-asr9k-lc-breakout-port-cfg {
  // Generated by yanger -t ncs
  tailf:mount-id "cisco-iosxr-nc-7.3:cisco-iosxr-nc-7.3";
  tailf:ncs-device-type "netconf";

  namespace "http://cisco.com/ns/yang/Cisco-IOS-XR-asr9k-lc-breakout-port-cfg";
  prefix asr9k-lc-breakout-port-cfg;

  import cisco-semver {
    prefix semver;
  }
  import Cisco-IOS-XR-config-mda-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-lc-breakout-port package configuration.

     This YANG module augments the
       Cisco-IOS-XR-config-mda-cfg
     module with configuration data.

     Copyright (c) 2013-2020 by Cisco Systems, Inc.
     All rights reserved.";

  revision 2020-09-10 {
    description
      "Added/modified to support HundredGigE interfaces.";
    semver:module-version "1.0.0";
  }
  revision 2019-04-05 {
    description
      "Establish semantic version baseline.";
  }
  revision 2015-11-09 {
    description
      "IOS XR 6.0 revision.";
  }

  typedef ncs_template_Hw-module-breakout-if {
    type string;
    description
      "Hw module breakout if";
  }

  typedef ncs_rpc_notif_Hw-module-breakout-if {
    type enumeration {
      enum "1x-hundred-gig-e" {
        value 0;
        description
          "1xHundredGigE interfaces";
      }
      enum "10x-ten-gig-e" {
        value 1;
        description
          "TenGigE interfaces";
      }
      enum "2x-forty-gig-e" {
        value 2;
        description
          "FortyGigE interfaces";
      }
      enum "1x-forty-gig-e" {
        value 3;
        description
          "FortyGigE interfaces";
      }
      enum "4x-ten-gig-e" {
        value 4;
        description
          "TenGigE interfaces";
      }
      enum "4x-twenty-five-gig-e" {
        value 5;
        description
          "TwentyFiveGigE interfaces";
      }
      enum "1x-four-hundred-gig-e" {
        value 6;
        description
          "FourHundredGigE interfaces";
      }
      enum "8x-fifty-gig-e" {
        value 7;
        description
          "FiftyGigE interfaces";
      }
      enum "4x-hundred-gig-e" {
        value 8;
        description
          "4xHundredGigE interfaces";
      }
      enum "2x-hundred-gig-e" {
        value 9;
        description
          "2xHundredGigE interfaces";
      }
    }
    description
      "Hw module breakout if";
  }

  typedef live_ncs_Hw-module-breakout-if {
    type enumeration {
      enum "1x-hundred-gig-e" {
        value 0;
        description
          "1xHundredGigE interfaces";
      }
      enum "10x-ten-gig-e" {
        value 1;
        description
          "TenGigE interfaces";
      }
      enum "2x-forty-gig-e" {
        value 2;
        description
          "FortyGigE interfaces";
      }
      enum "1x-forty-gig-e" {
        value 3;
        description
          "FortyGigE interfaces";
      }
      enum "4x-ten-gig-e" {
        value 4;
        description
          "TenGigE interfaces";
      }
      enum "4x-twenty-five-gig-e" {
        value 5;
        description
          "TwentyFiveGigE interfaces";
      }
      enum "1x-four-hundred-gig-e" {
        value 6;
        description
          "FourHundredGigE interfaces";
      }
      enum "8x-fifty-gig-e" {
        value 7;
        description
          "FiftyGigE interfaces";
      }
      enum "4x-hundred-gig-e" {
        value 8;
        description
          "4xHundredGigE interfaces";
      }
      enum "2x-hundred-gig-e" {
        value 9;
        description
          "2xHundredGigE interfaces";
      }
    }
    description
      "Hw module breakout if";
  }

  typedef Hw-module-breakout-if {
    type enumeration {
      enum "1x-hundred-gig-e" {
        value 0;
        description
          "1xHundredGigE interfaces";
      }
      enum "10x-ten-gig-e" {
        value 1;
        description
          "TenGigE interfaces";
      }
      enum "2x-forty-gig-e" {
        value 2;
        description
          "FortyGigE interfaces";
      }
      enum "1x-forty-gig-e" {
        value 3;
        description
          "FortyGigE interfaces";
      }
      enum "4x-ten-gig-e" {
        value 4;
        description
          "TenGigE interfaces";
      }
      enum "4x-twenty-five-gig-e" {
        value 5;
        description
          "TwentyFiveGigE interfaces";
      }
      enum "1x-four-hundred-gig-e" {
        value 6;
        description
          "FourHundredGigE interfaces";
      }
      enum "8x-fifty-gig-e" {
        value 7;
        description
          "FiftyGigE interfaces";
      }
      enum "4x-hundred-gig-e" {
        value 8;
        description
          "4xHundredGigE interfaces";
      }
      enum "2x-hundred-gig-e" {
        value 9;
        description
          "2xHundredGigE interfaces";
      }
    }
    description
      "Hw module breakout if";
  }

  grouping ncs_template_HARDWARE-MODULE-BREAKOUT {
    description
      "Common node of active-node, preconfigured-node";
    container hardware-module-breakout {
      description
        "HW module breakout config";
      container ports {
        description
          "Optics port configuration";
        list port {
          // NCS patched for predictable order
          ordered-by user;
          key "port-number";
          description
            "Optics port number";
          leaf iftype {
            type ncs_template_Hw-module-breakout-if;
            description
              "Breakout iftype";
          }
          leaf port-number {
            type string;
            description
              "Optics port number";
          }
        }
      }
    }
  }

  grouping ncs_rpc_notif_HARDWARE-MODULE-BREAKOUT {
    description
      "Common node of active-node, preconfigured-node";
    container hardware-module-breakout {
      description
        "HW module breakout config";
      container ports {
        description
          "Optics port configuration";
        list port {
          key "port-number";
          description
            "Optics port number";
          leaf iftype {
            type ncs_rpc_notif_Hw-module-breakout-if;
            description
              "Breakout iftype";
          }
          leaf port-number {
            type uint32 {
              range "0..21";
            }
            description
              "Optics port number";
          }
        }
      }
    }
  }

  grouping live_ncs_HARDWARE-MODULE-BREAKOUT {
    description
      "Common node of active-node, preconfigured-node";
    container hardware-module-breakout {
      description
        "HW module breakout config";
      container ports {
        description
          "Optics port configuration";
        list port {
          key "port-number";
          description
            "Optics port number";
          leaf iftype {
            type live_ncs_Hw-module-breakout-if;
            description
              "Breakout iftype";
          }
          leaf port-number {
            type uint32 {
              range "0..21";
            }
            description
              "Optics port number";
          }
        }
      }
    }
  }

  grouping HARDWARE-MODULE-BREAKOUT {
    description
      "Common node of active-node, preconfigured-node";
    container hardware-module-breakout {
      description
        "HW module breakout config";
      container ports {
        description
          "Optics port configuration";
        list port {
          key "port-number";
          description
            "Optics port number";
          leaf iftype {
            type Hw-module-breakout-if;
            description
              "Breakout iftype";
          }
          leaf port-number {
            type uint32 {
              range "0..21";
            }
            description
              "Optics port number";
          }
        }
      }
    }
  }

  augment "/ncs:devices/ncs:template/ncs:ned-id/ncs:config/a1:preconfigured-nodes/a1:preconfigured-node" {
    description
      "This augment extends the configuration data of
       'Cisco-IOS-XR-config-mda-cfg'";
    uses ncs_template_HARDWARE-MODULE-BREAKOUT;
  }
  augment "/ncs:devices/ncs:device/ncs:live-status/a1:preconfigured-nodes/a1:preconfigured-node" {
    description
      "This augment extends the configuration data of
       'Cisco-IOS-XR-config-mda-cfg'";
    uses live_ncs_HARDWARE-MODULE-BREAKOUT {
      refine hardware-module-breakout {
        tailf:ncs-device-type "netconf";
        tailf:display-when "not(../../../../ncs:module) or ../../../../ncs:module[ncs:name='Cisco-IOS-XR-asr9k-lc-breakout-port-cfg'] or (../../../../ncs:live-status-protocol[not(ncs:capability)]) or (../../../../ncs:live-status-protocol/ncs:capability/ncs:module[.='Cisco-IOS-XR-asr9k-lc-breakout-port-cfg'])";
      }
    }
  }
  augment "/ncs:devices/ncs:device/ncs:config/a1:preconfigured-nodes/a1:preconfigured-node" {
    description
      "This augment extends the configuration data of
       'Cisco-IOS-XR-config-mda-cfg'";
    uses HARDWARE-MODULE-BREAKOUT {
      refine hardware-module-breakout {
        tailf:ncs-device-type "netconf";
        tailf:display-when "not(../../../../ncs:module) or ../../../../ncs:module[ncs:name='Cisco-IOS-XR-asr9k-lc-breakout-port-cfg']";
      }
    }
  }
  augment "/ncs:devices/ncs:template/ncs:ned-id/ncs:config/a1:active-nodes/a1:active-node" {
    description
      "This augment extends the configuration data of
       'Cisco-IOS-XR-config-mda-cfg'";
    uses ncs_template_HARDWARE-MODULE-BREAKOUT;
  }
  augment "/ncs:devices/ncs:device/ncs:live-status/a1:active-nodes/a1:active-node" {
    description
      "This augment extends the configuration data of
       'Cisco-IOS-XR-config-mda-cfg'";
    uses live_ncs_HARDWARE-MODULE-BREAKOUT {
      refine hardware-module-breakout {
        tailf:ncs-device-type "netconf";
        tailf:display-when "not(../../../../ncs:module) or ../../../../ncs:module[ncs:name='Cisco-IOS-XR-asr9k-lc-breakout-port-cfg'] or (../../../../ncs:live-status-protocol[not(ncs:capability)]) or (../../../../ncs:live-status-protocol/ncs:capability/ncs:module[.='Cisco-IOS-XR-asr9k-lc-breakout-port-cfg'])";
      }
    }
  }
  augment "/ncs:devices/ncs:device/ncs:config/a1:active-nodes/a1:active-node" {
    description
      "This augment extends the configuration data of
       'Cisco-IOS-XR-config-mda-cfg'";
    uses HARDWARE-MODULE-BREAKOUT {
      refine hardware-module-breakout {
        tailf:ncs-device-type "netconf";
        tailf:display-when "not(../../../../ncs:module) or ../../../../ncs:module[ncs:name='Cisco-IOS-XR-asr9k-lc-breakout-port-cfg']";
      }
    }
  }
}

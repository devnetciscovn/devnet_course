module Cisco-IOS-XR-crypto-cepki-cfg-deviations {
  // Generated by yanger -t ncs
  tailf:mount-id "cisco-iosxr-nc-7.3:cisco-iosxr-nc-7.3";
  tailf:ncs-device-type "netconf";

  namespace "http://cisco.com/ns/yang/Cisco-IOS-XR-crypto-cepki-cfg-deviations";
  prefix crypto-cepki-cfg-deviations;

  import Cisco-IOS-XR-crypto-cepki-cfg {
    prefix crypto-cepki-cfg;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-cepki package configuration.

     Copyright (c) 2013-2021 by Cisco Systems, Inc.
     All rights reserved.";

  revision 2020-06-23 {
    description
      "Fips mode disabled for aarch64 platform";
  }

  deviation "/ncs:devices/ncs:template/ncs:ned-id/ncs:config/crypto-cepki-cfg:crypto-ca/crypto-cepki-cfg:fips-mode/crypto-cepki-cfg:enable" {
    deviate not-supported;
  }
  deviation "/ncs:devices/ncs:device/ncs:live-status/crypto-cepki-cfg:crypto-ca/crypto-cepki-cfg:fips-mode/crypto-cepki-cfg:enable" {
    deviate not-supported;
  }
  deviation "/ncs:devices/ncs:device/ncs:config/crypto-cepki-cfg:crypto-ca/crypto-cepki-cfg:fips-mode/crypto-cepki-cfg:enable" {
    deviate not-supported;
  }
}

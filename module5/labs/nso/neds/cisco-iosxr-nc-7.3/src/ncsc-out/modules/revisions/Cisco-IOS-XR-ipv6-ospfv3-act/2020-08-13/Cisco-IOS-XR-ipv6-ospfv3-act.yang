module Cisco-IOS-XR-ipv6-ospfv3-act {
  // Generated by yanger -t ncs
  tailf:mount-id "cisco-iosxr-nc-7.3:cisco-iosxr-nc-7.3";
  tailf:ncs-device-type "netconf";

  namespace "http://cisco.com/ns/yang/Cisco-IOS-XR-ipv6-ospfv3-act";
  prefix ospfv3-act;

  import cisco-semver {
    prefix semver;
  }
  import Cisco-IOS-XR-types {
    prefix xr;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv6 OSPFv3 action package configuration.

     Copyright (c) 2016-2020 by Cisco Systems, Inc.
     All rights reserved.";

  revision 2020-08-13 {
    description
      "Added xr-task name ospf to restrict unlimited permission";
    semver:module-version "1.1.0";
  }
  revision 2019-10-01 {
    description
      "Made changes to be RFC6087 compliant";
    semver:module-version "1.1.0";
  }
  revision 2019-04-05 {
    description
      "Establish semantic version baseline.";
    semver:module-version "1.0.0";
  }
  revision 2016-09-14 {
    description
      "IOS XR 6.2.1 revision.";
  }

  grouping ncs_template_OSPFv3-STAT-ATTRIBUTES {
    description
      "OSPFv3 Stat Attributes";
    leaf process {
      type empty;
      description
        "Reset OSPFv3 process";
    }
    leaf redistribution {
      type empty;
      description
        "Clear OSPFv3 route redistrbution";
    }
    leaf route {
      type empty;
      description
        "Clear OSPFv3 route table";
    }
    container stats {
      description
        "OSPFv3 counters and statistics";
      leaf spf {
        type empty;
        description
          "SPF statistics";
      }
      leaf prefix-priority {
        type empty;
        description
          "SPF Prefix Priority statistics";
      }
      container neighbor {
        description
          "Neighbor statistics per interface or neighbor id";
        leaf neighbor-id {
          type string;
          description
            "Neighbor ID";
        }
        container interface {
          description
            "Interface";
          leaf interface-name {
            type xr:ncs_template_Interface-name;
            description
              "OSPFv3 interface statistics";
          }
        }
      }
    }
  }

  grouping ncs_rpc_notif_OSPFv3-STAT-ATTRIBUTES {
    description
      "OSPFv3 Stat Attributes";
    leaf process {
      type empty;
      description
        "Reset OSPFv3 process";
    }
    leaf redistribution {
      type empty;
      description
        "Clear OSPFv3 route redistrbution";
    }
    leaf route {
      type empty;
      description
        "Clear OSPFv3 route table";
    }
    container stats {
      description
        "OSPFv3 counters and statistics";
      leaf spf {
        type empty;
        description
          "SPF statistics";
      }
      leaf prefix-priority {
        type empty;
        description
          "SPF Prefix Priority statistics";
      }
      container neighbor {
        description
          "Neighbor statistics per interface or neighbor id";
        leaf neighbor-id {
          type inet:ipv4-address;
          description
            "Neighbor ID";
        }
        container interface {
          description
            "Interface";
          leaf interface-name {
            type xr:ncs_rpc_notif_Interface-name;
            description
              "OSPFv3 interface statistics";
          }
        }
      }
    }
  }

  grouping live_ncs_OSPFv3-STAT-ATTRIBUTES {
    description
      "OSPFv3 Stat Attributes";
    leaf process {
      type empty;
      description
        "Reset OSPFv3 process";
    }
    leaf redistribution {
      type empty;
      description
        "Clear OSPFv3 route redistrbution";
    }
    leaf route {
      type empty;
      description
        "Clear OSPFv3 route table";
    }
    container stats {
      description
        "OSPFv3 counters and statistics";
      leaf spf {
        type empty;
        description
          "SPF statistics";
      }
      leaf prefix-priority {
        type empty;
        description
          "SPF Prefix Priority statistics";
      }
      container neighbor {
        description
          "Neighbor statistics per interface or neighbor id";
        leaf neighbor-id {
          type inet:ipv4-address;
          description
            "Neighbor ID";
        }
        container interface {
          description
            "Interface";
          leaf interface-name {
            type xr:live_ncs_Interface-name;
            description
              "OSPFv3 interface statistics";
          }
        }
      }
    }
  }

  grouping OSPFv3-STAT-ATTRIBUTES {
    description
      "OSPFv3 Stat Attributes";
    leaf process {
      type empty;
      description
        "Reset OSPFv3 process";
    }
    leaf redistribution {
      type empty;
      description
        "Clear OSPFv3 route redistrbution";
    }
    leaf route {
      type empty;
      description
        "Clear OSPFv3 route table";
    }
    container stats {
      description
        "OSPFv3 counters and statistics";
      leaf spf {
        type empty;
        description
          "SPF statistics";
      }
      leaf prefix-priority {
        type empty;
        description
          "SPF Prefix Priority statistics";
      }
      container neighbor {
        description
          "Neighbor statistics per interface or neighbor id";
        leaf neighbor-id {
          type inet:ipv4-address;
          description
            "Neighbor ID";
        }
        container interface {
          description
            "Interface";
          leaf interface-name {
            type xr:Interface-name;
            description
              "OSPFv3 interface statistics";
          }
        }
      }
    }
  }

  augment "/ncs:devices/ncs:device/ncs:rpc" {
    container rpc-clear-ospfv3-instance-vrf {
      tailf:ncs-device-type "netconf";
      tailf:display-when "not(../../ncs:module) or ../../ncs:module[ncs:name='Cisco-IOS-XR-ipv6-ospfv3-act']";
      tailf:action clear-ospfv3-instance-vrf {
        tailf:actionpoint ncsproxy {
          tailf:internal;
        }
        description
          "Clear one or more non-default OSPFv3 VRFs in process";
        input {
          container instance {
            description
              "OSPFv3 instance name";
            leaf instance-identifier {
              type string;
              mandatory true;
              description
                "OSPFv3 process instance identifier";
            }
            container vrf {
              description
                "Clear one or more non-default OSPFv3 VRFs in process";
              leaf vrf-name {
                type string;
                mandatory true;
                description
                  "OSPFv3 VRF name";
              }
              uses ncs_rpc_notif_OSPFv3-STAT-ATTRIBUTES;
            }
            container all {
              description
                "Clear all non-default OSPFv3 VRFs";
              uses ncs_rpc_notif_OSPFv3-STAT-ATTRIBUTES;
            }
            container all-inclusive {
              description
                "Clear all non-default and default OSPFv3 VRFs";
              uses ncs_rpc_notif_OSPFv3-STAT-ATTRIBUTES;
            }
          }
        }
      }
    }
  }
  augment "/ncs:devices/ncs:device-group/ncs:ned-id/ncs:rpc" {
    container rpc-clear-ospfv3-instance-vrf {
      tailf:ncs-device-type "netconf";
      tailf:display-when "/ncs:devices/ncs:device[ncs:name=current()/../../../ncs:member]/ncs:module[ncs:name='Cisco-IOS-XR-ipv6-ospfv3-act']";
      tailf:action clear-ospfv3-instance-vrf {
        tailf:actionpoint ncsproxy {
          tailf:internal;
        }
        description
          "Clear one or more non-default OSPFv3 VRFs in process";
        input {
          container instance {
            description
              "OSPFv3 instance name";
            leaf instance-identifier {
              type string;
              mandatory true;
              description
                "OSPFv3 process instance identifier";
            }
            container vrf {
              description
                "Clear one or more non-default OSPFv3 VRFs in process";
              leaf vrf-name {
                type string;
                mandatory true;
                description
                  "OSPFv3 VRF name";
              }
              uses ncs_rpc_notif_OSPFv3-STAT-ATTRIBUTES;
            }
            container all {
              description
                "Clear all non-default OSPFv3 VRFs";
              uses ncs_rpc_notif_OSPFv3-STAT-ATTRIBUTES;
            }
            container all-inclusive {
              description
                "Clear all non-default and default OSPFv3 VRFs";
              uses ncs_rpc_notif_OSPFv3-STAT-ATTRIBUTES;
            }
          }
        }
      }
    }
  }
  augment "/ncs:devices/ncs:device/ncs:rpc" {
    container rpc-clear-ospfv3-statistics {
      tailf:ncs-device-type "netconf";
      tailf:display-when "not(../../ncs:module) or ../../ncs:module[ncs:name='Cisco-IOS-XR-ipv6-ospfv3-act']";
      tailf:action clear-ospfv3-statistics {
        tailf:actionpoint ncsproxy {
          tailf:internal;
        }
        description
          "Clear OSPFv3 counters and statistics";
        input {
          container instance {
            description
              "Clear data from OSPFv3 instance";
            leaf instance-identifier {
              type string;
              description
                "OSPFv3 process instance identifier";
            }
          }
          leaf prefix-priority {
            type empty;
            description
              "All OSPFv3 counters and statistics";
          }
          leaf spf {
            type empty;
            description
              "SPF statistics";
          }
          leaf neighbor {
            type empty;
            description
              "Neighbor statistics per neighbor id";
          }
        }
      }
    }
  }
  augment "/ncs:devices/ncs:device-group/ncs:ned-id/ncs:rpc" {
    container rpc-clear-ospfv3-statistics {
      tailf:ncs-device-type "netconf";
      tailf:display-when "/ncs:devices/ncs:device[ncs:name=current()/../../../ncs:member]/ncs:module[ncs:name='Cisco-IOS-XR-ipv6-ospfv3-act']";
      tailf:action clear-ospfv3-statistics {
        tailf:actionpoint ncsproxy {
          tailf:internal;
        }
        description
          "Clear OSPFv3 counters and statistics";
        input {
          container instance {
            description
              "Clear data from OSPFv3 instance";
            leaf instance-identifier {
              type string;
              description
                "OSPFv3 process instance identifier";
            }
          }
          leaf prefix-priority {
            type empty;
            description
              "All OSPFv3 counters and statistics";
          }
          leaf spf {
            type empty;
            description
              "SPF statistics";
          }
          leaf neighbor {
            type empty;
            description
              "Neighbor statistics per neighbor id";
          }
        }
      }
    }
  }
  augment "/ncs:devices/ncs:device/ncs:rpc" {
    container rpc-clear-ospfv3-statistics-neighbor {
      tailf:ncs-device-type "netconf";
      tailf:display-when "not(../../ncs:module) or ../../ncs:module[ncs:name='Cisco-IOS-XR-ipv6-ospfv3-act']";
      tailf:action clear-ospfv3-statistics-neighbor {
        tailf:actionpoint ncsproxy {
          tailf:internal;
        }
        description
          "Clear OSPFv3 neighbor statistics per interface or neighbor id";
        input {
          container instance {
            description
              "Clear data from OSPFv3 instance";
            leaf instance-identifier {
              type string;
              description
                "OSPFv3 process instance identifier";
            }
          }
          container neighbor {
            description
              "Neighbor";
            leaf neighbor-id {
              type inet:ipv4-address;
              description
                "Neighbor ID";
            }
            leaf interface-name {
              type xr:ncs_rpc_notif_Interface-name;
              description
                "Interface";
            }
          }
        }
      }
    }
  }
  augment "/ncs:devices/ncs:device-group/ncs:ned-id/ncs:rpc" {
    container rpc-clear-ospfv3-statistics-neighbor {
      tailf:ncs-device-type "netconf";
      tailf:display-when "/ncs:devices/ncs:device[ncs:name=current()/../../../ncs:member]/ncs:module[ncs:name='Cisco-IOS-XR-ipv6-ospfv3-act']";
      tailf:action clear-ospfv3-statistics-neighbor {
        tailf:actionpoint ncsproxy {
          tailf:internal;
        }
        description
          "Clear OSPFv3 neighbor statistics per interface or neighbor id";
        input {
          container instance {
            description
              "Clear data from OSPFv3 instance";
            leaf instance-identifier {
              type string;
              description
                "OSPFv3 process instance identifier";
            }
          }
          container neighbor {
            description
              "Neighbor";
            leaf neighbor-id {
              type inet:ipv4-address;
              description
                "Neighbor ID";
            }
            leaf interface-name {
              type xr:ncs_rpc_notif_Interface-name;
              description
                "Interface";
            }
          }
        }
      }
    }
  }
  augment "/ncs:devices/ncs:device/ncs:rpc" {
    container rpc-clear-ospfv3-process {
      tailf:ncs-device-type "netconf";
      tailf:display-when "not(../../ncs:module) or ../../ncs:module[ncs:name='Cisco-IOS-XR-ipv6-ospfv3-act']";
      tailf:action clear-ospfv3-process {
        tailf:actionpoint ncsproxy {
          tailf:internal;
        }
        description
          "Clear (reset) OSPFv3 Process";
        input {
          container instance {
            description
              "Clear data from OSPFv3 instance";
            leaf instance-identifier {
              type string;
              description
                "OSPFv3 process instance identifier";
            }
          }
          leaf process {
            type empty;
            mandatory true;
            description
              "Reset OSPFv3 process";
          }
        }
      }
    }
  }
  augment "/ncs:devices/ncs:device-group/ncs:ned-id/ncs:rpc" {
    container rpc-clear-ospfv3-process {
      tailf:ncs-device-type "netconf";
      tailf:display-when "/ncs:devices/ncs:device[ncs:name=current()/../../../ncs:member]/ncs:module[ncs:name='Cisco-IOS-XR-ipv6-ospfv3-act']";
      tailf:action clear-ospfv3-process {
        tailf:actionpoint ncsproxy {
          tailf:internal;
        }
        description
          "Clear (reset) OSPFv3 Process";
        input {
          container instance {
            description
              "Clear data from OSPFv3 instance";
            leaf instance-identifier {
              type string;
              description
                "OSPFv3 process instance identifier";
            }
          }
          leaf process {
            type empty;
            mandatory true;
            description
              "Reset OSPFv3 process";
          }
        }
      }
    }
  }
  augment "/ncs:devices/ncs:device/ncs:rpc" {
    container rpc-clear-ospfv3-redistribution {
      tailf:ncs-device-type "netconf";
      tailf:display-when "not(../../ncs:module) or ../../ncs:module[ncs:name='Cisco-IOS-XR-ipv6-ospfv3-act']";
      tailf:action clear-ospfv3-redistribution {
        tailf:actionpoint ncsproxy {
          tailf:internal;
        }
        description
          "Clear OSPFv3 route redistribution";
        input {
          container instance {
            description
              "Clear data from OSPFv3 instance";
            leaf instance-identifier {
              type string;
              description
                "OSPFv3 process instance identifier";
            }
          }
          leaf redistribution {
            type empty;
            mandatory true;
            description
              "Clear OSPFv3 route redistribution";
          }
        }
      }
    }
  }
  augment "/ncs:devices/ncs:device-group/ncs:ned-id/ncs:rpc" {
    container rpc-clear-ospfv3-redistribution {
      tailf:ncs-device-type "netconf";
      tailf:display-when "/ncs:devices/ncs:device[ncs:name=current()/../../../ncs:member]/ncs:module[ncs:name='Cisco-IOS-XR-ipv6-ospfv3-act']";
      tailf:action clear-ospfv3-redistribution {
        tailf:actionpoint ncsproxy {
          tailf:internal;
        }
        description
          "Clear OSPFv3 route redistribution";
        input {
          container instance {
            description
              "Clear data from OSPFv3 instance";
            leaf instance-identifier {
              type string;
              description
                "OSPFv3 process instance identifier";
            }
          }
          leaf redistribution {
            type empty;
            mandatory true;
            description
              "Clear OSPFv3 route redistribution";
          }
        }
      }
    }
  }
  augment "/ncs:devices/ncs:device/ncs:rpc" {
    container rpc-clear-ospfv3-routes {
      tailf:ncs-device-type "netconf";
      tailf:display-when "not(../../ncs:module) or ../../ncs:module[ncs:name='Cisco-IOS-XR-ipv6-ospfv3-act']";
      tailf:action clear-ospfv3-routes {
        tailf:actionpoint ncsproxy {
          tailf:internal;
        }
        description
          "Clear OSPFv3 route table";
        input {
          container instance {
            description
              "Clear data from OSPFv3 instance";
            leaf instance-identifier {
              type string;
              description
                "OSPFv3 process instance identifier";
            }
          }
          leaf route {
            type empty;
            mandatory true;
            description
              "Clear OSPFv3 route table";
          }
        }
      }
    }
  }
  augment "/ncs:devices/ncs:device-group/ncs:ned-id/ncs:rpc" {
    container rpc-clear-ospfv3-routes {
      tailf:ncs-device-type "netconf";
      tailf:display-when "/ncs:devices/ncs:device[ncs:name=current()/../../../ncs:member]/ncs:module[ncs:name='Cisco-IOS-XR-ipv6-ospfv3-act']";
      tailf:action clear-ospfv3-routes {
        tailf:actionpoint ncsproxy {
          tailf:internal;
        }
        description
          "Clear OSPFv3 route table";
        input {
          container instance {
            description
              "Clear data from OSPFv3 instance";
            leaf instance-identifier {
              type string;
              description
                "OSPFv3 process instance identifier";
            }
          }
          leaf route {
            type empty;
            mandatory true;
            description
              "Clear OSPFv3 route table";
          }
        }
      }
    }
  }
}

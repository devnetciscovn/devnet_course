module Cisco-IOS-XR-lldp-clear-act {
  // Generated by yanger -t ncs
  tailf:mount-id "cisco-iosxr-nc-7.3:cisco-iosxr-nc-7.3";
  tailf:ncs-device-type "netconf";

  namespace "http://cisco.com/ns/yang/Cisco-IOS-XR-lldp-clear-act";
  prefix lldp-clear-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR clear per-interface adjacencies for lldp module.

     Copyright (c) 2018-2019 by Cisco Systems, Inc.
     All rights reserved.";

  revision 2019-11-13 {
    description
      "Establish semantic version baseline.";
    semver:module-version "1.0.0";
  }
  revision 2019-09-09 {
    description
      "IOS XR 6.5.1 revision.";
  }

  augment "/ncs:devices/ncs:device/ncs:rpc" {
    container rpc-clear-lldp-adj {
      tailf:ncs-device-type "netconf";
      tailf:display-when "not(../../ncs:module) or ../../ncs:module[ncs:name='Cisco-IOS-XR-lldp-clear-act']";
      tailf:action clear-lldp-adj {
        tailf:actionpoint ncsproxy {
          tailf:internal;
        }
        description
          "Clear lldp per interface adjacencies";
        input {
          leaf interface {
            type string;
            description
              "Interface name in R/S/I/P format";
          }
        }
      }
    }
  }
  augment "/ncs:devices/ncs:device-group/ncs:ned-id/ncs:rpc" {
    container rpc-clear-lldp-adj {
      tailf:ncs-device-type "netconf";
      tailf:display-when "/ncs:devices/ncs:device[ncs:name=current()/../../../ncs:member]/ncs:module[ncs:name='Cisco-IOS-XR-lldp-clear-act']";
      tailf:action clear-lldp-adj {
        tailf:actionpoint ncsproxy {
          tailf:internal;
        }
        description
          "Clear lldp per interface adjacencies";
        input {
          leaf interface {
            type string;
            description
              "Interface name in R/S/I/P format";
          }
        }
      }
    }
  }
}

submodule Cisco-IOS-XR-ip-udp-oper-sub1 {
  // Generated by yanger -t ncs
  tailf:mount-id "cisco-iosxr-nc-7.3:cisco-iosxr-nc-7.3";

  belongs-to Cisco-IOS-XR-ip-udp-oper {
    prefix Cisco-IOS-XR-ip-udp-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-udp package operational data.

     Copyright (c) 2013-2020 by Cisco Systems, Inc.
     All rights reserved.";

  revision 2020-04-06 {
    description
      "min_ttl_dropped field is added to PCB_DETAIL output.";
    semver:module-version "1.1.0";
  }
  revision 2019-04-05 {
    description
      "Establish semantic version baseline.";
    semver:module-version "1.0.0";
  }
  revision 2018-08-09 {
    description
      "bind_local field is added to PCB_DETAIL output";
  }
  revision 2018-03-04 {
    description
      "PCB_ID argument is passed in string format.";
  }
  revision 2017-09-07 {
    description
      "Fixed type translation error.";
  }
  revision 2016-02-26 {
    description
      "Descriptions updated.";
  }
  revision 2015-11-09 {
    description
      "IOS XR 6.0 revision.";
  }

  typedef ncs_template_Udp-in6-addr {
    type string;
    description
      "Udp in6 addr";
  }

  typedef ncs_template_Udp-address-family {
    type string;
    description
      "Address Family Type";
  }

  typedef ncs_rpc_notif_Udp-in6-addr {
    type inet:ipv6-address;
    description
      "Udp in6 addr";
  }

  typedef ncs_rpc_notif_Udp-address-family {
    type enumeration {
      enum "ipv4" {
        value 2;
        description
          "IPv4";
      }
      enum "ipv6" {
        value 10;
        description
          "IPv6";
      }
    }
    description
      "Address Family Type";
  }

  typedef live_ncs_Udp-in6-addr {
    type inet:ipv6-address;
    description
      "Udp in6 addr";
  }

  typedef live_ncs_Udp-address-family {
    type enumeration {
      enum "ipv4" {
        value 2;
        description
          "IPv4";
      }
      enum "ipv6" {
        value 10;
        description
          "IPv6";
      }
    }
    description
      "Address Family Type";
  }

  typedef Udp-in6-addr {
    type inet:ipv6-address;
    description
      "Udp in6 addr";
  }

  typedef Udp-address-family {
    type enumeration {
      enum "ipv4" {
        value 2;
        description
          "IPv4";
      }
      enum "ipv6" {
        value 10;
        description
          "IPv6";
      }
    }
    description
      "Address Family Type";
  }

  grouping ncs_template_UDP-SH-BRIEF-BAG {
    description
      "UDP connection brief information";
    container local-address {
      description
        "Local address";
      uses ncs_template_UDP-ADDRESS-TYPE;
    }
    container foreign-address {
      description
        "Foreign address";
      uses ncs_template_UDP-ADDRESS-TYPE;
    }
    leaf af-name {
      type ncs_template_Udp-address-family;
      description
        "Address family";
    }
    leaf local-port {
      type string;
      description
        "Local port";
    }
    leaf foreign-port {
      type string;
      description
        "Foreign port";
    }
    leaf receive-queue {
      type string;
      description
        "Receive queue count";
    }
    leaf send-queue {
      type string;
      description
        "Send queue count";
    }
    leaf vrf-id {
      type string;
      description
        "VRF ID";
    }
  }

  grouping ncs_template_UDP-PCB-FLAGS-BAG {
    description
      "UDP PCB flags";
    leaf recv-opts {
      type string;
      description
        "Receive input options";
    }
    leaf recv-ret-opts {
      type string;
      description
        "Receive input source-route options";
    }
    leaf recv-dest-addr {
      type string;
      description
        "Receive destination address";
    }
    leaf header-include {
      type string;
      description
        "Header include option";
    }
    leaf recv-intf {
      type string;
      description
        "Receive input interface";
    }
    leaf recv-header {
      type string;
      description
        "Receive header";
    }
    leaf mcast-loopback {
      type string;
      description
        "Loopback of multicast packet";
    }
    leaf recv-l2-header {
      type string;
      description
        "Receive L2 header";
    }
    leaf recv-packet-info {
      type string;
      description
        "Receive packet information";
    }
    leaf router-alert {
      type string;
      description
        "Receive router alert packets";
    }
    leaf recv-hop-limit {
      type string;
      description
        "Receive hop limit";
    }
    leaf recv-routing-header {
      type string;
      description
        "Receive routing header";
    }
    leaf recv-hop-header {
      type string;
      description
        "Receive hop by hop option header";
    }
    leaf recv-dest-header {
      type string;
      description
        "Receive destination option header";
    }
    leaf recv-traffic-class {
      type string;
      description
        "Receive traffic class";
    }
    leaf recv-ip-sec {
      type string;
      description
        "Receive IP security information";
    }
    leaf recv-tabel-id {
      type string;
      description
        "Receive table identifier";
    }
    leaf recv-pak-priority {
      type string;
      description
        "Receive packet priority";
    }
    leaf conn-limit {
      type string;
      description
        "Connection limit";
    }
    leaf opt-handled {
      type string;
      description
        "Option handled";
    }
    leaf bind-local {
      type string;
      description
        "Local node packet delivery";
    }
  }

  grouping ncs_template_UDP-ADDRESS-TYPE {
    description
      "UDP ADDRESS TYPE";
    leaf af-name {
      type ncs_template_Udp-address-family;
      description
        "AFName";
    }
    leaf ipv4-address {
      // NCS drop when statement
      type string;
      description
        "IPv4 Address";
    }
    leaf ipv6-address {
      // NCS drop when statement
      type ncs_template_Udp-in6-addr;
      description
        "IPv6 Address";
    }
  }

  grouping ncs_template_UDP-SH-TABLE-BAG {
    description
      "UDP detail pcb information";
    container local-address {
      description
        "Local address";
      uses ncs_template_UDP-ADDRESS-TYPE;
    }
    container foreign-address {
      description
        "Foreign address";
      uses ncs_template_UDP-ADDRESS-TYPE;
    }
    container pcb-flags {
      description
        "PCB flags";
      uses ncs_template_UDP-PCB-FLAGS-BAG;
    }
    leaf af-name {
      type ncs_template_Udp-address-family;
      description
        "Address family";
    }
    leaf local-process-id {
      type string;
      description
        "ID of local process";
    }
    leaf local-port {
      type string;
      description
        "Local port";
    }
    leaf foreign-port {
      type string;
      description
        "Foreign port";
    }
    leaf receive-queue {
      type string;
      description
        "Receive queue count";
    }
    leaf send-queue {
      type string;
      description
        "Send queue count";
    }
    leaf vrf-id {
      type string;
      description
        "VRF ID";
    }
    leaf flow-label {
      type string;
      description
        "Flow label set ";
    }
    leaf traffic-class {
      type string;
      description
        "Traffic Class set ";
    }
  }

  grouping ncs_template_UDP-PCB-RECEIVE-STATS-TYPE {
    description
      "UDP receive statistics";
    leaf received-network-packets {
      type string;
      description
        "Packets received from network";
    }
    leaf failed-queued-application-packets {
      type string;
      description
        "Packets failed queued to application";
    }
    leaf queued-application-packets {
      type string;
      description
        "Packets queued to application";
    }
    leaf failed-queued-application-socket-packets {
      type string;
      description
        "Packet that couldn't be queued to application.on
         socket";
    }
    leaf queued-application-socket-packets {
      type string;
      description
        "Packets queued to application on socket";
    }
    leaf min-ttl-dropped {
      type string;
      description
        "Received packets dropped due to minttl";
    }
  }

  grouping ncs_template_UDP-PCB-SEND-STATS-TYPE {
    description
      "UDP send statistics";
    leaf received-application-bytes {
      type string;
      units "byte";
      description
        "Bytes received from application";
    }
    leaf received-xipc-pulses {
      type string;
      description
        "XIPC pulses received from application";
    }
    leaf sent-network-packets {
      type string;
      description
        "Packets sent to network (v4/v6 IO)";
    }
    leaf sent-net-io-packets {
      type string;
      description
        "Packets sent to network (NetIO)";
    }
    leaf failed-queued-network-packets {
      type string;
      description
        "Packets failed getting queued to network (v4/v6
         IO)";
    }
    leaf failed-queued-net-io-packets {
      type string;
      description
        "Packets failed getting queued to network (NetIO)";
    }
  }

  grouping ncs_template_UDP-SH-PCB-STATS-BAG {
    description
      "UDP statistics";
    container send {
      description
        "UDP send statistics";
      uses ncs_template_UDP-PCB-SEND-STATS-TYPE;
    }
    container receive {
      description
        "UDP receive statistics";
      uses ncs_template_UDP-PCB-RECEIVE-STATS-TYPE;
    }
    leaf vrf-id {
      type string;
      description
        "VRF ID";
    }
    leaf is-paw-socket {
      type string;
      description
        "True if paw socket";
    }
  }

  grouping ncs_template_UDP-SH-STATS-BAG {
    description
      "UDP statistics summary";
    leaf received-total-packets {
      type string;
      description
        "Total packets received";
    }
    leaf received-no-port-packets {
      type string;
      description
        "Packets received when no wild listener";
    }
    leaf received-bad-checksum-packets {
      type string;
      description
        "Packets received has bad checksum";
    }
    leaf received-too-short-packets {
      type string;
      description
        "Packets received is too short";
    }
    leaf received-drop-packets {
      type string;
      description
        "Packets dropped for other reasons";
    }
    leaf sent-total-packets {
      type string;
      description
        "Total packets sent";
    }
    leaf sent-error-packets {
      type string;
      description
        "Total send erorr packets";
    }
    leaf forward-broadcast-packets {
      type string;
      description
        "Total forwarding broadcast packets";
    }
    leaf cloned-packets {
      type string;
      description
        "Total cloned packets";
    }
    leaf failed-clone-packets {
      type string;
      description
        "Total failed cloned packets";
    }
  }

  grouping ncs_rpc_notif_UDP-SH-BRIEF-BAG {
    description
      "UDP connection brief information";
    container local-address {
      description
        "Local address";
      uses ncs_rpc_notif_UDP-ADDRESS-TYPE;
    }
    container foreign-address {
      description
        "Foreign address";
      uses ncs_rpc_notif_UDP-ADDRESS-TYPE;
    }
    leaf af-name {
      type ncs_rpc_notif_Udp-address-family;
      description
        "Address family";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
  }

  grouping ncs_rpc_notif_UDP-PCB-FLAGS-BAG {
    description
      "UDP PCB flags";
    leaf recv-opts {
      type boolean;
      description
        "Receive input options";
    }
    leaf recv-ret-opts {
      type boolean;
      description
        "Receive input source-route options";
    }
    leaf recv-dest-addr {
      type boolean;
      description
        "Receive destination address";
    }
    leaf header-include {
      type boolean;
      description
        "Header include option";
    }
    leaf recv-intf {
      type boolean;
      description
        "Receive input interface";
    }
    leaf recv-header {
      type boolean;
      description
        "Receive header";
    }
    leaf mcast-loopback {
      type boolean;
      description
        "Loopback of multicast packet";
    }
    leaf recv-l2-header {
      type boolean;
      description
        "Receive L2 header";
    }
    leaf recv-packet-info {
      type boolean;
      description
        "Receive packet information";
    }
    leaf router-alert {
      type boolean;
      description
        "Receive router alert packets";
    }
    leaf recv-hop-limit {
      type boolean;
      description
        "Receive hop limit";
    }
    leaf recv-routing-header {
      type boolean;
      description
        "Receive routing header";
    }
    leaf recv-hop-header {
      type boolean;
      description
        "Receive hop by hop option header";
    }
    leaf recv-dest-header {
      type boolean;
      description
        "Receive destination option header";
    }
    leaf recv-traffic-class {
      type boolean;
      description
        "Receive traffic class";
    }
    leaf recv-ip-sec {
      type boolean;
      description
        "Receive IP security information";
    }
    leaf recv-tabel-id {
      type boolean;
      description
        "Receive table identifier";
    }
    leaf recv-pak-priority {
      type boolean;
      description
        "Receive packet priority";
    }
    leaf conn-limit {
      type boolean;
      description
        "Connection limit";
    }
    leaf opt-handled {
      type boolean;
      description
        "Option handled";
    }
    leaf bind-local {
      type boolean;
      description
        "Local node packet delivery";
    }
  }

  grouping ncs_rpc_notif_UDP-ADDRESS-TYPE {
    description
      "UDP ADDRESS TYPE";
    leaf af-name {
      type ncs_rpc_notif_Udp-address-family;
      description
        "AFName";
    }
    leaf ipv4-address {
      when "../af-name = 'ipv4'" {
        tailf:xpath-root 3;
        description
          "../AFName = 'IPv4'";
      }
      type inet:ipv4-address;
      description
        "IPv4 Address";
    }
    leaf ipv6-address {
      when "../af-name != 'ipv4'" {
        tailf:xpath-root 3;
        description
          "../AFName != 'IPv4'";
      }
      type ncs_rpc_notif_Udp-in6-addr;
      description
        "IPv6 Address";
    }
  }

  grouping ncs_rpc_notif_UDP-SH-TABLE-BAG {
    description
      "UDP detail pcb information";
    container local-address {
      description
        "Local address";
      uses ncs_rpc_notif_UDP-ADDRESS-TYPE;
    }
    container foreign-address {
      description
        "Foreign address";
      uses ncs_rpc_notif_UDP-ADDRESS-TYPE;
    }
    container pcb-flags {
      description
        "PCB flags";
      uses ncs_rpc_notif_UDP-PCB-FLAGS-BAG;
    }
    leaf af-name {
      type ncs_rpc_notif_Udp-address-family;
      description
        "Address family";
    }
    leaf local-process-id {
      type uint32;
      description
        "ID of local process";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
    leaf flow-label {
      type uint32;
      description
        "Flow label set ";
    }
    leaf traffic-class {
      type int32;
      description
        "Traffic Class set ";
    }
  }

  grouping ncs_rpc_notif_UDP-PCB-RECEIVE-STATS-TYPE {
    description
      "UDP receive statistics";
    leaf received-network-packets {
      type uint64;
      description
        "Packets received from network";
    }
    leaf failed-queued-application-packets {
      type uint32;
      description
        "Packets failed queued to application";
    }
    leaf queued-application-packets {
      type uint64;
      description
        "Packets queued to application";
    }
    leaf failed-queued-application-socket-packets {
      type uint32;
      description
        "Packet that couldn't be queued to application.on
         socket";
    }
    leaf queued-application-socket-packets {
      type uint64;
      description
        "Packets queued to application on socket";
    }
    leaf min-ttl-dropped {
      type uint64;
      description
        "Received packets dropped due to minttl";
    }
  }

  grouping ncs_rpc_notif_UDP-PCB-SEND-STATS-TYPE {
    description
      "UDP send statistics";
    leaf received-application-bytes {
      type uint64;
      units "byte";
      description
        "Bytes received from application";
    }
    leaf received-xipc-pulses {
      type uint64;
      description
        "XIPC pulses received from application";
    }
    leaf sent-network-packets {
      type uint64;
      description
        "Packets sent to network (v4/v6 IO)";
    }
    leaf sent-net-io-packets {
      type uint64;
      description
        "Packets sent to network (NetIO)";
    }
    leaf failed-queued-network-packets {
      type uint32;
      description
        "Packets failed getting queued to network (v4/v6
         IO)";
    }
    leaf failed-queued-net-io-packets {
      type uint32;
      description
        "Packets failed getting queued to network (NetIO)";
    }
  }

  grouping ncs_rpc_notif_UDP-SH-PCB-STATS-BAG {
    description
      "UDP statistics";
    container send {
      description
        "UDP send statistics";
      uses ncs_rpc_notif_UDP-PCB-SEND-STATS-TYPE;
    }
    container receive {
      description
        "UDP receive statistics";
      uses ncs_rpc_notif_UDP-PCB-RECEIVE-STATS-TYPE;
    }
    leaf vrf-id {
      type uint32;
      description
        "VRF ID";
    }
    leaf is-paw-socket {
      type boolean;
      description
        "True if paw socket";
    }
  }

  grouping ncs_rpc_notif_UDP-SH-STATS-BAG {
    description
      "UDP statistics summary";
    leaf received-total-packets {
      type uint32;
      description
        "Total packets received";
    }
    leaf received-no-port-packets {
      type uint32;
      description
        "Packets received when no wild listener";
    }
    leaf received-bad-checksum-packets {
      type uint32;
      description
        "Packets received has bad checksum";
    }
    leaf received-too-short-packets {
      type uint32;
      description
        "Packets received is too short";
    }
    leaf received-drop-packets {
      type uint32;
      description
        "Packets dropped for other reasons";
    }
    leaf sent-total-packets {
      type uint32;
      description
        "Total packets sent";
    }
    leaf sent-error-packets {
      type uint32;
      description
        "Total send erorr packets";
    }
    leaf forward-broadcast-packets {
      type uint32;
      description
        "Total forwarding broadcast packets";
    }
    leaf cloned-packets {
      type uint32;
      description
        "Total cloned packets";
    }
    leaf failed-clone-packets {
      type uint32;
      description
        "Total failed cloned packets";
    }
  }

  grouping live_ncs_UDP-SH-BRIEF-BAG {
    description
      "UDP connection brief information";
    container local-address {
      description
        "Local address";
      uses live_ncs_UDP-ADDRESS-TYPE;
    }
    container foreign-address {
      description
        "Foreign address";
      uses live_ncs_UDP-ADDRESS-TYPE;
    }
    leaf af-name {
      type live_ncs_Udp-address-family;
      description
        "Address family";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
  }

  grouping live_ncs_UDP-PCB-FLAGS-BAG {
    description
      "UDP PCB flags";
    leaf recv-opts {
      type boolean;
      description
        "Receive input options";
    }
    leaf recv-ret-opts {
      type boolean;
      description
        "Receive input source-route options";
    }
    leaf recv-dest-addr {
      type boolean;
      description
        "Receive destination address";
    }
    leaf header-include {
      type boolean;
      description
        "Header include option";
    }
    leaf recv-intf {
      type boolean;
      description
        "Receive input interface";
    }
    leaf recv-header {
      type boolean;
      description
        "Receive header";
    }
    leaf mcast-loopback {
      type boolean;
      description
        "Loopback of multicast packet";
    }
    leaf recv-l2-header {
      type boolean;
      description
        "Receive L2 header";
    }
    leaf recv-packet-info {
      type boolean;
      description
        "Receive packet information";
    }
    leaf router-alert {
      type boolean;
      description
        "Receive router alert packets";
    }
    leaf recv-hop-limit {
      type boolean;
      description
        "Receive hop limit";
    }
    leaf recv-routing-header {
      type boolean;
      description
        "Receive routing header";
    }
    leaf recv-hop-header {
      type boolean;
      description
        "Receive hop by hop option header";
    }
    leaf recv-dest-header {
      type boolean;
      description
        "Receive destination option header";
    }
    leaf recv-traffic-class {
      type boolean;
      description
        "Receive traffic class";
    }
    leaf recv-ip-sec {
      type boolean;
      description
        "Receive IP security information";
    }
    leaf recv-tabel-id {
      type boolean;
      description
        "Receive table identifier";
    }
    leaf recv-pak-priority {
      type boolean;
      description
        "Receive packet priority";
    }
    leaf conn-limit {
      type boolean;
      description
        "Connection limit";
    }
    leaf opt-handled {
      type boolean;
      description
        "Option handled";
    }
    leaf bind-local {
      type boolean;
      description
        "Local node packet delivery";
    }
  }

  grouping live_ncs_UDP-ADDRESS-TYPE {
    description
      "UDP ADDRESS TYPE";
    leaf af-name {
      type live_ncs_Udp-address-family;
      description
        "AFName";
    }
    leaf ipv4-address {
      // NCS drop when statement
      type inet:ipv4-address;
      description
        "IPv4 Address";
    }
    leaf ipv6-address {
      // NCS drop when statement
      type live_ncs_Udp-in6-addr;
      description
        "IPv6 Address";
    }
  }

  grouping live_ncs_UDP-SH-TABLE-BAG {
    description
      "UDP detail pcb information";
    container local-address {
      description
        "Local address";
      uses live_ncs_UDP-ADDRESS-TYPE;
    }
    container foreign-address {
      description
        "Foreign address";
      uses live_ncs_UDP-ADDRESS-TYPE;
    }
    container pcb-flags {
      description
        "PCB flags";
      uses live_ncs_UDP-PCB-FLAGS-BAG;
    }
    leaf af-name {
      type live_ncs_Udp-address-family;
      description
        "Address family";
    }
    leaf local-process-id {
      type uint32;
      description
        "ID of local process";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
    leaf flow-label {
      type uint32;
      description
        "Flow label set ";
    }
    leaf traffic-class {
      type int32;
      description
        "Traffic Class set ";
    }
  }

  grouping live_ncs_UDP-PCB-RECEIVE-STATS-TYPE {
    description
      "UDP receive statistics";
    leaf received-network-packets {
      type uint64;
      description
        "Packets received from network";
    }
    leaf failed-queued-application-packets {
      type uint32;
      description
        "Packets failed queued to application";
    }
    leaf queued-application-packets {
      type uint64;
      description
        "Packets queued to application";
    }
    leaf failed-queued-application-socket-packets {
      type uint32;
      description
        "Packet that couldn't be queued to application.on
         socket";
    }
    leaf queued-application-socket-packets {
      type uint64;
      description
        "Packets queued to application on socket";
    }
    leaf min-ttl-dropped {
      type uint64;
      description
        "Received packets dropped due to minttl";
    }
  }

  grouping live_ncs_UDP-PCB-SEND-STATS-TYPE {
    description
      "UDP send statistics";
    leaf received-application-bytes {
      type uint64;
      units "byte";
      description
        "Bytes received from application";
    }
    leaf received-xipc-pulses {
      type uint64;
      description
        "XIPC pulses received from application";
    }
    leaf sent-network-packets {
      type uint64;
      description
        "Packets sent to network (v4/v6 IO)";
    }
    leaf sent-net-io-packets {
      type uint64;
      description
        "Packets sent to network (NetIO)";
    }
    leaf failed-queued-network-packets {
      type uint32;
      description
        "Packets failed getting queued to network (v4/v6
         IO)";
    }
    leaf failed-queued-net-io-packets {
      type uint32;
      description
        "Packets failed getting queued to network (NetIO)";
    }
  }

  grouping live_ncs_UDP-SH-PCB-STATS-BAG {
    description
      "UDP statistics";
    container send {
      description
        "UDP send statistics";
      uses live_ncs_UDP-PCB-SEND-STATS-TYPE;
    }
    container receive {
      description
        "UDP receive statistics";
      uses live_ncs_UDP-PCB-RECEIVE-STATS-TYPE;
    }
    leaf vrf-id {
      type uint32;
      description
        "VRF ID";
    }
    leaf is-paw-socket {
      type boolean;
      description
        "True if paw socket";
    }
  }

  grouping live_ncs_UDP-SH-STATS-BAG {
    description
      "UDP statistics summary";
    leaf received-total-packets {
      type uint32;
      description
        "Total packets received";
    }
    leaf received-no-port-packets {
      type uint32;
      description
        "Packets received when no wild listener";
    }
    leaf received-bad-checksum-packets {
      type uint32;
      description
        "Packets received has bad checksum";
    }
    leaf received-too-short-packets {
      type uint32;
      description
        "Packets received is too short";
    }
    leaf received-drop-packets {
      type uint32;
      description
        "Packets dropped for other reasons";
    }
    leaf sent-total-packets {
      type uint32;
      description
        "Total packets sent";
    }
    leaf sent-error-packets {
      type uint32;
      description
        "Total send erorr packets";
    }
    leaf forward-broadcast-packets {
      type uint32;
      description
        "Total forwarding broadcast packets";
    }
    leaf cloned-packets {
      type uint32;
      description
        "Total cloned packets";
    }
    leaf failed-clone-packets {
      type uint32;
      description
        "Total failed cloned packets";
    }
  }

  grouping UDP-SH-BRIEF-BAG {
    description
      "UDP connection brief information";
    container local-address {
      description
        "Local address";
      uses UDP-ADDRESS-TYPE;
    }
    container foreign-address {
      description
        "Foreign address";
      uses UDP-ADDRESS-TYPE;
    }
    leaf af-name {
      type Udp-address-family;
      description
        "Address family";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
  }

  grouping UDP-PCB-FLAGS-BAG {
    description
      "UDP PCB flags";
    leaf recv-opts {
      type boolean;
      description
        "Receive input options";
    }
    leaf recv-ret-opts {
      type boolean;
      description
        "Receive input source-route options";
    }
    leaf recv-dest-addr {
      type boolean;
      description
        "Receive destination address";
    }
    leaf header-include {
      type boolean;
      description
        "Header include option";
    }
    leaf recv-intf {
      type boolean;
      description
        "Receive input interface";
    }
    leaf recv-header {
      type boolean;
      description
        "Receive header";
    }
    leaf mcast-loopback {
      type boolean;
      description
        "Loopback of multicast packet";
    }
    leaf recv-l2-header {
      type boolean;
      description
        "Receive L2 header";
    }
    leaf recv-packet-info {
      type boolean;
      description
        "Receive packet information";
    }
    leaf router-alert {
      type boolean;
      description
        "Receive router alert packets";
    }
    leaf recv-hop-limit {
      type boolean;
      description
        "Receive hop limit";
    }
    leaf recv-routing-header {
      type boolean;
      description
        "Receive routing header";
    }
    leaf recv-hop-header {
      type boolean;
      description
        "Receive hop by hop option header";
    }
    leaf recv-dest-header {
      type boolean;
      description
        "Receive destination option header";
    }
    leaf recv-traffic-class {
      type boolean;
      description
        "Receive traffic class";
    }
    leaf recv-ip-sec {
      type boolean;
      description
        "Receive IP security information";
    }
    leaf recv-tabel-id {
      type boolean;
      description
        "Receive table identifier";
    }
    leaf recv-pak-priority {
      type boolean;
      description
        "Receive packet priority";
    }
    leaf conn-limit {
      type boolean;
      description
        "Connection limit";
    }
    leaf opt-handled {
      type boolean;
      description
        "Option handled";
    }
    leaf bind-local {
      type boolean;
      description
        "Local node packet delivery";
    }
  }

  grouping UDP-ADDRESS-TYPE {
    description
      "UDP ADDRESS TYPE";
    leaf af-name {
      type Udp-address-family;
      description
        "AFName";
    }
    leaf ipv4-address {
      when "../af-name = 'ipv4'" {
        tailf:xpath-root 3;
        description
          "../AFName = 'IPv4'";
      }
      type inet:ipv4-address;
      description
        "IPv4 Address";
    }
    leaf ipv6-address {
      when "../af-name != 'ipv4'" {
        tailf:xpath-root 3;
        description
          "../AFName != 'IPv4'";
      }
      type Udp-in6-addr;
      description
        "IPv6 Address";
    }
  }

  grouping UDP-SH-TABLE-BAG {
    description
      "UDP detail pcb information";
    container local-address {
      description
        "Local address";
      uses UDP-ADDRESS-TYPE;
    }
    container foreign-address {
      description
        "Foreign address";
      uses UDP-ADDRESS-TYPE;
    }
    container pcb-flags {
      description
        "PCB flags";
      uses UDP-PCB-FLAGS-BAG;
    }
    leaf af-name {
      type Udp-address-family;
      description
        "Address family";
    }
    leaf local-process-id {
      type uint32;
      description
        "ID of local process";
    }
    leaf local-port {
      type uint16;
      description
        "Local port";
    }
    leaf foreign-port {
      type uint16;
      description
        "Foreign port";
    }
    leaf receive-queue {
      type uint32;
      description
        "Receive queue count";
    }
    leaf send-queue {
      type uint32;
      description
        "Send queue count";
    }
    leaf vrf-id {
      type uint32;
      description
        "VRF ID";
    }
    leaf flow-label {
      type uint32;
      description
        "Flow label set ";
    }
    leaf traffic-class {
      type int32;
      description
        "Traffic Class set ";
    }
  }

  grouping UDP-PCB-RECEIVE-STATS-TYPE {
    description
      "UDP receive statistics";
    leaf received-network-packets {
      type uint64;
      description
        "Packets received from network";
    }
    leaf failed-queued-application-packets {
      type uint32;
      description
        "Packets failed queued to application";
    }
    leaf queued-application-packets {
      type uint64;
      description
        "Packets queued to application";
    }
    leaf failed-queued-application-socket-packets {
      type uint32;
      description
        "Packet that couldn't be queued to application.on
         socket";
    }
    leaf queued-application-socket-packets {
      type uint64;
      description
        "Packets queued to application on socket";
    }
    leaf min-ttl-dropped {
      type uint64;
      description
        "Received packets dropped due to minttl";
    }
  }

  grouping UDP-PCB-SEND-STATS-TYPE {
    description
      "UDP send statistics";
    leaf received-application-bytes {
      type uint64;
      units "byte";
      description
        "Bytes received from application";
    }
    leaf received-xipc-pulses {
      type uint64;
      description
        "XIPC pulses received from application";
    }
    leaf sent-network-packets {
      type uint64;
      description
        "Packets sent to network (v4/v6 IO)";
    }
    leaf sent-net-io-packets {
      type uint64;
      description
        "Packets sent to network (NetIO)";
    }
    leaf failed-queued-network-packets {
      type uint32;
      description
        "Packets failed getting queued to network (v4/v6
         IO)";
    }
    leaf failed-queued-net-io-packets {
      type uint32;
      description
        "Packets failed getting queued to network (NetIO)";
    }
  }

  grouping UDP-SH-PCB-STATS-BAG {
    description
      "UDP statistics";
    container send {
      description
        "UDP send statistics";
      uses UDP-PCB-SEND-STATS-TYPE;
    }
    container receive {
      description
        "UDP receive statistics";
      uses UDP-PCB-RECEIVE-STATS-TYPE;
    }
    leaf vrf-id {
      type uint32;
      description
        "VRF ID";
    }
    leaf is-paw-socket {
      type boolean;
      description
        "True if paw socket";
    }
  }

  grouping UDP-SH-STATS-BAG {
    description
      "UDP statistics summary";
    leaf received-total-packets {
      type uint32;
      description
        "Total packets received";
    }
    leaf received-no-port-packets {
      type uint32;
      description
        "Packets received when no wild listener";
    }
    leaf received-bad-checksum-packets {
      type uint32;
      description
        "Packets received has bad checksum";
    }
    leaf received-too-short-packets {
      type uint32;
      description
        "Packets received is too short";
    }
    leaf received-drop-packets {
      type uint32;
      description
        "Packets dropped for other reasons";
    }
    leaf sent-total-packets {
      type uint32;
      description
        "Total packets sent";
    }
    leaf sent-error-packets {
      type uint32;
      description
        "Total send erorr packets";
    }
    leaf forward-broadcast-packets {
      type uint32;
      description
        "Total forwarding broadcast packets";
    }
    leaf cloned-packets {
      type uint32;
      description
        "Total cloned packets";
    }
    leaf failed-clone-packets {
      type uint32;
      description
        "Total failed cloned packets";
    }
  }
}

module Cisco-IOS-XR-cnbng-nal-aipc-client-oper {
  // Generated by yanger -t ncs
  tailf:mount-id "cisco-iosxr-nc-7.3:cisco-iosxr-nc-7.3";
  tailf:ncs-device-type "netconf";

  namespace "http://cisco.com/ns/yang/Cisco-IOS-XR-cnbng-nal-aipc-client-oper";
  prefix cnbng-nal-aipc-client-oper;

  import Cisco-IOS-XR-types {
    prefix xr;
  }
  import cisco-semver {
    prefix semver;
  }
  include Cisco-IOS-XR-cnbng-nal-aipc-client-oper-sub1 {
    revision-date 2020-08-14;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cnbng-nal-aipc-client package operational data.

     This module contains definitions
     for the following management objects:
       cnbng-nal-client: cnBNG NAL Client operational data

     Copyright (c) 2013-2020 by Cisco Systems, Inc.
     All rights reserved.";

  revision 2020-08-14 {
    description
      "adding schema support for aipc client.";
    semver:module-version "1.0.0";
  }
  revision 2019-04-05 {
    description
      "Establish semantic version baseline.";
  }
  revision 2015-11-09 {
    description
      "IOS XR 6.0 revision.";
  }

  augment "/ncs:devices/ncs:device/ncs:config" {
    // NCS drop config false container 'cnbng-nal-client'
  }
  augment "/ncs:devices/ncs:device/ncs:live-status" {
    container cnbng-nal-client {
      tailf:ncs-device-type "netconf";
      tailf:display-when "not(../../ncs:module) or ../../ncs:module[ncs:name='Cisco-IOS-XR-cnbng-nal-aipc-client-oper'] or (../../ncs:live-status-protocol[not(ncs:capability)]) or (../../ncs:live-status-protocol/ncs:capability/ncs:module[.='Cisco-IOS-XR-cnbng-nal-aipc-client-oper'])";
      description
        "cnBNG NAL Client operational data";
      container nodes {
        description
          "List of cnBNg NAL supported nodes";
        list node {
          key "node-name";
          description
            "cnBNg NAL operational data for a particular
             node";
          leaf node-name {
            type xr:live_ncs_Node-id;
            description
              "Node name";
          }
          list aipc-client-table {
            key "clientpath";
            description
              "operational data for NAL AIPC client stats";
            container aipc-client {
              description
                "operational data for aipc client stats ";
              uses live_ncs_NAL-AIPC-STATS-DATA;
            }
            leaf clientpath {
              type xr:live_ncs_Cisco-ios-xr-string;
              description
                "client";
            }
          }
        }
      }
    }
  }
  augment "/ncs:devices/ncs:template/ncs:ned-id/ncs:config" {
    // NCS drop config false container 'cnbng-nal-client'
  }
}

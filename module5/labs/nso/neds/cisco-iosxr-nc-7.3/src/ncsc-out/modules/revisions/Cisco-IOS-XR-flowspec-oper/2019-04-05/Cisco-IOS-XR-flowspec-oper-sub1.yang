submodule Cisco-IOS-XR-flowspec-oper-sub1 {
  // Generated by yanger -t ncs
  tailf:mount-id "cisco-iosxr-nc-7.3:cisco-iosxr-nc-7.3";

  belongs-to Cisco-IOS-XR-flowspec-oper {
    prefix Cisco-IOS-XR-flowspec-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR flowspec package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Fs-mgr-client-state {
    type string;
    description
      "FlowSpec manager client state";
  }

  typedef ncs_rpc_notif_Fs-mgr-client-state {
    type enumeration {
      enum "dormant" {
        description
          "Dormant";
      }
      enum "connected" {
        description
          "Connected";
      }
      enum "replay" {
        description
          "Replay";
      }
      enum "unconfigured" {
        description
          "Unconfigured";
      }
    }
    description
      "FlowSpec manager client state";
  }

  typedef live_ncs_Fs-mgr-client-state {
    type enumeration {
      enum "dormant" {
        description
          "Dormant";
      }
      enum "connected" {
        description
          "Connected";
      }
      enum "replay" {
        description
          "Replay";
      }
      enum "unconfigured" {
        description
          "Unconfigured";
      }
    }
    description
      "FlowSpec manager client state";
  }

  typedef Fs-mgr-client-state {
    type enumeration {
      enum "dormant" {
        description
          "Dormant";
      }
      enum "connected" {
        description
          "Connected";
      }
      enum "replay" {
        description
          "Replay";
      }
      enum "unconfigured" {
        description
          "Unconfigured";
      }
    }
    description
      "FlowSpec manager client state";
  }

  grouping ncs_template_FS-MGR-FLOW-STATS-CTRS {
    description
      "Flowspec class stats counters.";
    leaf packets {
      type string;
      description
        "Number of packets";
    }
    leaf bytes {
      type string;
      units "byte";
      description
        "Number of bytes";
    }
  }

  grouping ncs_template_FS-MGR-FLOW-STATS {
    description
      "Flowspec class classified and drop stats.";
    container classified {
      description
        "Classified statistics";
      uses ncs_template_FS-MGR-FLOW-STATS-CTRS;
    }
    container dropped {
      description
        "Drop statistics";
      uses ncs_template_FS-MGR-FLOW-STATS-CTRS;
    }
  }

  grouping ncs_template_FS-MGR-NLRI {
    description
      "FlowSpec manager NLRI information";
    container flow-statistics {
      description
        "Flow statistics";
      uses ncs_template_FS-MGR-FLOW-STATS;
    }
  }

  grouping ncs_template_FS-MGR-TBL-SUMMARY {
    description
      "FlowSpec manager table summary information";
    leaf total-flows {
      type string;
      description
        "Total number of flows";
    }
    leaf service-policies {
      type string;
      description
        "Total number of attached service policies";
    }
    leaf local-install-enabled {
      type string;
      description
        "Local installation of flowspec rules";
    }
  }

  grouping ncs_template_FS-MGR-SUMMARY {
    description
      "FlowSpec manager summary information";
    leaf vrfafi-tables {
      type string;
      description
        "Total VRF+AFI tables";
    }
    leaf flows {
      type string;
      description
        "Total flows";
    }
  }

  grouping ncs_template_FS-MGR-CLIENT {
    description
      "FlowSpec manager client information";
    leaf client-state {
      type ncs_template_Fs-mgr-client-state;
      description
        "State of FS client";
    }
    leaf client-flows {
      type string;
      description
        "Number of client flows";
    }
  }

  grouping ncs_rpc_notif_FS-MGR-FLOW-STATS-CTRS {
    description
      "Flowspec class stats counters.";
    leaf packets {
      type uint64;
      description
        "Number of packets";
    }
    leaf bytes {
      type uint64;
      units "byte";
      description
        "Number of bytes";
    }
  }

  grouping ncs_rpc_notif_FS-MGR-FLOW-STATS {
    description
      "Flowspec class classified and drop stats.";
    container classified {
      description
        "Classified statistics";
      uses ncs_rpc_notif_FS-MGR-FLOW-STATS-CTRS;
    }
    container dropped {
      description
        "Drop statistics";
      uses ncs_rpc_notif_FS-MGR-FLOW-STATS-CTRS;
    }
  }

  grouping ncs_rpc_notif_FS-MGR-NLRI {
    description
      "FlowSpec manager NLRI information";
    container flow-statistics {
      description
        "Flow statistics";
      uses ncs_rpc_notif_FS-MGR-FLOW-STATS;
    }
  }

  grouping ncs_rpc_notif_FS-MGR-TBL-SUMMARY {
    description
      "FlowSpec manager table summary information";
    leaf total-flows {
      type uint32;
      description
        "Total number of flows";
    }
    leaf service-policies {
      type uint32;
      description
        "Total number of attached service policies";
    }
    leaf local-install-enabled {
      type boolean;
      description
        "Local installation of flowspec rules";
    }
  }

  grouping ncs_rpc_notif_FS-MGR-SUMMARY {
    description
      "FlowSpec manager summary information";
    leaf vrfafi-tables {
      type uint32;
      description
        "Total VRF+AFI tables";
    }
    leaf flows {
      type uint32;
      description
        "Total flows";
    }
  }

  grouping ncs_rpc_notif_FS-MGR-CLIENT {
    description
      "FlowSpec manager client information";
    leaf client-state {
      type ncs_rpc_notif_Fs-mgr-client-state;
      description
        "State of FS client";
    }
    leaf client-flows {
      type uint32;
      description
        "Number of client flows";
    }
  }

  grouping live_ncs_FS-MGR-FLOW-STATS-CTRS {
    description
      "Flowspec class stats counters.";
    leaf packets {
      type uint64;
      description
        "Number of packets";
    }
    leaf bytes {
      type uint64;
      units "byte";
      description
        "Number of bytes";
    }
  }

  grouping live_ncs_FS-MGR-FLOW-STATS {
    description
      "Flowspec class classified and drop stats.";
    container classified {
      description
        "Classified statistics";
      uses live_ncs_FS-MGR-FLOW-STATS-CTRS;
    }
    container dropped {
      description
        "Drop statistics";
      uses live_ncs_FS-MGR-FLOW-STATS-CTRS;
    }
  }

  grouping live_ncs_FS-MGR-NLRI {
    description
      "FlowSpec manager NLRI information";
    container flow-statistics {
      description
        "Flow statistics";
      uses live_ncs_FS-MGR-FLOW-STATS;
    }
  }

  grouping live_ncs_FS-MGR-TBL-SUMMARY {
    description
      "FlowSpec manager table summary information";
    leaf total-flows {
      type uint32;
      description
        "Total number of flows";
    }
    leaf service-policies {
      type uint32;
      description
        "Total number of attached service policies";
    }
    leaf local-install-enabled {
      type boolean;
      description
        "Local installation of flowspec rules";
    }
  }

  grouping live_ncs_FS-MGR-SUMMARY {
    description
      "FlowSpec manager summary information";
    leaf vrfafi-tables {
      type uint32;
      description
        "Total VRF+AFI tables";
    }
    leaf flows {
      type uint32;
      description
        "Total flows";
    }
  }

  grouping live_ncs_FS-MGR-CLIENT {
    description
      "FlowSpec manager client information";
    leaf client-state {
      type live_ncs_Fs-mgr-client-state;
      description
        "State of FS client";
    }
    leaf client-flows {
      type uint32;
      description
        "Number of client flows";
    }
  }

  grouping FS-MGR-FLOW-STATS-CTRS {
    description
      "Flowspec class stats counters.";
    leaf packets {
      type uint64;
      description
        "Number of packets";
    }
    leaf bytes {
      type uint64;
      units "byte";
      description
        "Number of bytes";
    }
  }

  grouping FS-MGR-FLOW-STATS {
    description
      "Flowspec class classified and drop stats.";
    container classified {
      description
        "Classified statistics";
      uses FS-MGR-FLOW-STATS-CTRS;
    }
    container dropped {
      description
        "Drop statistics";
      uses FS-MGR-FLOW-STATS-CTRS;
    }
  }

  grouping FS-MGR-NLRI {
    description
      "FlowSpec manager NLRI information";
    container flow-statistics {
      description
        "Flow statistics";
      uses FS-MGR-FLOW-STATS;
    }
  }

  grouping FS-MGR-TBL-SUMMARY {
    description
      "FlowSpec manager table summary information";
    leaf total-flows {
      type uint32;
      description
        "Total number of flows";
    }
    leaf service-policies {
      type uint32;
      description
        "Total number of attached service policies";
    }
    leaf local-install-enabled {
      type boolean;
      description
        "Local installation of flowspec rules";
    }
  }

  grouping FS-MGR-SUMMARY {
    description
      "FlowSpec manager summary information";
    leaf vrfafi-tables {
      type uint32;
      description
        "Total VRF+AFI tables";
    }
    leaf flows {
      type uint32;
      description
        "Total flows";
    }
  }

  grouping FS-MGR-CLIENT {
    description
      "FlowSpec manager client information";
    leaf client-state {
      type Fs-mgr-client-state;
      description
        "State of FS client";
    }
    leaf client-flows {
      type uint32;
      description
        "Number of client flows";
    }
  }
}

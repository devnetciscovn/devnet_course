module Cisco-IOS-XR-appmgr-oper {
  // Generated by yanger -t ncs
  tailf:mount-id "cisco-iosxr-nc-7.3:cisco-iosxr-nc-7.3";
  tailf:ncs-device-type "netconf";

  namespace "http://cisco.com/ns/yang/Cisco-IOS-XR-appmgr-oper";
  prefix appmgr-oper;

  import Cisco-IOS-XR-types {
    prefix xr;
  }
  import cisco-semver {
    prefix semver;
  }
  include Cisco-IOS-XR-appmgr-oper-sub1 {
    revision-date 2021-05-15;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR appmgr package operational data.

     This module contains definitions
     for the following management objects:
       appmgr: Appmgr Operational data space

     Copyright (c) 2013-2021 by Cisco Systems, Inc.
     All rights reserved.";

  revision 2021-05-15 {
    description
      "Unused application types removed
       2021-03-01
         Adding information about installed packages
       2021-02-15
         Support for process scripts.
       2021-02-15
         Support for process scripts added.";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    // NCS drop config false container appmgr
  }
  augment "/ncs:devices/ncs:device/ncs:live-status" {
    container appmgr {
      tailf:ncs-device-type "netconf";
      tailf:display-when "not(../../ncs:module) or ../../ncs:module[ncs:name='Cisco-IOS-XR-appmgr-oper'] or (../../ncs:live-status-protocol[not(ncs:capability)]) or (../../ncs:live-status-protocol/ncs:capability/ncs:module[.='Cisco-IOS-XR-appmgr-oper'])";
      description
        "Appmgr Operational data space";
      container packages {
        description
          "Packages managed by the App Mgr";
        container installed {
          description
            "Installed packages";
          uses live_ncs_APPMGR-PACKAGES;
        }
      }
      container sources {
        description
          "Sources downloaded by the App Manager";
        list source {
          key "name";
          description
            "Information about a source";
          leaf name {
            type xr:live_ncs_Cisco-ios-xr-string;
            description
              "Name";
          }
          uses live_ncs_APPMGR-SOURCE;
        }
      }
      container process-scripts {
        description
          "Process scripts managed by the App Mgr";
        list process-script {
          key "name";
          description
            "Information about individual process script";
          container info {
            description
              "Information about a process script";
            uses live_ncs_APPMGR-DAEMON-INFO;
          }
          leaf name {
            type xr:live_ncs_Cisco-ios-xr-string;
            description
              "Name";
          }
        }
      }
      container applications {
        description
          "Applications managed by the App Mgr";
        list application {
          key "name";
          description
            "Information about individual application";
          container stats {
            description
              "Information about an application";
            uses live_ncs_APPMGR-APP-STATS;
          }
          container info {
            description
              "Information about an application";
            uses live_ncs_APPMGR-APP-INFO;
          }
          leaf name {
            type xr:live_ncs_Cisco-ios-xr-string;
            description
              "Name";
          }
        }
      }
    }
  }
  augment "/ncs:devices/ncs:template/ncs:ned-id/ncs:config" {
    // NCS drop config false container appmgr
  }
}

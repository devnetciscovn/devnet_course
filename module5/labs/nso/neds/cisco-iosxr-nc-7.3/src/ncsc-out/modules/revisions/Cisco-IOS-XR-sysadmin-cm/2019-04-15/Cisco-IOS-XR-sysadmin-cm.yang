module Cisco-IOS-XR-sysadmin-cm {
  // Generated by yanger -t ncs
  tailf:mount-id "cisco-iosxr-nc-7.3:cisco-iosxr-nc-7.3";
  tailf:ncs-device-type "netconf";

  namespace "http://www.cisco.com/ns/yang/Cisco-IOS-XR-sysadmin-cm";
  prefix cmh;

  import tailf-common {
    prefix tailf;
  }
  import tailf-xsd-types {
    prefix xs;
  }
  import Cisco-IOS-XR-sysadmin-types {
    prefix calvados;
  }
  import ietf-yang-types {
    prefix yang;
  }
  import ietf-inet-types {
    prefix inet;
  }
  import Cisco-IOS-XR-sysadmin-show-trace-cm {
    prefix cm;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     The System Admin Manager (CM)

     Copyright (c) 2010-2020 by Cisco Systems, Inc.
     All rights reserved.";

  revision 2019-04-15 {
    description
      "Establish semantic version baseline.";
    semver:module-version "1.0.0";
  }
  revision 2018-07-03 {
    description
      "Suppress Tail-f warnings in ConfD 6.4.5";
  }
  revision 2018-04-09 {
    description
      "Required changes for ConfD 6.4.5";
  }
  revision 2017-04-12 {
    description
      "Changed the namespace and module name";
  }
  revision 2016-05-11 {
    description
      "Initial version";
  }

  typedef ncs_template_area_type {
    type string;
  }

  typedef ncs_template_hex8ValueType {
    type string;
  }

  typedef ncs_rpc_notif_area_type {
    type enumeration {
      enum "SYSTEM";
      enum "RACK";
      enum "UNKNOWN";
    }
  }

  typedef ncs_rpc_notif_hex8ValueType {
    type xs:hexBinary;
  }

  typedef live_ncs_area_type {
    type enumeration {
      enum "SYSTEM";
      enum "RACK";
      enum "UNKNOWN";
    }
  }

  typedef live_ncs_hex8ValueType {
    type xs:hexBinary;
  }

  typedef area_type {
    type enumeration {
      enum "SYSTEM";
      enum "RACK";
      enum "UNKNOWN";
    }
  }

  typedef hex8ValueType {
    type xs:hexBinary;
  }

  grouping ncs_template_nodeInfoGroup {
    // NCS drop config false container summary
    // NCS drop config false container detail
  }

  grouping ncs_template_nodeInfoSummary {
    description
      "All the parameters needed to describe a node as
       represented in CM.";
    leaf type {
      type string;
      description
        "Node Type";
    }
    leaf ip_address {
      type string;
      description
        "IP address of the node";
    }
    leaf mac_address {
      type string;
      description
        "Node MAC";
    }
    leaf card_serial {
      type string;
      description
        "Card serial# the node belongs to";
    }
    leaf nti {
      type string;
      description
        "Node NTI";
    }
  }

  grouping ncs_template_nodeInfoDetail {
    description
      "All the parameters needed to describe a node as
       represented in CM.";
    leaf restart {
      type string;
      description
        "Node in Restart";
    }
    leaf data {
      type ncs_template_hex8ValueType;
      description
        "Node Data";
    }
    leaf sdr {
      type string;
      description
        "SDR Name the node belongs to";
    }
  }

  grouping ncs_template_cardInfo {
    description
      "All the parameters needed to describe a card as
       represented in CM.";
    leaf node_id {
      type string;
      description
        "Node name";
    }
    leaf card_type {
      type string;
      description
        "Card Type";
    }
    leaf hw_state {
      type string;
      description
        "Card State";
    }
    leaf sw_state {
      type string;
      description
        "Card Software State";
    }
    leaf slot {
      type string;
      description
        "Card Slot Number";
    }
    leaf card_serial {
      type string;
      description
        "Serial Number of the Card";
    }
    leaf cti {
      type string;
      description
        "Card CTI";
    }
  }

  grouping ncs_template_rackInfo {
    description
      "All the parameters needed to describe a rack as
       represented in CM.";
    leaf rack_number {
      type string;
      description
        "Rack Number";
    }
    leaf rack_serial {
      type string;
      description
        "Serial Number of the Rack";
    }
    leaf rack_state {
      type string;
      description
        "Rack State";
    }
  }

  grouping ncs_template_serviceInfo {
    description
      "All the parameters needed to describe a service as
       represented in CM.";
    leaf svc_name {
      type string;
      description
        "Service Name";
    }
    leaf placement_first {
      type string;
      description
        "Serial Number of the first card selected";
    }
    leaf nodeid_first {
      type string;
      description
        "Node id of the first card selected";
    }
    leaf placement_second {
      type string;
      description
        "Serial Number of the second card selected";
    }
    leaf nodeid_second {
      type string;
      description
        "Node id of the second card selected";
    }
    leaf svc_load {
      type string;
      description
        "Service Load";
    }
  }

  grouping ncs_template_sdrInfo {
    description
      "All the parameters needed to describe a SDR as
       represented in CM.";
    leaf sdr_id {
      type string;
      description
        "SDR ID";
    }
    leaf sdr_name {
      type string;
      description
        "SDR NAME";
    }
    leaf sdr_vlan_baseid {
      type string;
      description
        "SDR VLAN ID";
    }
    leaf sdr_version {
      type string;
      description
        "SDR Image Version";
    }
  }

  grouping ncs_template_ldrInfo {
    description
      "All the parameters needed to describe leader statistics.";
    leaf syslead {
      type string;
      description
        "Primary System Leader";
    }
    leaf bkup_syslead {
      type string;
      description
        "Backup System Leader";
    }
    leaf racklead {
      type string;
      description
        "Primary Rack Leader";
    }
    leaf bkup_racklead {
      type string;
      description
        "Backup Rack Leader";
    }
    leaf l1_dis {
      type string;
      description
        "L1 DIS";
    }
    leaf l2_dis {
      type string;
      description
        "L2 DIS";
    }
  }

  grouping ncs_template_nbrInfo {
    description
      "All the parameters needed to describe a topology neighbor";
    leaf nbr_system_id {
      type string;
      description
        "Neighbor System ID";
    }
    leaf nbr_area_type {
      type string;
      description
        "Neighbor Area Type";
    }
    leaf nbr_interface {
      type string;
      description
        "Adjacency Interface";
    }
    leaf nbr_state {
      type string;
      description
        "Neighbor State";
    }
    leaf nbr_holdtime {
      type string;
      description
        "Neighbor Hold Time";
    }
    leaf nbr_uptime {
      type string;
      description
        "Neighbor Up Time";
    }
  }

  grouping ncs_template_lspdbInfo {
    description
      "All the parameters needed to describe a lsps from lspdb";
    leaf lsp_id {
      type string;
      description
        "LSP System ID";
    }
    leaf lsp_area_type {
      type ncs_template_area_type;
      description
        "LSP Area Type";
    }
    leaf lsp_sequence {
      type string;
      description
        "LSP sequence number";
    }
    leaf lsp_core {
      type string;
      description
        "LSP core data bits";
    }
    leaf-list lsp_tlvs {
      // NCS patched for predictable order
      ordered-by user;
      type string;
      description
        "LSP TLV data";
    }
  }

  grouping ncs_rpc_notif_nodeInfoGroup {
    container summary {
      config false;
      description
        "System Admin Manager Node Inventory. All accesses are
         read-only. CLI show command looks like show node-inventory
         location <location>";
      list node_locations {
        key "node_location";
        leaf node_location {
          type calvados:ncs_rpc_notif_location-id;
        }
        list nodei {
          key "ip_address";
          uses ncs_rpc_notif_nodeInfoSummary;
        }
      }
    }
    container detail {
      config false;
      description
        "System Admin Manager Node Inventory. All accesses are
         read-only. CLI show command looks like show node-inventory
         location <location>";
      list node_locations {
        key "node_location";
        leaf node_location {
          type calvados:ncs_rpc_notif_location-id;
        }
        list nodei {
          key "ip_address";
          uses ncs_rpc_notif_nodeInfoSummary;
          uses ncs_rpc_notif_nodeInfoDetail;
        }
      }
    }
  }

  grouping ncs_rpc_notif_nodeInfoSummary {
    description
      "All the parameters needed to describe a node as
       represented in CM.";
    leaf type {
      type string;
      description
        "Node Type";
    }
    leaf ip_address {
      type inet:ip-address;
      description
        "IP address of the node";
    }
    leaf mac_address {
      type yang:mac-address;
      description
        "Node MAC";
    }
    leaf card_serial {
      type string;
      description
        "Card serial# the node belongs to";
    }
    leaf nti {
      type uint32;
      description
        "Node NTI";
    }
  }

  grouping ncs_rpc_notif_nodeInfoDetail {
    description
      "All the parameters needed to describe a node as
       represented in CM.";
    leaf restart {
      type boolean;
      description
        "Node in Restart";
    }
    leaf data {
      type ncs_rpc_notif_hex8ValueType;
      description
        "Node Data";
    }
    leaf sdr {
      type string;
      description
        "SDR Name the node belongs to";
    }
  }

  grouping ncs_rpc_notif_cardInfo {
    description
      "All the parameters needed to describe a card as
       represented in CM.";
    leaf node_id {
      type string;
      description
        "Node name";
    }
    leaf card_type {
      type string;
      description
        "Card Type";
    }
    leaf hw_state {
      type string;
      description
        "Card State";
    }
    leaf sw_state {
      type string;
      description
        "Card Software State";
    }
    leaf slot {
      type uint32;
      description
        "Card Slot Number";
    }
    leaf card_serial {
      type string;
      description
        "Serial Number of the Card";
    }
    leaf cti {
      type uint32;
      description
        "Card CTI";
    }
  }

  grouping ncs_rpc_notif_rackInfo {
    description
      "All the parameters needed to describe a rack as
       represented in CM.";
    leaf rack_number {
      type int32;
      description
        "Rack Number";
    }
    leaf rack_serial {
      type string;
      description
        "Serial Number of the Rack";
    }
    leaf rack_state {
      type int32;
      description
        "Rack State";
    }
  }

  grouping ncs_rpc_notif_serviceInfo {
    description
      "All the parameters needed to describe a service as
       represented in CM.";
    leaf svc_name {
      type string;
      description
        "Service Name";
    }
    leaf placement_first {
      type string;
      description
        "Serial Number of the first card selected";
    }
    leaf nodeid_first {
      type string;
      description
        "Node id of the first card selected";
    }
    leaf placement_second {
      type string;
      description
        "Serial Number of the second card selected";
    }
    leaf nodeid_second {
      type string;
      description
        "Node id of the second card selected";
    }
    leaf svc_load {
      type uint8;
      description
        "Service Load";
    }
  }

  grouping ncs_rpc_notif_sdrInfo {
    description
      "All the parameters needed to describe a SDR as
       represented in CM.";
    leaf sdr_id {
      type uint32;
      description
        "SDR ID";
    }
    leaf sdr_name {
      type string;
      description
        "SDR NAME";
    }
    leaf sdr_vlan_baseid {
      type uint8;
      description
        "SDR VLAN ID";
    }
    leaf sdr_version {
      type uint64;
      description
        "SDR Image Version";
    }
  }

  grouping ncs_rpc_notif_ldrInfo {
    description
      "All the parameters needed to describe leader statistics.";
    leaf syslead {
      type string;
      description
        "Primary System Leader";
    }
    leaf bkup_syslead {
      type string;
      description
        "Backup System Leader";
    }
    leaf racklead {
      type string;
      description
        "Primary Rack Leader";
    }
    leaf bkup_racklead {
      type string;
      description
        "Backup Rack Leader";
    }
    leaf l1_dis {
      type string;
      description
        "L1 DIS";
    }
    leaf l2_dis {
      type string;
      description
        "L2 DIS";
    }
  }

  grouping ncs_rpc_notif_nbrInfo {
    description
      "All the parameters needed to describe a topology neighbor";
    leaf nbr_system_id {
      type string;
      description
        "Neighbor System ID";
    }
    leaf nbr_area_type {
      type string;
      description
        "Neighbor Area Type";
    }
    leaf nbr_interface {
      type string;
      description
        "Adjacency Interface";
    }
    leaf nbr_state {
      type string;
      description
        "Neighbor State";
    }
    leaf nbr_holdtime {
      type uint64;
      description
        "Neighbor Hold Time";
    }
    leaf nbr_uptime {
      type xs:duration;
      description
        "Neighbor Up Time";
    }
  }

  grouping ncs_rpc_notif_lspdbInfo {
    description
      "All the parameters needed to describe a lsps from lspdb";
    leaf lsp_id {
      type string;
      description
        "LSP System ID";
    }
    leaf lsp_area_type {
      type ncs_rpc_notif_area_type;
      description
        "LSP Area Type";
    }
    leaf lsp_sequence {
      type uint32;
      description
        "LSP sequence number";
    }
    leaf lsp_core {
      type string;
      description
        "LSP core data bits";
    }
    leaf-list lsp_tlvs {
      type string;
      description
        "LSP TLV data";
    }
  }

  grouping live_ncs_nodeInfoGroup {
    container summary {
      description
        "System Admin Manager Node Inventory. All accesses are
         read-only. CLI show command looks like show node-inventory
         location <location>";
      list node_locations {
        key "node_location";
        leaf node_location {
          type calvados:live_ncs_location-id;
        }
        list nodei {
          key "ip_address";
          uses live_ncs_nodeInfoSummary;
        }
      }
    }
    container detail {
      description
        "System Admin Manager Node Inventory. All accesses are
         read-only. CLI show command looks like show node-inventory
         location <location>";
      list node_locations {
        key "node_location";
        leaf node_location {
          type calvados:live_ncs_location-id;
        }
        list nodei {
          key "ip_address";
          uses live_ncs_nodeInfoSummary;
          uses live_ncs_nodeInfoDetail;
        }
      }
    }
  }

  grouping live_ncs_nodeInfoSummary {
    description
      "All the parameters needed to describe a node as
       represented in CM.";
    leaf type {
      type string;
      description
        "Node Type";
    }
    leaf ip_address {
      type inet:ip-address;
      description
        "IP address of the node";
    }
    leaf mac_address {
      type yang:mac-address;
      description
        "Node MAC";
    }
    leaf card_serial {
      type string;
      description
        "Card serial# the node belongs to";
    }
    leaf nti {
      type uint32;
      description
        "Node NTI";
    }
  }

  grouping live_ncs_nodeInfoDetail {
    description
      "All the parameters needed to describe a node as
       represented in CM.";
    leaf restart {
      type boolean;
      description
        "Node in Restart";
    }
    leaf data {
      type live_ncs_hex8ValueType;
      description
        "Node Data";
    }
    leaf sdr {
      type string;
      description
        "SDR Name the node belongs to";
    }
  }

  grouping live_ncs_cardInfo {
    description
      "All the parameters needed to describe a card as
       represented in CM.";
    leaf node_id {
      type string;
      description
        "Node name";
    }
    leaf card_type {
      type string;
      description
        "Card Type";
    }
    leaf hw_state {
      type string;
      description
        "Card State";
    }
    leaf sw_state {
      type string;
      description
        "Card Software State";
    }
    leaf slot {
      type uint32;
      description
        "Card Slot Number";
    }
    leaf card_serial {
      type string;
      description
        "Serial Number of the Card";
    }
    leaf cti {
      type uint32;
      description
        "Card CTI";
    }
  }

  grouping live_ncs_rackInfo {
    description
      "All the parameters needed to describe a rack as
       represented in CM.";
    leaf rack_number {
      type int32;
      description
        "Rack Number";
    }
    leaf rack_serial {
      type string;
      description
        "Serial Number of the Rack";
    }
    leaf rack_state {
      type int32;
      description
        "Rack State";
    }
  }

  grouping live_ncs_serviceInfo {
    description
      "All the parameters needed to describe a service as
       represented in CM.";
    leaf svc_name {
      type string;
      description
        "Service Name";
    }
    leaf placement_first {
      type string;
      description
        "Serial Number of the first card selected";
    }
    leaf nodeid_first {
      type string;
      description
        "Node id of the first card selected";
    }
    leaf placement_second {
      type string;
      description
        "Serial Number of the second card selected";
    }
    leaf nodeid_second {
      type string;
      description
        "Node id of the second card selected";
    }
    leaf svc_load {
      type uint8;
      description
        "Service Load";
    }
  }

  grouping live_ncs_sdrInfo {
    description
      "All the parameters needed to describe a SDR as
       represented in CM.";
    leaf sdr_id {
      type uint32;
      description
        "SDR ID";
    }
    leaf sdr_name {
      type string;
      description
        "SDR NAME";
    }
    leaf sdr_vlan_baseid {
      type uint8;
      description
        "SDR VLAN ID";
    }
    leaf sdr_version {
      type uint64;
      description
        "SDR Image Version";
    }
  }

  grouping live_ncs_ldrInfo {
    description
      "All the parameters needed to describe leader statistics.";
    leaf syslead {
      type string;
      description
        "Primary System Leader";
    }
    leaf bkup_syslead {
      type string;
      description
        "Backup System Leader";
    }
    leaf racklead {
      type string;
      description
        "Primary Rack Leader";
    }
    leaf bkup_racklead {
      type string;
      description
        "Backup Rack Leader";
    }
    leaf l1_dis {
      type string;
      description
        "L1 DIS";
    }
    leaf l2_dis {
      type string;
      description
        "L2 DIS";
    }
  }

  grouping live_ncs_nbrInfo {
    description
      "All the parameters needed to describe a topology neighbor";
    leaf nbr_system_id {
      type string;
      description
        "Neighbor System ID";
    }
    leaf nbr_area_type {
      type string;
      description
        "Neighbor Area Type";
    }
    leaf nbr_interface {
      type string;
      description
        "Adjacency Interface";
    }
    leaf nbr_state {
      type string;
      description
        "Neighbor State";
    }
    leaf nbr_holdtime {
      type uint64;
      description
        "Neighbor Hold Time";
    }
    leaf nbr_uptime {
      type xs:duration;
      description
        "Neighbor Up Time";
    }
  }

  grouping live_ncs_lspdbInfo {
    description
      "All the parameters needed to describe a lsps from lspdb";
    leaf lsp_id {
      type string;
      description
        "LSP System ID";
    }
    leaf lsp_area_type {
      type live_ncs_area_type;
      description
        "LSP Area Type";
    }
    leaf lsp_sequence {
      type uint32;
      description
        "LSP sequence number";
    }
    leaf lsp_core {
      type string;
      description
        "LSP core data bits";
    }
    leaf-list lsp_tlvs {
      type string;
      description
        "LSP TLV data";
    }
  }

  grouping nodeInfoGroup {
    // NCS drop config false container summary
    // NCS drop config false container detail
  }

  grouping nodeInfoSummary {
    description
      "All the parameters needed to describe a node as
       represented in CM.";
    leaf type {
      type string;
      description
        "Node Type";
    }
    leaf ip_address {
      type inet:ip-address;
      description
        "IP address of the node";
    }
    leaf mac_address {
      type yang:mac-address;
      description
        "Node MAC";
    }
    leaf card_serial {
      type string;
      description
        "Card serial# the node belongs to";
    }
    leaf nti {
      type uint32;
      description
        "Node NTI";
    }
  }

  grouping nodeInfoDetail {
    description
      "All the parameters needed to describe a node as
       represented in CM.";
    leaf restart {
      type boolean;
      description
        "Node in Restart";
    }
    leaf data {
      type hex8ValueType;
      description
        "Node Data";
    }
    leaf sdr {
      type string;
      description
        "SDR Name the node belongs to";
    }
  }

  grouping cardInfo {
    description
      "All the parameters needed to describe a card as
       represented in CM.";
    leaf node_id {
      type string;
      description
        "Node name";
    }
    leaf card_type {
      type string;
      description
        "Card Type";
    }
    leaf hw_state {
      type string;
      description
        "Card State";
    }
    leaf sw_state {
      type string;
      description
        "Card Software State";
    }
    leaf slot {
      type uint32;
      description
        "Card Slot Number";
    }
    leaf card_serial {
      type string;
      description
        "Serial Number of the Card";
    }
    leaf cti {
      type uint32;
      description
        "Card CTI";
    }
  }

  grouping rackInfo {
    description
      "All the parameters needed to describe a rack as
       represented in CM.";
    leaf rack_number {
      type int32;
      description
        "Rack Number";
    }
    leaf rack_serial {
      type string;
      description
        "Serial Number of the Rack";
    }
    leaf rack_state {
      type int32;
      description
        "Rack State";
    }
  }

  grouping serviceInfo {
    description
      "All the parameters needed to describe a service as
       represented in CM.";
    leaf svc_name {
      type string;
      description
        "Service Name";
    }
    leaf placement_first {
      type string;
      description
        "Serial Number of the first card selected";
    }
    leaf nodeid_first {
      type string;
      description
        "Node id of the first card selected";
    }
    leaf placement_second {
      type string;
      description
        "Serial Number of the second card selected";
    }
    leaf nodeid_second {
      type string;
      description
        "Node id of the second card selected";
    }
    leaf svc_load {
      type uint8;
      description
        "Service Load";
    }
  }

  grouping sdrInfo {
    description
      "All the parameters needed to describe a SDR as
       represented in CM.";
    leaf sdr_id {
      type uint32;
      description
        "SDR ID";
    }
    leaf sdr_name {
      type string;
      description
        "SDR NAME";
    }
    leaf sdr_vlan_baseid {
      type uint8;
      description
        "SDR VLAN ID";
    }
    leaf sdr_version {
      type uint64;
      description
        "SDR Image Version";
    }
  }

  grouping ldrInfo {
    description
      "All the parameters needed to describe leader statistics.";
    leaf syslead {
      type string;
      description
        "Primary System Leader";
    }
    leaf bkup_syslead {
      type string;
      description
        "Backup System Leader";
    }
    leaf racklead {
      type string;
      description
        "Primary Rack Leader";
    }
    leaf bkup_racklead {
      type string;
      description
        "Backup Rack Leader";
    }
    leaf l1_dis {
      type string;
      description
        "L1 DIS";
    }
    leaf l2_dis {
      type string;
      description
        "L2 DIS";
    }
  }

  grouping nbrInfo {
    description
      "All the parameters needed to describe a topology neighbor";
    leaf nbr_system_id {
      type string;
      description
        "Neighbor System ID";
    }
    leaf nbr_area_type {
      type string;
      description
        "Neighbor Area Type";
    }
    leaf nbr_interface {
      type string;
      description
        "Adjacency Interface";
    }
    leaf nbr_state {
      type string;
      description
        "Neighbor State";
    }
    leaf nbr_holdtime {
      type uint64;
      description
        "Neighbor Hold Time";
    }
    leaf nbr_uptime {
      type xs:duration;
      description
        "Neighbor Up Time";
    }
  }

  grouping lspdbInfo {
    description
      "All the parameters needed to describe a lsps from lspdb";
    leaf lsp_id {
      type string;
      description
        "LSP System ID";
    }
    leaf lsp_area_type {
      type area_type;
      description
        "LSP Area Type";
    }
    leaf lsp_sequence {
      type uint32;
      description
        "LSP sequence number";
    }
    leaf lsp_core {
      type string;
      description
        "LSP core data bits";
    }
    leaf-list lsp_tlvs {
      type string;
      description
        "LSP TLV data";
    }
  }

  augment "/ncs:devices/ncs:device/ncs:config" {
    // NCS drop config false container 'node-inventory'
    // NCS drop config false container 'card-inventory'
    // NCS drop config false container 'rack-inventory'
    // NCS drop config false container 'system-service-inventory'
    // NCS drop config false container 'rack-service-inventory'
    // NCS drop config false container 'sdr-inventory'
    // NCS drop config false container 'leader-statistics'
    // NCS drop config false container 'topology-neighbors'
    container placement {
      tailf:ncs-device-type "netconf";
      tailf:display-when "not(../../ncs:module) or ../../ncs:module[ncs:name='Cisco-IOS-XR-sysadmin-cm']";
    }
  }
  augment "/ncs:devices/ncs:device/ncs:live-status" {
    container node-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Node Inventory. All accesses are
         read-only. CLI show command looks like show node-inventory
         location <location>";
      uses live_ncs_nodeInfoGroup;
    }
    container card-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Card Inventory. All accesses are
         read-only. CLI show command looks like show card-inventory
         location <location>";
      list card_locations {
        key "card_location";
        leaf card_location {
          type calvados:live_ncs_location-id;
        }
        list cardi {
          key "card_serial";
          uses live_ncs_cardInfo;
        }
      }
    }
    container rack-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Rack Inventory";
      list rack_locations {
        key "rack_location";
        leaf rack_location {
          type calvados:live_ncs_location-id;
        }
        list racki {
          key "rack_serial";
          uses live_ncs_rackInfo;
        }
      }
    }
    container system-service-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager System Services Inventory";
      list ssvc_locations {
        key "ssvc_location";
        leaf ssvc_location {
          type calvados:live_ncs_location-id;
        }
        list ssvci {
          key "svc_name";
          uses live_ncs_serviceInfo;
        }
      }
    }
    container rack-service-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Rack Services Inventory";
      list rsvc_locations {
        key "rsvc_location";
        leaf rsvc_location {
          type calvados:live_ncs_location-id;
        }
        list rsvci {
          key "svc_name";
          uses live_ncs_serviceInfo;
        }
      }
    }
    container sdr-inventory {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager SDR Inventory";
      list sdr_locations {
        key "sdr_location";
        leaf sdr_location {
          type calvados:live_ncs_location-id;
        }
        list sdri {
          key "sdr_name";
          uses live_ncs_sdrInfo;
        }
      }
    }
    container leader-statistics {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Leader Statistics";
      list ldr_locations {
        key "ldr_location";
        leaf ldr_location {
          type calvados:live_ncs_location-id;
        }
        uses live_ncs_ldrInfo;
      }
    }
    container topology-neighbors {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
      description
        "System Admin Manager Neighbors of a location";
      list nbr_locations {
        key "nbr_location";
        leaf nbr_location {
          type calvados:live_ncs_location-id;
        }
        list nbri {
          key "nbr_system_id nbr_area_type";
          uses live_ncs_nbrInfo;
        }
      }
    }
    container placement {
      tailf:ncs-device-type "netconf";
      tailf:display-when "not(../../ncs:module) or ../../ncs:module[ncs:name='Cisco-IOS-XR-sysadmin-cm'] or (../../ncs:live-status-protocol[not(ncs:capability)]) or (../../ncs:live-status-protocol/ncs:capability/ncs:module[.='Cisco-IOS-XR-sysadmin-cm'])";
    }
  }
  augment "/ncs:devices/ncs:template/ncs:ned-id/ncs:config" {
    // NCS drop config false container 'node-inventory'
    // NCS drop config false container 'card-inventory'
    // NCS drop config false container 'rack-inventory'
    // NCS drop config false container 'system-service-inventory'
    // NCS drop config false container 'rack-service-inventory'
    // NCS drop config false container 'sdr-inventory'
    // NCS drop config false container 'leader-statistics'
    // NCS drop config false container 'topology-neighbors'
    container placement;
  }
  augment "/ncs:devices/ncs:device/ncs:live-status/cm:cm" {
    container lsp {
      tailf:ncs-device-type "netconf";
      tailf:display-when "not(../../../ncs:module) or ../../../ncs:module[ncs:name='Cisco-IOS-XR-sysadmin-cm'] or (../../../ncs:live-status-protocol[not(ncs:capability)]) or (../../../ncs:live-status-protocol/ncs:capability/ncs:module[.='Cisco-IOS-XR-sysadmin-cm'])";
      description
        "System Admin Manager lspdb of a location";
      list lspdb_locations {
        key "lspdb_location";
        leaf lspdb_location {
          type calvados:live_ncs_location-id;
        }
        list lspdbi {
          key "lsp_id lsp_area_type";
          uses live_ncs_lspdbInfo;
        }
      }
    }
  }
}

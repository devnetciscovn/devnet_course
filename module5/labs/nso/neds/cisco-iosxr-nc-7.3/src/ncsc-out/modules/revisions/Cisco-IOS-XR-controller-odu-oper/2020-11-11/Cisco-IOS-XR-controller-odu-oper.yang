module Cisco-IOS-XR-controller-odu-oper {
  // Generated by yanger -t ncs
  tailf:mount-id "cisco-iosxr-nc-7.3:cisco-iosxr-nc-7.3";
  tailf:ncs-device-type "netconf";

  namespace "http://cisco.com/ns/yang/Cisco-IOS-XR-controller-odu-oper";
  prefix controller-odu-oper;

  import Cisco-IOS-XR-types {
    prefix xr;
  }
  import cisco-semver {
    prefix semver;
  }
  include Cisco-IOS-XR-controller-odu-oper-sub1 {
    revision-date 2020-11-11;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-odu package operational data.

     This module contains definitions
     for the following management objects:
       odu: ODU operational data

     Copyright (c) 2013-2020 by Cisco Systems, Inc.
     All rights reserved.";

  revision 2020-11-11 {
    description
      "Added PRBS bit errors and lock time support in bag odu_prbs_info.";
    semver:module-version "1.3.0";
  }
  revision 2019-08-05 {
    description
      "Separated ODTU info variables from ODU info bag and created new bag for ODTU data.";
    semver:module-version "1.2.0";
  }
  revision 2019-04-05 {
    description
      "Establish semantic version baseline.";
    semver:module-version "1.1.0";
  }
  revision 2015-11-09 {
    description
      "IOS XR 6.0 revision.";
  }

  augment "/ncs:devices/ncs:device/ncs:config" {
    // NCS drop config false container odu
  }
  augment "/ncs:devices/ncs:device/ncs:live-status" {
    container odu {
      tailf:ncs-device-type "netconf";
      tailf:display-when "not(../../ncs:module) or ../../ncs:module[ncs:name='Cisco-IOS-XR-controller-odu-oper'] or (../../ncs:live-status-protocol[not(ncs:capability)]) or (../../ncs:live-status-protocol/ncs:capability/ncs:module[.='Cisco-IOS-XR-controller-odu-oper'])";
      description
        "ODU operational data";
      container controllers {
        description
          "All ODU Port operational data";
        list controller {
          key "controller-name";
          description
            "ODU Port operational data";
          container prbs {
            description
              "ODU port operational data";
            uses live_ncs_ODU-PRBS-INFO;
          }
          container info {
            description
              "ODU port operational data";
            uses live_ncs_ODU-PER-PORT-INFO;
          }
          container odtu-info {
            description
              "ODU port ODTU data";
            uses live_ncs_ODU-ODTU-OPER-DATA;
          }
          leaf controller-name {
            type xr:live_ncs_Interface-name;
            description
              "Port name";
          }
        }
      }
    }
  }
  augment "/ncs:devices/ncs:template/ncs:ned-id/ncs:config" {
    // NCS drop config false container odu
  }
}

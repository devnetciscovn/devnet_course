submodule Cisco-IOS-XR-mpls-ldp-oper-sub1 {
  // Generated by yanger -t ncs
  tailf:mount-id "cisco-iosxr-nc-7.3:cisco-iosxr-nc-7.3";

  belongs-to Cisco-IOS-XR-mpls-ldp-oper {
    prefix Cisco-IOS-XR-mpls-ldp-oper;
  }

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-ldp package operational data.

     Copyright (c) 2013-2021 by Cisco Systems, Inc.
     All rights reserved.";

  revision 2021-04-06 {
    description
      "Added BSID data in LDP forwarding
       2021-03-10
         Added adj_grp count leaf to ldp summary";
    semver:module-version "1.2.0";
  }
  revision 2020-08-14 {
    description
      "Added ELC parameter.";
    semver:module-version "1.1.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef ncs_template_Mgmt-ldp-nbr-bgp-advt-state {
    type string;
    description
      "MPLS LDP Neighbor BGP Label Advertisement State
       Type";
  }

  typedef ncs_template_Mgmt-ldp-nsr-peer-ldp-sync-nack-rsn {
    type string;
    description
      "Mgmt ldp nsr peer ldp sync nack rsn";
  }

  typedef ncs_template_Mgmt-ldp-nsr-peer-sync-err {
    type string;
    description
      "Mgmt ldp nsr peer sync err";
  }

  typedef ncs_template_Mgmt-ldp-nsr-peer-sync-state {
    type string;
    description
      "Mgmt ldp nsr peer sync state";
  }

  typedef ncs_template_Ldp-adj-union-discrim {
    type string;
    description
      "MPLS LDP Hello Type";
  }

  typedef ncs_template_Show-nsr-state {
    type string;
    description
      "NSR State Type";
  }

  typedef ncs_template_Ldp-route-path-lbl-owner {
    type string;
    description
      "Route path label owner";
  }

  typedef ncs_template_Label-value {
    type string;
    description
      "Label Value Type";
  }

  typedef ncs_template_Ldp-fwd-unlbl-rsn {
    type string;
    description
      "Ldp fwd unlbl rsn";
  }

  typedef ncs_template_Ldp-route-path-flags {
    type string;
    description
      "Route path flags";
  }

  typedef ncs_template_Dhcb-state {
    type string;
    description
      "DHCB State Type";
  }

  typedef ncs_template_Ldp-igp-sync-down-reason {
    type string;
    description
      "Reason IGP Sync Not Achieved";
  }

  typedef ncs_template_String-td2 {
    type string;
    description
      "String td2";
  }

  typedef ncs_template_Ldp-igp-sync-state {
    type string;
    description
      "IGP Sync State";
  }

  typedef ncs_template_Local-label-state {
    type string;
    description
      "MPLS LDP Local Label State Type";
  }

  typedef ncs_template_Ldp-af {
    type string;
    description
      "Ldp af";
  }

  typedef ncs_template_Ldp-in6-addr {
    type string;
    description
      "Ldp in6 addr";
  }

  typedef ncs_template_Ldp-in-addr {
    type string;
    description
      "Ldp in addr";
  }

  typedef ncs_template_Ldp-af-id {
    type string;
    description
      "Ldp af id";
  }

  typedef ncs_rpc_notif_Mgmt-ldp-nbr-bgp-advt-state {
    type enumeration {
      enum "not-applicable" {
        value 0;
        description
          "Not applicable";
      }
      enum "permit" {
        value 1;
        description
          "Advertisement permitted";
      }
      enum "deny" {
        value 2;
        description
          "Advertisement denied";
      }
    }
    description
      "MPLS LDP Neighbor BGP Label Advertisement State
       Type";
  }

  typedef ncs_rpc_notif_Mgmt-ldp-nsr-peer-ldp-sync-nack-rsn {
    type enumeration {
      enum "mgmt-ldp-nsr-peer-ldp-sync-nack-rsn-none" {
        description
          "mgmt ldp nsr peer ldp sync nack rsn none";
      }
      enum "mgmt-ldp-nsr-peer-ldp-sync-nack-rsn-tbl-id-mismatch" {
        description
          "mgmt ldp nsr peer ldp sync nack rsn tbl id
           mismatch";
      }
      enum "mgmt-ldp-nsr-peer-ldp-sync-nack-rsn-pp-exists" {
        description
          "mgmt ldp nsr peer ldp sync nack rsn pp exists";
      }
      enum "mgmt-ldp-nsr-peer-ldp-sync-nack-rsn-missing-elem" {
        description
          "mgmt ldp nsr peer ldp sync nack rsn missing
           elem";
      }
      enum "mgmt-ldp-nsr-peer-ldp-sync-nack-rsn-no-p-end-sock" {
        description
          "mgmt ldp nsr peer ldp sync nack rsn no p end
           sock";
      }
      enum "mgmt-ldp-nsr-peer-ldp-sync-nack-rsn-p-end-sock-not-synced" {
        description
          "mgmt ldp nsr peer ldp sync nack rsn p end sock
           not synced";
      }
      enum "mgmt-ldp-nsr-peer-ldp-sync-nack-rsn-err-adj-add" {
        description
          "mgmt ldp nsr peer ldp sync nack rsn err adj add";
      }
      enum "mgmt-ldp-nsr-peer-ldp-sync-nack-rsn-err-dhcb-add" {
        description
          "mgmt ldp nsr peer ldp sync nack rsn err dhcb
           add";
      }
      enum "mgmt-ldp-nsr-peer-ldp-sync-nack-rsn-enomem" {
        description
          "mgmt ldp nsr peer ldp sync nack rsn enomem";
      }
      enum "mgmt-ldp-nsr-peer-ldp-sync-nack-rsn-err-tp-create" {
        description
          "mgmt ldp nsr peer ldp sync nack rsn err tp
           create";
      }
      enum "mgmt-ldp-nsr-peer-ldp-sync-nack-rsn-err-pp-create" {
        description
          "mgmt ldp nsr peer ldp sync nack rsn err pp
           create";
      }
      enum "mgmt-ldp-nsr-peer-ldp-sync-nack-rsn-err-addr-bind" {
        description
          "mgmt ldp nsr peer ldp sync nack rsn err addr
           bind";
      }
      enum "mgmt-ldp-nsr-peer-ldp-sync-nack-rsn-err-rx-bad-pie" {
        description
          "mgmt ldp nsr peer ldp sync nack rsn err rx bad
           pie";
      }
      enum "mgmt-ldp-nsr-peer-ldp-sync-nack-rsn-err-rx-notif" {
        description
          "mgmt ldp nsr peer ldp sync nack rsn err rx
           notif";
      }
      enum "mgmt-ldp-nsr-peer-ldp-sync-nack-rsn-err-rx-unexp-open" {
        description
          "mgmt ldp nsr peer ldp sync nack rsn err rx
           unexp open";
      }
      enum "mgmt-ldp-nsr-peer-ldp-sync-nack-rsn-err-unexp-peer-down" {
        description
          "mgmt ldp nsr peer ldp sync nack rsn err unexp
           peer down";
      }
      enum "mgmt-ldp-nsr-peer-ldp-sync-nack-rsn-err-app-not-found" {
        description
          "mgmt ldp nsr peer ldp sync nack rsn err app not
           found";
      }
      enum "mgmt-ldp-nsr-peer-ldp-sync-nack-rsn-err-app-invalid" {
        description
          "mgmt ldp nsr peer ldp sync nack rsn err app
           invalid";
      }
      enum "mgmt-ldp-nsr-peer-ldp-sync-nack-rsn-err-adj-grp-not-found" {
        description
          "mgmt ldp nsr peer ldp sync nack rsn err adj grp
           not found";
      }
      enum "mgmt-ldp-nsr-peer-ldp-sync-nack-rsn-invalid-elem" {
        description
          "mgmt ldp nsr peer ldp sync nack rsn invalid
           elem";
      }
      enum "mgmt-ldp-nsr-peer-ldp-sync-nack-rsn-err-app-data-invalid" {
        description
          "mgmt ldp nsr peer ldp sync nack rsn err app
           data invalid";
      }
      enum "mgmt-ldp-nsr-peer-ldp-sync-nack-rsn-err-invalid-per-idx" {
        description
          "mgmt ldp nsr peer ldp sync nack rsn err invalid
           per idx";
      }
      enum "mgmt-ldp-nsr-peer-ldp-sync-nack-rsn-err-pfx-not-found" {
        description
          "mgmt ldp nsr peer ldp sync nack rsn err pfx not
           found";
      }
      enum "mgmt-ldp-nsr-peer-ldp-sync-nack-rsn-err-bm-size-invalid" {
        description
          "mgmt ldp nsr peer ldp sync nack rsn err bm size
           invalid";
      }
      enum "mgmt-ldp-nsr-peer-ldp-sync-nack-rsn-err-adv-bm-clear" {
        description
          "mgmt ldp nsr peer ldp sync nack rsn err adv bm
           clear";
      }
      enum "mgmt-ldp-nsr-peer-ldp-sync-nack-rsn-err-tcp-struct-create" {
        description
          "mgmt ldp nsr peer ldp sync nack rsn err tcp
           struct create";
      }
      enum "mgmt-ldp-nsr-peer-ldp-sync-nack-rsn-no-ctx" {
        description
          "mgmt ldp nsr peer ldp sync nack rsn no ctx";
      }
    }
    description
      "Mgmt ldp nsr peer ldp sync nack rsn";
  }

  typedef ncs_rpc_notif_Mgmt-ldp-nsr-peer-sync-err {
    type enumeration {
      enum "mgmt-ldp-nsr-peer-sync-err-none" {
        description
          "mgmt ldp nsr peer sync err none";
      }
      enum "mgmt-ldp-nsr-peer-sync-err-ldp-sync-nack" {
        description
          "mgmt ldp nsr peer sync err ldp sync nack";
      }
      enum "mgmt-ldp-nsr-peer-sync-err-sync-prep" {
        description
          "mgmt ldp nsr peer sync err sync prep";
      }
      enum "mgmt-ldp-nsr-peer-sync-err-tcp-peer" {
        description
          "mgmt ldp nsr peer sync err tcp peer";
      }
      enum "mgmt-ldp-nsr-peer-sync-err-tcp-gbl" {
        description
          "mgmt ldp nsr peer sync err tcp gbl";
      }
      enum "mgmt-ldp-nsr-peer-sync-err-ldp-peer" {
        description
          "mgmt ldp nsr peer sync err ldp peer";
      }
      enum "mgmt-ldp-nsr-peer-sync-err-ldp-gbl" {
        description
          "mgmt ldp nsr peer sync err ldp gbl";
      }
      enum "mgmt-ldp-nsr-peer-sync-err-app-fail" {
        description
          "mgmt ldp nsr peer sync err app fail";
      }
      enum "mgmt-ldp-nsr-peer-sync-err-sync-tcp-phase1" {
        description
          "mgmt ldp nsr peer sync err sync tcp phase1";
      }
      enum "mgmt-ldp-nsr-peer-sync-err-sync-tcp-phase2" {
        description
          "mgmt ldp nsr peer sync err sync tcp phase2";
      }
    }
    description
      "Mgmt ldp nsr peer sync err";
  }

  typedef ncs_rpc_notif_Mgmt-ldp-nsr-peer-sync-state {
    type enumeration {
      enum "mgmt-ldp-nsr-peer-sync-st-none" {
        description
          "mgmt ldp nsr peer sync st none";
      }
      enum "mgmt-ldp-nsr-peer-sync-st-wait" {
        description
          "mgmt ldp nsr peer sync st wait";
      }
      enum "mgmt-ldp-nsr-peer-sync-st-ready" {
        description
          "mgmt ldp nsr peer sync st ready";
      }
      enum "mgmt-ldp-nsr-peer-sync-st-prep" {
        description
          "mgmt ldp nsr peer sync st prep";
      }
      enum "mgmt-ldp-nsr-peer-sync-st-app-wait" {
        description
          "mgmt ldp nsr peer sync st app wait";
      }
      enum "mgmt-ldp-nsr-peer-sync-st-oper" {
        description
          "mgmt ldp nsr peer sync st oper";
      }
      enum "mgmt-ldp-nsr-peer-sync-st-tcp-phase1" {
        description
          "mgmt ldp nsr peer sync st tcp phase1";
      }
      enum "mgmt-ldp-nsr-peer-sync-st-tcp-phase2" {
        description
          "mgmt ldp nsr peer sync st tcp phase2";
      }
    }
    description
      "Mgmt ldp nsr peer sync state";
  }

  typedef ncs_rpc_notif_Ldp-adj-union-discrim {
    type enumeration {
      enum "link-hello" {
        description
          "Link hello";
      }
      enum "targeted-hello" {
        description
          "Targeted hello";
      }
    }
    description
      "MPLS LDP Hello Type";
  }

  typedef ncs_rpc_notif_Show-nsr-state {
    type enumeration {
      enum "nsr-ready" {
        description
          "NSR ready";
      }
      enum "nsr-not-ready" {
        description
          "NSR not ready";
      }
      enum "nsr-na" {
        description
          "NSR not applicable";
      }
    }
    description
      "NSR State Type";
  }

  typedef ncs_rpc_notif_Ldp-route-path-lbl-owner {
    type enumeration {
      enum "ip-path-lbl-owner-none" {
        value 0;
        description
          "No label and no owner";
      }
      enum "ip-path-lbl-owner-ldp" {
        value 1;
        description
          "Path outgoing label owned by LDP";
      }
      enum "ip-path-lbl-owner-bgp" {
        value 2;
        description
          "Path outgoing label owned by BGP";
      }
    }
    description
      "Route path label owner";
  }

  typedef ncs_rpc_notif_Label-value {
    type enumeration {
      enum "mpls-label" {
        description
          "MPLS Label";
      }
      enum "un-labelled" {
        description
          "Unlabelled";
      }
      enum "unknown" {
        description
          "Unknown label";
      }
    }
    description
      "Label Value Type";
  }

  typedef ncs_rpc_notif_Ldp-fwd-unlbl-rsn {
    type enumeration {
      enum "ldp-fwd-labelled" {
        description
          "ldp fwd labelled";
      }
      enum "ldp-fwd-un-labelled-vrf-down" {
        description
          "ldp fwd un labelled vrf down";
      }
      enum "ldp-fwd-un-labelled-no-nh" {
        description
          "ldp fwd un labelled no nh";
      }
      enum "ldp-fwd-un-labelled-recursive-path" {
        description
          "ldp fwd un labelled recursive path";
      }
      enum "ldp-fwd-un-labelled-intf-not-ldp" {
        description
          "ldp fwd un labelled intf not ldp";
      }
      enum "ldp-fwd-un-labelled-no-rmt" {
        description
          "ldp fwd un labelled no rmt";
      }
      enum "ldp-fwd-un-labelled-no-ldp-adj" {
        description
          "ldp fwd un labelled no ldp adj";
      }
      enum "ldp-fwd-un-labelled-no-session" {
        description
          "ldp fwd un labelled no session";
      }
      enum "ldp-fwd-un-labelled-unknown" {
        description
          "ldp fwd un labelled unknown";
      }
    }
    description
      "Ldp fwd unlbl rsn";
  }

  typedef ncs_rpc_notif_Ldp-route-path-flags {
    type enumeration {
      enum "ip-path-no-flag" {
        value 0;
        description
          "A primary path with no special flag/attribute";
      }
      enum "ip-path-protected" {
        value 1;
        description
          "A primary path with LFA FRR protection";
      }
      enum "ip-path-backup" {
        value 2;
        description
          "A non-primary local LFA FRR (pure) backup path";
      }
      enum "ip-path-backup-remote" {
        value 3;
        description
          "A non-primary remote LFA FRR (pure) backup path";
      }
      enum "ip-path-bgp-backup" {
        value 4;
        description
          "A non-primary BGP backup path";
      }
    }
    description
      "Route path flags";
  }

  typedef ncs_rpc_notif_Dhcb-state {
    type enumeration {
      enum "none" {
        description
          "None";
      }
      enum "dhcb-active" {
        description
          "Active";
      }
      enum "dhcb-passive" {
        description
          "Passive";
      }
      enum "dhcb-active-passive" {
        description
          "Active and Passive";
      }
    }
    description
      "DHCB State Type";
  }

  typedef ncs_rpc_notif_Ldp-igp-sync-down-reason {
    type enumeration {
      enum "igp-sync-down-reason-not-applicable" {
        description
          "Not Applicable";
      }
      enum "no-hello-adjacency" {
        description
          "No hello adjacency";
      }
      enum "no-peer-session" {
        description
          "No peer session";
      }
      enum "initial-update-to-peer-not-done" {
        description
          "Initial update to peer not done yet";
      }
      enum "initial-update-from-peer-not-received" {
        description
          "Initial update from peer not received yet";
      }
      enum "internal-reason" {
        description
          "Internal reason";
      }
    }
    description
      "Reason IGP Sync Not Achieved";
  }

  typedef ncs_rpc_notif_String-td2 {
    type string;
    description
      "String td2";
  }

  typedef ncs_rpc_notif_Ldp-igp-sync-state {
    type enumeration {
      enum "isync-ready" {
        description
          "Acheived";
      }
      enum "isync-not-ready" {
        description
          "Not acheived";
      }
      enum "isync-deferred" {
        description
          "Deferred due to interface delay or global
           restart delay";
      }
    }
    description
      "IGP Sync State";
  }

  typedef ncs_rpc_notif_Local-label-state {
    type enumeration {
      enum "local-label-state-none" {
        value 1;
        description
          "None";
      }
      enum "local-label-state-assigned" {
        value 2;
        description
          "Assigned";
      }
      enum "local-label-state-withdrawn" {
        value 3;
        description
          "Withdrawn";
      }
    }
    description
      "MPLS LDP Local Label State Type";
  }

  typedef ncs_rpc_notif_Ldp-af {
    type enumeration {
      enum "ldp-show-af-none" {
        value 0;
        description
          "No Address Family";
      }
      enum "ldp-show-af-ipv4" {
        value 1;
        description
          "IPv4 AFI";
      }
      enum "ldp-show-af-ipv6" {
        value 2;
        description
          "IPv6 AFI";
      }
      enum "ldp-show-af-ipv4-ipv6" {
        value 3;
        description
          "Both IPv4/IPv6 AFIs";
      }
    }
    description
      "Ldp af";
  }

  typedef ncs_rpc_notif_Ldp-in6-addr {
    type inet:ipv6-address;
    description
      "Ldp in6 addr";
  }

  typedef ncs_rpc_notif_Ldp-in-addr {
    type inet:ipv4-address;
    description
      "Ldp in addr";
  }

  typedef ncs_rpc_notif_Ldp-af-id {
    type enumeration {
      enum "ldp-af-id-none" {
        value 0;
        description
          "No Address Family";
      }
      enum "ldp-af-id-ipv4" {
        value 2;
        description
          "IPv4 AFI";
      }
      enum "ldp-af-id-ipv6" {
        value 10;
        description
          "IPv6 AFI";
      }
    }
    description
      "Ldp af id";
  }

  typedef live_ncs_Mgmt-ldp-nbr-bgp-advt-state {
    type enumeration {
      enum "not-applicable" {
        value 0;
        description
          "Not applicable";
      }
      enum "permit" {
        value 1;
        description
          "Advertisement permitted";
      }
      enum "deny" {
        value 2;
        description
          "Advertisement denied";
      }
    }
    description
      "MPLS LDP Neighbor BGP Label Advertisement State
       Type";
  }

  typedef live_ncs_Mgmt-ldp-nsr-peer-ldp-sync-nack-rsn {
    type enumeration {
      enum "mgmt-ldp-nsr-peer-ldp-sync-nack-rsn-none" {
        description
          "mgmt ldp nsr peer ldp sync nack rsn none";
      }
      enum "mgmt-ldp-nsr-peer-ldp-sync-nack-rsn-tbl-id-mismatch" {
        description
          "mgmt ldp nsr peer ldp sync nack rsn tbl id
           mismatch";
      }
      enum "mgmt-ldp-nsr-peer-ldp-sync-nack-rsn-pp-exists" {
        description
          "mgmt ldp nsr peer ldp sync nack rsn pp exists";
      }
      enum "mgmt-ldp-nsr-peer-ldp-sync-nack-rsn-missing-elem" {
        description
          "mgmt ldp nsr peer ldp sync nack rsn missing
           elem";
      }
      enum "mgmt-ldp-nsr-peer-ldp-sync-nack-rsn-no-p-end-sock" {
        description
          "mgmt ldp nsr peer ldp sync nack rsn no p end
           sock";
      }
      enum "mgmt-ldp-nsr-peer-ldp-sync-nack-rsn-p-end-sock-not-synced" {
        description
          "mgmt ldp nsr peer ldp sync nack rsn p end sock
           not synced";
      }
      enum "mgmt-ldp-nsr-peer-ldp-sync-nack-rsn-err-adj-add" {
        description
          "mgmt ldp nsr peer ldp sync nack rsn err adj add";
      }
      enum "mgmt-ldp-nsr-peer-ldp-sync-nack-rsn-err-dhcb-add" {
        description
          "mgmt ldp nsr peer ldp sync nack rsn err dhcb
           add";
      }
      enum "mgmt-ldp-nsr-peer-ldp-sync-nack-rsn-enomem" {
        description
          "mgmt ldp nsr peer ldp sync nack rsn enomem";
      }
      enum "mgmt-ldp-nsr-peer-ldp-sync-nack-rsn-err-tp-create" {
        description
          "mgmt ldp nsr peer ldp sync nack rsn err tp
           create";
      }
      enum "mgmt-ldp-nsr-peer-ldp-sync-nack-rsn-err-pp-create" {
        description
          "mgmt ldp nsr peer ldp sync nack rsn err pp
           create";
      }
      enum "mgmt-ldp-nsr-peer-ldp-sync-nack-rsn-err-addr-bind" {
        description
          "mgmt ldp nsr peer ldp sync nack rsn err addr
           bind";
      }
      enum "mgmt-ldp-nsr-peer-ldp-sync-nack-rsn-err-rx-bad-pie" {
        description
          "mgmt ldp nsr peer ldp sync nack rsn err rx bad
           pie";
      }
      enum "mgmt-ldp-nsr-peer-ldp-sync-nack-rsn-err-rx-notif" {
        description
          "mgmt ldp nsr peer ldp sync nack rsn err rx
           notif";
      }
      enum "mgmt-ldp-nsr-peer-ldp-sync-nack-rsn-err-rx-unexp-open" {
        description
          "mgmt ldp nsr peer ldp sync nack rsn err rx
           unexp open";
      }
      enum "mgmt-ldp-nsr-peer-ldp-sync-nack-rsn-err-unexp-peer-down" {
        description
          "mgmt ldp nsr peer ldp sync nack rsn err unexp
           peer down";
      }
      enum "mgmt-ldp-nsr-peer-ldp-sync-nack-rsn-err-app-not-found" {
        description
          "mgmt ldp nsr peer ldp sync nack rsn err app not
           found";
      }
      enum "mgmt-ldp-nsr-peer-ldp-sync-nack-rsn-err-app-invalid" {
        description
          "mgmt ldp nsr peer ldp sync nack rsn err app
           invalid";
      }
      enum "mgmt-ldp-nsr-peer-ldp-sync-nack-rsn-err-adj-grp-not-found" {
        description
          "mgmt ldp nsr peer ldp sync nack rsn err adj grp
           not found";
      }
      enum "mgmt-ldp-nsr-peer-ldp-sync-nack-rsn-invalid-elem" {
        description
          "mgmt ldp nsr peer ldp sync nack rsn invalid
           elem";
      }
      enum "mgmt-ldp-nsr-peer-ldp-sync-nack-rsn-err-app-data-invalid" {
        description
          "mgmt ldp nsr peer ldp sync nack rsn err app
           data invalid";
      }
      enum "mgmt-ldp-nsr-peer-ldp-sync-nack-rsn-err-invalid-per-idx" {
        description
          "mgmt ldp nsr peer ldp sync nack rsn err invalid
           per idx";
      }
      enum "mgmt-ldp-nsr-peer-ldp-sync-nack-rsn-err-pfx-not-found" {
        description
          "mgmt ldp nsr peer ldp sync nack rsn err pfx not
           found";
      }
      enum "mgmt-ldp-nsr-peer-ldp-sync-nack-rsn-err-bm-size-invalid" {
        description
          "mgmt ldp nsr peer ldp sync nack rsn err bm size
           invalid";
      }
      enum "mgmt-ldp-nsr-peer-ldp-sync-nack-rsn-err-adv-bm-clear" {
        description
          "mgmt ldp nsr peer ldp sync nack rsn err adv bm
           clear";
      }
      enum "mgmt-ldp-nsr-peer-ldp-sync-nack-rsn-err-tcp-struct-create" {
        description
          "mgmt ldp nsr peer ldp sync nack rsn err tcp
           struct create";
      }
      enum "mgmt-ldp-nsr-peer-ldp-sync-nack-rsn-no-ctx" {
        description
          "mgmt ldp nsr peer ldp sync nack rsn no ctx";
      }
    }
    description
      "Mgmt ldp nsr peer ldp sync nack rsn";
  }

  typedef live_ncs_Mgmt-ldp-nsr-peer-sync-err {
    type enumeration {
      enum "mgmt-ldp-nsr-peer-sync-err-none" {
        description
          "mgmt ldp nsr peer sync err none";
      }
      enum "mgmt-ldp-nsr-peer-sync-err-ldp-sync-nack" {
        description
          "mgmt ldp nsr peer sync err ldp sync nack";
      }
      enum "mgmt-ldp-nsr-peer-sync-err-sync-prep" {
        description
          "mgmt ldp nsr peer sync err sync prep";
      }
      enum "mgmt-ldp-nsr-peer-sync-err-tcp-peer" {
        description
          "mgmt ldp nsr peer sync err tcp peer";
      }
      enum "mgmt-ldp-nsr-peer-sync-err-tcp-gbl" {
        description
          "mgmt ldp nsr peer sync err tcp gbl";
      }
      enum "mgmt-ldp-nsr-peer-sync-err-ldp-peer" {
        description
          "mgmt ldp nsr peer sync err ldp peer";
      }
      enum "mgmt-ldp-nsr-peer-sync-err-ldp-gbl" {
        description
          "mgmt ldp nsr peer sync err ldp gbl";
      }
      enum "mgmt-ldp-nsr-peer-sync-err-app-fail" {
        description
          "mgmt ldp nsr peer sync err app fail";
      }
      enum "mgmt-ldp-nsr-peer-sync-err-sync-tcp-phase1" {
        description
          "mgmt ldp nsr peer sync err sync tcp phase1";
      }
      enum "mgmt-ldp-nsr-peer-sync-err-sync-tcp-phase2" {
        description
          "mgmt ldp nsr peer sync err sync tcp phase2";
      }
    }
    description
      "Mgmt ldp nsr peer sync err";
  }

  typedef live_ncs_Mgmt-ldp-nsr-peer-sync-state {
    type enumeration {
      enum "mgmt-ldp-nsr-peer-sync-st-none" {
        description
          "mgmt ldp nsr peer sync st none";
      }
      enum "mgmt-ldp-nsr-peer-sync-st-wait" {
        description
          "mgmt ldp nsr peer sync st wait";
      }
      enum "mgmt-ldp-nsr-peer-sync-st-ready" {
        description
          "mgmt ldp nsr peer sync st ready";
      }
      enum "mgmt-ldp-nsr-peer-sync-st-prep" {
        description
          "mgmt ldp nsr peer sync st prep";
      }
      enum "mgmt-ldp-nsr-peer-sync-st-app-wait" {
        description
          "mgmt ldp nsr peer sync st app wait";
      }
      enum "mgmt-ldp-nsr-peer-sync-st-oper" {
        description
          "mgmt ldp nsr peer sync st oper";
      }
      enum "mgmt-ldp-nsr-peer-sync-st-tcp-phase1" {
        description
          "mgmt ldp nsr peer sync st tcp phase1";
      }
      enum "mgmt-ldp-nsr-peer-sync-st-tcp-phase2" {
        description
          "mgmt ldp nsr peer sync st tcp phase2";
      }
    }
    description
      "Mgmt ldp nsr peer sync state";
  }

  typedef live_ncs_Ldp-adj-union-discrim {
    type enumeration {
      enum "link-hello" {
        description
          "Link hello";
      }
      enum "targeted-hello" {
        description
          "Targeted hello";
      }
    }
    description
      "MPLS LDP Hello Type";
  }

  typedef live_ncs_Show-nsr-state {
    type enumeration {
      enum "nsr-ready" {
        description
          "NSR ready";
      }
      enum "nsr-not-ready" {
        description
          "NSR not ready";
      }
      enum "nsr-na" {
        description
          "NSR not applicable";
      }
    }
    description
      "NSR State Type";
  }

  typedef live_ncs_Ldp-route-path-lbl-owner {
    type enumeration {
      enum "ip-path-lbl-owner-none" {
        value 0;
        description
          "No label and no owner";
      }
      enum "ip-path-lbl-owner-ldp" {
        value 1;
        description
          "Path outgoing label owned by LDP";
      }
      enum "ip-path-lbl-owner-bgp" {
        value 2;
        description
          "Path outgoing label owned by BGP";
      }
    }
    description
      "Route path label owner";
  }

  typedef live_ncs_Label-value {
    type enumeration {
      enum "mpls-label" {
        description
          "MPLS Label";
      }
      enum "un-labelled" {
        description
          "Unlabelled";
      }
      enum "unknown" {
        description
          "Unknown label";
      }
    }
    description
      "Label Value Type";
  }

  typedef live_ncs_Ldp-fwd-unlbl-rsn {
    type enumeration {
      enum "ldp-fwd-labelled" {
        description
          "ldp fwd labelled";
      }
      enum "ldp-fwd-un-labelled-vrf-down" {
        description
          "ldp fwd un labelled vrf down";
      }
      enum "ldp-fwd-un-labelled-no-nh" {
        description
          "ldp fwd un labelled no nh";
      }
      enum "ldp-fwd-un-labelled-recursive-path" {
        description
          "ldp fwd un labelled recursive path";
      }
      enum "ldp-fwd-un-labelled-intf-not-ldp" {
        description
          "ldp fwd un labelled intf not ldp";
      }
      enum "ldp-fwd-un-labelled-no-rmt" {
        description
          "ldp fwd un labelled no rmt";
      }
      enum "ldp-fwd-un-labelled-no-ldp-adj" {
        description
          "ldp fwd un labelled no ldp adj";
      }
      enum "ldp-fwd-un-labelled-no-session" {
        description
          "ldp fwd un labelled no session";
      }
      enum "ldp-fwd-un-labelled-unknown" {
        description
          "ldp fwd un labelled unknown";
      }
    }
    description
      "Ldp fwd unlbl rsn";
  }

  typedef live_ncs_Ldp-route-path-flags {
    type enumeration {
      enum "ip-path-no-flag" {
        value 0;
        description
          "A primary path with no special flag/attribute";
      }
      enum "ip-path-protected" {
        value 1;
        description
          "A primary path with LFA FRR protection";
      }
      enum "ip-path-backup" {
        value 2;
        description
          "A non-primary local LFA FRR (pure) backup path";
      }
      enum "ip-path-backup-remote" {
        value 3;
        description
          "A non-primary remote LFA FRR (pure) backup path";
      }
      enum "ip-path-bgp-backup" {
        value 4;
        description
          "A non-primary BGP backup path";
      }
    }
    description
      "Route path flags";
  }

  typedef live_ncs_Dhcb-state {
    type enumeration {
      enum "none" {
        description
          "None";
      }
      enum "dhcb-active" {
        description
          "Active";
      }
      enum "dhcb-passive" {
        description
          "Passive";
      }
      enum "dhcb-active-passive" {
        description
          "Active and Passive";
      }
    }
    description
      "DHCB State Type";
  }

  typedef live_ncs_Ldp-igp-sync-down-reason {
    type enumeration {
      enum "igp-sync-down-reason-not-applicable" {
        description
          "Not Applicable";
      }
      enum "no-hello-adjacency" {
        description
          "No hello adjacency";
      }
      enum "no-peer-session" {
        description
          "No peer session";
      }
      enum "initial-update-to-peer-not-done" {
        description
          "Initial update to peer not done yet";
      }
      enum "initial-update-from-peer-not-received" {
        description
          "Initial update from peer not received yet";
      }
      enum "internal-reason" {
        description
          "Internal reason";
      }
    }
    description
      "Reason IGP Sync Not Achieved";
  }

  typedef live_ncs_String-td2 {
    type string;
    description
      "String td2";
  }

  typedef live_ncs_Ldp-igp-sync-state {
    type enumeration {
      enum "isync-ready" {
        description
          "Acheived";
      }
      enum "isync-not-ready" {
        description
          "Not acheived";
      }
      enum "isync-deferred" {
        description
          "Deferred due to interface delay or global
           restart delay";
      }
    }
    description
      "IGP Sync State";
  }

  typedef live_ncs_Local-label-state {
    type enumeration {
      enum "local-label-state-none" {
        value 1;
        description
          "None";
      }
      enum "local-label-state-assigned" {
        value 2;
        description
          "Assigned";
      }
      enum "local-label-state-withdrawn" {
        value 3;
        description
          "Withdrawn";
      }
    }
    description
      "MPLS LDP Local Label State Type";
  }

  typedef live_ncs_Ldp-af {
    type enumeration {
      enum "ldp-show-af-none" {
        value 0;
        description
          "No Address Family";
      }
      enum "ldp-show-af-ipv4" {
        value 1;
        description
          "IPv4 AFI";
      }
      enum "ldp-show-af-ipv6" {
        value 2;
        description
          "IPv6 AFI";
      }
      enum "ldp-show-af-ipv4-ipv6" {
        value 3;
        description
          "Both IPv4/IPv6 AFIs";
      }
    }
    description
      "Ldp af";
  }

  typedef live_ncs_Ldp-in6-addr {
    type inet:ipv6-address;
    description
      "Ldp in6 addr";
  }

  typedef live_ncs_Ldp-in-addr {
    type inet:ipv4-address;
    description
      "Ldp in addr";
  }

  typedef live_ncs_Ldp-af-id {
    type enumeration {
      enum "ldp-af-id-none" {
        value 0;
        description
          "No Address Family";
      }
      enum "ldp-af-id-ipv4" {
        value 2;
        description
          "IPv4 AFI";
      }
      enum "ldp-af-id-ipv6" {
        value 10;
        description
          "IPv6 AFI";
      }
    }
    description
      "Ldp af id";
  }

  typedef Mgmt-ldp-nbr-bgp-advt-state {
    type enumeration {
      enum "not-applicable" {
        value 0;
        description
          "Not applicable";
      }
      enum "permit" {
        value 1;
        description
          "Advertisement permitted";
      }
      enum "deny" {
        value 2;
        description
          "Advertisement denied";
      }
    }
    description
      "MPLS LDP Neighbor BGP Label Advertisement State
       Type";
  }

  typedef Mgmt-ldp-nsr-peer-ldp-sync-nack-rsn {
    type enumeration {
      enum "mgmt-ldp-nsr-peer-ldp-sync-nack-rsn-none" {
        description
          "mgmt ldp nsr peer ldp sync nack rsn none";
      }
      enum "mgmt-ldp-nsr-peer-ldp-sync-nack-rsn-tbl-id-mismatch" {
        description
          "mgmt ldp nsr peer ldp sync nack rsn tbl id
           mismatch";
      }
      enum "mgmt-ldp-nsr-peer-ldp-sync-nack-rsn-pp-exists" {
        description
          "mgmt ldp nsr peer ldp sync nack rsn pp exists";
      }
      enum "mgmt-ldp-nsr-peer-ldp-sync-nack-rsn-missing-elem" {
        description
          "mgmt ldp nsr peer ldp sync nack rsn missing
           elem";
      }
      enum "mgmt-ldp-nsr-peer-ldp-sync-nack-rsn-no-p-end-sock" {
        description
          "mgmt ldp nsr peer ldp sync nack rsn no p end
           sock";
      }
      enum "mgmt-ldp-nsr-peer-ldp-sync-nack-rsn-p-end-sock-not-synced" {
        description
          "mgmt ldp nsr peer ldp sync nack rsn p end sock
           not synced";
      }
      enum "mgmt-ldp-nsr-peer-ldp-sync-nack-rsn-err-adj-add" {
        description
          "mgmt ldp nsr peer ldp sync nack rsn err adj add";
      }
      enum "mgmt-ldp-nsr-peer-ldp-sync-nack-rsn-err-dhcb-add" {
        description
          "mgmt ldp nsr peer ldp sync nack rsn err dhcb
           add";
      }
      enum "mgmt-ldp-nsr-peer-ldp-sync-nack-rsn-enomem" {
        description
          "mgmt ldp nsr peer ldp sync nack rsn enomem";
      }
      enum "mgmt-ldp-nsr-peer-ldp-sync-nack-rsn-err-tp-create" {
        description
          "mgmt ldp nsr peer ldp sync nack rsn err tp
           create";
      }
      enum "mgmt-ldp-nsr-peer-ldp-sync-nack-rsn-err-pp-create" {
        description
          "mgmt ldp nsr peer ldp sync nack rsn err pp
           create";
      }
      enum "mgmt-ldp-nsr-peer-ldp-sync-nack-rsn-err-addr-bind" {
        description
          "mgmt ldp nsr peer ldp sync nack rsn err addr
           bind";
      }
      enum "mgmt-ldp-nsr-peer-ldp-sync-nack-rsn-err-rx-bad-pie" {
        description
          "mgmt ldp nsr peer ldp sync nack rsn err rx bad
           pie";
      }
      enum "mgmt-ldp-nsr-peer-ldp-sync-nack-rsn-err-rx-notif" {
        description
          "mgmt ldp nsr peer ldp sync nack rsn err rx
           notif";
      }
      enum "mgmt-ldp-nsr-peer-ldp-sync-nack-rsn-err-rx-unexp-open" {
        description
          "mgmt ldp nsr peer ldp sync nack rsn err rx
           unexp open";
      }
      enum "mgmt-ldp-nsr-peer-ldp-sync-nack-rsn-err-unexp-peer-down" {
        description
          "mgmt ldp nsr peer ldp sync nack rsn err unexp
           peer down";
      }
      enum "mgmt-ldp-nsr-peer-ldp-sync-nack-rsn-err-app-not-found" {
        description
          "mgmt ldp nsr peer ldp sync nack rsn err app not
           found";
      }
      enum "mgmt-ldp-nsr-peer-ldp-sync-nack-rsn-err-app-invalid" {
        description
          "mgmt ldp nsr peer ldp sync nack rsn err app
           invalid";
      }
      enum "mgmt-ldp-nsr-peer-ldp-sync-nack-rsn-err-adj-grp-not-found" {
        description
          "mgmt ldp nsr peer ldp sync nack rsn err adj grp
           not found";
      }
      enum "mgmt-ldp-nsr-peer-ldp-sync-nack-rsn-invalid-elem" {
        description
          "mgmt ldp nsr peer ldp sync nack rsn invalid
           elem";
      }
      enum "mgmt-ldp-nsr-peer-ldp-sync-nack-rsn-err-app-data-invalid" {
        description
          "mgmt ldp nsr peer ldp sync nack rsn err app
           data invalid";
      }
      enum "mgmt-ldp-nsr-peer-ldp-sync-nack-rsn-err-invalid-per-idx" {
        description
          "mgmt ldp nsr peer ldp sync nack rsn err invalid
           per idx";
      }
      enum "mgmt-ldp-nsr-peer-ldp-sync-nack-rsn-err-pfx-not-found" {
        description
          "mgmt ldp nsr peer ldp sync nack rsn err pfx not
           found";
      }
      enum "mgmt-ldp-nsr-peer-ldp-sync-nack-rsn-err-bm-size-invalid" {
        description
          "mgmt ldp nsr peer ldp sync nack rsn err bm size
           invalid";
      }
      enum "mgmt-ldp-nsr-peer-ldp-sync-nack-rsn-err-adv-bm-clear" {
        description
          "mgmt ldp nsr peer ldp sync nack rsn err adv bm
           clear";
      }
      enum "mgmt-ldp-nsr-peer-ldp-sync-nack-rsn-err-tcp-struct-create" {
        description
          "mgmt ldp nsr peer ldp sync nack rsn err tcp
           struct create";
      }
      enum "mgmt-ldp-nsr-peer-ldp-sync-nack-rsn-no-ctx" {
        description
          "mgmt ldp nsr peer ldp sync nack rsn no ctx";
      }
    }
    description
      "Mgmt ldp nsr peer ldp sync nack rsn";
  }

  typedef Mgmt-ldp-nsr-peer-sync-err {
    type enumeration {
      enum "mgmt-ldp-nsr-peer-sync-err-none" {
        description
          "mgmt ldp nsr peer sync err none";
      }
      enum "mgmt-ldp-nsr-peer-sync-err-ldp-sync-nack" {
        description
          "mgmt ldp nsr peer sync err ldp sync nack";
      }
      enum "mgmt-ldp-nsr-peer-sync-err-sync-prep" {
        description
          "mgmt ldp nsr peer sync err sync prep";
      }
      enum "mgmt-ldp-nsr-peer-sync-err-tcp-peer" {
        description
          "mgmt ldp nsr peer sync err tcp peer";
      }
      enum "mgmt-ldp-nsr-peer-sync-err-tcp-gbl" {
        description
          "mgmt ldp nsr peer sync err tcp gbl";
      }
      enum "mgmt-ldp-nsr-peer-sync-err-ldp-peer" {
        description
          "mgmt ldp nsr peer sync err ldp peer";
      }
      enum "mgmt-ldp-nsr-peer-sync-err-ldp-gbl" {
        description
          "mgmt ldp nsr peer sync err ldp gbl";
      }
      enum "mgmt-ldp-nsr-peer-sync-err-app-fail" {
        description
          "mgmt ldp nsr peer sync err app fail";
      }
      enum "mgmt-ldp-nsr-peer-sync-err-sync-tcp-phase1" {
        description
          "mgmt ldp nsr peer sync err sync tcp phase1";
      }
      enum "mgmt-ldp-nsr-peer-sync-err-sync-tcp-phase2" {
        description
          "mgmt ldp nsr peer sync err sync tcp phase2";
      }
    }
    description
      "Mgmt ldp nsr peer sync err";
  }

  typedef Mgmt-ldp-nsr-peer-sync-state {
    type enumeration {
      enum "mgmt-ldp-nsr-peer-sync-st-none" {
        description
          "mgmt ldp nsr peer sync st none";
      }
      enum "mgmt-ldp-nsr-peer-sync-st-wait" {
        description
          "mgmt ldp nsr peer sync st wait";
      }
      enum "mgmt-ldp-nsr-peer-sync-st-ready" {
        description
          "mgmt ldp nsr peer sync st ready";
      }
      enum "mgmt-ldp-nsr-peer-sync-st-prep" {
        description
          "mgmt ldp nsr peer sync st prep";
      }
      enum "mgmt-ldp-nsr-peer-sync-st-app-wait" {
        description
          "mgmt ldp nsr peer sync st app wait";
      }
      enum "mgmt-ldp-nsr-peer-sync-st-oper" {
        description
          "mgmt ldp nsr peer sync st oper";
      }
      enum "mgmt-ldp-nsr-peer-sync-st-tcp-phase1" {
        description
          "mgmt ldp nsr peer sync st tcp phase1";
      }
      enum "mgmt-ldp-nsr-peer-sync-st-tcp-phase2" {
        description
          "mgmt ldp nsr peer sync st tcp phase2";
      }
    }
    description
      "Mgmt ldp nsr peer sync state";
  }

  typedef Ldp-adj-union-discrim {
    type enumeration {
      enum "link-hello" {
        description
          "Link hello";
      }
      enum "targeted-hello" {
        description
          "Targeted hello";
      }
    }
    description
      "MPLS LDP Hello Type";
  }

  typedef Show-nsr-state {
    type enumeration {
      enum "nsr-ready" {
        description
          "NSR ready";
      }
      enum "nsr-not-ready" {
        description
          "NSR not ready";
      }
      enum "nsr-na" {
        description
          "NSR not applicable";
      }
    }
    description
      "NSR State Type";
  }

  typedef Ldp-route-path-lbl-owner {
    type enumeration {
      enum "ip-path-lbl-owner-none" {
        value 0;
        description
          "No label and no owner";
      }
      enum "ip-path-lbl-owner-ldp" {
        value 1;
        description
          "Path outgoing label owned by LDP";
      }
      enum "ip-path-lbl-owner-bgp" {
        value 2;
        description
          "Path outgoing label owned by BGP";
      }
    }
    description
      "Route path label owner";
  }

  typedef Label-value {
    type enumeration {
      enum "mpls-label" {
        description
          "MPLS Label";
      }
      enum "un-labelled" {
        description
          "Unlabelled";
      }
      enum "unknown" {
        description
          "Unknown label";
      }
    }
    description
      "Label Value Type";
  }

  typedef Ldp-fwd-unlbl-rsn {
    type enumeration {
      enum "ldp-fwd-labelled" {
        description
          "ldp fwd labelled";
      }
      enum "ldp-fwd-un-labelled-vrf-down" {
        description
          "ldp fwd un labelled vrf down";
      }
      enum "ldp-fwd-un-labelled-no-nh" {
        description
          "ldp fwd un labelled no nh";
      }
      enum "ldp-fwd-un-labelled-recursive-path" {
        description
          "ldp fwd un labelled recursive path";
      }
      enum "ldp-fwd-un-labelled-intf-not-ldp" {
        description
          "ldp fwd un labelled intf not ldp";
      }
      enum "ldp-fwd-un-labelled-no-rmt" {
        description
          "ldp fwd un labelled no rmt";
      }
      enum "ldp-fwd-un-labelled-no-ldp-adj" {
        description
          "ldp fwd un labelled no ldp adj";
      }
      enum "ldp-fwd-un-labelled-no-session" {
        description
          "ldp fwd un labelled no session";
      }
      enum "ldp-fwd-un-labelled-unknown" {
        description
          "ldp fwd un labelled unknown";
      }
    }
    description
      "Ldp fwd unlbl rsn";
  }

  typedef Ldp-route-path-flags {
    type enumeration {
      enum "ip-path-no-flag" {
        value 0;
        description
          "A primary path with no special flag/attribute";
      }
      enum "ip-path-protected" {
        value 1;
        description
          "A primary path with LFA FRR protection";
      }
      enum "ip-path-backup" {
        value 2;
        description
          "A non-primary local LFA FRR (pure) backup path";
      }
      enum "ip-path-backup-remote" {
        value 3;
        description
          "A non-primary remote LFA FRR (pure) backup path";
      }
      enum "ip-path-bgp-backup" {
        value 4;
        description
          "A non-primary BGP backup path";
      }
    }
    description
      "Route path flags";
  }

  typedef Dhcb-state {
    type enumeration {
      enum "none" {
        description
          "None";
      }
      enum "dhcb-active" {
        description
          "Active";
      }
      enum "dhcb-passive" {
        description
          "Passive";
      }
      enum "dhcb-active-passive" {
        description
          "Active and Passive";
      }
    }
    description
      "DHCB State Type";
  }

  typedef Ldp-igp-sync-down-reason {
    type enumeration {
      enum "igp-sync-down-reason-not-applicable" {
        description
          "Not Applicable";
      }
      enum "no-hello-adjacency" {
        description
          "No hello adjacency";
      }
      enum "no-peer-session" {
        description
          "No peer session";
      }
      enum "initial-update-to-peer-not-done" {
        description
          "Initial update to peer not done yet";
      }
      enum "initial-update-from-peer-not-received" {
        description
          "Initial update from peer not received yet";
      }
      enum "internal-reason" {
        description
          "Internal reason";
      }
    }
    description
      "Reason IGP Sync Not Achieved";
  }

  typedef String-td2 {
    type string;
    description
      "String td2";
  }

  typedef Ldp-igp-sync-state {
    type enumeration {
      enum "isync-ready" {
        description
          "Acheived";
      }
      enum "isync-not-ready" {
        description
          "Not acheived";
      }
      enum "isync-deferred" {
        description
          "Deferred due to interface delay or global
           restart delay";
      }
    }
    description
      "IGP Sync State";
  }

  typedef Local-label-state {
    type enumeration {
      enum "local-label-state-none" {
        value 1;
        description
          "None";
      }
      enum "local-label-state-assigned" {
        value 2;
        description
          "Assigned";
      }
      enum "local-label-state-withdrawn" {
        value 3;
        description
          "Withdrawn";
      }
    }
    description
      "MPLS LDP Local Label State Type";
  }

  typedef Ldp-af {
    type enumeration {
      enum "ldp-show-af-none" {
        value 0;
        description
          "No Address Family";
      }
      enum "ldp-show-af-ipv4" {
        value 1;
        description
          "IPv4 AFI";
      }
      enum "ldp-show-af-ipv6" {
        value 2;
        description
          "IPv6 AFI";
      }
      enum "ldp-show-af-ipv4-ipv6" {
        value 3;
        description
          "Both IPv4/IPv6 AFIs";
      }
    }
    description
      "Ldp af";
  }

  typedef Ldp-in6-addr {
    type inet:ipv6-address;
    description
      "Ldp in6 addr";
  }

  typedef Ldp-in-addr {
    type inet:ipv4-address;
    description
      "Ldp in addr";
  }

  typedef Ldp-af-id {
    type enumeration {
      enum "ldp-af-id-none" {
        value 0;
        description
          "No Address Family";
      }
      enum "ldp-af-id-ipv4" {
        value 2;
        description
          "IPv4 AFI";
      }
      enum "ldp-af-id-ipv6" {
        value 10;
        description
          "IPv6 AFI";
      }
    }
    description
      "Ldp af id";
  }

  grouping ncs_template_LDP-SUMMARY {
    description
      "MPLS LDP Summarized Information";
    container common {
      description
        "Common Summary information";
      uses ncs_template_LDP-SUMMARY-COMMON;
    }
    leaf number-of-vrf {
      type string;
      description
        "Number of configured VRFs (including default)";
    }
    leaf number-of-vrf-oper {
      type string;
      description
        "Number of configured operational VRFs (including
         default)";
    }
    leaf number-of-interfaces {
      type string;
      description
        "Number of known interfaces";
    }
    leaf number-of-fwd-ref-interfaces {
      type string;
      description
        "Number of Forward Referenc interfaces";
    }
    leaf number-of-autocfg-interfaces {
      type string;
      description
        "Number of auto-configured interfaces";
    }
    leaf is-bound-with-sysdb {
      type string;
      description
        "Bound status with sysdb";
    }
    leaf is-registered-with-sysdb {
      type string;
      description
        "Registration status with Sysdb";
    }
    leaf is-bound-with-rsi {
      type string;
      description
        "Bound status with rsi";
    }
    leaf is-bound-with-interface-manager {
      type string;
      description
        "Bound status with Interface Manager";
    }
    leaf is-registered-with-interface-manager {
      type string;
      description
        "Registration status with Interface Manager";
    }
    leaf is-bound-with-ip-arm {
      type string;
      description
        "Bound status with IP Arm";
    }
    leaf is-bound-with-lsd {
      type string;
      description
        "Bound status with LSD";
    }
    leaf is-registered-with-lsd {
      type string;
      description
        "Registration status with LSD";
    }
    leaf is-bound-with-ipv4-rib {
      type string;
      description
        "Bound status with IPv4 RIB";
    }
    leaf is-registered-with-ipv4-rib {
      type string;
      description
        "Registration status with IPv4 RIB";
    }
    leaf number-of-ipv4rib-tables {
      type string;
      description
        "Total number of ipv4 RIB tables";
    }
    leaf number-of-registered-ipv4rib-tables {
      type string;
      description
        "Number of ipv4 RIB tables registered";
    }
    leaf is-bound-with-ipv6-rib {
      type string;
      description
        "Bound status with IPv6 RIB";
    }
    leaf is-registered-with-ipv6-rib {
      type string;
      description
        "Registration status with IPv6 RIB";
    }
    leaf number-of-ipv6rib-tables {
      type string;
      description
        "Total number of ipv6 RIB tables";
    }
    leaf number-of-registered-ipv6rib-tables {
      type string;
      description
        "Number of ipv6 RIB tables registered";
    }
    leaf is-bound-with-atom {
      type string;
      description
        "Bound status with L2VPN ATOM";
    }
    leaf is-bound-with-nsr-mate {
      type string;
      description
        "Bound status with NSR Mate";
    }
    leaf is-nsr-configured {
      type string;
      description
        "NSR configured";
    }
    leaf is-mldp-registered {
      type string;
      description
        "mLDP registration status";
    }
  }

  grouping ncs_template_LDP-MSG-COUNTERS {
    description
      "MPLS LDP Session Message Counters Information";
    leaf total-count {
      type string;
      description
        "Total message count";
    }
    leaf init-count {
      type string;
      description
        "Init message count";
    }
    leaf address-count {
      type string;
      description
        "Address message count";
    }
    leaf address-withdraw-count {
      type string;
      description
        "Address withdraw count";
    }
    leaf label-map-count {
      type string;
      description
        "Label map count";
    }
    leaf label-withdraw-count {
      type string;
      description
        "Label withdraw count";
    }
    leaf label-release-count {
      type string;
      description
        "Label release count";
    }
    leaf label-request-count {
      type string;
      description
        "Label request count";
    }
    leaf label-abort-request-count {
      type string;
      description
        "Label abort request count";
    }
    leaf notification-count {
      type string;
      description
        "Notification count";
    }
    leaf keep-alive-count {
      type string;
      description
        "Keepalive count";
    }
    leaf iccp-rg-conn-count {
      type string;
      description
        "ICCP RG Connect count";
    }
    leaf iccp-rg-disconn-count {
      type string;
      description
        "ICCP RG Disconnect count";
    }
    leaf iccp-rg-notif-count {
      type string;
      description
        "ICCP RG Notif count";
    }
    leaf iccp-rg-app-data-count {
      type string;
      description
        "ICCP RG App Data count";
    }
  }

  grouping ncs_template_LDP-STATS-INFO {
    description
      "MPLS LDP Statistics Information";
    container message-out {
      description
        "Message out count";
      uses ncs_template_LDP-MSG-COUNTERS;
    }
    container message-in {
      description
        "Message in count";
      uses ncs_template_LDP-MSG-COUNTERS;
    }
    leaf iccp-enabled {
      type string;
      description
        "Is session ICCP enabled?";
    }
  }

  grouping ncs_template_LDP-NBR-CLIENTS-INFO {
    description
      "MPLS LDP Session client Information";
    leaf name {
      type string;
      description
        "Client's name";
    }
  }

  grouping ncs_template_LDP-NBR-DETAILED-INFO {
    description
      "MPLS LDP Neighbor Detailed Information";
    container capabilities {
      description
        "Capabilities sent to and received from neighbor";
      uses ncs_template_LDP-NBR-CAP-INFO;
    }
    leaf peer-holdtime {
      type string;
      units "second";
      description
        "Session holdtime value in seconds from the peer";
    }
    leaf keep-alive-interval {
      type string;
      units "second";
      description
        "Session keepalive interval in seconds";
    }
    leaf peer-state {
      type string;
      description
        "Peer state";
    }
    leaf has-ipv4-inbound {
      type string;
      description
        "IPv4 Inbound label filtering present";
    }
    leaf inbound-ipv4acl {
      type string;
      description
        "IPv4 Inbound accept ACL";
    }
    leaf has-ipv6-inbound {
      type string;
      description
        "IPv6 Inbound label filtering present";
    }
    leaf inbound-ipv6acl {
      type string;
      description
        "IPv6 Inbound accept ACL";
    }
    leaf has-ipv4-outbound {
      type string;
      description
        "IPv4 Outbound label filtering present";
    }
    leaf outbound-ipv4acl {
      type string;
      description
        "IPv4 Outbound advertise ACL";
    }
    leaf has-ipv6-outbound {
      type string;
      description
        "IPv6 Outbound label filtering present";
    }
    leaf outbound-ipv6acl {
      type string;
      description
        "IPv6 Outbound advertise ACL";
    }
    leaf has-sp {
      type string;
      description
        "Session Protection enabled";
    }
    leaf sp-state {
      type string;
      description
        "Session Protection state";
    }
    leaf sp-has-acl {
      type string;
      description
        "Session protection ACL is present";
    }
    leaf spacl {
      type string;
      description
        "Session Protection ACL";
    }
    leaf sp-has-duration {
      type string;
      description
        "Session Protection has non-default duration";
    }
    leaf sp-duration {
      type string;
      units "second";
      description
        "Session protection holdup time duration in
         seconds";
    }
    leaf spht-running {
      type string;
      description
        "Session Protection holdup timer is running";
    }
    leaf spht-remaining {
      type string;
      units "second";
      description
        "Session Protection holdup time remaining value
         in seconds";
    }
    leaf nsr-sync-state {
      type ncs_template_Mgmt-ldp-nsr-peer-sync-state;
      description
        "NSR Sync State";
    }
    leaf nsr-last-sync-error {
      type ncs_template_Mgmt-ldp-nsr-peer-sync-err;
      description
        "Last NSR sync error";
    }
    leaf nsr-last-sync-nack-reason {
      type ncs_template_Mgmt-ldp-nsr-peer-ldp-sync-nack-rsn;
      description
        "Last NSR sync NACK reaston";
    }
    leaf bgp-advertisement-state {
      type ncs_template_Mgmt-ldp-nbr-bgp-advt-state;
      description
        "BGP labelled prefixes advertisement state";
    }
    leaf advertise-bgp-prefixes {
      type string;
      description
        "Is BGP labelled prefixes advertised to the
         neighbor";
    }
    list client {
      // NCS patched for predictable order
      ordered-by user;
      description
        "Targeted Session clients";
      uses ncs_template_LDP-NBR-CLIENTS-INFO;
    }
    list ipv4-duplicate-address {
      // NCS patched for predictable order
      ordered-by user;
      description
        "Duplicate IPv4 address bound to this peer";
      uses ncs_template_LDP-NBR-ADDR-INFO;
    }
    list ipv6-duplicate-address {
      // NCS patched for predictable order
      ordered-by user;
      description
        "Duplicate IPv6 address bound to this peer";
      uses ncs_template_LDP-NBR-ADDR-INFO;
    }
  }

  grouping ncs_template_TARGETED-HELLO {
    description
      "MPLS LDP Targeted Hello Information";
    container local-address {
      description
        "Local Address";
      uses ncs_template_LDP-IP-ADDR-T-UNION;
    }
    container target-address {
      description
        "Target Address";
      uses ncs_template_LDP-IP-ADDR-T-UNION;
    }
    leaf state {
      type ncs_template_Dhcb-state;
      description
        "State";
    }
  }

  grouping ncs_template_LINK-HELLO {
    description
      "MPLS LDP Link Hello Information";
    leaf interface {
      type xr:ncs_template_Interface-name;
      description
        "Interface name";
    }
    leaf interface-name {
      type string;
      description
        "Interface name";
    }
  }

  grouping ncs_template_LDP-ADJ-UNION {
    description
      "LDP ADJ UNION";
    container link-hello-data {
      // NCS drop when statement
      description
        "Link hello";
      uses ncs_template_LINK-HELLO;
    }
    container target-hello-data {
      // NCS drop when statement
      description
        "Target Hello";
      uses ncs_template_TARGETED-HELLO;
    }
    leaf hello-type {
      type ncs_template_Ldp-adj-union-discrim;
      description
        "HelloType";
    }
  }

  grouping ncs_template_LDP-NBR-ADJ-INFO {
    description
      "MPLS LDP Neighbor Adjacency Information";
    container adjacency-group {
      description
        "Adjacency group";
      uses ncs_template_LDP-ADJ-UNION;
    }
  }

  grouping ncs_template_LDP-NBR-ADDR-INFO {
    description
      "MPLS LDP Neighbor Bound Address Information";
    container address {
      description
        "Neighbor Address";
      uses ncs_template_LDP-IP-ADDR-T-UNION;
    }
  }

  grouping ncs_template_LDP-TCP-INFO {
    description
      "MPLS LDP Neighbor TCP Information";
    container foreign-host {
      description
        "Foreign host address";
      uses ncs_template_LDP-IP-ADDR-T-UNION;
    }
    container local-host {
      description
        "Local host address";
      uses ncs_template_LDP-IP-ADDR-T-UNION;
    }
    leaf foreign-port {
      type string;
      description
        "Foreign port number";
    }
    leaf local-port {
      type string;
      description
        "Local port number";
    }
    leaf is-md5-on {
      type string;
      description
        "Is MD5 Digest on";
    }
  }

  grouping ncs_template_LDP-GR-ADJ-INFO {
    description
      "MPLS LDP Neighbor Graceful Restart Adjacency
       Information";
    leaf is-graceful-restartable {
      type string;
      description
        "Is graceful restartable";
    }
    leaf reconnect-timeout {
      type string;
      description
        "Reconnect timeout";
    }
    leaf recovery-time {
      type string;
      description
        "Recovery time";
    }
  }

  grouping ncs_template_LDP-PTCL-ADJ-INFO {
    description
      "MPLS LDP PTCL Adjacency Information";
    container ta-graceful-restart-adjacency {
      description
        "Graceful restart information";
      uses ncs_template_LDP-GR-ADJ-INFO;
    }
    leaf ta-holdtime {
      type string;
      description
        "Session holdtime in sec";
    }
    leaf ta-state {
      type string;
      description
        "State";
    }
    leaf ta-pies-sent {
      type string;
      description
        "Number of pies sent";
    }
    leaf ta-pies-rcvd {
      type string;
      description
        "Number of pies received";
    }
    leaf ta-up-time-seconds {
      type string;
      units "second";
      description
        "Up time in seconds";
    }
    leaf downstream-on-demand {
      type string;
      description
        "Is Label advertisment mode in Downstream On
         Demand mode or Not";
    }
  }

  grouping ncs_template_LDP-NEIGHBOR-INFO {
    description
      "MPLS LDP Neighbor Information";
    container protocol-information {
      description
        "Protocol Information";
      uses ncs_template_LDP-PTCL-ADJ-INFO;
    }
    container tcp-information {
      description
        "TCP Information";
      uses ncs_template_LDP-TCP-INFO;
    }
    container detailed-information {
      description
        "Detailed information with regards to holdtime,
         KA, inbound filtering, and Session protection";
      uses ncs_template_LDP-NBR-DETAILED-INFO;
    }
    list ldp-nbr-bound-ipv4-address-info {
      // NCS patched for predictable order
      ordered-by user;
      description
        "Neighbor IPv4 Address Info";
      uses ncs_template_LDP-NBR-ADDR-INFO;
    }
    list ldp-nbr-bound-ipv6-address-info {
      // NCS patched for predictable order
      ordered-by user;
      description
        "Neighbor IPv6 Address Info";
      uses ncs_template_LDP-NBR-ADDR-INFO;
    }
    list ldp-nbr-ipv4-adj-info {
      // NCS patched for predictable order
      ordered-by user;
      description
        "Neighbor's IPv4 Adjacency Information";
      uses ncs_template_LDP-NBR-ADJ-INFO;
    }
    list ldp-nbr-ipv6-adj-info {
      // NCS patched for predictable order
      ordered-by user;
      description
        "Neighbor's IPv6 Adjacency Information";
      uses ncs_template_LDP-NBR-ADJ-INFO;
    }
  }

  grouping ncs_template_LDP-NBR-CAP-INFO {
    description
      "MPLS LDP Neighbor Capability Information";
    list sent {
      // NCS patched for predictable order
      ordered-by user;
      description
        "List of sent capabilities";
      uses ncs_template_LDP-CAP-DESC;
    }
    list received {
      // NCS patched for predictable order
      ordered-by user;
      description
        "List of received capabilities";
      uses ncs_template_LDP-CAP-DESC;
    }
  }

  grouping ncs_template_LDP-PARAMETERS-AF {
    description
      "MPLS LDP per AF Parameters Information";
    container discovery-transport-address {
      description
        "Discovery transport address";
      uses ncs_template_LDP-IP-ADDR-T-UNION;
    }
    leaf address-family {
      type ncs_template_Ldp-af;
      description
        "Address Family";
    }
    leaf null-label {
      type string;
      description
        "Null label";
    }
    leaf label-imp-null-override-acl {
      type string;
      description
        "ACL to override local label to use implicit-null";
    }
    leaf is-accepting-targeted-hellos {
      type string;
      description
        "Accepting targeted Hellos";
    }
    leaf targeted-hello-acl {
      type string;
      description
        "Targeted Hello ACL";
    }
  }

  grouping ncs_template_LDP-GRACEFUL-RESTART-INFO {
    description
      "MPLS LDP Global Graceful Restart Information";
    leaf is-graceful-restart-configured {
      type string;
      description
        "Is graceful restart configured";
    }
    leaf graceful-restart-reconnect-timeout {
      type string;
      description
        "Reconnect timeout value";
    }
    leaf graceful-restart-forwarding-state-hold-time {
      type string;
      description
        "Graceful restart forward state hold time";
    }
  }

  grouping ncs_template_LDP-PARAMETERS {
    description
      "MPLS LDP Global Parameters";
    container graceful-restart-information {
      description
        "Graceful restart information";
      uses ncs_template_LDP-GRACEFUL-RESTART-INFO;
    }
    leaf role-is-active {
      type string;
      description
        "Is process role active or standby";
    }
    leaf global-md5-password-enabled {
      type string;
      description
        "Global MD5 password enabled";
    }
    leaf protocol-version {
      type string;
      description
        "Protocol version";
    }
    leaf router-id {
      type string;
      description
        "Router ID";
    }
    leaf keepalive-interval {
      type string;
      description
        "Keepalive interval";
    }
    leaf hello-hold-time {
      type string;
      description
        "Hello hold time";
    }
    leaf hello-interval {
      type string;
      description
        "Hello interval";
    }
    leaf targeted-hello-hold-time {
      type string;
      description
        "Targeted hello hold time";
    }
    leaf targeted-hello-interval {
      type string;
      description
        "Targeted hello interval";
    }
    leaf session-hold-time {
      type string;
      description
        "Session hold time";
    }
    leaf housekeeping-timer-interval {
      type string;
      description
        "Housekeeping periodic timer interval";
    }
    leaf le-no-route-timeout {
      type string;
      description
        "LIB entry no route timeout";
    }
    leaf ldp-recovery-timeout {
      type string;
      description
        "LDP recovery timeout with LSD";
    }
    leaf af-binding-withdraw-delay {
      type string;
      description
        "Delay (sec) in Binding Withdrawal for an Address
         Family";
    }
    leaf max-intf-attached {
      type string;
      description
        "Maximum number of LDP enabled attached
         interfaces";
    }
    leaf max-intf-te {
      type string;
      description
        "Maximum number of LDP enabled TE interfaces";
    }
    leaf max-peer {
      type string;
      description
        "Maximum number of LDP peers";
    }
    leaf ldp-out-of-mem-state {
      type string;
      description
        "LDP Out of memory state";
    }
    leaf nsr-enabled {
      type string;
      description
        "TRUE if NSR is enabled";
    }
    leaf nsr-synced {
      type string;
      description
        "TRUE if LDP is standby and is NSR Sync-ed with
         active";
    }
    leaf igp-sync-delay-time-for-interface {
      type string;
      units "second";
      description
        "Interface IGP sync delay time in seconds";
    }
    leaf igp-sync-delay-time-on-restart {
      type string;
      units "second";
      description
        "IGP sync delay time on process restart in
         seconds";
    }
    leaf global-discovery-quick-start-disabled {
      type string;
      description
        "Discovery quick-start globally disabled";
    }
    leaf discovery-quick-start-disabled-on-interfaces {
      type string;
      description
        "Discovery quick-start disabled on some
         LDP-enabled interfaces";
    }
    list address-family-parameter {
      // NCS patched for predictable order
      ordered-by user;
      description
        "Per AF parameters";
      uses ncs_template_LDP-PARAMETERS-AF;
    }
  }

  grouping ncs_template_LDP-NSR-SUM-SESS {
    description
      "MPLS LDP NSR session summary";
    leaf total {
      type string;
      description
        "Total sessions";
    }
    leaf nsr-eligible {
      type string;
      description
        "NSR eligible sessions";
    }
    leaf nsr-state-none {
      type string;
      description
        "Number of sessions in NSR none state";
    }
    leaf nsr-state-wait {
      type string;
      description
        "Number of sessions in NSR wait state";
    }
    leaf nsr-state-ready {
      type string;
      description
        "Number of sessions in NSR ready state";
    }
    leaf nsr-state-prepare {
      type string;
      description
        "Number of sessions in NSR prepare state";
    }
    leaf nsr-state-app-wait {
      type string;
      description
        "Number of sessions in NSR app-wait state";
    }
    leaf nsr-state-operational {
      type string;
      description
        "Number of sessions in NSR operational state";
    }
    leaf nsr-state-tcp-phase1 {
      type string;
      description
        "Number of sessions in NSR TCP phase 1 state";
    }
    leaf nsr-state-tcp-phase2 {
      type string;
      description
        "Number of sessions in NSR TCP phase 2 state";
    }
  }

  grouping ncs_template_LDP-NSR-SUM {
    description
      "MPLS LDP NSR summary";
    container vrf {
      description
        "VRF information";
      uses ncs_template_LDP-VRF-INFO;
    }
    container sessions {
      description
        "Session summary";
      uses ncs_template_LDP-NSR-SUM-SESS;
    }
  }

  grouping ncs_template_LDP-BACKOFF-ENTRY-INFO {
    description
      "MPLS LDP Session Backoff Entry Information";
    leaf backoff-seconds {
      type string;
      units "second";
      description
        "Backoff seconds";
    }
    leaf waiting-seconds {
      type string;
      units "second";
      description
        "Backoff waiting seconds";
    }
  }

  grouping ncs_template_LDP-BACKOFF-INFO {
    description
      "MPLS LDP Session Backoff Information";
    leaf initial-seconds {
      type string;
      units "second";
      description
        "Initial backoff value in seconds";
    }
    leaf maximum-seconds {
      type string;
      units "second";
      description
        "Maximum backoff value in seconds";
    }
  }

  grouping ncs_template_LDP-NEIGHBOR-BRIEF-AF-INFO {
    description
      "MPLS LDP Neighbor Brief AF information";
    leaf address-family {
      type ncs_template_Ldp-af;
      description
        "Neighbor Brief Address Family";
    }
    leaf num-of-nbr-discovery {
      type string;
      description
        "Number of neighbor discovery sources";
    }
    leaf num-of-nbr-addresses {
      type string;
      description
        "Number of neighbor addresses";
    }
    leaf num-of-nbr-lbl {
      type string;
      description
        "Number of neighbor labels";
    }
  }

  grouping ncs_template_LDP-NEIGHBOR-BRIEF-INFO {
    description
      "MPLS LDP Neighbor Brief Information";
    container vrf {
      description
        "VRF information";
      uses ncs_template_LDP-VRF-INFO;
    }
    leaf is-graceful-restartable {
      type string;
      description
        "Is graceful restartable";
    }
    leaf nsr-state {
      type ncs_template_Show-nsr-state;
      description
        "NSR readiness state";
    }
    leaf up-time-seconds {
      type string;
      units "second";
      description
        "Up time in seconds";
    }
    list nbr-br-af-info {
      // NCS patched for predictable order
      ordered-by user;
      // NCS drop max-elements statement
      description
        "Neighbor Brief AF Info";
      uses ncs_template_LDP-NEIGHBOR-BRIEF-AF-INFO;
    }
  }

  grouping ncs_template_LDP-FWD-RW-PATH-SUMM {
    description
      "MPLS LDP fowarding rewrite nexthop/path summary";
    leaf total-paths {
      type string;
      description
        "Total path count";
    }
    leaf protected-paths {
      type string;
      description
        "Count of FRR protected paths";
    }
    leaf backup-paths {
      type string;
      description
        "Count of non-primary backup paths";
    }
    leaf remote-backup-paths {
      type string;
      description
        "Count of non-primary remote backup paths";
    }
    leaf labeled-paths {
      type string;
      description
        "Count of all labeled paths";
    }
    leaf labeled-backup-paths {
      type string;
      description
        "Count of labeled backup paths";
    }
  }

  grouping ncs_template_LDP-FWD-RW-PFX-LBL-SUMM {
    description
      "MPLS LDP forwarding rewrite prefix nexthops
       labeled summary";
    leaf labeled-pfxs {
      type string;
      description
        "Count of labeled prefixes with 1 or more paths
         labeled";
    }
    leaf labeled-pfxs-partial {
      type string;
      description
        "Count of labeled prefixes with some (but not
         ALL) paths labeled";
    }
    leaf unlabeled-pfxs {
      type string;
      description
        "Count of labeled prefixes with ALL paths
         unlabeled";
    }
  }

  grouping ncs_template_LDP-FWD-RW-PFX-SUMM {
    description
      "MPLS LDP fowarding rewrite prefix summary";
    container labeled-pfxs-aggr {
      description
        "Labeled prefix count for all paths";
      uses ncs_template_LDP-FWD-RW-PFX-LBL-SUMM;
    }
    container labeled-pfxs-primary {
      description
        "Labeled prefix count related to primary paths
         only";
      uses ncs_template_LDP-FWD-RW-PFX-LBL-SUMM;
    }
    container labeled-pfxs-backup {
      description
        "Labeled prefix count related to backup paths
         only";
      uses ncs_template_LDP-FWD-RW-PFX-LBL-SUMM;
    }
    leaf total-pfxs {
      type string;
      description
        "Total Prefix count";
    }
    leaf ecmp-pfxs {
      type string;
      description
        "Count of prefixes with ECMP";
    }
    leaf protected-pfxs {
      type string;
      description
        "Count of FRR protected prefixes";
    }
  }

  grouping ncs_template_LDP-FWD-RW-SUMM {
    description
      "MPLS LDP fowarding rewrite summary";
    container pfxs {
      description
        "Forwarding rewrites prefix summary";
      uses ncs_template_LDP-FWD-RW-PFX-SUMM;
    }
    container nhs {
      description
        "Forwarding rewrites nexthops (paths) summary";
      uses ncs_template_LDP-FWD-RW-PATH-SUMM;
    }
  }

  grouping ncs_template_LDP-FWD-SUMM-INFO {
    description
      "MPLS LDP fowarding summary";
    container vrf {
      description
        "VRF information";
      uses ncs_template_LDP-VRF-INFO;
    }
    container rws {
      description
        "Forwarding rewrites summary";
      uses ncs_template_LDP-FWD-RW-SUMM;
    }
    leaf is-lsd-bound {
      type string;
      description
        "LDP is connected to LSD server";
    }
    leaf fsht {
      type string;
      description
        "Forwarding state hold time registered with LSD";
    }
    leaf intfs {
      type string;
      description
        "MPLS forwarding enabled interface count";
    }
    leaf lbls {
      type string;
      description
        "Local label allocated count";
    }
  }

  grouping ncs_template_LDP-BINDING-ALLOC {
    description
      "MPLS LDP Binding local label allocation filter";
    leaf has-acl {
      type string;
      description
        "Has ACL filter?";
    }
    leaf prefix-acl {
      type string;
      description
        "Prefix ACL";
    }
    leaf is-host-route-only {
      type string;
      description
        "Host-routes only?";
    }
  }

  grouping ncs_template_LDP-BINDING-ADVT-ACL-PAIR {
    description
      "MPLS LDP Binding advertisement ACL pair";
    leaf prefix-acl {
      type string;
      description
        "Prefix ACL";
    }
    leaf peer-acl {
      type string;
      description
        "Peer ACL";
    }
  }

  grouping ncs_template_LDP-BINDING-ADVT-SPEC {
    description
      "MPLS LDP Binding advertisement specification ACLs";
    container allocation-acl {
      description
        "Local label Allocation filter";
      uses ncs_template_LDP-BINDING-ALLOC;
    }
    list advt-acl {
      // NCS patched for predictable order
      ordered-by user;
      description
        "Advertisement ACLs";
      uses ncs_template_LDP-BINDING-ADVT-ACL-PAIR;
    }
  }

  grouping ncs_template_LDP-FWD-PATH-RLFA-MOI-INFO {
    description
      "MPLS LDP Forwarding Path Remote LFA-FRR backup
       MPLS MOI info";
    list stack {
      // NCS patched for predictable order
      ordered-by user;
      description
        "Inner label stack info";
      uses ncs_template_LDP-FWD-PATH-MPLS-NH-INFO;
    }
  }

  grouping ncs_template_LDP-FWD-PATH-RLFA-MPLS-INFO {
    description
      "MPLS LDP Forwarding Path Remote LFA-FRR backup
       MPLS info";
    container mpls-outgoing-info {
      description
        "Remote LFA MPLS nexthop(s_ info";
      uses ncs_template_LDP-FWD-PATH-RLFA-MOI-INFO;
    }
    leaf has-remote-lfa-bkup {
      type string;
      description
        "Whether path has remote LFA backup";
    }
  }

  grouping ncs_template_LDP-FWD-PATH-MPLS-NH-INFO {
    description
      "Forwarding Path MPLS nexthop info";
    container nexthop-peer-ldp-ident {
      description
        "Nexthop LDP peer";
      uses ncs_template_LDP-LDPID-INFO;
    }
    leaf out-label {
      type string;
      description
        "Outgoing label";
    }
    leaf out-label-rsn {
      type ncs_template_Ldp-fwd-unlbl-rsn;
      description
        "Outgoing label reason";
    }
    leaf out-label-type {
      type ncs_template_Label-value;
      description
        "Outgoing Label Type";
    }
    leaf out-label-owner {
      type ncs_template_Ldp-route-path-lbl-owner;
      description
        "Outgoing label owner";
    }
    leaf is-from-graceful-restartable-neighbor {
      type string;
      description
        "Is from a GR neighbor";
    }
    leaf is-stale {
      type string;
      description
        "Is the entry stale";
    }
    leaf entropy-label-capability {
      type string;
      description
        "Entropy Label Capability";
    }
  }

  grouping ncs_template_LDP-FWD-PATH-MPLS-INFO {
    description
      "MPLS LDP Forwarding Path MPLS information";
    container mpls-outgoing-info {
      description
        "MPLS nexthop info";
      uses ncs_template_LDP-FWD-PATH-MPLS-NH-INFO;
    }
    container remote-lfa {
      description
        "Remote LFA-FRR backup info";
      uses ncs_template_LDP-FWD-PATH-RLFA-MPLS-INFO;
    }
  }

  grouping ncs_template_LDP-FWD-PATH-RLFA-ROUTING-INFO {
    description
      "MPLS LDP Forwarding Path Remote LFA-FRR backup
       routing info";
    container remote-p-node-id {
      description
        "Remote/P node address";
      uses ncs_template_LDP-IP-ADDR-T-UNION;
    }
    container remote-q-node-id {
      description
        "Remote/Q node address";
      uses ncs_template_LDP-IP-ADDR-T-UNION;
    }
    leaf has-remote-lfa-bkup {
      type string;
      description
        "Whether path has remote LFA backup";
    }
    leaf needs-tldp {
      type string;
      description
        "Whether TLDP is needed with remote PQ node";
    }
    leaf has-q-node {
      type string;
      description
        "Whether remote LFA path has a Q node associated";
    }
  }

  grouping ncs_template_LDP-FWD-PATH-ROUTING-INFO {
    description
      "MPLS LDP Forwarding Path IP Routing information";
    container next-hop {
      description
        "Next Hop";
      uses ncs_template_LDP-IP-ADDR-T-UNION;
    }
    container remote-lfa {
      description
        "Remote LFA-FRR backup info";
      uses ncs_template_LDP-FWD-PATH-RLFA-ROUTING-INFO;
    }
    leaf interface {
      type xr:ncs_template_Interface-name;
      description
        "Interface name";
    }
    leaf interface-name {
      type string;
      description
        "Interface Name";
    }
    leaf nh-is-overriden {
      type string;
      description
        "Nexthop is overriden by LDP";
    }
    leaf nexthop-id {
      type string;
      description
        "Nexthop Identifier";
    }
    leaf next-hop-table-id {
      type string;
      description
        "Table ID for nexthop address";
    }
    leaf flags {
      type string;
      description
        "Route path flags";
    }
    leaf load-metric {
      type string;
      description
        "Path's load metric for load balancing";
    }
    leaf binding-label {
      type string;
      description
        "Binding label obtained via RIB";
    }
    leaf path-id {
      type string;
      description
        "path Id";
    }
    leaf bkup-path-id {
      type string;
      description
        "Backup path Id";
    }
    leaf path-flags {
      type ncs_template_Ldp-route-path-flags;
      description
        "Routing path flags decoded";
    }
  }

  grouping ncs_template_LDP-FWD-PATH-INFO {
    description
      "MPLS LDP Forwarding Path info";
    container routing {
      description
        "IP routing information";
      uses ncs_template_LDP-FWD-PATH-ROUTING-INFO;
    }
    container mpls {
      description
        "MPLS information";
      uses ncs_template_LDP-FWD-PATH-MPLS-INFO;
    }
  }

  grouping ncs_template_LDP-FWD-ROUTE-MPLS-INFO {
    description
      "MPLS LDP Forwarding Route LDP information";
    leaf local-label {
      type string;
      description
        "Local label";
    }
    leaf forwarding-update-count {
      type string;
      description
        "Number of forwarding updates";
    }
    leaf forwarding-update-timestamp {
      type string;
      description
        "Last Forwarding update nanosec timestamp";
    }
    leaf forwarding-update-age {
      type string;
      description
        "Last Forwarding update nanosec age";
    }
  }

  grouping ncs_template_LDP-FWD-ROUTE-ROUTING-INFO {
    description
      "MPLS LDP Forwarding Route IP Routing information";
    leaf version {
      type string;
      description
        "Route RIB ersion";
    }
    leaf priority {
      type string;
      description
        "Route priority";
    }
    leaf source {
      type string;
      description
        "Route source protol Id";
    }
    leaf type {
      type string;
      description
        "Route type";
    }
    leaf flags {
      type string;
      description
        "Route RIB flags";
    }
    leaf metric {
      type string;
      description
        "Route metric";
    }
    leaf is-local-vrf-leaked {
      type string;
      description
        "Is route leaked across local VRFs?";
    }
    leaf routing-update-count {
      type string;
      description
        "Number of routing updates";
    }
    leaf routing-update-timestamp {
      type string;
      description
        "Last Routing update nanosec timestamp";
    }
    leaf routing-update-age {
      type string;
      description
        "Last Routing update nanosec age";
    }
    leaf sr-local-label {
      type string;
      description
        "SR Local-label";
    }
  }

  grouping ncs_template_LDP-FWD-ROUTE-INFO {
    description
      "MPLS LDP Forwarding Route information";
    container routing {
      description
        "IP routing information";
      uses ncs_template_LDP-FWD-ROUTE-ROUTING-INFO;
    }
    container mpls {
      description
        "MPLS information";
      uses ncs_template_LDP-FWD-ROUTE-MPLS-INFO;
    }
  }

  grouping ncs_template_LDP-FWD-PFX-INFO {
    description
      "MPLS LDP Forwarding Prefix Information";
    container vrf {
      description
        "VRF information";
      uses ncs_template_LDP-VRF-INFO;
    }
    container prefix-xr {
      description
        "IP Prefix";
      uses ncs_template_LDP-IP-ADDR-T-UNION;
    }
    container route {
      description
        "Route";
      uses ncs_template_LDP-FWD-ROUTE-INFO;
    }
    leaf table-id {
      type string;
      description
        "Table ID associated with IP prefix";
    }
    leaf prefix-length {
      type string;
      description
        "Prefix length";
    }
    list paths {
      // NCS patched for predictable order
      ordered-by user;
      description
        "Paths";
      uses ncs_template_LDP-FWD-PATH-INFO;
    }
  }

  grouping ncs_template_LDP-DISCOVERY-ADJ-GRP-INFO {
    description
      "MPLS LDP Discovery Adjacency Group Information";
    leaf adjacency-group-up-time {
      type string;
      units "second";
      description
        "Adjacency group up time in seconds";
    }
    leaf tcp-open-count {
      type string;
      description
        "Count of attempted TCP opens";
    }
    leaf tcp-arb-chg-count {
      type string;
      description
        "Count of changes in TCP arbitration";
    }
    leaf tcp-role {
      type string;
      description
        "TCP Role";
    }
  }

  grouping ncs_template_LDP-TARGETED-HELLO-BRIEF-INFO {
    description
      "MPLS LDP Discovery Targeted Brief Information";
    container vrf {
      description
        "VRF information";
      uses ncs_template_LDP-VRF-INFO;
    }
    container dhcb-target-address {
      description
        "DHCB target address";
      uses ncs_template_LDP-IP-ADDR-T-UNION;
    }
    leaf address-family {
      type ncs_template_Ldp-af;
      description
        "Targeted Discovery Address Family";
    }
    list hello-information {
      // NCS patched for predictable order
      ordered-by user;
      description
        "LDP hello info";
      uses ncs_template_LDP-HELLO-BRIEF-INFO;
    }
  }

  grouping ncs_template_LDP-HELLO-BRIEF-INFO {
    description
      "MPLS LDP Hello Brief Information";
    leaf neighbor-ldp-identifier {
      type string;
      description
        "Neighbor LDP Identifier";
    }
    leaf hold-time {
      type string;
      description
        "Session hold time in sec";
    }
    leaf session-up {
      type string;
      description
        "Is session up for this adj";
    }
  }

  grouping ncs_template_LDP-DISCOVERY-LINK-BRIEF-INFO {
    description
      "MPLS LDP Discovery Link Brief Information";
    container vrf {
      description
        "VRF information";
      uses ncs_template_LDP-VRF-INFO;
    }
    leaf address-family {
      type ncs_template_Ldp-af;
      description
        "Discovery Brief Address Family";
    }
    leaf address-family-set {
      type ncs_template_Ldp-af;
      description
        "Discovery Brief Address Family Set";
    }
    leaf interface {
      type xr:ncs_template_Interface-name;
      description
        "Interface name";
    }
    leaf interface-name-xr {
      type string;
      description
        "Interface name";
    }
    list hello-information {
      // NCS patched for predictable order
      ordered-by user;
      description
        "LDP hello info";
      uses ncs_template_LDP-HELLO-BRIEF-INFO;
    }
  }

  grouping ncs_template_LDP-TARGETED-HELLO-INFO {
    description
      "MPLS LDP Targeted Hello Information";
    container dhcb-local-address {
      description
        "DHCB local address";
      uses ncs_template_LDP-IP-ADDR-T-UNION;
    }
    container dhcb-target-address {
      description
        "DHCB target address";
      uses ncs_template_LDP-IP-ADDR-T-UNION;
    }
    leaf state {
      type ncs_template_Dhcb-state;
      description
        "Targeted hello state";
    }
    leaf adjacency-ldp-identifier {
      type string;
      description
        "Adjacency LDP Identifier";
    }
    leaf interval {
      type string;
      description
        "Hello interval in sec";
    }
    leaf next-hello {
      type string;
      description
        "Next hello due time in msec";
    }
    leaf hold-time {
      type string;
      description
        "Targeted hello hold time";
    }
    leaf local-hold-time {
      type string;
      description
        "Local hold time";
    }
    leaf neighbor-hold-time {
      type string;
      description
        "Neighbor hold time";
    }
    leaf disc-expiry {
      type string;
      description
        "Discovery expiry time in msec";
    }
    leaf quick-start-disabled {
      type string;
      description
        "Quick-start disabled";
    }
    leaf established-time {
      type string;
      description
        "Hello adjacency estabished time in nanosec";
    }
    leaf established-age {
      type string;
      description
        "Hello adjacency estabished age in nanosec";
    }
    leaf session-up {
      type string;
      description
        "Is session up for this adj";
    }
    leaf session-bringup-failure-reason {
      type string;
      description
        "session bringup failure reason";
    }
    list last-session-down-info {
      // NCS patched for predictable order
      ordered-by user;
      description
        "Last session down information";
      uses ncs_template_LDP-LAST-SESS-INFO;
    }
  }

  grouping ncs_template_LDP-DISCOVERY-SUMMARY-INFO {
    description
      "MPLS LDP Discovery Summary Information";
    container vrf {
      description
        "VRF information";
      uses ncs_template_LDP-VRF-INFO;
    }
    leaf local-ldp-id {
      type string;
      description
        "Local LDP identifier";
    }
    leaf num-of-ldp-interfaces {
      type string;
      description
        "Total Number of LDP configured interfaces";
    }
    leaf num-of-active-ldp-interfaces {
      type string;
      description
        "Number of active LDP enabled interfaces";
    }
    leaf num-of-lnk-disc-xmit {
      type string;
      description
        "Number of link hello discoveries in xmit state";
    }
    leaf num-of-tgt-disc-xmit {
      type string;
      description
        "Number of targeted hello discoveries in xmit
         state";
    }
    leaf num-of-lnk-disc-recv {
      type string;
      description
        "Number of link hello discoveries in recv state";
    }
    leaf num-of-tgt-disc-recv {
      type string;
      description
        "Number of targeted hello discoveries in recv
         state";
    }
    leaf num-of-disc-with-bad-addr-recv {
      type string;
      description
        "Number of hello discoveries received with bad
         source address";
    }
    leaf num-of-disc-with-bad-hello-pdu {
      type string;
      description
        "Number of hello discoveries received with bad
         hello PDU";
    }
    leaf num-of-disc-with-bad-xport-addr {
      type string;
      description
        "Number of hello discoveries received with bad
         export address";
    }
    leaf num-of-disc-with-same-router-id {
      type string;
      description
        "Number of hello discoveries received with the
         same router id as this router";
    }
    leaf num-of-disc-with-wrong-router-id {
      type string;
      description
        "Number of hello discoveries received with the
         router id that is not destined for this router";
    }
  }

  grouping ncs_template_LDP-DISCOVERY-LINK-AF-INFO {
    description
      "MPLS LDP Discovery Link Address Family
       Information";
    container local-src-address {
      description
        "Local source address";
      uses ncs_template_LDP-IP-ADDR-T-UNION;
    }
    container local-transport-address {
      description
        "Local transport address";
      uses ncs_template_LDP-IP-ADDR-T-UNION;
    }
    leaf interval {
      type string;
      description
        "Hello interval in sec";
    }
  }

  grouping ncs_template_LDP-LAST-SESS-INFO {
    description
      "LDP last down session information";
    leaf last-session-down-reason {
      type string;
      description
        "The reason of last socket failure";
    }
    leaf last-session-down-time {
      type string;
      description
        "Timestamp of when the last session went down";
    }
    leaf last-session-up-time {
      type string;
      description
        "The time duration the last session was up";
    }
  }

  grouping ncs_template_LDP-HELLO-INFO {
    description
      "MPLS LDP Hello Information";
    container neighbor-src-address {
      description
        "Neighbor source address";
      uses ncs_template_LDP-IP-ADDR-T-UNION;
    }
    container neighbor-transport-address {
      description
        "Neighbor transport address";
      uses ncs_template_LDP-IP-ADDR-T-UNION;
    }
    container target {
      description
        "Target address";
      uses ncs_template_LDP-IP-ADDR-T-UNION;
    }
    leaf neighbor-ldp-identifier {
      type string;
      description
        "Neighbor LDP Identifier";
    }
    leaf is-no-route {
      type string;
      description
        "Is route valid";
    }
    leaf hold-time {
      type string;
      units "second";
      description
        "Session hold time in seconds";
    }
    leaf local-hold-time {
      type string;
      units "second";
      description
        "Local hold time in seconds";
    }
    leaf neighbor-hold-time {
      type string;
      units "second";
      description
        "Neighbor hold time in seconds";
    }
    leaf disc-expiry {
      type string;
      description
        "Discovery expiry time in sec";
    }
    leaf is-targeted {
      type string;
      description
        "Is session a targeted session";
    }
    leaf session-up {
      type string;
      description
        "Is session up for this adj";
    }
    leaf established-time {
      type string;
      description
        "Hello adjacency estabished time in nanosec";
    }
    leaf established-age {
      type string;
      description
        "Hello adjacency estabished age in nanosec";
    }
    leaf session-bringup-failure-reason {
      type string;
      description
        "session bringup failure reason";
    }
    list last-session-down-info {
      // NCS patched for predictable order
      ordered-by user;
      description
        "Last session down information";
      uses ncs_template_LDP-LAST-SESS-INFO;
    }
  }

  grouping ncs_template_LDP-DISCOVERY-LINK-INFO {
    description
      "MPLS LDP Discovery Link Information";
    container vrf {
      description
        "VRF information";
      uses ncs_template_LDP-VRF-INFO;
    }
    leaf next-hello {
      type string;
      description
        "Next hello due time in msec";
    }
    leaf interface {
      type xr:ncs_template_Interface-name;
      description
        "Interface name";
    }
    leaf interface-name-xr {
      type string;
      description
        "Interface name";
    }
    leaf quick-start-disabled {
      type string;
      description
        "Quick-start disabled";
    }
    list hello-information {
      // NCS patched for predictable order
      ordered-by user;
      description
        "LDP hello info";
      uses ncs_template_LDP-HELLO-INFO;
    }
    list discovery-link-af {
      // NCS patched for predictable order
      ordered-by user;
      // NCS drop max-elements statement
      description
        "LDP hello AF info";
      uses ncs_template_LDP-DISCOVERY-LINK-AF-INFO;
    }
  }

  grouping ncs_template_LDP-INTF-AUTOCFG {
    description
      "MPLS LDP auto configure";
    leaf tuple {
      type string;
      description
        "Tuple";
    }
  }

  grouping ncs_template_LDP-INTF-TE-MESH-GRP {
    description
      "MPLS LDP interface tunnel mesh group";
    leaf ldp-te-mesh-group-all-cfgd {
      type string;
      description
        "LDP has enabled all TE mesh-groups";
    }
    leaf ldp-mesh-group-enabled {
      type string;
      description
        "LDP has enabled this TE mesh-group";
    }
    leaf te-mesh-group-id {
      type string;
      description
        "TE tunnel Mesh Group ID";
    }
  }

  grouping ncs_template_LDP-INTF {
    description
      "MPLS LDP interface information";
    container vrf {
      description
        "VRF information";
      uses ncs_template_LDP-VRF-INFO;
    }
    leaf interface {
      type xr:ncs_template_Interface-name;
      description
        "Interface name";
    }
    leaf interface-name-xr {
      type string;
      description
        "Interface name";
    }
    leaf ldp-enabled {
      type string;
      description
        "LDP enabled";
    }
    leaf is-im-stale {
      type string;
      description
        "Is IM information stale";
    }
    leaf ldp-config-mode {
      type string;
      description
        "LDP config mode";
    }
    leaf ldp-autoconfig-disable {
      type string;
      description
        "LDP autoconfig disable";
    }
    list te-mesh-grp {
      // NCS patched for predictable order
      ordered-by user;
      description
        "TE tunnel mesh-group";
      uses ncs_template_LDP-INTF-TE-MESH-GRP;
    }
    list auto-config {
      // NCS patched for predictable order
      ordered-by user;
      description
        "Auto config";
      uses ncs_template_LDP-INTF-AUTOCFG;
    }
  }

  grouping ncs_template_LDP-BINDING-SUMMARY-AF {
    description
      "MPLS LDP Binding Summary AF Information";
    leaf address-family {
      type ncs_template_Ldp-af;
      description
        "Binding Summary Address Family";
    }
    leaf last-lib-update {
      type string;
      description
        "Last update to LIB local binding";
    }
    leaf lib-minimum-revision-sent-all {
      type string;
      description
        "Last update sent to all peers";
    }
    leaf binding-total {
      type string;
      description
        "Total bindings";
    }
    leaf binding-local {
      type string;
      description
        "Number of local bindings";
    }
    leaf binding-remote {
      type string;
      description
        "Number of remote bindings";
    }
  }

  grouping ncs_template_LDP-BINDING-SUMMARY {
    description
      "MPLS LDP Binding Summary Information";
    container vrf {
      description
        "VRF information";
      uses ncs_template_LDP-VRF-INFO;
    }
    leaf address-family {
      type ncs_template_Ldp-af;
      description
        "Address Family";
    }
    leaf binding-no-route {
      type string;
      description
        "Bindings with no route";
    }
    leaf binding-local-no-route {
      type string;
      description
        "Local bindings with no route";
    }
    leaf binding-local-null {
      type string;
      description
        "Number of local null bindings";
    }
    leaf binding-local-implicit-null {
      type string;
      description
        "Number of local implicit null bindings";
    }
    leaf binding-local-explicit-null {
      type string;
      description
        "Number of local explicit null bindings";
    }
    leaf binding-local-non-null {
      type string;
      description
        "Number of local non-null bindings";
    }
    leaf binding-local-oor {
      type string;
      description
        "Number of local bindings        needing label -
         OOR";
    }
    leaf lowest-allocated-label {
      type string;
      description
        "Lowest allocated label";
    }
    leaf highest-allocated-label {
      type string;
      description
        "Highest allocated label";
    }
    list bind-af {
      // NCS patched for predictable order
      ordered-by user;
      // NCS drop max-elements statement
      description
        "bind af";
      uses ncs_template_LDP-BINDING-SUMMARY-AF;
    }
  }

  grouping ncs_template_LDP-IGP-SYNC-DELAY-RESTART-INFO {
    description
      "MPLS LDP IGP Sync Restart Delay Information";
    leaf configured {
      type string;
      description
        "Is restart delay configured";
    }
    leaf delay-secs {
      type string;
      description
        "Delay time";
    }
    leaf timer-running {
      type string;
      description
        "Is restart delay timer running";
    }
    leaf remaining-secs {
      type string;
      description
        "Delay timer remaining time";
    }
  }

  grouping ncs_template_LDP-IGP-SYNC-INTF-GR-ONLY {
    description
      "MPLS LDP IGP Sync Interface GR-only reachable
       Peer Information";
    leaf peer-id {
      type ncs_template_String-td2;
      description
        "Peer Identifier";
    }
    leaf is-chkpt-created {
      type string;
      description
        "Is created due to checkpointing";
    }
  }

  grouping ncs_template_LDP-IGP-SYNC-INTF-PEER {
    description
      "MPLS LDP IGP Sync Interface Peer Information";
    leaf peer-id {
      type ncs_template_String-td2;
      description
        "Peer Identifier";
    }
    leaf is-gr-enabled {
      type string;
      description
        "Is GR enabled session";
    }
  }

  grouping ncs_template_LDP-IGP-SYNC-INFO {
    description
      "MPLS LDP IGP Sync Information";
    container vrf {
      description
        "VRF information";
      uses ncs_template_LDP-VRF-INFO;
    }
    leaf interface-name-xr {
      type string;
      description
        "Interface name";
    }
    leaf igp-sync-state {
      type ncs_template_Ldp-igp-sync-state;
      description
        "IGP Sync state";
    }
    leaf igp-sync-delay {
      type string;
      units "second";
      description
        "IGP sync delay in seconds";
    }
    leaf is-delay-timer-running {
      type string;
      description
        "Is sync delay timer running";
    }
    leaf delay-timer-remaining {
      type string;
      units "second";
      description
        "Remaining timer (seconds) till expiry of sync
         delay timer";
    }
    leaf igp-sync-down-reason {
      type ncs_template_Ldp-igp-sync-down-reason;
      description
        "Reason IGP Sync Not Achieved";
    }
    list peers {
      // NCS patched for predictable order
      ordered-by user;
      description
        "Interface Peers";
      uses ncs_template_LDP-IGP-SYNC-INTF-PEER;
    }
    list gr-only-peer {
      // NCS patched for predictable order
      ordered-by user;
      description
        "Interface GR-only reachable peers";
      uses ncs_template_LDP-IGP-SYNC-INTF-GR-ONLY;
    }
  }

  grouping ncs_template_LDP-TIB-ENTRY-REMOTE {
    description
      "MPLS LDP Remote Binding Information";
    container assigning-peer-ldp-ident {
      description
        "Assigning peer";
      uses ncs_template_LDP-LDPID-INFO;
    }
    leaf remote-label {
      type string;
      description
        "Remote Label";
    }
    leaf is-stale {
      type string;
      description
        "Is the entry stale";
    }
    leaf is-elc {
      type string;
      description
        "Is the entry entropy label capable";
    }
  }

  grouping ncs_template_LDP-TIB-ENTRY-DETAIL {
    description
      "MPLS LDP Binding Detail Information";
    container vrf {
      description
        "VRF information";
      uses ncs_template_LDP-VRF-INFO;
    }
    container prefix-xr {
      description
        "IP Prefix";
      uses ncs_template_LDP-IP-ADDR-T-UNION;
    }
    leaf prefix-length {
      type string;
      description
        "Prefix Length";
    }
    leaf local-label {
      type string;
      description
        "Local label";
    }
    leaf le-local-binding-revision {
      type string;
      description
        "Local Binding revision";
    }
    leaf le-local-label-state {
      type ncs_template_Local-label-state;
      description
        "Local label state";
    }
    leaf is-no-route {
      type string;
      description
        "No route";
    }
    leaf label-oor {
      type string;
      description
        "Label space depletion OOR";
    }
    leaf advertise-prefix-acl {
      type string;
      description
        "Advertise Prerfix ACL";
    }
    leaf advertise-tsr-acl {
      type string;
      description
        "Advertise TSR ACL";
    }
    leaf config-enforced-local-label-value {
      type string;
      description
        "Config/User enforced local label value";
    }
    leaf is-elc {
      type string;
      description
        "Is the entry entropy label capable";
    }
    list remote-binding {
      // NCS patched for predictable order
      ordered-by user;
      description
        "Remote binding";
      uses ncs_template_LDP-TIB-ENTRY-REMOTE;
    }
    list peers-advertised-to {
      // NCS patched for predictable order
      ordered-by user;
      description
        "Peers this entry is advertised to";
      uses ncs_template_LDP-LDPID-INFO;
    }
    list peers-acked {
      // NCS patched for predictable order
      ordered-by user;
      description
        "Peers that have ACKed this entry";
      uses ncs_template_LDP-LDPID-INFO;
    }
  }

  grouping ncs_template_LDP-INTF-SUM {
    description
      "MPLS LDP interface summary";
    leaf known-ip-interface-count {
      type string;
      description
        "Number of known IP Interfaces";
    }
    leaf known-ip-interface-ldp-enabled {
      type string;
      description
        "Number of known IP Interfaces with LDP Enabled";
    }
    leaf ldp-configured-attached-interface {
      type string;
      description
        "Number of attached interfaces configured in LDP";
    }
    leaf ldp-configured-te-interface {
      type string;
      description
        "Number of TE tunnel interfaces configured in LDP";
    }
    leaf forward-references {
      type string;
      description
        "Number of forward referenced interfaces";
    }
    leaf auto-config-disabled {
      type string;
      description
        "Autoconfigure disabled";
    }
    leaf auto-config {
      type string;
      description
        "Auto-configured interfaces";
    }
    leaf auto-config-forward-reference-interfaces {
      type string;
      description
        "Auto-configured forward references";
    }
  }

  grouping ncs_template_LDP-SUMMARY-COMMON {
    description
      "MPLS LDP common summary Information";
    leaf address-families {
      type ncs_template_Ldp-af;
      description
        "Address Families enabled";
    }
    leaf number-of-ipv4af {
      type string;
      description
        "Number of IPv4 address-families enabled";
    }
    leaf number-of-ipv6af {
      type string;
      description
        "Number of IPv6 address-families enabled";
    }
    leaf number-of-neighbors {
      type string;
      description
        "Number of neighbors";
    }
    leaf number-of-adj-grps {
      type string;
      description
        "Number of Adjacency Groups";
    }
    leaf number-of-nsr-synced-neighbors {
      type string;
      description
        "Number of NSR-synced/operational neighbors";
    }
    leaf number-of-graceful-restart-neighbors {
      type string;
      description
        "Number of Graceful Restart neighbors";
    }
    leaf number-of-downstream-on-demand-neighbors {
      type string;
      description
        "Number of Downstream-On-Demand neighbors";
    }
    leaf number-of-ipv4-hello-adj {
      type string;
      description
        "Number of LDP discovery IPv4 hello adjacencies";
    }
    leaf number-of-ipv6-hello-adj {
      type string;
      description
        "Number of LDP discovery IPv6 hello adjacencies";
    }
    leaf number-of-ipv4-routes {
      type string;
      description
        "Number of resolved IPv4 routes";
    }
    leaf number-of-ipv6-routes {
      type string;
      description
        "Number of resolved IPv6 routes";
    }
    leaf number-of-ipv4-local-addresses {
      type string;
      description
        "Number of IPv4 local addresses";
    }
    leaf number-of-ipv6-local-addresses {
      type string;
      description
        "Number of IPv6 local addresses";
    }
    leaf number-of-ldp-interfaces {
      type string;
      description
        "Number of LDP configured interfaces";
    }
    leaf number-of-ipv4ldp-interfaces {
      type string;
      description
        "Number of LDP IPv4 configured interfaces";
    }
    leaf number-of-ipv6ldp-interfaces {
      type string;
      description
        "Number of LDP IPv6 configured interfaces";
    }
    leaf number-of-bindings-ipv4 {
      type string;
      description
        "Total number of ipv4 bindings";
    }
    leaf number-of-bindings-ipv6 {
      type string;
      description
        "Total number of ipv6 bindings";
    }
    leaf number-of-local-bindings-ipv4 {
      type string;
      description
        "Total number of ipv4 local label bindings";
    }
    leaf number-of-local-bindings-ipv6 {
      type string;
      description
        "Total number of ipv6 local label bindings";
    }
    leaf number-of-remote-bindings-ipv4 {
      type string;
      description
        "Total number of ipv4 remote label bindings";
    }
    leaf number-of-remote-bindings-ipv6 {
      type string;
      description
        "Total number of ipv6 remote label bindings";
    }
  }

  grouping ncs_template_LDP-SUMMARY-VRF {
    description
      "MPLS LDP per VRF summarized Information";
    container vrf {
      description
        "VRF information";
      uses ncs_template_LDP-VRF-INFO;
    }
    container common {
      description
        "Common Summary information";
      uses ncs_template_LDP-SUMMARY-COMMON;
    }
  }

  grouping ncs_template_LDP-CAP-DESC {
    description
      "MPLS LDP Capability Description";
    leaf type {
      type string;
      description
        "Capability type (IANA assigned)";
    }
    leaf description {
      type string;
      description
        "Capability description";
    }
    leaf capability-data-length {
      type string;
      description
        "Capability data length";
    }
    leaf capability-data {
      type string;
      description
        "Capability data";
    }
  }

  grouping ncs_template_LDP-CAP-INFO {
    description
      "MPLS LDP Capability Information";
    container capability {
      description
        "Capability information";
      uses ncs_template_LDP-CAP-DESC;
    }
    leaf capability-owner {
      type string;
      description
        "Capability owner";
    }
  }

  grouping ncs_template_LDP-IP-ADDR-T-UNION {
    description
      "LDP IP ADDR T UNION";
    leaf afi {
      type ncs_template_Ldp-af-id;
      description
        "AFI";
    }
    leaf dummy {
      // NCS drop when statement
      type string;
      description
        "No Address";
    }
    leaf ipv4 {
      // NCS drop when statement
      type ncs_template_Ldp-in-addr;
      description
        "IPv4 address type";
    }
    leaf ipv6 {
      // NCS drop when statement
      type ncs_template_Ldp-in6-addr;
      description
        "IPv6 address type";
    }
  }

  grouping ncs_template_LDP-GR-DNBR-INTF-INFO {
    description
      "MPLS LDP GR DownNbr Interface Info";
    leaf address-family {
      type ncs_template_Ldp-af-id;
      description
        "Interface adj Address Family";
    }
    leaf interface-handle {
      type xr:ncs_template_Interface-name;
      description
        "Interfaces handle";
    }
  }

  grouping ncs_template_LDP-LDPID-INFO {
    description
      "MPLS LDP Identifier Information";
    leaf lsr-id {
      type string;
      description
        "LSR identifier";
    }
    leaf label-space-id {
      type string;
      description
        "Label space identifier";
    }
    leaf ldp-id {
      type string;
      description
        "LDP identifier";
    }
  }

  grouping ncs_template_LDP-GR-NBR-INFO {
    description
      "MPLS LDP Graceful Restart Neighbor Information";
    container gr-peer {
      description
        "GR peer LDP Id";
      uses ncs_template_LDP-LDPID-INFO;
    }
    leaf connect-count {
      type string;
      description
        "ConnectCount";
    }
    leaf is-neighbor-up {
      type string;
      description
        "Is neighbor up";
    }
    leaf is-liveness-timer-running {
      type string;
      description
        "Is liveness timer running";
    }
    leaf liveness-timer-remaining-seconds {
      type string;
      description
        "Remaining time from liveness timer";
    }
    leaf is-recovery-timer-running {
      type string;
      description
        "Is recovery timer running";
    }
    leaf recovery-timer-remaining-seconds {
      type string;
      description
        "Recovery timer remining time";
    }
    leaf down-nbr-flap-count {
      type string;
      description
        "Count of back2back flaps";
    }
    leaf down-nbr-flags {
      type string;
      description
        "Flags";
    }
    leaf down-nbr-down-reason {
      type string;
      description
        "Session down reason code";
    }
    list down-nbr-interface {
      // NCS patched for predictable order
      ordered-by user;
      description
        "Interfaces bound to GR down Nbr";
      uses ncs_template_LDP-GR-DNBR-INTF-INFO;
    }
    list down-nbr-address {
      // NCS patched for predictable order
      ordered-by user;
      description
        "Addresses bound to GR down Nbr";
      uses ncs_template_LDP-IP-ADDR-T-UNION;
    }
  }

  grouping ncs_template_LDP-VRF-INFO {
    description
      "MPLS LDP VRF information";
    leaf name {
      type string;
      description
        "VRF Name";
    }
    leaf id {
      type string;
      description
        "VRF Id";
    }
  }

  grouping ncs_template_LDP-GR-GLOBAL-INFO {
    description
      "MPLS LDP Graceful Restart Information";
    container vrf {
      description
        "VRF information";
      uses ncs_template_LDP-VRF-INFO;
    }
    leaf is-forwarding-state-hold-timer-running {
      type string;
      description
        "Is graceful restart forwarding state hold timer
         running";
    }
    leaf forwarding-state-hold-timer-remaining-seconds {
      type string;
      units "second";
      description
        "Forwarding state hold timer remaining time in
         seconds";
    }
    list graceful-restartable-neighbor {
      // NCS patched for predictable order
      ordered-by user;
      description
        "Vector of graceful restart neighbor information";
      uses ncs_template_LDP-GR-NBR-INFO;
    }
  }

  grouping ncs_rpc_notif_LDP-SUMMARY {
    description
      "MPLS LDP Summarized Information";
    container common {
      description
        "Common Summary information";
      uses ncs_rpc_notif_LDP-SUMMARY-COMMON;
    }
    leaf number-of-vrf {
      type uint32;
      description
        "Number of configured VRFs (including default)";
    }
    leaf number-of-vrf-oper {
      type uint32;
      description
        "Number of configured operational VRFs (including
         default)";
    }
    leaf number-of-interfaces {
      type uint32;
      description
        "Number of known interfaces";
    }
    leaf number-of-fwd-ref-interfaces {
      type uint32;
      description
        "Number of Forward Referenc interfaces";
    }
    leaf number-of-autocfg-interfaces {
      type uint32;
      description
        "Number of auto-configured interfaces";
    }
    leaf is-bound-with-sysdb {
      type boolean;
      description
        "Bound status with sysdb";
    }
    leaf is-registered-with-sysdb {
      type boolean;
      description
        "Registration status with Sysdb";
    }
    leaf is-bound-with-rsi {
      type boolean;
      description
        "Bound status with rsi";
    }
    leaf is-bound-with-interface-manager {
      type boolean;
      description
        "Bound status with Interface Manager";
    }
    leaf is-registered-with-interface-manager {
      type boolean;
      description
        "Registration status with Interface Manager";
    }
    leaf is-bound-with-ip-arm {
      type boolean;
      description
        "Bound status with IP Arm";
    }
    leaf is-bound-with-lsd {
      type boolean;
      description
        "Bound status with LSD";
    }
    leaf is-registered-with-lsd {
      type boolean;
      description
        "Registration status with LSD";
    }
    leaf is-bound-with-ipv4-rib {
      type boolean;
      description
        "Bound status with IPv4 RIB";
    }
    leaf is-registered-with-ipv4-rib {
      type boolean;
      description
        "Registration status with IPv4 RIB";
    }
    leaf number-of-ipv4rib-tables {
      type uint32;
      description
        "Total number of ipv4 RIB tables";
    }
    leaf number-of-registered-ipv4rib-tables {
      type uint32;
      description
        "Number of ipv4 RIB tables registered";
    }
    leaf is-bound-with-ipv6-rib {
      type boolean;
      description
        "Bound status with IPv6 RIB";
    }
    leaf is-registered-with-ipv6-rib {
      type boolean;
      description
        "Registration status with IPv6 RIB";
    }
    leaf number-of-ipv6rib-tables {
      type uint32;
      description
        "Total number of ipv6 RIB tables";
    }
    leaf number-of-registered-ipv6rib-tables {
      type uint32;
      description
        "Number of ipv6 RIB tables registered";
    }
    leaf is-bound-with-atom {
      type boolean;
      description
        "Bound status with L2VPN ATOM";
    }
    leaf is-bound-with-nsr-mate {
      type boolean;
      description
        "Bound status with NSR Mate";
    }
    leaf is-nsr-configured {
      type boolean;
      description
        "NSR configured";
    }
    leaf is-mldp-registered {
      type boolean;
      description
        "mLDP registration status";
    }
  }

  grouping ncs_rpc_notif_LDP-MSG-COUNTERS {
    description
      "MPLS LDP Session Message Counters Information";
    leaf total-count {
      type uint32;
      description
        "Total message count";
    }
    leaf init-count {
      type uint32;
      description
        "Init message count";
    }
    leaf address-count {
      type uint32;
      description
        "Address message count";
    }
    leaf address-withdraw-count {
      type uint32;
      description
        "Address withdraw count";
    }
    leaf label-map-count {
      type uint32;
      description
        "Label map count";
    }
    leaf label-withdraw-count {
      type uint32;
      description
        "Label withdraw count";
    }
    leaf label-release-count {
      type uint32;
      description
        "Label release count";
    }
    leaf label-request-count {
      type uint32;
      description
        "Label request count";
    }
    leaf label-abort-request-count {
      type uint32;
      description
        "Label abort request count";
    }
    leaf notification-count {
      type uint32;
      description
        "Notification count";
    }
    leaf keep-alive-count {
      type uint32;
      description
        "Keepalive count";
    }
    leaf iccp-rg-conn-count {
      type uint32;
      description
        "ICCP RG Connect count";
    }
    leaf iccp-rg-disconn-count {
      type uint32;
      description
        "ICCP RG Disconnect count";
    }
    leaf iccp-rg-notif-count {
      type uint32;
      description
        "ICCP RG Notif count";
    }
    leaf iccp-rg-app-data-count {
      type uint32;
      description
        "ICCP RG App Data count";
    }
  }

  grouping ncs_rpc_notif_LDP-STATS-INFO {
    description
      "MPLS LDP Statistics Information";
    container message-out {
      description
        "Message out count";
      uses ncs_rpc_notif_LDP-MSG-COUNTERS;
    }
    container message-in {
      description
        "Message in count";
      uses ncs_rpc_notif_LDP-MSG-COUNTERS;
    }
    leaf iccp-enabled {
      type boolean;
      description
        "Is session ICCP enabled?";
    }
  }

  grouping ncs_rpc_notif_LDP-NBR-CLIENTS-INFO {
    description
      "MPLS LDP Session client Information";
    leaf name {
      type string;
      description
        "Client's name";
    }
  }

  grouping ncs_rpc_notif_LDP-NBR-DETAILED-INFO {
    description
      "MPLS LDP Neighbor Detailed Information";
    container capabilities {
      description
        "Capabilities sent to and received from neighbor";
      uses ncs_rpc_notif_LDP-NBR-CAP-INFO;
    }
    leaf peer-holdtime {
      type uint32;
      units "second";
      description
        "Session holdtime value in seconds from the peer";
    }
    leaf keep-alive-interval {
      type uint32;
      units "second";
      description
        "Session keepalive interval in seconds";
    }
    leaf peer-state {
      type string {
        length "0..80";
      }
      description
        "Peer state";
    }
    leaf has-ipv4-inbound {
      type boolean;
      description
        "IPv4 Inbound label filtering present";
    }
    leaf inbound-ipv4acl {
      type string {
        length "0..80";
      }
      description
        "IPv4 Inbound accept ACL";
    }
    leaf has-ipv6-inbound {
      type boolean;
      description
        "IPv6 Inbound label filtering present";
    }
    leaf inbound-ipv6acl {
      type string {
        length "0..80";
      }
      description
        "IPv6 Inbound accept ACL";
    }
    leaf has-ipv4-outbound {
      type boolean;
      description
        "IPv4 Outbound label filtering present";
    }
    leaf outbound-ipv4acl {
      type string {
        length "0..80";
      }
      description
        "IPv4 Outbound advertise ACL";
    }
    leaf has-ipv6-outbound {
      type boolean;
      description
        "IPv6 Outbound label filtering present";
    }
    leaf outbound-ipv6acl {
      type string {
        length "0..80";
      }
      description
        "IPv6 Outbound advertise ACL";
    }
    leaf has-sp {
      type boolean;
      description
        "Session Protection enabled";
    }
    leaf sp-state {
      type string {
        length "0..80";
      }
      description
        "Session Protection state";
    }
    leaf sp-has-acl {
      type boolean;
      description
        "Session protection ACL is present";
    }
    leaf spacl {
      type string {
        length "0..80";
      }
      description
        "Session Protection ACL";
    }
    leaf sp-has-duration {
      type boolean;
      description
        "Session Protection has non-default duration";
    }
    leaf sp-duration {
      type uint32;
      units "second";
      description
        "Session protection holdup time duration in
         seconds";
    }
    leaf spht-running {
      type boolean;
      description
        "Session Protection holdup timer is running";
    }
    leaf spht-remaining {
      type uint32;
      units "second";
      description
        "Session Protection holdup time remaining value
         in seconds";
    }
    leaf nsr-sync-state {
      type ncs_rpc_notif_Mgmt-ldp-nsr-peer-sync-state;
      description
        "NSR Sync State";
    }
    leaf nsr-last-sync-error {
      type ncs_rpc_notif_Mgmt-ldp-nsr-peer-sync-err;
      description
        "Last NSR sync error";
    }
    leaf nsr-last-sync-nack-reason {
      type ncs_rpc_notif_Mgmt-ldp-nsr-peer-ldp-sync-nack-rsn;
      description
        "Last NSR sync NACK reaston";
    }
    leaf bgp-advertisement-state {
      type ncs_rpc_notif_Mgmt-ldp-nbr-bgp-advt-state;
      description
        "BGP labelled prefixes advertisement state";
    }
    leaf advertise-bgp-prefixes {
      type boolean;
      description
        "Is BGP labelled prefixes advertised to the
         neighbor";
    }
    list client {
      description
        "Targeted Session clients";
      uses ncs_rpc_notif_LDP-NBR-CLIENTS-INFO;
    }
    list ipv4-duplicate-address {
      description
        "Duplicate IPv4 address bound to this peer";
      uses ncs_rpc_notif_LDP-NBR-ADDR-INFO;
    }
    list ipv6-duplicate-address {
      description
        "Duplicate IPv6 address bound to this peer";
      uses ncs_rpc_notif_LDP-NBR-ADDR-INFO;
    }
  }

  grouping ncs_rpc_notif_TARGETED-HELLO {
    description
      "MPLS LDP Targeted Hello Information";
    container local-address {
      description
        "Local Address";
      uses ncs_rpc_notif_LDP-IP-ADDR-T-UNION;
    }
    container target-address {
      description
        "Target Address";
      uses ncs_rpc_notif_LDP-IP-ADDR-T-UNION;
    }
    leaf state {
      type ncs_rpc_notif_Dhcb-state;
      description
        "State";
    }
  }

  grouping ncs_rpc_notif_LINK-HELLO {
    description
      "MPLS LDP Link Hello Information";
    leaf interface {
      type xr:ncs_rpc_notif_Interface-name;
      description
        "Interface name";
    }
    leaf interface-name {
      type string;
      description
        "Interface name";
    }
  }

  grouping ncs_rpc_notif_LDP-ADJ-UNION {
    description
      "LDP ADJ UNION";
    container link-hello-data {
      when "../hello-type = 'link-hello'" {
        tailf:xpath-root 3;
        description
          "../HelloType = 'LinkHello'";
      }
      description
        "Link hello";
      uses ncs_rpc_notif_LINK-HELLO;
    }
    container target-hello-data {
      when "../hello-type = 'targeted-hello'" {
        tailf:xpath-root 3;
        description
          "../HelloType = 'TargetedHello'";
      }
      description
        "Target Hello";
      uses ncs_rpc_notif_TARGETED-HELLO;
    }
    leaf hello-type {
      type ncs_rpc_notif_Ldp-adj-union-discrim;
      description
        "HelloType";
    }
  }

  grouping ncs_rpc_notif_LDP-NBR-ADJ-INFO {
    description
      "MPLS LDP Neighbor Adjacency Information";
    container adjacency-group {
      description
        "Adjacency group";
      uses ncs_rpc_notif_LDP-ADJ-UNION;
    }
  }

  grouping ncs_rpc_notif_LDP-NBR-ADDR-INFO {
    description
      "MPLS LDP Neighbor Bound Address Information";
    container address {
      description
        "Neighbor Address";
      uses ncs_rpc_notif_LDP-IP-ADDR-T-UNION;
    }
  }

  grouping ncs_rpc_notif_LDP-TCP-INFO {
    description
      "MPLS LDP Neighbor TCP Information";
    container foreign-host {
      description
        "Foreign host address";
      uses ncs_rpc_notif_LDP-IP-ADDR-T-UNION;
    }
    container local-host {
      description
        "Local host address";
      uses ncs_rpc_notif_LDP-IP-ADDR-T-UNION;
    }
    leaf foreign-port {
      type uint16;
      description
        "Foreign port number";
    }
    leaf local-port {
      type uint16;
      description
        "Local port number";
    }
    leaf is-md5-on {
      type boolean;
      description
        "Is MD5 Digest on";
    }
  }

  grouping ncs_rpc_notif_LDP-GR-ADJ-INFO {
    description
      "MPLS LDP Neighbor Graceful Restart Adjacency
       Information";
    leaf is-graceful-restartable {
      type boolean;
      description
        "Is graceful restartable";
    }
    leaf reconnect-timeout {
      type uint32;
      description
        "Reconnect timeout";
    }
    leaf recovery-time {
      type uint32;
      description
        "Recovery time";
    }
  }

  grouping ncs_rpc_notif_LDP-PTCL-ADJ-INFO {
    description
      "MPLS LDP PTCL Adjacency Information";
    container ta-graceful-restart-adjacency {
      description
        "Graceful restart information";
      uses ncs_rpc_notif_LDP-GR-ADJ-INFO;
    }
    leaf ta-holdtime {
      type uint32;
      description
        "Session holdtime in sec";
    }
    leaf ta-state {
      type string;
      description
        "State";
    }
    leaf ta-pies-sent {
      type uint32;
      description
        "Number of pies sent";
    }
    leaf ta-pies-rcvd {
      type uint32;
      description
        "Number of pies received";
    }
    leaf ta-up-time-seconds {
      type uint32;
      units "second";
      description
        "Up time in seconds";
    }
    leaf downstream-on-demand {
      type boolean;
      description
        "Is Label advertisment mode in Downstream On
         Demand mode or Not";
    }
  }

  grouping ncs_rpc_notif_LDP-NEIGHBOR-INFO {
    description
      "MPLS LDP Neighbor Information";
    container protocol-information {
      description
        "Protocol Information";
      uses ncs_rpc_notif_LDP-PTCL-ADJ-INFO;
    }
    container tcp-information {
      description
        "TCP Information";
      uses ncs_rpc_notif_LDP-TCP-INFO;
    }
    container detailed-information {
      description
        "Detailed information with regards to holdtime,
         KA, inbound filtering, and Session protection";
      uses ncs_rpc_notif_LDP-NBR-DETAILED-INFO;
    }
    list ldp-nbr-bound-ipv4-address-info {
      description
        "Neighbor IPv4 Address Info";
      uses ncs_rpc_notif_LDP-NBR-ADDR-INFO;
    }
    list ldp-nbr-bound-ipv6-address-info {
      description
        "Neighbor IPv6 Address Info";
      uses ncs_rpc_notif_LDP-NBR-ADDR-INFO;
    }
    list ldp-nbr-ipv4-adj-info {
      description
        "Neighbor's IPv4 Adjacency Information";
      uses ncs_rpc_notif_LDP-NBR-ADJ-INFO;
    }
    list ldp-nbr-ipv6-adj-info {
      description
        "Neighbor's IPv6 Adjacency Information";
      uses ncs_rpc_notif_LDP-NBR-ADJ-INFO;
    }
  }

  grouping ncs_rpc_notif_LDP-NBR-CAP-INFO {
    description
      "MPLS LDP Neighbor Capability Information";
    list sent {
      description
        "List of sent capabilities";
      uses ncs_rpc_notif_LDP-CAP-DESC;
    }
    list received {
      description
        "List of received capabilities";
      uses ncs_rpc_notif_LDP-CAP-DESC;
    }
  }

  grouping ncs_rpc_notif_LDP-PARAMETERS-AF {
    description
      "MPLS LDP per AF Parameters Information";
    container discovery-transport-address {
      description
        "Discovery transport address";
      uses ncs_rpc_notif_LDP-IP-ADDR-T-UNION;
    }
    leaf address-family {
      type ncs_rpc_notif_Ldp-af;
      description
        "Address Family";
    }
    leaf null-label {
      type string;
      description
        "Null label";
    }
    leaf label-imp-null-override-acl {
      type string;
      description
        "ACL to override local label to use implicit-null";
    }
    leaf is-accepting-targeted-hellos {
      type boolean;
      description
        "Accepting targeted Hellos";
    }
    leaf targeted-hello-acl {
      type string;
      description
        "Targeted Hello ACL";
    }
  }

  grouping ncs_rpc_notif_LDP-GRACEFUL-RESTART-INFO {
    description
      "MPLS LDP Global Graceful Restart Information";
    leaf is-graceful-restart-configured {
      type boolean;
      description
        "Is graceful restart configured";
    }
    leaf graceful-restart-reconnect-timeout {
      type uint32;
      description
        "Reconnect timeout value";
    }
    leaf graceful-restart-forwarding-state-hold-time {
      type uint32;
      description
        "Graceful restart forward state hold time";
    }
  }

  grouping ncs_rpc_notif_LDP-PARAMETERS {
    description
      "MPLS LDP Global Parameters";
    container graceful-restart-information {
      description
        "Graceful restart information";
      uses ncs_rpc_notif_LDP-GRACEFUL-RESTART-INFO;
    }
    leaf role-is-active {
      type boolean;
      description
        "Is process role active or standby";
    }
    leaf global-md5-password-enabled {
      type boolean;
      description
        "Global MD5 password enabled";
    }
    leaf protocol-version {
      type uint32;
      description
        "Protocol version";
    }
    leaf router-id {
      type inet:ipv4-address;
      description
        "Router ID";
    }
    leaf keepalive-interval {
      type uint32;
      description
        "Keepalive interval";
    }
    leaf hello-hold-time {
      type uint32;
      description
        "Hello hold time";
    }
    leaf hello-interval {
      type uint32;
      description
        "Hello interval";
    }
    leaf targeted-hello-hold-time {
      type uint32;
      description
        "Targeted hello hold time";
    }
    leaf targeted-hello-interval {
      type uint32;
      description
        "Targeted hello interval";
    }
    leaf session-hold-time {
      type uint32;
      description
        "Session hold time";
    }
    leaf housekeeping-timer-interval {
      type uint32;
      description
        "Housekeeping periodic timer interval";
    }
    leaf le-no-route-timeout {
      type uint32;
      description
        "LIB entry no route timeout";
    }
    leaf ldp-recovery-timeout {
      type uint32;
      description
        "LDP recovery timeout with LSD";
    }
    leaf af-binding-withdraw-delay {
      type uint32;
      description
        "Delay (sec) in Binding Withdrawal for an Address
         Family";
    }
    leaf max-intf-attached {
      type uint32;
      description
        "Maximum number of LDP enabled attached
         interfaces";
    }
    leaf max-intf-te {
      type uint32;
      description
        "Maximum number of LDP enabled TE interfaces";
    }
    leaf max-peer {
      type uint32;
      description
        "Maximum number of LDP peers";
    }
    leaf ldp-out-of-mem-state {
      type uint32;
      description
        "LDP Out of memory state";
    }
    leaf nsr-enabled {
      type boolean;
      description
        "TRUE if NSR is enabled";
    }
    leaf nsr-synced {
      type boolean;
      description
        "TRUE if LDP is standby and is NSR Sync-ed with
         active";
    }
    leaf igp-sync-delay-time-for-interface {
      type uint32;
      units "second";
      description
        "Interface IGP sync delay time in seconds";
    }
    leaf igp-sync-delay-time-on-restart {
      type uint32;
      units "second";
      description
        "IGP sync delay time on process restart in
         seconds";
    }
    leaf global-discovery-quick-start-disabled {
      type boolean;
      description
        "Discovery quick-start globally disabled";
    }
    leaf discovery-quick-start-disabled-on-interfaces {
      type boolean;
      description
        "Discovery quick-start disabled on some
         LDP-enabled interfaces";
    }
    list address-family-parameter {
      description
        "Per AF parameters";
      uses ncs_rpc_notif_LDP-PARAMETERS-AF;
    }
  }

  grouping ncs_rpc_notif_LDP-NSR-SUM-SESS {
    description
      "MPLS LDP NSR session summary";
    leaf total {
      type uint32;
      description
        "Total sessions";
    }
    leaf nsr-eligible {
      type uint32;
      description
        "NSR eligible sessions";
    }
    leaf nsr-state-none {
      type uint32;
      description
        "Number of sessions in NSR none state";
    }
    leaf nsr-state-wait {
      type uint32;
      description
        "Number of sessions in NSR wait state";
    }
    leaf nsr-state-ready {
      type uint32;
      description
        "Number of sessions in NSR ready state";
    }
    leaf nsr-state-prepare {
      type uint32;
      description
        "Number of sessions in NSR prepare state";
    }
    leaf nsr-state-app-wait {
      type uint32;
      description
        "Number of sessions in NSR app-wait state";
    }
    leaf nsr-state-operational {
      type uint32;
      description
        "Number of sessions in NSR operational state";
    }
    leaf nsr-state-tcp-phase1 {
      type uint32;
      description
        "Number of sessions in NSR TCP phase 1 state";
    }
    leaf nsr-state-tcp-phase2 {
      type uint32;
      description
        "Number of sessions in NSR TCP phase 2 state";
    }
  }

  grouping ncs_rpc_notif_LDP-NSR-SUM {
    description
      "MPLS LDP NSR summary";
    container vrf {
      description
        "VRF information";
      uses ncs_rpc_notif_LDP-VRF-INFO;
    }
    container sessions {
      description
        "Session summary";
      uses ncs_rpc_notif_LDP-NSR-SUM-SESS;
    }
  }

  grouping ncs_rpc_notif_LDP-BACKOFF-ENTRY-INFO {
    description
      "MPLS LDP Session Backoff Entry Information";
    leaf backoff-seconds {
      type uint32;
      units "second";
      description
        "Backoff seconds";
    }
    leaf waiting-seconds {
      type uint32;
      units "second";
      description
        "Backoff waiting seconds";
    }
  }

  grouping ncs_rpc_notif_LDP-BACKOFF-INFO {
    description
      "MPLS LDP Session Backoff Information";
    leaf initial-seconds {
      type uint32;
      units "second";
      description
        "Initial backoff value in seconds";
    }
    leaf maximum-seconds {
      type uint32;
      units "second";
      description
        "Maximum backoff value in seconds";
    }
  }

  grouping ncs_rpc_notif_LDP-NEIGHBOR-BRIEF-AF-INFO {
    description
      "MPLS LDP Neighbor Brief AF information";
    leaf address-family {
      type ncs_rpc_notif_Ldp-af;
      description
        "Neighbor Brief Address Family";
    }
    leaf num-of-nbr-discovery {
      type uint32;
      description
        "Number of neighbor discovery sources";
    }
    leaf num-of-nbr-addresses {
      type uint32;
      description
        "Number of neighbor addresses";
    }
    leaf num-of-nbr-lbl {
      type uint32;
      description
        "Number of neighbor labels";
    }
  }

  grouping ncs_rpc_notif_LDP-NEIGHBOR-BRIEF-INFO {
    description
      "MPLS LDP Neighbor Brief Information";
    container vrf {
      description
        "VRF information";
      uses ncs_rpc_notif_LDP-VRF-INFO;
    }
    leaf is-graceful-restartable {
      type boolean;
      description
        "Is graceful restartable";
    }
    leaf nsr-state {
      type ncs_rpc_notif_Show-nsr-state;
      description
        "NSR readiness state";
    }
    leaf up-time-seconds {
      type uint32;
      units "second";
      description
        "Up time in seconds";
    }
    list nbr-br-af-info {
      max-elements 2;
      description
        "Neighbor Brief AF Info";
      uses ncs_rpc_notif_LDP-NEIGHBOR-BRIEF-AF-INFO;
    }
  }

  grouping ncs_rpc_notif_LDP-FWD-RW-PATH-SUMM {
    description
      "MPLS LDP fowarding rewrite nexthop/path summary";
    leaf total-paths {
      type uint32;
      description
        "Total path count";
    }
    leaf protected-paths {
      type uint32;
      description
        "Count of FRR protected paths";
    }
    leaf backup-paths {
      type uint32;
      description
        "Count of non-primary backup paths";
    }
    leaf remote-backup-paths {
      type uint32;
      description
        "Count of non-primary remote backup paths";
    }
    leaf labeled-paths {
      type uint32;
      description
        "Count of all labeled paths";
    }
    leaf labeled-backup-paths {
      type uint32;
      description
        "Count of labeled backup paths";
    }
  }

  grouping ncs_rpc_notif_LDP-FWD-RW-PFX-LBL-SUMM {
    description
      "MPLS LDP forwarding rewrite prefix nexthops
       labeled summary";
    leaf labeled-pfxs {
      type uint16;
      description
        "Count of labeled prefixes with 1 or more paths
         labeled";
    }
    leaf labeled-pfxs-partial {
      type uint16;
      description
        "Count of labeled prefixes with some (but not
         ALL) paths labeled";
    }
    leaf unlabeled-pfxs {
      type uint16;
      description
        "Count of labeled prefixes with ALL paths
         unlabeled";
    }
  }

  grouping ncs_rpc_notif_LDP-FWD-RW-PFX-SUMM {
    description
      "MPLS LDP fowarding rewrite prefix summary";
    container labeled-pfxs-aggr {
      description
        "Labeled prefix count for all paths";
      uses ncs_rpc_notif_LDP-FWD-RW-PFX-LBL-SUMM;
    }
    container labeled-pfxs-primary {
      description
        "Labeled prefix count related to primary paths
         only";
      uses ncs_rpc_notif_LDP-FWD-RW-PFX-LBL-SUMM;
    }
    container labeled-pfxs-backup {
      description
        "Labeled prefix count related to backup paths
         only";
      uses ncs_rpc_notif_LDP-FWD-RW-PFX-LBL-SUMM;
    }
    leaf total-pfxs {
      type uint16;
      description
        "Total Prefix count";
    }
    leaf ecmp-pfxs {
      type uint16;
      description
        "Count of prefixes with ECMP";
    }
    leaf protected-pfxs {
      type uint16;
      description
        "Count of FRR protected prefixes";
    }
  }

  grouping ncs_rpc_notif_LDP-FWD-RW-SUMM {
    description
      "MPLS LDP fowarding rewrite summary";
    container pfxs {
      description
        "Forwarding rewrites prefix summary";
      uses ncs_rpc_notif_LDP-FWD-RW-PFX-SUMM;
    }
    container nhs {
      description
        "Forwarding rewrites nexthops (paths) summary";
      uses ncs_rpc_notif_LDP-FWD-RW-PATH-SUMM;
    }
  }

  grouping ncs_rpc_notif_LDP-FWD-SUMM-INFO {
    description
      "MPLS LDP fowarding summary";
    container vrf {
      description
        "VRF information";
      uses ncs_rpc_notif_LDP-VRF-INFO;
    }
    container rws {
      description
        "Forwarding rewrites summary";
      uses ncs_rpc_notif_LDP-FWD-RW-SUMM;
    }
    leaf is-lsd-bound {
      type boolean;
      description
        "LDP is connected to LSD server";
    }
    leaf fsht {
      type uint16;
      description
        "Forwarding state hold time registered with LSD";
    }
    leaf intfs {
      type uint16;
      description
        "MPLS forwarding enabled interface count";
    }
    leaf lbls {
      type uint16;
      description
        "Local label allocated count";
    }
  }

  grouping ncs_rpc_notif_LDP-BINDING-ALLOC {
    description
      "MPLS LDP Binding local label allocation filter";
    leaf has-acl {
      type boolean;
      description
        "Has ACL filter?";
    }
    leaf prefix-acl {
      type string {
        length "0..64";
      }
      description
        "Prefix ACL";
    }
    leaf is-host-route-only {
      type boolean;
      description
        "Host-routes only?";
    }
  }

  grouping ncs_rpc_notif_LDP-BINDING-ADVT-ACL-PAIR {
    description
      "MPLS LDP Binding advertisement ACL pair";
    leaf prefix-acl {
      type string {
        length "0..64";
      }
      description
        "Prefix ACL";
    }
    leaf peer-acl {
      type string {
        length "0..64";
      }
      description
        "Peer ACL";
    }
  }

  grouping ncs_rpc_notif_LDP-BINDING-ADVT-SPEC {
    description
      "MPLS LDP Binding advertisement specification ACLs";
    container allocation-acl {
      description
        "Local label Allocation filter";
      uses ncs_rpc_notif_LDP-BINDING-ALLOC;
    }
    list advt-acl {
      description
        "Advertisement ACLs";
      uses ncs_rpc_notif_LDP-BINDING-ADVT-ACL-PAIR;
    }
  }

  grouping ncs_rpc_notif_LDP-FWD-PATH-RLFA-MOI-INFO {
    description
      "MPLS LDP Forwarding Path Remote LFA-FRR backup
       MPLS MOI info";
    list stack {
      description
        "Inner label stack info";
      uses ncs_rpc_notif_LDP-FWD-PATH-MPLS-NH-INFO;
    }
  }

  grouping ncs_rpc_notif_LDP-FWD-PATH-RLFA-MPLS-INFO {
    description
      "MPLS LDP Forwarding Path Remote LFA-FRR backup
       MPLS info";
    container mpls-outgoing-info {
      description
        "Remote LFA MPLS nexthop(s_ info";
      uses ncs_rpc_notif_LDP-FWD-PATH-RLFA-MOI-INFO;
    }
    leaf has-remote-lfa-bkup {
      type boolean;
      description
        "Whether path has remote LFA backup";
    }
  }

  grouping ncs_rpc_notif_LDP-FWD-PATH-MPLS-NH-INFO {
    description
      "Forwarding Path MPLS nexthop info";
    container nexthop-peer-ldp-ident {
      description
        "Nexthop LDP peer";
      uses ncs_rpc_notif_LDP-LDPID-INFO;
    }
    leaf out-label {
      type uint32;
      description
        "Outgoing label";
    }
    leaf out-label-rsn {
      type ncs_rpc_notif_Ldp-fwd-unlbl-rsn;
      description
        "Outgoing label reason";
    }
    leaf out-label-type {
      type ncs_rpc_notif_Label-value;
      description
        "Outgoing Label Type";
    }
    leaf out-label-owner {
      type ncs_rpc_notif_Ldp-route-path-lbl-owner;
      description
        "Outgoing label owner";
    }
    leaf is-from-graceful-restartable-neighbor {
      type boolean;
      description
        "Is from a GR neighbor";
    }
    leaf is-stale {
      type boolean;
      description
        "Is the entry stale";
    }
    leaf entropy-label-capability {
      type boolean;
      description
        "Entropy Label Capability";
    }
  }

  grouping ncs_rpc_notif_LDP-FWD-PATH-MPLS-INFO {
    description
      "MPLS LDP Forwarding Path MPLS information";
    container mpls-outgoing-info {
      description
        "MPLS nexthop info";
      uses ncs_rpc_notif_LDP-FWD-PATH-MPLS-NH-INFO;
    }
    container remote-lfa {
      description
        "Remote LFA-FRR backup info";
      uses ncs_rpc_notif_LDP-FWD-PATH-RLFA-MPLS-INFO;
    }
  }

  grouping ncs_rpc_notif_LDP-FWD-PATH-RLFA-ROUTING-INFO {
    description
      "MPLS LDP Forwarding Path Remote LFA-FRR backup
       routing info";
    container remote-p-node-id {
      description
        "Remote/P node address";
      uses ncs_rpc_notif_LDP-IP-ADDR-T-UNION;
    }
    container remote-q-node-id {
      description
        "Remote/Q node address";
      uses ncs_rpc_notif_LDP-IP-ADDR-T-UNION;
    }
    leaf has-remote-lfa-bkup {
      type boolean;
      description
        "Whether path has remote LFA backup";
    }
    leaf needs-tldp {
      type boolean;
      description
        "Whether TLDP is needed with remote PQ node";
    }
    leaf has-q-node {
      type boolean;
      description
        "Whether remote LFA path has a Q node associated";
    }
  }

  grouping ncs_rpc_notif_LDP-FWD-PATH-ROUTING-INFO {
    description
      "MPLS LDP Forwarding Path IP Routing information";
    container next-hop {
      description
        "Next Hop";
      uses ncs_rpc_notif_LDP-IP-ADDR-T-UNION;
    }
    container remote-lfa {
      description
        "Remote LFA-FRR backup info";
      uses ncs_rpc_notif_LDP-FWD-PATH-RLFA-ROUTING-INFO;
    }
    leaf interface {
      type xr:ncs_rpc_notif_Interface-name;
      description
        "Interface name";
    }
    leaf interface-name {
      type string;
      description
        "Interface Name";
    }
    leaf nh-is-overriden {
      type boolean;
      description
        "Nexthop is overriden by LDP";
    }
    leaf nexthop-id {
      type uint32;
      description
        "Nexthop Identifier";
    }
    leaf next-hop-table-id {
      type uint32;
      description
        "Table ID for nexthop address";
    }
    leaf flags {
      type uint32;
      description
        "Route path flags";
    }
    leaf load-metric {
      type uint32;
      description
        "Path's load metric for load balancing";
    }
    leaf binding-label {
      type uint32;
      description
        "Binding label obtained via RIB";
    }
    leaf path-id {
      type uint8;
      description
        "path Id";
    }
    leaf bkup-path-id {
      type uint8;
      description
        "Backup path Id";
    }
    leaf path-flags {
      type ncs_rpc_notif_Ldp-route-path-flags;
      description
        "Routing path flags decoded";
    }
  }

  grouping ncs_rpc_notif_LDP-FWD-PATH-INFO {
    description
      "MPLS LDP Forwarding Path info";
    container routing {
      description
        "IP routing information";
      uses ncs_rpc_notif_LDP-FWD-PATH-ROUTING-INFO;
    }
    container mpls {
      description
        "MPLS information";
      uses ncs_rpc_notif_LDP-FWD-PATH-MPLS-INFO;
    }
  }

  grouping ncs_rpc_notif_LDP-FWD-ROUTE-MPLS-INFO {
    description
      "MPLS LDP Forwarding Route LDP information";
    leaf local-label {
      type uint32;
      description
        "Local label";
    }
    leaf forwarding-update-count {
      type uint32;
      description
        "Number of forwarding updates";
    }
    leaf forwarding-update-timestamp {
      type uint64;
      description
        "Last Forwarding update nanosec timestamp";
    }
    leaf forwarding-update-age {
      type uint64;
      description
        "Last Forwarding update nanosec age";
    }
  }

  grouping ncs_rpc_notif_LDP-FWD-ROUTE-ROUTING-INFO {
    description
      "MPLS LDP Forwarding Route IP Routing information";
    leaf version {
      type uint32;
      description
        "Route RIB ersion";
    }
    leaf priority {
      type uint8;
      description
        "Route priority";
    }
    leaf source {
      type uint16;
      description
        "Route source protol Id";
    }
    leaf type {
      type uint16;
      description
        "Route type";
    }
    leaf flags {
      type uint32;
      description
        "Route RIB flags";
    }
    leaf metric {
      type uint32;
      description
        "Route metric";
    }
    leaf is-local-vrf-leaked {
      type boolean;
      description
        "Is route leaked across local VRFs?";
    }
    leaf routing-update-count {
      type uint32;
      description
        "Number of routing updates";
    }
    leaf routing-update-timestamp {
      type uint64;
      description
        "Last Routing update nanosec timestamp";
    }
    leaf routing-update-age {
      type uint64;
      description
        "Last Routing update nanosec age";
    }
    leaf sr-local-label {
      type uint32;
      description
        "SR Local-label";
    }
  }

  grouping ncs_rpc_notif_LDP-FWD-ROUTE-INFO {
    description
      "MPLS LDP Forwarding Route information";
    container routing {
      description
        "IP routing information";
      uses ncs_rpc_notif_LDP-FWD-ROUTE-ROUTING-INFO;
    }
    container mpls {
      description
        "MPLS information";
      uses ncs_rpc_notif_LDP-FWD-ROUTE-MPLS-INFO;
    }
  }

  grouping ncs_rpc_notif_LDP-FWD-PFX-INFO {
    description
      "MPLS LDP Forwarding Prefix Information";
    container vrf {
      description
        "VRF information";
      uses ncs_rpc_notif_LDP-VRF-INFO;
    }
    container prefix-xr {
      description
        "IP Prefix";
      uses ncs_rpc_notif_LDP-IP-ADDR-T-UNION;
    }
    container route {
      description
        "Route";
      uses ncs_rpc_notif_LDP-FWD-ROUTE-INFO;
    }
    leaf table-id {
      type uint32;
      description
        "Table ID associated with IP prefix";
    }
    leaf prefix-length {
      type uint8;
      description
        "Prefix length";
    }
    list paths {
      description
        "Paths";
      uses ncs_rpc_notif_LDP-FWD-PATH-INFO;
    }
  }

  grouping ncs_rpc_notif_LDP-DISCOVERY-ADJ-GRP-INFO {
    description
      "MPLS LDP Discovery Adjacency Group Information";
    leaf adjacency-group-up-time {
      type uint32;
      units "second";
      description
        "Adjacency group up time in seconds";
    }
    leaf tcp-open-count {
      type uint32;
      description
        "Count of attempted TCP opens";
    }
    leaf tcp-arb-chg-count {
      type uint32;
      description
        "Count of changes in TCP arbitration";
    }
    leaf tcp-role {
      type uint32;
      description
        "TCP Role";
    }
  }

  grouping ncs_rpc_notif_LDP-TARGETED-HELLO-BRIEF-INFO {
    description
      "MPLS LDP Discovery Targeted Brief Information";
    container vrf {
      description
        "VRF information";
      uses ncs_rpc_notif_LDP-VRF-INFO;
    }
    container dhcb-target-address {
      description
        "DHCB target address";
      uses ncs_rpc_notif_LDP-IP-ADDR-T-UNION;
    }
    leaf address-family {
      type ncs_rpc_notif_Ldp-af;
      description
        "Targeted Discovery Address Family";
    }
    list hello-information {
      description
        "LDP hello info";
      uses ncs_rpc_notif_LDP-HELLO-BRIEF-INFO;
    }
  }

  grouping ncs_rpc_notif_LDP-HELLO-BRIEF-INFO {
    description
      "MPLS LDP Hello Brief Information";
    leaf neighbor-ldp-identifier {
      type string;
      description
        "Neighbor LDP Identifier";
    }
    leaf hold-time {
      type uint32;
      description
        "Session hold time in sec";
    }
    leaf session-up {
      type boolean;
      description
        "Is session up for this adj";
    }
  }

  grouping ncs_rpc_notif_LDP-DISCOVERY-LINK-BRIEF-INFO {
    description
      "MPLS LDP Discovery Link Brief Information";
    container vrf {
      description
        "VRF information";
      uses ncs_rpc_notif_LDP-VRF-INFO;
    }
    leaf address-family {
      type ncs_rpc_notif_Ldp-af;
      description
        "Discovery Brief Address Family";
    }
    leaf address-family-set {
      type ncs_rpc_notif_Ldp-af;
      description
        "Discovery Brief Address Family Set";
    }
    leaf interface {
      type xr:ncs_rpc_notif_Interface-name;
      description
        "Interface name";
    }
    leaf interface-name-xr {
      type string;
      description
        "Interface name";
    }
    list hello-information {
      description
        "LDP hello info";
      uses ncs_rpc_notif_LDP-HELLO-BRIEF-INFO;
    }
  }

  grouping ncs_rpc_notif_LDP-TARGETED-HELLO-INFO {
    description
      "MPLS LDP Targeted Hello Information";
    container dhcb-local-address {
      description
        "DHCB local address";
      uses ncs_rpc_notif_LDP-IP-ADDR-T-UNION;
    }
    container dhcb-target-address {
      description
        "DHCB target address";
      uses ncs_rpc_notif_LDP-IP-ADDR-T-UNION;
    }
    leaf state {
      type ncs_rpc_notif_Dhcb-state;
      description
        "Targeted hello state";
    }
    leaf adjacency-ldp-identifier {
      type string;
      description
        "Adjacency LDP Identifier";
    }
    leaf interval {
      type uint32;
      description
        "Hello interval in sec";
    }
    leaf next-hello {
      type uint32;
      description
        "Next hello due time in msec";
    }
    leaf hold-time {
      type uint32;
      description
        "Targeted hello hold time";
    }
    leaf local-hold-time {
      type uint32;
      description
        "Local hold time";
    }
    leaf neighbor-hold-time {
      type uint32;
      description
        "Neighbor hold time";
    }
    leaf disc-expiry {
      type uint32;
      description
        "Discovery expiry time in msec";
    }
    leaf quick-start-disabled {
      type boolean;
      description
        "Quick-start disabled";
    }
    leaf established-time {
      type uint64;
      description
        "Hello adjacency estabished time in nanosec";
    }
    leaf established-age {
      type uint64;
      description
        "Hello adjacency estabished age in nanosec";
    }
    leaf session-up {
      type boolean;
      description
        "Is session up for this adj";
    }
    leaf session-bringup-failure-reason {
      type string;
      description
        "session bringup failure reason";
    }
    list last-session-down-info {
      description
        "Last session down information";
      uses ncs_rpc_notif_LDP-LAST-SESS-INFO;
    }
  }

  grouping ncs_rpc_notif_LDP-DISCOVERY-SUMMARY-INFO {
    description
      "MPLS LDP Discovery Summary Information";
    container vrf {
      description
        "VRF information";
      uses ncs_rpc_notif_LDP-VRF-INFO;
    }
    leaf local-ldp-id {
      type string;
      description
        "Local LDP identifier";
    }
    leaf num-of-ldp-interfaces {
      type uint32;
      description
        "Total Number of LDP configured interfaces";
    }
    leaf num-of-active-ldp-interfaces {
      type uint32;
      description
        "Number of active LDP enabled interfaces";
    }
    leaf num-of-lnk-disc-xmit {
      type uint32;
      description
        "Number of link hello discoveries in xmit state";
    }
    leaf num-of-tgt-disc-xmit {
      type uint32;
      description
        "Number of targeted hello discoveries in xmit
         state";
    }
    leaf num-of-lnk-disc-recv {
      type uint32;
      description
        "Number of link hello discoveries in recv state";
    }
    leaf num-of-tgt-disc-recv {
      type uint32;
      description
        "Number of targeted hello discoveries in recv
         state";
    }
    leaf num-of-disc-with-bad-addr-recv {
      type uint32;
      description
        "Number of hello discoveries received with bad
         source address";
    }
    leaf num-of-disc-with-bad-hello-pdu {
      type uint32;
      description
        "Number of hello discoveries received with bad
         hello PDU";
    }
    leaf num-of-disc-with-bad-xport-addr {
      type uint32;
      description
        "Number of hello discoveries received with bad
         export address";
    }
    leaf num-of-disc-with-same-router-id {
      type uint32;
      description
        "Number of hello discoveries received with the
         same router id as this router";
    }
    leaf num-of-disc-with-wrong-router-id {
      type uint32;
      description
        "Number of hello discoveries received with the
         router id that is not destined for this router";
    }
  }

  grouping ncs_rpc_notif_LDP-DISCOVERY-LINK-AF-INFO {
    description
      "MPLS LDP Discovery Link Address Family
       Information";
    container local-src-address {
      description
        "Local source address";
      uses ncs_rpc_notif_LDP-IP-ADDR-T-UNION;
    }
    container local-transport-address {
      description
        "Local transport address";
      uses ncs_rpc_notif_LDP-IP-ADDR-T-UNION;
    }
    leaf interval {
      type uint32;
      description
        "Hello interval in sec";
    }
  }

  grouping ncs_rpc_notif_LDP-LAST-SESS-INFO {
    description
      "LDP last down session information";
    leaf last-session-down-reason {
      type string;
      description
        "The reason of last socket failure";
    }
    leaf last-session-down-time {
      type uint64;
      description
        "Timestamp of when the last session went down";
    }
    leaf last-session-up-time {
      type uint32;
      description
        "The time duration the last session was up";
    }
  }

  grouping ncs_rpc_notif_LDP-HELLO-INFO {
    description
      "MPLS LDP Hello Information";
    container neighbor-src-address {
      description
        "Neighbor source address";
      uses ncs_rpc_notif_LDP-IP-ADDR-T-UNION;
    }
    container neighbor-transport-address {
      description
        "Neighbor transport address";
      uses ncs_rpc_notif_LDP-IP-ADDR-T-UNION;
    }
    container target {
      description
        "Target address";
      uses ncs_rpc_notif_LDP-IP-ADDR-T-UNION;
    }
    leaf neighbor-ldp-identifier {
      type string;
      description
        "Neighbor LDP Identifier";
    }
    leaf is-no-route {
      type boolean;
      description
        "Is route valid";
    }
    leaf hold-time {
      type uint32;
      units "second";
      description
        "Session hold time in seconds";
    }
    leaf local-hold-time {
      type uint32;
      units "second";
      description
        "Local hold time in seconds";
    }
    leaf neighbor-hold-time {
      type uint32;
      units "second";
      description
        "Neighbor hold time in seconds";
    }
    leaf disc-expiry {
      type uint32;
      description
        "Discovery expiry time in sec";
    }
    leaf is-targeted {
      type boolean;
      description
        "Is session a targeted session";
    }
    leaf session-up {
      type boolean;
      description
        "Is session up for this adj";
    }
    leaf established-time {
      type uint64;
      description
        "Hello adjacency estabished time in nanosec";
    }
    leaf established-age {
      type uint64;
      description
        "Hello adjacency estabished age in nanosec";
    }
    leaf session-bringup-failure-reason {
      type string;
      description
        "session bringup failure reason";
    }
    list last-session-down-info {
      description
        "Last session down information";
      uses ncs_rpc_notif_LDP-LAST-SESS-INFO;
    }
  }

  grouping ncs_rpc_notif_LDP-DISCOVERY-LINK-INFO {
    description
      "MPLS LDP Discovery Link Information";
    container vrf {
      description
        "VRF information";
      uses ncs_rpc_notif_LDP-VRF-INFO;
    }
    leaf next-hello {
      type uint32;
      description
        "Next hello due time in msec";
    }
    leaf interface {
      type xr:ncs_rpc_notif_Interface-name;
      description
        "Interface name";
    }
    leaf interface-name-xr {
      type string;
      description
        "Interface name";
    }
    leaf quick-start-disabled {
      type boolean;
      description
        "Quick-start disabled";
    }
    list hello-information {
      description
        "LDP hello info";
      uses ncs_rpc_notif_LDP-HELLO-INFO;
    }
    list discovery-link-af {
      max-elements 2;
      description
        "LDP hello AF info";
      uses ncs_rpc_notif_LDP-DISCOVERY-LINK-AF-INFO;
    }
  }

  grouping ncs_rpc_notif_LDP-INTF-AUTOCFG {
    description
      "MPLS LDP auto configure";
    leaf tuple {
      type string;
      description
        "Tuple";
    }
  }

  grouping ncs_rpc_notif_LDP-INTF-TE-MESH-GRP {
    description
      "MPLS LDP interface tunnel mesh group";
    leaf ldp-te-mesh-group-all-cfgd {
      type boolean;
      description
        "LDP has enabled all TE mesh-groups";
    }
    leaf ldp-mesh-group-enabled {
      type boolean;
      description
        "LDP has enabled this TE mesh-group";
    }
    leaf te-mesh-group-id {
      type uint32;
      description
        "TE tunnel Mesh Group ID";
    }
  }

  grouping ncs_rpc_notif_LDP-INTF {
    description
      "MPLS LDP interface information";
    container vrf {
      description
        "VRF information";
      uses ncs_rpc_notif_LDP-VRF-INFO;
    }
    leaf interface {
      type xr:ncs_rpc_notif_Interface-name;
      description
        "Interface name";
    }
    leaf interface-name-xr {
      type string;
      description
        "Interface name";
    }
    leaf ldp-enabled {
      type boolean;
      description
        "LDP enabled";
    }
    leaf is-im-stale {
      type boolean;
      description
        "Is IM information stale";
    }
    leaf ldp-config-mode {
      type boolean;
      description
        "LDP config mode";
    }
    leaf ldp-autoconfig-disable {
      type boolean;
      description
        "LDP autoconfig disable";
    }
    list te-mesh-grp {
      description
        "TE tunnel mesh-group";
      uses ncs_rpc_notif_LDP-INTF-TE-MESH-GRP;
    }
    list auto-config {
      description
        "Auto config";
      uses ncs_rpc_notif_LDP-INTF-AUTOCFG;
    }
  }

  grouping ncs_rpc_notif_LDP-BINDING-SUMMARY-AF {
    description
      "MPLS LDP Binding Summary AF Information";
    leaf address-family {
      type ncs_rpc_notif_Ldp-af;
      description
        "Binding Summary Address Family";
    }
    leaf last-lib-update {
      type uint32;
      description
        "Last update to LIB local binding";
    }
    leaf lib-minimum-revision-sent-all {
      type uint32;
      description
        "Last update sent to all peers";
    }
    leaf binding-total {
      type uint32;
      description
        "Total bindings";
    }
    leaf binding-local {
      type uint32;
      description
        "Number of local bindings";
    }
    leaf binding-remote {
      type uint32;
      description
        "Number of remote bindings";
    }
  }

  grouping ncs_rpc_notif_LDP-BINDING-SUMMARY {
    description
      "MPLS LDP Binding Summary Information";
    container vrf {
      description
        "VRF information";
      uses ncs_rpc_notif_LDP-VRF-INFO;
    }
    leaf address-family {
      type ncs_rpc_notif_Ldp-af;
      description
        "Address Family";
    }
    leaf binding-no-route {
      type uint32;
      description
        "Bindings with no route";
    }
    leaf binding-local-no-route {
      type uint32;
      description
        "Local bindings with no route";
    }
    leaf binding-local-null {
      type uint32;
      description
        "Number of local null bindings";
    }
    leaf binding-local-implicit-null {
      type uint32;
      description
        "Number of local implicit null bindings";
    }
    leaf binding-local-explicit-null {
      type uint32;
      description
        "Number of local explicit null bindings";
    }
    leaf binding-local-non-null {
      type uint32;
      description
        "Number of local non-null bindings";
    }
    leaf binding-local-oor {
      type uint32;
      description
        "Number of local bindings        needing label -
         OOR";
    }
    leaf lowest-allocated-label {
      type uint32;
      description
        "Lowest allocated label";
    }
    leaf highest-allocated-label {
      type uint32;
      description
        "Highest allocated label";
    }
    list bind-af {
      max-elements 2;
      description
        "bind af";
      uses ncs_rpc_notif_LDP-BINDING-SUMMARY-AF;
    }
  }

  grouping ncs_rpc_notif_LDP-IGP-SYNC-DELAY-RESTART-INFO {
    description
      "MPLS LDP IGP Sync Restart Delay Information";
    leaf configured {
      type boolean;
      description
        "Is restart delay configured";
    }
    leaf delay-secs {
      type uint32;
      description
        "Delay time";
    }
    leaf timer-running {
      type boolean;
      description
        "Is restart delay timer running";
    }
    leaf remaining-secs {
      type uint32;
      description
        "Delay timer remaining time";
    }
  }

  grouping ncs_rpc_notif_LDP-IGP-SYNC-INTF-GR-ONLY {
    description
      "MPLS LDP IGP Sync Interface GR-only reachable
       Peer Information";
    leaf peer-id {
      type ncs_rpc_notif_String-td2;
      description
        "Peer Identifier";
    }
    leaf is-chkpt-created {
      type boolean;
      description
        "Is created due to checkpointing";
    }
  }

  grouping ncs_rpc_notif_LDP-IGP-SYNC-INTF-PEER {
    description
      "MPLS LDP IGP Sync Interface Peer Information";
    leaf peer-id {
      type ncs_rpc_notif_String-td2;
      description
        "Peer Identifier";
    }
    leaf is-gr-enabled {
      type boolean;
      description
        "Is GR enabled session";
    }
  }

  grouping ncs_rpc_notif_LDP-IGP-SYNC-INFO {
    description
      "MPLS LDP IGP Sync Information";
    container vrf {
      description
        "VRF information";
      uses ncs_rpc_notif_LDP-VRF-INFO;
    }
    leaf interface-name-xr {
      type string;
      description
        "Interface name";
    }
    leaf igp-sync-state {
      type ncs_rpc_notif_Ldp-igp-sync-state;
      description
        "IGP Sync state";
    }
    leaf igp-sync-delay {
      type uint32;
      units "second";
      description
        "IGP sync delay in seconds";
    }
    leaf is-delay-timer-running {
      type boolean;
      description
        "Is sync delay timer running";
    }
    leaf delay-timer-remaining {
      type uint32;
      units "second";
      description
        "Remaining timer (seconds) till expiry of sync
         delay timer";
    }
    leaf igp-sync-down-reason {
      type ncs_rpc_notif_Ldp-igp-sync-down-reason;
      description
        "Reason IGP Sync Not Achieved";
    }
    list peers {
      description
        "Interface Peers";
      uses ncs_rpc_notif_LDP-IGP-SYNC-INTF-PEER;
    }
    list gr-only-peer {
      description
        "Interface GR-only reachable peers";
      uses ncs_rpc_notif_LDP-IGP-SYNC-INTF-GR-ONLY;
    }
  }

  grouping ncs_rpc_notif_LDP-TIB-ENTRY-REMOTE {
    description
      "MPLS LDP Remote Binding Information";
    container assigning-peer-ldp-ident {
      description
        "Assigning peer";
      uses ncs_rpc_notif_LDP-LDPID-INFO;
    }
    leaf remote-label {
      type uint32;
      description
        "Remote Label";
    }
    leaf is-stale {
      type boolean;
      description
        "Is the entry stale";
    }
    leaf is-elc {
      type boolean;
      description
        "Is the entry entropy label capable";
    }
  }

  grouping ncs_rpc_notif_LDP-TIB-ENTRY-DETAIL {
    description
      "MPLS LDP Binding Detail Information";
    container vrf {
      description
        "VRF information";
      uses ncs_rpc_notif_LDP-VRF-INFO;
    }
    container prefix-xr {
      description
        "IP Prefix";
      uses ncs_rpc_notif_LDP-IP-ADDR-T-UNION;
    }
    leaf prefix-length {
      type uint8;
      description
        "Prefix Length";
    }
    leaf local-label {
      type uint32;
      description
        "Local label";
    }
    leaf le-local-binding-revision {
      type uint32;
      description
        "Local Binding revision";
    }
    leaf le-local-label-state {
      type ncs_rpc_notif_Local-label-state;
      description
        "Local label state";
    }
    leaf is-no-route {
      type boolean;
      description
        "No route";
    }
    leaf label-oor {
      type boolean;
      description
        "Label space depletion OOR";
    }
    leaf advertise-prefix-acl {
      type string;
      description
        "Advertise Prerfix ACL";
    }
    leaf advertise-tsr-acl {
      type string;
      description
        "Advertise TSR ACL";
    }
    leaf config-enforced-local-label-value {
      type boolean;
      description
        "Config/User enforced local label value";
    }
    leaf is-elc {
      type boolean;
      description
        "Is the entry entropy label capable";
    }
    list remote-binding {
      description
        "Remote binding";
      uses ncs_rpc_notif_LDP-TIB-ENTRY-REMOTE;
    }
    list peers-advertised-to {
      description
        "Peers this entry is advertised to";
      uses ncs_rpc_notif_LDP-LDPID-INFO;
    }
    list peers-acked {
      description
        "Peers that have ACKed this entry";
      uses ncs_rpc_notif_LDP-LDPID-INFO;
    }
  }

  grouping ncs_rpc_notif_LDP-INTF-SUM {
    description
      "MPLS LDP interface summary";
    leaf known-ip-interface-count {
      type uint32;
      description
        "Number of known IP Interfaces";
    }
    leaf known-ip-interface-ldp-enabled {
      type uint32;
      description
        "Number of known IP Interfaces with LDP Enabled";
    }
    leaf ldp-configured-attached-interface {
      type uint32;
      description
        "Number of attached interfaces configured in LDP";
    }
    leaf ldp-configured-te-interface {
      type uint32;
      description
        "Number of TE tunnel interfaces configured in LDP";
    }
    leaf forward-references {
      type uint32;
      description
        "Number of forward referenced interfaces";
    }
    leaf auto-config-disabled {
      type uint32;
      description
        "Autoconfigure disabled";
    }
    leaf auto-config {
      type uint32;
      description
        "Auto-configured interfaces";
    }
    leaf auto-config-forward-reference-interfaces {
      type uint32;
      description
        "Auto-configured forward references";
    }
  }

  grouping ncs_rpc_notif_LDP-SUMMARY-COMMON {
    description
      "MPLS LDP common summary Information";
    leaf address-families {
      type ncs_rpc_notif_Ldp-af;
      description
        "Address Families enabled";
    }
    leaf number-of-ipv4af {
      type uint32;
      description
        "Number of IPv4 address-families enabled";
    }
    leaf number-of-ipv6af {
      type uint32;
      description
        "Number of IPv6 address-families enabled";
    }
    leaf number-of-neighbors {
      type uint32;
      description
        "Number of neighbors";
    }
    leaf number-of-adj-grps {
      type uint32;
      description
        "Number of Adjacency Groups";
    }
    leaf number-of-nsr-synced-neighbors {
      type uint32;
      description
        "Number of NSR-synced/operational neighbors";
    }
    leaf number-of-graceful-restart-neighbors {
      type uint32;
      description
        "Number of Graceful Restart neighbors";
    }
    leaf number-of-downstream-on-demand-neighbors {
      type uint32;
      description
        "Number of Downstream-On-Demand neighbors";
    }
    leaf number-of-ipv4-hello-adj {
      type uint32;
      description
        "Number of LDP discovery IPv4 hello adjacencies";
    }
    leaf number-of-ipv6-hello-adj {
      type uint32;
      description
        "Number of LDP discovery IPv6 hello adjacencies";
    }
    leaf number-of-ipv4-routes {
      type uint32;
      description
        "Number of resolved IPv4 routes";
    }
    leaf number-of-ipv6-routes {
      type uint32;
      description
        "Number of resolved IPv6 routes";
    }
    leaf number-of-ipv4-local-addresses {
      type uint32;
      description
        "Number of IPv4 local addresses";
    }
    leaf number-of-ipv6-local-addresses {
      type uint32;
      description
        "Number of IPv6 local addresses";
    }
    leaf number-of-ldp-interfaces {
      type uint32;
      description
        "Number of LDP configured interfaces";
    }
    leaf number-of-ipv4ldp-interfaces {
      type uint32;
      description
        "Number of LDP IPv4 configured interfaces";
    }
    leaf number-of-ipv6ldp-interfaces {
      type uint32;
      description
        "Number of LDP IPv6 configured interfaces";
    }
    leaf number-of-bindings-ipv4 {
      type uint32;
      description
        "Total number of ipv4 bindings";
    }
    leaf number-of-bindings-ipv6 {
      type uint32;
      description
        "Total number of ipv6 bindings";
    }
    leaf number-of-local-bindings-ipv4 {
      type uint32;
      description
        "Total number of ipv4 local label bindings";
    }
    leaf number-of-local-bindings-ipv6 {
      type uint32;
      description
        "Total number of ipv6 local label bindings";
    }
    leaf number-of-remote-bindings-ipv4 {
      type uint32;
      description
        "Total number of ipv4 remote label bindings";
    }
    leaf number-of-remote-bindings-ipv6 {
      type uint32;
      description
        "Total number of ipv6 remote label bindings";
    }
  }

  grouping ncs_rpc_notif_LDP-SUMMARY-VRF {
    description
      "MPLS LDP per VRF summarized Information";
    container vrf {
      description
        "VRF information";
      uses ncs_rpc_notif_LDP-VRF-INFO;
    }
    container common {
      description
        "Common Summary information";
      uses ncs_rpc_notif_LDP-SUMMARY-COMMON;
    }
  }

  grouping ncs_rpc_notif_LDP-CAP-DESC {
    description
      "MPLS LDP Capability Description";
    leaf type {
      type uint16;
      description
        "Capability type (IANA assigned)";
    }
    leaf description {
      type string {
        length "0..80";
      }
      description
        "Capability description";
    }
    leaf capability-data-length {
      type uint16;
      description
        "Capability data length";
    }
    leaf capability-data {
      type string;
      description
        "Capability data";
    }
  }

  grouping ncs_rpc_notif_LDP-CAP-INFO {
    description
      "MPLS LDP Capability Information";
    container capability {
      description
        "Capability information";
      uses ncs_rpc_notif_LDP-CAP-DESC;
    }
    leaf capability-owner {
      type string;
      description
        "Capability owner";
    }
  }

  grouping ncs_rpc_notif_LDP-IP-ADDR-T-UNION {
    description
      "LDP IP ADDR T UNION";
    leaf afi {
      type ncs_rpc_notif_Ldp-af-id;
      description
        "AFI";
    }
    leaf dummy {
      when "../afi = 'ldp-af-id-none'" {
        tailf:xpath-root 3;
        description
          "../AFI = 'LDP_AF_ID_NONE'";
      }
      type uint8;
      description
        "No Address";
    }
    leaf ipv4 {
      when "../afi = 'ldp-af-id-ipv4'" {
        tailf:xpath-root 3;
        description
          "../AFI = 'LDP_AF_ID_IPV4'";
      }
      type ncs_rpc_notif_Ldp-in-addr;
      description
        "IPv4 address type";
    }
    leaf ipv6 {
      when "../afi = 'ldp-af-id-ipv6'" {
        tailf:xpath-root 3;
        description
          "../AFI = 'LDP_AF_ID_IPV6'";
      }
      type ncs_rpc_notif_Ldp-in6-addr;
      description
        "IPv6 address type";
    }
  }

  grouping ncs_rpc_notif_LDP-GR-DNBR-INTF-INFO {
    description
      "MPLS LDP GR DownNbr Interface Info";
    leaf address-family {
      type ncs_rpc_notif_Ldp-af-id;
      description
        "Interface adj Address Family";
    }
    leaf interface-handle {
      type xr:ncs_rpc_notif_Interface-name;
      description
        "Interfaces handle";
    }
  }

  grouping ncs_rpc_notif_LDP-LDPID-INFO {
    description
      "MPLS LDP Identifier Information";
    leaf lsr-id {
      type inet:ipv4-address;
      description
        "LSR identifier";
    }
    leaf label-space-id {
      type uint16;
      description
        "Label space identifier";
    }
    leaf ldp-id {
      type string;
      description
        "LDP identifier";
    }
  }

  grouping ncs_rpc_notif_LDP-GR-NBR-INFO {
    description
      "MPLS LDP Graceful Restart Neighbor Information";
    container gr-peer {
      description
        "GR peer LDP Id";
      uses ncs_rpc_notif_LDP-LDPID-INFO;
    }
    leaf connect-count {
      type uint32;
      description
        "ConnectCount";
    }
    leaf is-neighbor-up {
      type boolean;
      description
        "Is neighbor up";
    }
    leaf is-liveness-timer-running {
      type boolean;
      description
        "Is liveness timer running";
    }
    leaf liveness-timer-remaining-seconds {
      type uint32;
      description
        "Remaining time from liveness timer";
    }
    leaf is-recovery-timer-running {
      type boolean;
      description
        "Is recovery timer running";
    }
    leaf recovery-timer-remaining-seconds {
      type uint32;
      description
        "Recovery timer remining time";
    }
    leaf down-nbr-flap-count {
      type uint8;
      description
        "Count of back2back flaps";
    }
    leaf down-nbr-flags {
      type uint32;
      description
        "Flags";
    }
    leaf down-nbr-down-reason {
      type uint32;
      description
        "Session down reason code";
    }
    list down-nbr-interface {
      description
        "Interfaces bound to GR down Nbr";
      uses ncs_rpc_notif_LDP-GR-DNBR-INTF-INFO;
    }
    list down-nbr-address {
      description
        "Addresses bound to GR down Nbr";
      uses ncs_rpc_notif_LDP-IP-ADDR-T-UNION;
    }
  }

  grouping ncs_rpc_notif_LDP-VRF-INFO {
    description
      "MPLS LDP VRF information";
    leaf name {
      type string;
      description
        "VRF Name";
    }
    leaf id {
      type uint32;
      description
        "VRF Id";
    }
  }

  grouping ncs_rpc_notif_LDP-GR-GLOBAL-INFO {
    description
      "MPLS LDP Graceful Restart Information";
    container vrf {
      description
        "VRF information";
      uses ncs_rpc_notif_LDP-VRF-INFO;
    }
    leaf is-forwarding-state-hold-timer-running {
      type boolean;
      description
        "Is graceful restart forwarding state hold timer
         running";
    }
    leaf forwarding-state-hold-timer-remaining-seconds {
      type uint32;
      units "second";
      description
        "Forwarding state hold timer remaining time in
         seconds";
    }
    list graceful-restartable-neighbor {
      description
        "Vector of graceful restart neighbor information";
      uses ncs_rpc_notif_LDP-GR-NBR-INFO;
    }
  }

  grouping live_ncs_LDP-SUMMARY {
    description
      "MPLS LDP Summarized Information";
    container common {
      description
        "Common Summary information";
      uses live_ncs_LDP-SUMMARY-COMMON;
    }
    leaf number-of-vrf {
      type uint32;
      description
        "Number of configured VRFs (including default)";
    }
    leaf number-of-vrf-oper {
      type uint32;
      description
        "Number of configured operational VRFs (including
         default)";
    }
    leaf number-of-interfaces {
      type uint32;
      description
        "Number of known interfaces";
    }
    leaf number-of-fwd-ref-interfaces {
      type uint32;
      description
        "Number of Forward Referenc interfaces";
    }
    leaf number-of-autocfg-interfaces {
      type uint32;
      description
        "Number of auto-configured interfaces";
    }
    leaf is-bound-with-sysdb {
      type boolean;
      description
        "Bound status with sysdb";
    }
    leaf is-registered-with-sysdb {
      type boolean;
      description
        "Registration status with Sysdb";
    }
    leaf is-bound-with-rsi {
      type boolean;
      description
        "Bound status with rsi";
    }
    leaf is-bound-with-interface-manager {
      type boolean;
      description
        "Bound status with Interface Manager";
    }
    leaf is-registered-with-interface-manager {
      type boolean;
      description
        "Registration status with Interface Manager";
    }
    leaf is-bound-with-ip-arm {
      type boolean;
      description
        "Bound status with IP Arm";
    }
    leaf is-bound-with-lsd {
      type boolean;
      description
        "Bound status with LSD";
    }
    leaf is-registered-with-lsd {
      type boolean;
      description
        "Registration status with LSD";
    }
    leaf is-bound-with-ipv4-rib {
      type boolean;
      description
        "Bound status with IPv4 RIB";
    }
    leaf is-registered-with-ipv4-rib {
      type boolean;
      description
        "Registration status with IPv4 RIB";
    }
    leaf number-of-ipv4rib-tables {
      type uint32;
      description
        "Total number of ipv4 RIB tables";
    }
    leaf number-of-registered-ipv4rib-tables {
      type uint32;
      description
        "Number of ipv4 RIB tables registered";
    }
    leaf is-bound-with-ipv6-rib {
      type boolean;
      description
        "Bound status with IPv6 RIB";
    }
    leaf is-registered-with-ipv6-rib {
      type boolean;
      description
        "Registration status with IPv6 RIB";
    }
    leaf number-of-ipv6rib-tables {
      type uint32;
      description
        "Total number of ipv6 RIB tables";
    }
    leaf number-of-registered-ipv6rib-tables {
      type uint32;
      description
        "Number of ipv6 RIB tables registered";
    }
    leaf is-bound-with-atom {
      type boolean;
      description
        "Bound status with L2VPN ATOM";
    }
    leaf is-bound-with-nsr-mate {
      type boolean;
      description
        "Bound status with NSR Mate";
    }
    leaf is-nsr-configured {
      type boolean;
      description
        "NSR configured";
    }
    leaf is-mldp-registered {
      type boolean;
      description
        "mLDP registration status";
    }
  }

  grouping live_ncs_LDP-MSG-COUNTERS {
    description
      "MPLS LDP Session Message Counters Information";
    leaf total-count {
      type uint32;
      description
        "Total message count";
    }
    leaf init-count {
      type uint32;
      description
        "Init message count";
    }
    leaf address-count {
      type uint32;
      description
        "Address message count";
    }
    leaf address-withdraw-count {
      type uint32;
      description
        "Address withdraw count";
    }
    leaf label-map-count {
      type uint32;
      description
        "Label map count";
    }
    leaf label-withdraw-count {
      type uint32;
      description
        "Label withdraw count";
    }
    leaf label-release-count {
      type uint32;
      description
        "Label release count";
    }
    leaf label-request-count {
      type uint32;
      description
        "Label request count";
    }
    leaf label-abort-request-count {
      type uint32;
      description
        "Label abort request count";
    }
    leaf notification-count {
      type uint32;
      description
        "Notification count";
    }
    leaf keep-alive-count {
      type uint32;
      description
        "Keepalive count";
    }
    leaf iccp-rg-conn-count {
      type uint32;
      description
        "ICCP RG Connect count";
    }
    leaf iccp-rg-disconn-count {
      type uint32;
      description
        "ICCP RG Disconnect count";
    }
    leaf iccp-rg-notif-count {
      type uint32;
      description
        "ICCP RG Notif count";
    }
    leaf iccp-rg-app-data-count {
      type uint32;
      description
        "ICCP RG App Data count";
    }
  }

  grouping live_ncs_LDP-STATS-INFO {
    description
      "MPLS LDP Statistics Information";
    container message-out {
      description
        "Message out count";
      uses live_ncs_LDP-MSG-COUNTERS;
    }
    container message-in {
      description
        "Message in count";
      uses live_ncs_LDP-MSG-COUNTERS;
    }
    leaf iccp-enabled {
      type boolean;
      description
        "Is session ICCP enabled?";
    }
  }

  grouping live_ncs_LDP-NBR-CLIENTS-INFO {
    description
      "MPLS LDP Session client Information";
    leaf name {
      type string;
      description
        "Client's name";
    }
  }

  grouping live_ncs_LDP-NBR-DETAILED-INFO {
    description
      "MPLS LDP Neighbor Detailed Information";
    container capabilities {
      description
        "Capabilities sent to and received from neighbor";
      uses live_ncs_LDP-NBR-CAP-INFO;
    }
    leaf peer-holdtime {
      type uint32;
      units "second";
      description
        "Session holdtime value in seconds from the peer";
    }
    leaf keep-alive-interval {
      type uint32;
      units "second";
      description
        "Session keepalive interval in seconds";
    }
    leaf peer-state {
      type string {
        length "0..80";
      }
      description
        "Peer state";
    }
    leaf has-ipv4-inbound {
      type boolean;
      description
        "IPv4 Inbound label filtering present";
    }
    leaf inbound-ipv4acl {
      type string {
        length "0..80";
      }
      description
        "IPv4 Inbound accept ACL";
    }
    leaf has-ipv6-inbound {
      type boolean;
      description
        "IPv6 Inbound label filtering present";
    }
    leaf inbound-ipv6acl {
      type string {
        length "0..80";
      }
      description
        "IPv6 Inbound accept ACL";
    }
    leaf has-ipv4-outbound {
      type boolean;
      description
        "IPv4 Outbound label filtering present";
    }
    leaf outbound-ipv4acl {
      type string {
        length "0..80";
      }
      description
        "IPv4 Outbound advertise ACL";
    }
    leaf has-ipv6-outbound {
      type boolean;
      description
        "IPv6 Outbound label filtering present";
    }
    leaf outbound-ipv6acl {
      type string {
        length "0..80";
      }
      description
        "IPv6 Outbound advertise ACL";
    }
    leaf has-sp {
      type boolean;
      description
        "Session Protection enabled";
    }
    leaf sp-state {
      type string {
        length "0..80";
      }
      description
        "Session Protection state";
    }
    leaf sp-has-acl {
      type boolean;
      description
        "Session protection ACL is present";
    }
    leaf spacl {
      type string {
        length "0..80";
      }
      description
        "Session Protection ACL";
    }
    leaf sp-has-duration {
      type boolean;
      description
        "Session Protection has non-default duration";
    }
    leaf sp-duration {
      type uint32;
      units "second";
      description
        "Session protection holdup time duration in
         seconds";
    }
    leaf spht-running {
      type boolean;
      description
        "Session Protection holdup timer is running";
    }
    leaf spht-remaining {
      type uint32;
      units "second";
      description
        "Session Protection holdup time remaining value
         in seconds";
    }
    leaf nsr-sync-state {
      type live_ncs_Mgmt-ldp-nsr-peer-sync-state;
      description
        "NSR Sync State";
    }
    leaf nsr-last-sync-error {
      type live_ncs_Mgmt-ldp-nsr-peer-sync-err;
      description
        "Last NSR sync error";
    }
    leaf nsr-last-sync-nack-reason {
      type live_ncs_Mgmt-ldp-nsr-peer-ldp-sync-nack-rsn;
      description
        "Last NSR sync NACK reaston";
    }
    leaf bgp-advertisement-state {
      type live_ncs_Mgmt-ldp-nbr-bgp-advt-state;
      description
        "BGP labelled prefixes advertisement state";
    }
    leaf advertise-bgp-prefixes {
      type boolean;
      description
        "Is BGP labelled prefixes advertised to the
         neighbor";
    }
    list client {
      description
        "Targeted Session clients";
      uses live_ncs_LDP-NBR-CLIENTS-INFO;
    }
    list ipv4-duplicate-address {
      description
        "Duplicate IPv4 address bound to this peer";
      uses live_ncs_LDP-NBR-ADDR-INFO;
    }
    list ipv6-duplicate-address {
      description
        "Duplicate IPv6 address bound to this peer";
      uses live_ncs_LDP-NBR-ADDR-INFO;
    }
  }

  grouping live_ncs_TARGETED-HELLO {
    description
      "MPLS LDP Targeted Hello Information";
    container local-address {
      description
        "Local Address";
      uses live_ncs_LDP-IP-ADDR-T-UNION;
    }
    container target-address {
      description
        "Target Address";
      uses live_ncs_LDP-IP-ADDR-T-UNION;
    }
    leaf state {
      type live_ncs_Dhcb-state;
      description
        "State";
    }
  }

  grouping live_ncs_LINK-HELLO {
    description
      "MPLS LDP Link Hello Information";
    leaf interface {
      type xr:live_ncs_Interface-name;
      description
        "Interface name";
    }
    leaf interface-name {
      type string;
      description
        "Interface name";
    }
  }

  grouping live_ncs_LDP-ADJ-UNION {
    description
      "LDP ADJ UNION";
    container link-hello-data {
      // NCS drop when statement
      description
        "Link hello";
      uses live_ncs_LINK-HELLO;
    }
    container target-hello-data {
      // NCS drop when statement
      description
        "Target Hello";
      uses live_ncs_TARGETED-HELLO;
    }
    leaf hello-type {
      type live_ncs_Ldp-adj-union-discrim;
      description
        "HelloType";
    }
  }

  grouping live_ncs_LDP-NBR-ADJ-INFO {
    description
      "MPLS LDP Neighbor Adjacency Information";
    container adjacency-group {
      description
        "Adjacency group";
      uses live_ncs_LDP-ADJ-UNION;
    }
  }

  grouping live_ncs_LDP-NBR-ADDR-INFO {
    description
      "MPLS LDP Neighbor Bound Address Information";
    container address {
      description
        "Neighbor Address";
      uses live_ncs_LDP-IP-ADDR-T-UNION;
    }
  }

  grouping live_ncs_LDP-TCP-INFO {
    description
      "MPLS LDP Neighbor TCP Information";
    container foreign-host {
      description
        "Foreign host address";
      uses live_ncs_LDP-IP-ADDR-T-UNION;
    }
    container local-host {
      description
        "Local host address";
      uses live_ncs_LDP-IP-ADDR-T-UNION;
    }
    leaf foreign-port {
      type uint16;
      description
        "Foreign port number";
    }
    leaf local-port {
      type uint16;
      description
        "Local port number";
    }
    leaf is-md5-on {
      type boolean;
      description
        "Is MD5 Digest on";
    }
  }

  grouping live_ncs_LDP-GR-ADJ-INFO {
    description
      "MPLS LDP Neighbor Graceful Restart Adjacency
       Information";
    leaf is-graceful-restartable {
      type boolean;
      description
        "Is graceful restartable";
    }
    leaf reconnect-timeout {
      type uint32;
      description
        "Reconnect timeout";
    }
    leaf recovery-time {
      type uint32;
      description
        "Recovery time";
    }
  }

  grouping live_ncs_LDP-PTCL-ADJ-INFO {
    description
      "MPLS LDP PTCL Adjacency Information";
    container ta-graceful-restart-adjacency {
      description
        "Graceful restart information";
      uses live_ncs_LDP-GR-ADJ-INFO;
    }
    leaf ta-holdtime {
      type uint32;
      description
        "Session holdtime in sec";
    }
    leaf ta-state {
      type string;
      description
        "State";
    }
    leaf ta-pies-sent {
      type uint32;
      description
        "Number of pies sent";
    }
    leaf ta-pies-rcvd {
      type uint32;
      description
        "Number of pies received";
    }
    leaf ta-up-time-seconds {
      type uint32;
      units "second";
      description
        "Up time in seconds";
    }
    leaf downstream-on-demand {
      type boolean;
      description
        "Is Label advertisment mode in Downstream On
         Demand mode or Not";
    }
  }

  grouping live_ncs_LDP-NEIGHBOR-INFO {
    description
      "MPLS LDP Neighbor Information";
    container protocol-information {
      description
        "Protocol Information";
      uses live_ncs_LDP-PTCL-ADJ-INFO;
    }
    container tcp-information {
      description
        "TCP Information";
      uses live_ncs_LDP-TCP-INFO;
    }
    container detailed-information {
      description
        "Detailed information with regards to holdtime,
         KA, inbound filtering, and Session protection";
      uses live_ncs_LDP-NBR-DETAILED-INFO;
    }
    list ldp-nbr-bound-ipv4-address-info {
      description
        "Neighbor IPv4 Address Info";
      uses live_ncs_LDP-NBR-ADDR-INFO;
    }
    list ldp-nbr-bound-ipv6-address-info {
      description
        "Neighbor IPv6 Address Info";
      uses live_ncs_LDP-NBR-ADDR-INFO;
    }
    list ldp-nbr-ipv4-adj-info {
      description
        "Neighbor's IPv4 Adjacency Information";
      uses live_ncs_LDP-NBR-ADJ-INFO;
    }
    list ldp-nbr-ipv6-adj-info {
      description
        "Neighbor's IPv6 Adjacency Information";
      uses live_ncs_LDP-NBR-ADJ-INFO;
    }
  }

  grouping live_ncs_LDP-NBR-CAP-INFO {
    description
      "MPLS LDP Neighbor Capability Information";
    list sent {
      description
        "List of sent capabilities";
      uses live_ncs_LDP-CAP-DESC;
    }
    list received {
      description
        "List of received capabilities";
      uses live_ncs_LDP-CAP-DESC;
    }
  }

  grouping live_ncs_LDP-PARAMETERS-AF {
    description
      "MPLS LDP per AF Parameters Information";
    container discovery-transport-address {
      description
        "Discovery transport address";
      uses live_ncs_LDP-IP-ADDR-T-UNION;
    }
    leaf address-family {
      type live_ncs_Ldp-af;
      description
        "Address Family";
    }
    leaf null-label {
      type string;
      description
        "Null label";
    }
    leaf label-imp-null-override-acl {
      type string;
      description
        "ACL to override local label to use implicit-null";
    }
    leaf is-accepting-targeted-hellos {
      type boolean;
      description
        "Accepting targeted Hellos";
    }
    leaf targeted-hello-acl {
      type string;
      description
        "Targeted Hello ACL";
    }
  }

  grouping live_ncs_LDP-GRACEFUL-RESTART-INFO {
    description
      "MPLS LDP Global Graceful Restart Information";
    leaf is-graceful-restart-configured {
      type boolean;
      description
        "Is graceful restart configured";
    }
    leaf graceful-restart-reconnect-timeout {
      type uint32;
      description
        "Reconnect timeout value";
    }
    leaf graceful-restart-forwarding-state-hold-time {
      type uint32;
      description
        "Graceful restart forward state hold time";
    }
  }

  grouping live_ncs_LDP-PARAMETERS {
    description
      "MPLS LDP Global Parameters";
    container graceful-restart-information {
      description
        "Graceful restart information";
      uses live_ncs_LDP-GRACEFUL-RESTART-INFO;
    }
    leaf role-is-active {
      type boolean;
      description
        "Is process role active or standby";
    }
    leaf global-md5-password-enabled {
      type boolean;
      description
        "Global MD5 password enabled";
    }
    leaf protocol-version {
      type uint32;
      description
        "Protocol version";
    }
    leaf router-id {
      type inet:ipv4-address;
      description
        "Router ID";
    }
    leaf keepalive-interval {
      type uint32;
      description
        "Keepalive interval";
    }
    leaf hello-hold-time {
      type uint32;
      description
        "Hello hold time";
    }
    leaf hello-interval {
      type uint32;
      description
        "Hello interval";
    }
    leaf targeted-hello-hold-time {
      type uint32;
      description
        "Targeted hello hold time";
    }
    leaf targeted-hello-interval {
      type uint32;
      description
        "Targeted hello interval";
    }
    leaf session-hold-time {
      type uint32;
      description
        "Session hold time";
    }
    leaf housekeeping-timer-interval {
      type uint32;
      description
        "Housekeeping periodic timer interval";
    }
    leaf le-no-route-timeout {
      type uint32;
      description
        "LIB entry no route timeout";
    }
    leaf ldp-recovery-timeout {
      type uint32;
      description
        "LDP recovery timeout with LSD";
    }
    leaf af-binding-withdraw-delay {
      type uint32;
      description
        "Delay (sec) in Binding Withdrawal for an Address
         Family";
    }
    leaf max-intf-attached {
      type uint32;
      description
        "Maximum number of LDP enabled attached
         interfaces";
    }
    leaf max-intf-te {
      type uint32;
      description
        "Maximum number of LDP enabled TE interfaces";
    }
    leaf max-peer {
      type uint32;
      description
        "Maximum number of LDP peers";
    }
    leaf ldp-out-of-mem-state {
      type uint32;
      description
        "LDP Out of memory state";
    }
    leaf nsr-enabled {
      type boolean;
      description
        "TRUE if NSR is enabled";
    }
    leaf nsr-synced {
      type boolean;
      description
        "TRUE if LDP is standby and is NSR Sync-ed with
         active";
    }
    leaf igp-sync-delay-time-for-interface {
      type uint32;
      units "second";
      description
        "Interface IGP sync delay time in seconds";
    }
    leaf igp-sync-delay-time-on-restart {
      type uint32;
      units "second";
      description
        "IGP sync delay time on process restart in
         seconds";
    }
    leaf global-discovery-quick-start-disabled {
      type boolean;
      description
        "Discovery quick-start globally disabled";
    }
    leaf discovery-quick-start-disabled-on-interfaces {
      type boolean;
      description
        "Discovery quick-start disabled on some
         LDP-enabled interfaces";
    }
    list address-family-parameter {
      description
        "Per AF parameters";
      uses live_ncs_LDP-PARAMETERS-AF;
    }
  }

  grouping live_ncs_LDP-NSR-SUM-SESS {
    description
      "MPLS LDP NSR session summary";
    leaf total {
      type uint32;
      description
        "Total sessions";
    }
    leaf nsr-eligible {
      type uint32;
      description
        "NSR eligible sessions";
    }
    leaf nsr-state-none {
      type uint32;
      description
        "Number of sessions in NSR none state";
    }
    leaf nsr-state-wait {
      type uint32;
      description
        "Number of sessions in NSR wait state";
    }
    leaf nsr-state-ready {
      type uint32;
      description
        "Number of sessions in NSR ready state";
    }
    leaf nsr-state-prepare {
      type uint32;
      description
        "Number of sessions in NSR prepare state";
    }
    leaf nsr-state-app-wait {
      type uint32;
      description
        "Number of sessions in NSR app-wait state";
    }
    leaf nsr-state-operational {
      type uint32;
      description
        "Number of sessions in NSR operational state";
    }
    leaf nsr-state-tcp-phase1 {
      type uint32;
      description
        "Number of sessions in NSR TCP phase 1 state";
    }
    leaf nsr-state-tcp-phase2 {
      type uint32;
      description
        "Number of sessions in NSR TCP phase 2 state";
    }
  }

  grouping live_ncs_LDP-NSR-SUM {
    description
      "MPLS LDP NSR summary";
    container vrf {
      description
        "VRF information";
      uses live_ncs_LDP-VRF-INFO;
    }
    container sessions {
      description
        "Session summary";
      uses live_ncs_LDP-NSR-SUM-SESS;
    }
  }

  grouping live_ncs_LDP-BACKOFF-ENTRY-INFO {
    description
      "MPLS LDP Session Backoff Entry Information";
    leaf backoff-seconds {
      type uint32;
      units "second";
      description
        "Backoff seconds";
    }
    leaf waiting-seconds {
      type uint32;
      units "second";
      description
        "Backoff waiting seconds";
    }
  }

  grouping live_ncs_LDP-BACKOFF-INFO {
    description
      "MPLS LDP Session Backoff Information";
    leaf initial-seconds {
      type uint32;
      units "second";
      description
        "Initial backoff value in seconds";
    }
    leaf maximum-seconds {
      type uint32;
      units "second";
      description
        "Maximum backoff value in seconds";
    }
  }

  grouping live_ncs_LDP-NEIGHBOR-BRIEF-AF-INFO {
    description
      "MPLS LDP Neighbor Brief AF information";
    leaf address-family {
      type live_ncs_Ldp-af;
      description
        "Neighbor Brief Address Family";
    }
    leaf num-of-nbr-discovery {
      type uint32;
      description
        "Number of neighbor discovery sources";
    }
    leaf num-of-nbr-addresses {
      type uint32;
      description
        "Number of neighbor addresses";
    }
    leaf num-of-nbr-lbl {
      type uint32;
      description
        "Number of neighbor labels";
    }
  }

  grouping live_ncs_LDP-NEIGHBOR-BRIEF-INFO {
    description
      "MPLS LDP Neighbor Brief Information";
    container vrf {
      description
        "VRF information";
      uses live_ncs_LDP-VRF-INFO;
    }
    leaf is-graceful-restartable {
      type boolean;
      description
        "Is graceful restartable";
    }
    leaf nsr-state {
      type live_ncs_Show-nsr-state;
      description
        "NSR readiness state";
    }
    leaf up-time-seconds {
      type uint32;
      units "second";
      description
        "Up time in seconds";
    }
    list nbr-br-af-info {
      // NCS drop max-elements statement
      description
        "Neighbor Brief AF Info";
      uses live_ncs_LDP-NEIGHBOR-BRIEF-AF-INFO;
    }
  }

  grouping live_ncs_LDP-FWD-RW-PATH-SUMM {
    description
      "MPLS LDP fowarding rewrite nexthop/path summary";
    leaf total-paths {
      type uint32;
      description
        "Total path count";
    }
    leaf protected-paths {
      type uint32;
      description
        "Count of FRR protected paths";
    }
    leaf backup-paths {
      type uint32;
      description
        "Count of non-primary backup paths";
    }
    leaf remote-backup-paths {
      type uint32;
      description
        "Count of non-primary remote backup paths";
    }
    leaf labeled-paths {
      type uint32;
      description
        "Count of all labeled paths";
    }
    leaf labeled-backup-paths {
      type uint32;
      description
        "Count of labeled backup paths";
    }
  }

  grouping live_ncs_LDP-FWD-RW-PFX-LBL-SUMM {
    description
      "MPLS LDP forwarding rewrite prefix nexthops
       labeled summary";
    leaf labeled-pfxs {
      type uint16;
      description
        "Count of labeled prefixes with 1 or more paths
         labeled";
    }
    leaf labeled-pfxs-partial {
      type uint16;
      description
        "Count of labeled prefixes with some (but not
         ALL) paths labeled";
    }
    leaf unlabeled-pfxs {
      type uint16;
      description
        "Count of labeled prefixes with ALL paths
         unlabeled";
    }
  }

  grouping live_ncs_LDP-FWD-RW-PFX-SUMM {
    description
      "MPLS LDP fowarding rewrite prefix summary";
    container labeled-pfxs-aggr {
      description
        "Labeled prefix count for all paths";
      uses live_ncs_LDP-FWD-RW-PFX-LBL-SUMM;
    }
    container labeled-pfxs-primary {
      description
        "Labeled prefix count related to primary paths
         only";
      uses live_ncs_LDP-FWD-RW-PFX-LBL-SUMM;
    }
    container labeled-pfxs-backup {
      description
        "Labeled prefix count related to backup paths
         only";
      uses live_ncs_LDP-FWD-RW-PFX-LBL-SUMM;
    }
    leaf total-pfxs {
      type uint16;
      description
        "Total Prefix count";
    }
    leaf ecmp-pfxs {
      type uint16;
      description
        "Count of prefixes with ECMP";
    }
    leaf protected-pfxs {
      type uint16;
      description
        "Count of FRR protected prefixes";
    }
  }

  grouping live_ncs_LDP-FWD-RW-SUMM {
    description
      "MPLS LDP fowarding rewrite summary";
    container pfxs {
      description
        "Forwarding rewrites prefix summary";
      uses live_ncs_LDP-FWD-RW-PFX-SUMM;
    }
    container nhs {
      description
        "Forwarding rewrites nexthops (paths) summary";
      uses live_ncs_LDP-FWD-RW-PATH-SUMM;
    }
  }

  grouping live_ncs_LDP-FWD-SUMM-INFO {
    description
      "MPLS LDP fowarding summary";
    container vrf {
      description
        "VRF information";
      uses live_ncs_LDP-VRF-INFO;
    }
    container rws {
      description
        "Forwarding rewrites summary";
      uses live_ncs_LDP-FWD-RW-SUMM;
    }
    leaf is-lsd-bound {
      type boolean;
      description
        "LDP is connected to LSD server";
    }
    leaf fsht {
      type uint16;
      description
        "Forwarding state hold time registered with LSD";
    }
    leaf intfs {
      type uint16;
      description
        "MPLS forwarding enabled interface count";
    }
    leaf lbls {
      type uint16;
      description
        "Local label allocated count";
    }
  }

  grouping live_ncs_LDP-BINDING-ALLOC {
    description
      "MPLS LDP Binding local label allocation filter";
    leaf has-acl {
      type boolean;
      description
        "Has ACL filter?";
    }
    leaf prefix-acl {
      type string {
        length "0..64";
      }
      description
        "Prefix ACL";
    }
    leaf is-host-route-only {
      type boolean;
      description
        "Host-routes only?";
    }
  }

  grouping live_ncs_LDP-BINDING-ADVT-ACL-PAIR {
    description
      "MPLS LDP Binding advertisement ACL pair";
    leaf prefix-acl {
      type string {
        length "0..64";
      }
      description
        "Prefix ACL";
    }
    leaf peer-acl {
      type string {
        length "0..64";
      }
      description
        "Peer ACL";
    }
  }

  grouping live_ncs_LDP-BINDING-ADVT-SPEC {
    description
      "MPLS LDP Binding advertisement specification ACLs";
    container allocation-acl {
      description
        "Local label Allocation filter";
      uses live_ncs_LDP-BINDING-ALLOC;
    }
    list advt-acl {
      description
        "Advertisement ACLs";
      uses live_ncs_LDP-BINDING-ADVT-ACL-PAIR;
    }
  }

  grouping live_ncs_LDP-FWD-PATH-RLFA-MOI-INFO {
    description
      "MPLS LDP Forwarding Path Remote LFA-FRR backup
       MPLS MOI info";
    list stack {
      description
        "Inner label stack info";
      uses live_ncs_LDP-FWD-PATH-MPLS-NH-INFO;
    }
  }

  grouping live_ncs_LDP-FWD-PATH-RLFA-MPLS-INFO {
    description
      "MPLS LDP Forwarding Path Remote LFA-FRR backup
       MPLS info";
    container mpls-outgoing-info {
      description
        "Remote LFA MPLS nexthop(s_ info";
      uses live_ncs_LDP-FWD-PATH-RLFA-MOI-INFO;
    }
    leaf has-remote-lfa-bkup {
      type boolean;
      description
        "Whether path has remote LFA backup";
    }
  }

  grouping live_ncs_LDP-FWD-PATH-MPLS-NH-INFO {
    description
      "Forwarding Path MPLS nexthop info";
    container nexthop-peer-ldp-ident {
      description
        "Nexthop LDP peer";
      uses live_ncs_LDP-LDPID-INFO;
    }
    leaf out-label {
      type uint32;
      description
        "Outgoing label";
    }
    leaf out-label-rsn {
      type live_ncs_Ldp-fwd-unlbl-rsn;
      description
        "Outgoing label reason";
    }
    leaf out-label-type {
      type live_ncs_Label-value;
      description
        "Outgoing Label Type";
    }
    leaf out-label-owner {
      type live_ncs_Ldp-route-path-lbl-owner;
      description
        "Outgoing label owner";
    }
    leaf is-from-graceful-restartable-neighbor {
      type boolean;
      description
        "Is from a GR neighbor";
    }
    leaf is-stale {
      type boolean;
      description
        "Is the entry stale";
    }
    leaf entropy-label-capability {
      type boolean;
      description
        "Entropy Label Capability";
    }
  }

  grouping live_ncs_LDP-FWD-PATH-MPLS-INFO {
    description
      "MPLS LDP Forwarding Path MPLS information";
    container mpls-outgoing-info {
      description
        "MPLS nexthop info";
      uses live_ncs_LDP-FWD-PATH-MPLS-NH-INFO;
    }
    container remote-lfa {
      description
        "Remote LFA-FRR backup info";
      uses live_ncs_LDP-FWD-PATH-RLFA-MPLS-INFO;
    }
  }

  grouping live_ncs_LDP-FWD-PATH-RLFA-ROUTING-INFO {
    description
      "MPLS LDP Forwarding Path Remote LFA-FRR backup
       routing info";
    container remote-p-node-id {
      description
        "Remote/P node address";
      uses live_ncs_LDP-IP-ADDR-T-UNION;
    }
    container remote-q-node-id {
      description
        "Remote/Q node address";
      uses live_ncs_LDP-IP-ADDR-T-UNION;
    }
    leaf has-remote-lfa-bkup {
      type boolean;
      description
        "Whether path has remote LFA backup";
    }
    leaf needs-tldp {
      type boolean;
      description
        "Whether TLDP is needed with remote PQ node";
    }
    leaf has-q-node {
      type boolean;
      description
        "Whether remote LFA path has a Q node associated";
    }
  }

  grouping live_ncs_LDP-FWD-PATH-ROUTING-INFO {
    description
      "MPLS LDP Forwarding Path IP Routing information";
    container next-hop {
      description
        "Next Hop";
      uses live_ncs_LDP-IP-ADDR-T-UNION;
    }
    container remote-lfa {
      description
        "Remote LFA-FRR backup info";
      uses live_ncs_LDP-FWD-PATH-RLFA-ROUTING-INFO;
    }
    leaf interface {
      type xr:live_ncs_Interface-name;
      description
        "Interface name";
    }
    leaf interface-name {
      type string;
      description
        "Interface Name";
    }
    leaf nh-is-overriden {
      type boolean;
      description
        "Nexthop is overriden by LDP";
    }
    leaf nexthop-id {
      type uint32;
      description
        "Nexthop Identifier";
    }
    leaf next-hop-table-id {
      type uint32;
      description
        "Table ID for nexthop address";
    }
    leaf flags {
      type uint32;
      description
        "Route path flags";
    }
    leaf load-metric {
      type uint32;
      description
        "Path's load metric for load balancing";
    }
    leaf binding-label {
      type uint32;
      description
        "Binding label obtained via RIB";
    }
    leaf path-id {
      type uint8;
      description
        "path Id";
    }
    leaf bkup-path-id {
      type uint8;
      description
        "Backup path Id";
    }
    leaf path-flags {
      type live_ncs_Ldp-route-path-flags;
      description
        "Routing path flags decoded";
    }
  }

  grouping live_ncs_LDP-FWD-PATH-INFO {
    description
      "MPLS LDP Forwarding Path info";
    container routing {
      description
        "IP routing information";
      uses live_ncs_LDP-FWD-PATH-ROUTING-INFO;
    }
    container mpls {
      description
        "MPLS information";
      uses live_ncs_LDP-FWD-PATH-MPLS-INFO;
    }
  }

  grouping live_ncs_LDP-FWD-ROUTE-MPLS-INFO {
    description
      "MPLS LDP Forwarding Route LDP information";
    leaf local-label {
      type uint32;
      description
        "Local label";
    }
    leaf forwarding-update-count {
      type uint32;
      description
        "Number of forwarding updates";
    }
    leaf forwarding-update-timestamp {
      type uint64;
      description
        "Last Forwarding update nanosec timestamp";
    }
    leaf forwarding-update-age {
      type uint64;
      description
        "Last Forwarding update nanosec age";
    }
  }

  grouping live_ncs_LDP-FWD-ROUTE-ROUTING-INFO {
    description
      "MPLS LDP Forwarding Route IP Routing information";
    leaf version {
      type uint32;
      description
        "Route RIB ersion";
    }
    leaf priority {
      type uint8;
      description
        "Route priority";
    }
    leaf source {
      type uint16;
      description
        "Route source protol Id";
    }
    leaf type {
      type uint16;
      description
        "Route type";
    }
    leaf flags {
      type uint32;
      description
        "Route RIB flags";
    }
    leaf metric {
      type uint32;
      description
        "Route metric";
    }
    leaf is-local-vrf-leaked {
      type boolean;
      description
        "Is route leaked across local VRFs?";
    }
    leaf routing-update-count {
      type uint32;
      description
        "Number of routing updates";
    }
    leaf routing-update-timestamp {
      type uint64;
      description
        "Last Routing update nanosec timestamp";
    }
    leaf routing-update-age {
      type uint64;
      description
        "Last Routing update nanosec age";
    }
    leaf sr-local-label {
      type uint32;
      description
        "SR Local-label";
    }
  }

  grouping live_ncs_LDP-FWD-ROUTE-INFO {
    description
      "MPLS LDP Forwarding Route information";
    container routing {
      description
        "IP routing information";
      uses live_ncs_LDP-FWD-ROUTE-ROUTING-INFO;
    }
    container mpls {
      description
        "MPLS information";
      uses live_ncs_LDP-FWD-ROUTE-MPLS-INFO;
    }
  }

  grouping live_ncs_LDP-FWD-PFX-INFO {
    description
      "MPLS LDP Forwarding Prefix Information";
    container vrf {
      description
        "VRF information";
      uses live_ncs_LDP-VRF-INFO;
    }
    container prefix-xr {
      description
        "IP Prefix";
      uses live_ncs_LDP-IP-ADDR-T-UNION;
    }
    container route {
      description
        "Route";
      uses live_ncs_LDP-FWD-ROUTE-INFO;
    }
    leaf table-id {
      type uint32;
      description
        "Table ID associated with IP prefix";
    }
    leaf prefix-length {
      type uint8;
      description
        "Prefix length";
    }
    list paths {
      description
        "Paths";
      uses live_ncs_LDP-FWD-PATH-INFO;
    }
  }

  grouping live_ncs_LDP-DISCOVERY-ADJ-GRP-INFO {
    description
      "MPLS LDP Discovery Adjacency Group Information";
    leaf adjacency-group-up-time {
      type uint32;
      units "second";
      description
        "Adjacency group up time in seconds";
    }
    leaf tcp-open-count {
      type uint32;
      description
        "Count of attempted TCP opens";
    }
    leaf tcp-arb-chg-count {
      type uint32;
      description
        "Count of changes in TCP arbitration";
    }
    leaf tcp-role {
      type uint32;
      description
        "TCP Role";
    }
  }

  grouping live_ncs_LDP-TARGETED-HELLO-BRIEF-INFO {
    description
      "MPLS LDP Discovery Targeted Brief Information";
    container vrf {
      description
        "VRF information";
      uses live_ncs_LDP-VRF-INFO;
    }
    container dhcb-target-address {
      description
        "DHCB target address";
      uses live_ncs_LDP-IP-ADDR-T-UNION;
    }
    leaf address-family {
      type live_ncs_Ldp-af;
      description
        "Targeted Discovery Address Family";
    }
    list hello-information {
      description
        "LDP hello info";
      uses live_ncs_LDP-HELLO-BRIEF-INFO;
    }
  }

  grouping live_ncs_LDP-HELLO-BRIEF-INFO {
    description
      "MPLS LDP Hello Brief Information";
    leaf neighbor-ldp-identifier {
      type string;
      description
        "Neighbor LDP Identifier";
    }
    leaf hold-time {
      type uint32;
      description
        "Session hold time in sec";
    }
    leaf session-up {
      type boolean;
      description
        "Is session up for this adj";
    }
  }

  grouping live_ncs_LDP-DISCOVERY-LINK-BRIEF-INFO {
    description
      "MPLS LDP Discovery Link Brief Information";
    container vrf {
      description
        "VRF information";
      uses live_ncs_LDP-VRF-INFO;
    }
    leaf address-family {
      type live_ncs_Ldp-af;
      description
        "Discovery Brief Address Family";
    }
    leaf address-family-set {
      type live_ncs_Ldp-af;
      description
        "Discovery Brief Address Family Set";
    }
    leaf interface {
      type xr:live_ncs_Interface-name;
      description
        "Interface name";
    }
    leaf interface-name-xr {
      type string;
      description
        "Interface name";
    }
    list hello-information {
      description
        "LDP hello info";
      uses live_ncs_LDP-HELLO-BRIEF-INFO;
    }
  }

  grouping live_ncs_LDP-TARGETED-HELLO-INFO {
    description
      "MPLS LDP Targeted Hello Information";
    container dhcb-local-address {
      description
        "DHCB local address";
      uses live_ncs_LDP-IP-ADDR-T-UNION;
    }
    container dhcb-target-address {
      description
        "DHCB target address";
      uses live_ncs_LDP-IP-ADDR-T-UNION;
    }
    leaf state {
      type live_ncs_Dhcb-state;
      description
        "Targeted hello state";
    }
    leaf adjacency-ldp-identifier {
      type string;
      description
        "Adjacency LDP Identifier";
    }
    leaf interval {
      type uint32;
      description
        "Hello interval in sec";
    }
    leaf next-hello {
      type uint32;
      description
        "Next hello due time in msec";
    }
    leaf hold-time {
      type uint32;
      description
        "Targeted hello hold time";
    }
    leaf local-hold-time {
      type uint32;
      description
        "Local hold time";
    }
    leaf neighbor-hold-time {
      type uint32;
      description
        "Neighbor hold time";
    }
    leaf disc-expiry {
      type uint32;
      description
        "Discovery expiry time in msec";
    }
    leaf quick-start-disabled {
      type boolean;
      description
        "Quick-start disabled";
    }
    leaf established-time {
      type uint64;
      description
        "Hello adjacency estabished time in nanosec";
    }
    leaf established-age {
      type uint64;
      description
        "Hello adjacency estabished age in nanosec";
    }
    leaf session-up {
      type boolean;
      description
        "Is session up for this adj";
    }
    leaf session-bringup-failure-reason {
      type string;
      description
        "session bringup failure reason";
    }
    list last-session-down-info {
      description
        "Last session down information";
      uses live_ncs_LDP-LAST-SESS-INFO;
    }
  }

  grouping live_ncs_LDP-DISCOVERY-SUMMARY-INFO {
    description
      "MPLS LDP Discovery Summary Information";
    container vrf {
      description
        "VRF information";
      uses live_ncs_LDP-VRF-INFO;
    }
    leaf local-ldp-id {
      type string;
      description
        "Local LDP identifier";
    }
    leaf num-of-ldp-interfaces {
      type uint32;
      description
        "Total Number of LDP configured interfaces";
    }
    leaf num-of-active-ldp-interfaces {
      type uint32;
      description
        "Number of active LDP enabled interfaces";
    }
    leaf num-of-lnk-disc-xmit {
      type uint32;
      description
        "Number of link hello discoveries in xmit state";
    }
    leaf num-of-tgt-disc-xmit {
      type uint32;
      description
        "Number of targeted hello discoveries in xmit
         state";
    }
    leaf num-of-lnk-disc-recv {
      type uint32;
      description
        "Number of link hello discoveries in recv state";
    }
    leaf num-of-tgt-disc-recv {
      type uint32;
      description
        "Number of targeted hello discoveries in recv
         state";
    }
    leaf num-of-disc-with-bad-addr-recv {
      type uint32;
      description
        "Number of hello discoveries received with bad
         source address";
    }
    leaf num-of-disc-with-bad-hello-pdu {
      type uint32;
      description
        "Number of hello discoveries received with bad
         hello PDU";
    }
    leaf num-of-disc-with-bad-xport-addr {
      type uint32;
      description
        "Number of hello discoveries received with bad
         export address";
    }
    leaf num-of-disc-with-same-router-id {
      type uint32;
      description
        "Number of hello discoveries received with the
         same router id as this router";
    }
    leaf num-of-disc-with-wrong-router-id {
      type uint32;
      description
        "Number of hello discoveries received with the
         router id that is not destined for this router";
    }
  }

  grouping live_ncs_LDP-DISCOVERY-LINK-AF-INFO {
    description
      "MPLS LDP Discovery Link Address Family
       Information";
    container local-src-address {
      description
        "Local source address";
      uses live_ncs_LDP-IP-ADDR-T-UNION;
    }
    container local-transport-address {
      description
        "Local transport address";
      uses live_ncs_LDP-IP-ADDR-T-UNION;
    }
    leaf interval {
      type uint32;
      description
        "Hello interval in sec";
    }
  }

  grouping live_ncs_LDP-LAST-SESS-INFO {
    description
      "LDP last down session information";
    leaf last-session-down-reason {
      type string;
      description
        "The reason of last socket failure";
    }
    leaf last-session-down-time {
      type uint64;
      description
        "Timestamp of when the last session went down";
    }
    leaf last-session-up-time {
      type uint32;
      description
        "The time duration the last session was up";
    }
  }

  grouping live_ncs_LDP-HELLO-INFO {
    description
      "MPLS LDP Hello Information";
    container neighbor-src-address {
      description
        "Neighbor source address";
      uses live_ncs_LDP-IP-ADDR-T-UNION;
    }
    container neighbor-transport-address {
      description
        "Neighbor transport address";
      uses live_ncs_LDP-IP-ADDR-T-UNION;
    }
    container target {
      description
        "Target address";
      uses live_ncs_LDP-IP-ADDR-T-UNION;
    }
    leaf neighbor-ldp-identifier {
      type string;
      description
        "Neighbor LDP Identifier";
    }
    leaf is-no-route {
      type boolean;
      description
        "Is route valid";
    }
    leaf hold-time {
      type uint32;
      units "second";
      description
        "Session hold time in seconds";
    }
    leaf local-hold-time {
      type uint32;
      units "second";
      description
        "Local hold time in seconds";
    }
    leaf neighbor-hold-time {
      type uint32;
      units "second";
      description
        "Neighbor hold time in seconds";
    }
    leaf disc-expiry {
      type uint32;
      description
        "Discovery expiry time in sec";
    }
    leaf is-targeted {
      type boolean;
      description
        "Is session a targeted session";
    }
    leaf session-up {
      type boolean;
      description
        "Is session up for this adj";
    }
    leaf established-time {
      type uint64;
      description
        "Hello adjacency estabished time in nanosec";
    }
    leaf established-age {
      type uint64;
      description
        "Hello adjacency estabished age in nanosec";
    }
    leaf session-bringup-failure-reason {
      type string;
      description
        "session bringup failure reason";
    }
    list last-session-down-info {
      description
        "Last session down information";
      uses live_ncs_LDP-LAST-SESS-INFO;
    }
  }

  grouping live_ncs_LDP-DISCOVERY-LINK-INFO {
    description
      "MPLS LDP Discovery Link Information";
    container vrf {
      description
        "VRF information";
      uses live_ncs_LDP-VRF-INFO;
    }
    leaf next-hello {
      type uint32;
      description
        "Next hello due time in msec";
    }
    leaf interface {
      type xr:live_ncs_Interface-name;
      description
        "Interface name";
    }
    leaf interface-name-xr {
      type string;
      description
        "Interface name";
    }
    leaf quick-start-disabled {
      type boolean;
      description
        "Quick-start disabled";
    }
    list hello-information {
      description
        "LDP hello info";
      uses live_ncs_LDP-HELLO-INFO;
    }
    list discovery-link-af {
      // NCS drop max-elements statement
      description
        "LDP hello AF info";
      uses live_ncs_LDP-DISCOVERY-LINK-AF-INFO;
    }
  }

  grouping live_ncs_LDP-INTF-AUTOCFG {
    description
      "MPLS LDP auto configure";
    leaf tuple {
      type string;
      description
        "Tuple";
    }
  }

  grouping live_ncs_LDP-INTF-TE-MESH-GRP {
    description
      "MPLS LDP interface tunnel mesh group";
    leaf ldp-te-mesh-group-all-cfgd {
      type boolean;
      description
        "LDP has enabled all TE mesh-groups";
    }
    leaf ldp-mesh-group-enabled {
      type boolean;
      description
        "LDP has enabled this TE mesh-group";
    }
    leaf te-mesh-group-id {
      type uint32;
      description
        "TE tunnel Mesh Group ID";
    }
  }

  grouping live_ncs_LDP-INTF {
    description
      "MPLS LDP interface information";
    container vrf {
      description
        "VRF information";
      uses live_ncs_LDP-VRF-INFO;
    }
    leaf interface {
      type xr:live_ncs_Interface-name;
      description
        "Interface name";
    }
    leaf interface-name-xr {
      type string;
      description
        "Interface name";
    }
    leaf ldp-enabled {
      type boolean;
      description
        "LDP enabled";
    }
    leaf is-im-stale {
      type boolean;
      description
        "Is IM information stale";
    }
    leaf ldp-config-mode {
      type boolean;
      description
        "LDP config mode";
    }
    leaf ldp-autoconfig-disable {
      type boolean;
      description
        "LDP autoconfig disable";
    }
    list te-mesh-grp {
      description
        "TE tunnel mesh-group";
      uses live_ncs_LDP-INTF-TE-MESH-GRP;
    }
    list auto-config {
      description
        "Auto config";
      uses live_ncs_LDP-INTF-AUTOCFG;
    }
  }

  grouping live_ncs_LDP-BINDING-SUMMARY-AF {
    description
      "MPLS LDP Binding Summary AF Information";
    leaf address-family {
      type live_ncs_Ldp-af;
      description
        "Binding Summary Address Family";
    }
    leaf last-lib-update {
      type uint32;
      description
        "Last update to LIB local binding";
    }
    leaf lib-minimum-revision-sent-all {
      type uint32;
      description
        "Last update sent to all peers";
    }
    leaf binding-total {
      type uint32;
      description
        "Total bindings";
    }
    leaf binding-local {
      type uint32;
      description
        "Number of local bindings";
    }
    leaf binding-remote {
      type uint32;
      description
        "Number of remote bindings";
    }
  }

  grouping live_ncs_LDP-BINDING-SUMMARY {
    description
      "MPLS LDP Binding Summary Information";
    container vrf {
      description
        "VRF information";
      uses live_ncs_LDP-VRF-INFO;
    }
    leaf address-family {
      type live_ncs_Ldp-af;
      description
        "Address Family";
    }
    leaf binding-no-route {
      type uint32;
      description
        "Bindings with no route";
    }
    leaf binding-local-no-route {
      type uint32;
      description
        "Local bindings with no route";
    }
    leaf binding-local-null {
      type uint32;
      description
        "Number of local null bindings";
    }
    leaf binding-local-implicit-null {
      type uint32;
      description
        "Number of local implicit null bindings";
    }
    leaf binding-local-explicit-null {
      type uint32;
      description
        "Number of local explicit null bindings";
    }
    leaf binding-local-non-null {
      type uint32;
      description
        "Number of local non-null bindings";
    }
    leaf binding-local-oor {
      type uint32;
      description
        "Number of local bindings        needing label -
         OOR";
    }
    leaf lowest-allocated-label {
      type uint32;
      description
        "Lowest allocated label";
    }
    leaf highest-allocated-label {
      type uint32;
      description
        "Highest allocated label";
    }
    list bind-af {
      // NCS drop max-elements statement
      description
        "bind af";
      uses live_ncs_LDP-BINDING-SUMMARY-AF;
    }
  }

  grouping live_ncs_LDP-IGP-SYNC-DELAY-RESTART-INFO {
    description
      "MPLS LDP IGP Sync Restart Delay Information";
    leaf configured {
      type boolean;
      description
        "Is restart delay configured";
    }
    leaf delay-secs {
      type uint32;
      description
        "Delay time";
    }
    leaf timer-running {
      type boolean;
      description
        "Is restart delay timer running";
    }
    leaf remaining-secs {
      type uint32;
      description
        "Delay timer remaining time";
    }
  }

  grouping live_ncs_LDP-IGP-SYNC-INTF-GR-ONLY {
    description
      "MPLS LDP IGP Sync Interface GR-only reachable
       Peer Information";
    leaf peer-id {
      type live_ncs_String-td2;
      description
        "Peer Identifier";
    }
    leaf is-chkpt-created {
      type boolean;
      description
        "Is created due to checkpointing";
    }
  }

  grouping live_ncs_LDP-IGP-SYNC-INTF-PEER {
    description
      "MPLS LDP IGP Sync Interface Peer Information";
    leaf peer-id {
      type live_ncs_String-td2;
      description
        "Peer Identifier";
    }
    leaf is-gr-enabled {
      type boolean;
      description
        "Is GR enabled session";
    }
  }

  grouping live_ncs_LDP-IGP-SYNC-INFO {
    description
      "MPLS LDP IGP Sync Information";
    container vrf {
      description
        "VRF information";
      uses live_ncs_LDP-VRF-INFO;
    }
    leaf interface-name-xr {
      type string;
      description
        "Interface name";
    }
    leaf igp-sync-state {
      type live_ncs_Ldp-igp-sync-state;
      description
        "IGP Sync state";
    }
    leaf igp-sync-delay {
      type uint32;
      units "second";
      description
        "IGP sync delay in seconds";
    }
    leaf is-delay-timer-running {
      type boolean;
      description
        "Is sync delay timer running";
    }
    leaf delay-timer-remaining {
      type uint32;
      units "second";
      description
        "Remaining timer (seconds) till expiry of sync
         delay timer";
    }
    leaf igp-sync-down-reason {
      type live_ncs_Ldp-igp-sync-down-reason;
      description
        "Reason IGP Sync Not Achieved";
    }
    list peers {
      description
        "Interface Peers";
      uses live_ncs_LDP-IGP-SYNC-INTF-PEER;
    }
    list gr-only-peer {
      description
        "Interface GR-only reachable peers";
      uses live_ncs_LDP-IGP-SYNC-INTF-GR-ONLY;
    }
  }

  grouping live_ncs_LDP-TIB-ENTRY-REMOTE {
    description
      "MPLS LDP Remote Binding Information";
    container assigning-peer-ldp-ident {
      description
        "Assigning peer";
      uses live_ncs_LDP-LDPID-INFO;
    }
    leaf remote-label {
      type uint32;
      description
        "Remote Label";
    }
    leaf is-stale {
      type boolean;
      description
        "Is the entry stale";
    }
    leaf is-elc {
      type boolean;
      description
        "Is the entry entropy label capable";
    }
  }

  grouping live_ncs_LDP-TIB-ENTRY-DETAIL {
    description
      "MPLS LDP Binding Detail Information";
    container vrf {
      description
        "VRF information";
      uses live_ncs_LDP-VRF-INFO;
    }
    container prefix-xr {
      description
        "IP Prefix";
      uses live_ncs_LDP-IP-ADDR-T-UNION;
    }
    leaf prefix-length {
      type uint8;
      description
        "Prefix Length";
    }
    leaf local-label {
      type uint32;
      description
        "Local label";
    }
    leaf le-local-binding-revision {
      type uint32;
      description
        "Local Binding revision";
    }
    leaf le-local-label-state {
      type live_ncs_Local-label-state;
      description
        "Local label state";
    }
    leaf is-no-route {
      type boolean;
      description
        "No route";
    }
    leaf label-oor {
      type boolean;
      description
        "Label space depletion OOR";
    }
    leaf advertise-prefix-acl {
      type string;
      description
        "Advertise Prerfix ACL";
    }
    leaf advertise-tsr-acl {
      type string;
      description
        "Advertise TSR ACL";
    }
    leaf config-enforced-local-label-value {
      type boolean;
      description
        "Config/User enforced local label value";
    }
    leaf is-elc {
      type boolean;
      description
        "Is the entry entropy label capable";
    }
    list remote-binding {
      description
        "Remote binding";
      uses live_ncs_LDP-TIB-ENTRY-REMOTE;
    }
    list peers-advertised-to {
      description
        "Peers this entry is advertised to";
      uses live_ncs_LDP-LDPID-INFO;
    }
    list peers-acked {
      description
        "Peers that have ACKed this entry";
      uses live_ncs_LDP-LDPID-INFO;
    }
  }

  grouping live_ncs_LDP-INTF-SUM {
    description
      "MPLS LDP interface summary";
    leaf known-ip-interface-count {
      type uint32;
      description
        "Number of known IP Interfaces";
    }
    leaf known-ip-interface-ldp-enabled {
      type uint32;
      description
        "Number of known IP Interfaces with LDP Enabled";
    }
    leaf ldp-configured-attached-interface {
      type uint32;
      description
        "Number of attached interfaces configured in LDP";
    }
    leaf ldp-configured-te-interface {
      type uint32;
      description
        "Number of TE tunnel interfaces configured in LDP";
    }
    leaf forward-references {
      type uint32;
      description
        "Number of forward referenced interfaces";
    }
    leaf auto-config-disabled {
      type uint32;
      description
        "Autoconfigure disabled";
    }
    leaf auto-config {
      type uint32;
      description
        "Auto-configured interfaces";
    }
    leaf auto-config-forward-reference-interfaces {
      type uint32;
      description
        "Auto-configured forward references";
    }
  }

  grouping live_ncs_LDP-SUMMARY-COMMON {
    description
      "MPLS LDP common summary Information";
    leaf address-families {
      type live_ncs_Ldp-af;
      description
        "Address Families enabled";
    }
    leaf number-of-ipv4af {
      type uint32;
      description
        "Number of IPv4 address-families enabled";
    }
    leaf number-of-ipv6af {
      type uint32;
      description
        "Number of IPv6 address-families enabled";
    }
    leaf number-of-neighbors {
      type uint32;
      description
        "Number of neighbors";
    }
    leaf number-of-adj-grps {
      type uint32;
      description
        "Number of Adjacency Groups";
    }
    leaf number-of-nsr-synced-neighbors {
      type uint32;
      description
        "Number of NSR-synced/operational neighbors";
    }
    leaf number-of-graceful-restart-neighbors {
      type uint32;
      description
        "Number of Graceful Restart neighbors";
    }
    leaf number-of-downstream-on-demand-neighbors {
      type uint32;
      description
        "Number of Downstream-On-Demand neighbors";
    }
    leaf number-of-ipv4-hello-adj {
      type uint32;
      description
        "Number of LDP discovery IPv4 hello adjacencies";
    }
    leaf number-of-ipv6-hello-adj {
      type uint32;
      description
        "Number of LDP discovery IPv6 hello adjacencies";
    }
    leaf number-of-ipv4-routes {
      type uint32;
      description
        "Number of resolved IPv4 routes";
    }
    leaf number-of-ipv6-routes {
      type uint32;
      description
        "Number of resolved IPv6 routes";
    }
    leaf number-of-ipv4-local-addresses {
      type uint32;
      description
        "Number of IPv4 local addresses";
    }
    leaf number-of-ipv6-local-addresses {
      type uint32;
      description
        "Number of IPv6 local addresses";
    }
    leaf number-of-ldp-interfaces {
      type uint32;
      description
        "Number of LDP configured interfaces";
    }
    leaf number-of-ipv4ldp-interfaces {
      type uint32;
      description
        "Number of LDP IPv4 configured interfaces";
    }
    leaf number-of-ipv6ldp-interfaces {
      type uint32;
      description
        "Number of LDP IPv6 configured interfaces";
    }
    leaf number-of-bindings-ipv4 {
      type uint32;
      description
        "Total number of ipv4 bindings";
    }
    leaf number-of-bindings-ipv6 {
      type uint32;
      description
        "Total number of ipv6 bindings";
    }
    leaf number-of-local-bindings-ipv4 {
      type uint32;
      description
        "Total number of ipv4 local label bindings";
    }
    leaf number-of-local-bindings-ipv6 {
      type uint32;
      description
        "Total number of ipv6 local label bindings";
    }
    leaf number-of-remote-bindings-ipv4 {
      type uint32;
      description
        "Total number of ipv4 remote label bindings";
    }
    leaf number-of-remote-bindings-ipv6 {
      type uint32;
      description
        "Total number of ipv6 remote label bindings";
    }
  }

  grouping live_ncs_LDP-SUMMARY-VRF {
    description
      "MPLS LDP per VRF summarized Information";
    container vrf {
      description
        "VRF information";
      uses live_ncs_LDP-VRF-INFO;
    }
    container common {
      description
        "Common Summary information";
      uses live_ncs_LDP-SUMMARY-COMMON;
    }
  }

  grouping live_ncs_LDP-CAP-DESC {
    description
      "MPLS LDP Capability Description";
    leaf type {
      type uint16;
      description
        "Capability type (IANA assigned)";
    }
    leaf description {
      type string {
        length "0..80";
      }
      description
        "Capability description";
    }
    leaf capability-data-length {
      type uint16;
      description
        "Capability data length";
    }
    leaf capability-data {
      type string;
      description
        "Capability data";
    }
  }

  grouping live_ncs_LDP-CAP-INFO {
    description
      "MPLS LDP Capability Information";
    container capability {
      description
        "Capability information";
      uses live_ncs_LDP-CAP-DESC;
    }
    leaf capability-owner {
      type string;
      description
        "Capability owner";
    }
  }

  grouping live_ncs_LDP-IP-ADDR-T-UNION {
    description
      "LDP IP ADDR T UNION";
    leaf afi {
      type live_ncs_Ldp-af-id;
      description
        "AFI";
    }
    leaf dummy {
      // NCS drop when statement
      type uint8;
      description
        "No Address";
    }
    leaf ipv4 {
      // NCS drop when statement
      type live_ncs_Ldp-in-addr;
      description
        "IPv4 address type";
    }
    leaf ipv6 {
      // NCS drop when statement
      type live_ncs_Ldp-in6-addr;
      description
        "IPv6 address type";
    }
  }

  grouping live_ncs_LDP-GR-DNBR-INTF-INFO {
    description
      "MPLS LDP GR DownNbr Interface Info";
    leaf address-family {
      type live_ncs_Ldp-af-id;
      description
        "Interface adj Address Family";
    }
    leaf interface-handle {
      type xr:live_ncs_Interface-name;
      description
        "Interfaces handle";
    }
  }

  grouping live_ncs_LDP-LDPID-INFO {
    description
      "MPLS LDP Identifier Information";
    leaf lsr-id {
      type inet:ipv4-address;
      description
        "LSR identifier";
    }
    leaf label-space-id {
      type uint16;
      description
        "Label space identifier";
    }
    leaf ldp-id {
      type string;
      description
        "LDP identifier";
    }
  }

  grouping live_ncs_LDP-GR-NBR-INFO {
    description
      "MPLS LDP Graceful Restart Neighbor Information";
    container gr-peer {
      description
        "GR peer LDP Id";
      uses live_ncs_LDP-LDPID-INFO;
    }
    leaf connect-count {
      type uint32;
      description
        "ConnectCount";
    }
    leaf is-neighbor-up {
      type boolean;
      description
        "Is neighbor up";
    }
    leaf is-liveness-timer-running {
      type boolean;
      description
        "Is liveness timer running";
    }
    leaf liveness-timer-remaining-seconds {
      type uint32;
      description
        "Remaining time from liveness timer";
    }
    leaf is-recovery-timer-running {
      type boolean;
      description
        "Is recovery timer running";
    }
    leaf recovery-timer-remaining-seconds {
      type uint32;
      description
        "Recovery timer remining time";
    }
    leaf down-nbr-flap-count {
      type uint8;
      description
        "Count of back2back flaps";
    }
    leaf down-nbr-flags {
      type uint32;
      description
        "Flags";
    }
    leaf down-nbr-down-reason {
      type uint32;
      description
        "Session down reason code";
    }
    list down-nbr-interface {
      description
        "Interfaces bound to GR down Nbr";
      uses live_ncs_LDP-GR-DNBR-INTF-INFO;
    }
    list down-nbr-address {
      description
        "Addresses bound to GR down Nbr";
      uses live_ncs_LDP-IP-ADDR-T-UNION;
    }
  }

  grouping live_ncs_LDP-VRF-INFO {
    description
      "MPLS LDP VRF information";
    leaf name {
      type string;
      description
        "VRF Name";
    }
    leaf id {
      type uint32;
      description
        "VRF Id";
    }
  }

  grouping live_ncs_LDP-GR-GLOBAL-INFO {
    description
      "MPLS LDP Graceful Restart Information";
    container vrf {
      description
        "VRF information";
      uses live_ncs_LDP-VRF-INFO;
    }
    leaf is-forwarding-state-hold-timer-running {
      type boolean;
      description
        "Is graceful restart forwarding state hold timer
         running";
    }
    leaf forwarding-state-hold-timer-remaining-seconds {
      type uint32;
      units "second";
      description
        "Forwarding state hold timer remaining time in
         seconds";
    }
    list graceful-restartable-neighbor {
      description
        "Vector of graceful restart neighbor information";
      uses live_ncs_LDP-GR-NBR-INFO;
    }
  }

  grouping LDP-SUMMARY {
    description
      "MPLS LDP Summarized Information";
    container common {
      description
        "Common Summary information";
      uses LDP-SUMMARY-COMMON;
    }
    leaf number-of-vrf {
      type uint32;
      description
        "Number of configured VRFs (including default)";
    }
    leaf number-of-vrf-oper {
      type uint32;
      description
        "Number of configured operational VRFs (including
         default)";
    }
    leaf number-of-interfaces {
      type uint32;
      description
        "Number of known interfaces";
    }
    leaf number-of-fwd-ref-interfaces {
      type uint32;
      description
        "Number of Forward Referenc interfaces";
    }
    leaf number-of-autocfg-interfaces {
      type uint32;
      description
        "Number of auto-configured interfaces";
    }
    leaf is-bound-with-sysdb {
      type boolean;
      description
        "Bound status with sysdb";
    }
    leaf is-registered-with-sysdb {
      type boolean;
      description
        "Registration status with Sysdb";
    }
    leaf is-bound-with-rsi {
      type boolean;
      description
        "Bound status with rsi";
    }
    leaf is-bound-with-interface-manager {
      type boolean;
      description
        "Bound status with Interface Manager";
    }
    leaf is-registered-with-interface-manager {
      type boolean;
      description
        "Registration status with Interface Manager";
    }
    leaf is-bound-with-ip-arm {
      type boolean;
      description
        "Bound status with IP Arm";
    }
    leaf is-bound-with-lsd {
      type boolean;
      description
        "Bound status with LSD";
    }
    leaf is-registered-with-lsd {
      type boolean;
      description
        "Registration status with LSD";
    }
    leaf is-bound-with-ipv4-rib {
      type boolean;
      description
        "Bound status with IPv4 RIB";
    }
    leaf is-registered-with-ipv4-rib {
      type boolean;
      description
        "Registration status with IPv4 RIB";
    }
    leaf number-of-ipv4rib-tables {
      type uint32;
      description
        "Total number of ipv4 RIB tables";
    }
    leaf number-of-registered-ipv4rib-tables {
      type uint32;
      description
        "Number of ipv4 RIB tables registered";
    }
    leaf is-bound-with-ipv6-rib {
      type boolean;
      description
        "Bound status with IPv6 RIB";
    }
    leaf is-registered-with-ipv6-rib {
      type boolean;
      description
        "Registration status with IPv6 RIB";
    }
    leaf number-of-ipv6rib-tables {
      type uint32;
      description
        "Total number of ipv6 RIB tables";
    }
    leaf number-of-registered-ipv6rib-tables {
      type uint32;
      description
        "Number of ipv6 RIB tables registered";
    }
    leaf is-bound-with-atom {
      type boolean;
      description
        "Bound status with L2VPN ATOM";
    }
    leaf is-bound-with-nsr-mate {
      type boolean;
      description
        "Bound status with NSR Mate";
    }
    leaf is-nsr-configured {
      type boolean;
      description
        "NSR configured";
    }
    leaf is-mldp-registered {
      type boolean;
      description
        "mLDP registration status";
    }
  }

  grouping LDP-MSG-COUNTERS {
    description
      "MPLS LDP Session Message Counters Information";
    leaf total-count {
      type uint32;
      description
        "Total message count";
    }
    leaf init-count {
      type uint32;
      description
        "Init message count";
    }
    leaf address-count {
      type uint32;
      description
        "Address message count";
    }
    leaf address-withdraw-count {
      type uint32;
      description
        "Address withdraw count";
    }
    leaf label-map-count {
      type uint32;
      description
        "Label map count";
    }
    leaf label-withdraw-count {
      type uint32;
      description
        "Label withdraw count";
    }
    leaf label-release-count {
      type uint32;
      description
        "Label release count";
    }
    leaf label-request-count {
      type uint32;
      description
        "Label request count";
    }
    leaf label-abort-request-count {
      type uint32;
      description
        "Label abort request count";
    }
    leaf notification-count {
      type uint32;
      description
        "Notification count";
    }
    leaf keep-alive-count {
      type uint32;
      description
        "Keepalive count";
    }
    leaf iccp-rg-conn-count {
      type uint32;
      description
        "ICCP RG Connect count";
    }
    leaf iccp-rg-disconn-count {
      type uint32;
      description
        "ICCP RG Disconnect count";
    }
    leaf iccp-rg-notif-count {
      type uint32;
      description
        "ICCP RG Notif count";
    }
    leaf iccp-rg-app-data-count {
      type uint32;
      description
        "ICCP RG App Data count";
    }
  }

  grouping LDP-STATS-INFO {
    description
      "MPLS LDP Statistics Information";
    container message-out {
      description
        "Message out count";
      uses LDP-MSG-COUNTERS;
    }
    container message-in {
      description
        "Message in count";
      uses LDP-MSG-COUNTERS;
    }
    leaf iccp-enabled {
      type boolean;
      description
        "Is session ICCP enabled?";
    }
  }

  grouping LDP-NBR-CLIENTS-INFO {
    description
      "MPLS LDP Session client Information";
    leaf name {
      type string;
      description
        "Client's name";
    }
  }

  grouping LDP-NBR-DETAILED-INFO {
    description
      "MPLS LDP Neighbor Detailed Information";
    container capabilities {
      description
        "Capabilities sent to and received from neighbor";
      uses LDP-NBR-CAP-INFO;
    }
    leaf peer-holdtime {
      type uint32;
      units "second";
      description
        "Session holdtime value in seconds from the peer";
    }
    leaf keep-alive-interval {
      type uint32;
      units "second";
      description
        "Session keepalive interval in seconds";
    }
    leaf peer-state {
      type string {
        length "0..80";
      }
      description
        "Peer state";
    }
    leaf has-ipv4-inbound {
      type boolean;
      description
        "IPv4 Inbound label filtering present";
    }
    leaf inbound-ipv4acl {
      type string {
        length "0..80";
      }
      description
        "IPv4 Inbound accept ACL";
    }
    leaf has-ipv6-inbound {
      type boolean;
      description
        "IPv6 Inbound label filtering present";
    }
    leaf inbound-ipv6acl {
      type string {
        length "0..80";
      }
      description
        "IPv6 Inbound accept ACL";
    }
    leaf has-ipv4-outbound {
      type boolean;
      description
        "IPv4 Outbound label filtering present";
    }
    leaf outbound-ipv4acl {
      type string {
        length "0..80";
      }
      description
        "IPv4 Outbound advertise ACL";
    }
    leaf has-ipv6-outbound {
      type boolean;
      description
        "IPv6 Outbound label filtering present";
    }
    leaf outbound-ipv6acl {
      type string {
        length "0..80";
      }
      description
        "IPv6 Outbound advertise ACL";
    }
    leaf has-sp {
      type boolean;
      description
        "Session Protection enabled";
    }
    leaf sp-state {
      type string {
        length "0..80";
      }
      description
        "Session Protection state";
    }
    leaf sp-has-acl {
      type boolean;
      description
        "Session protection ACL is present";
    }
    leaf spacl {
      type string {
        length "0..80";
      }
      description
        "Session Protection ACL";
    }
    leaf sp-has-duration {
      type boolean;
      description
        "Session Protection has non-default duration";
    }
    leaf sp-duration {
      type uint32;
      units "second";
      description
        "Session protection holdup time duration in
         seconds";
    }
    leaf spht-running {
      type boolean;
      description
        "Session Protection holdup timer is running";
    }
    leaf spht-remaining {
      type uint32;
      units "second";
      description
        "Session Protection holdup time remaining value
         in seconds";
    }
    leaf nsr-sync-state {
      type Mgmt-ldp-nsr-peer-sync-state;
      description
        "NSR Sync State";
    }
    leaf nsr-last-sync-error {
      type Mgmt-ldp-nsr-peer-sync-err;
      description
        "Last NSR sync error";
    }
    leaf nsr-last-sync-nack-reason {
      type Mgmt-ldp-nsr-peer-ldp-sync-nack-rsn;
      description
        "Last NSR sync NACK reaston";
    }
    leaf bgp-advertisement-state {
      type Mgmt-ldp-nbr-bgp-advt-state;
      description
        "BGP labelled prefixes advertisement state";
    }
    leaf advertise-bgp-prefixes {
      type boolean;
      description
        "Is BGP labelled prefixes advertised to the
         neighbor";
    }
    list client {
      description
        "Targeted Session clients";
      uses LDP-NBR-CLIENTS-INFO;
    }
    list ipv4-duplicate-address {
      description
        "Duplicate IPv4 address bound to this peer";
      uses LDP-NBR-ADDR-INFO;
    }
    list ipv6-duplicate-address {
      description
        "Duplicate IPv6 address bound to this peer";
      uses LDP-NBR-ADDR-INFO;
    }
  }

  grouping TARGETED-HELLO {
    description
      "MPLS LDP Targeted Hello Information";
    container local-address {
      description
        "Local Address";
      uses LDP-IP-ADDR-T-UNION;
    }
    container target-address {
      description
        "Target Address";
      uses LDP-IP-ADDR-T-UNION;
    }
    leaf state {
      type Dhcb-state;
      description
        "State";
    }
  }

  grouping LINK-HELLO {
    description
      "MPLS LDP Link Hello Information";
    leaf interface {
      type xr:Interface-name;
      description
        "Interface name";
    }
    leaf interface-name {
      type string;
      description
        "Interface name";
    }
  }

  grouping LDP-ADJ-UNION {
    description
      "LDP ADJ UNION";
    container link-hello-data {
      when "../hello-type = 'link-hello'" {
        tailf:xpath-root 3;
        description
          "../HelloType = 'LinkHello'";
      }
      description
        "Link hello";
      uses LINK-HELLO;
    }
    container target-hello-data {
      when "../hello-type = 'targeted-hello'" {
        tailf:xpath-root 3;
        description
          "../HelloType = 'TargetedHello'";
      }
      description
        "Target Hello";
      uses TARGETED-HELLO;
    }
    leaf hello-type {
      type Ldp-adj-union-discrim;
      description
        "HelloType";
    }
  }

  grouping LDP-NBR-ADJ-INFO {
    description
      "MPLS LDP Neighbor Adjacency Information";
    container adjacency-group {
      description
        "Adjacency group";
      uses LDP-ADJ-UNION;
    }
  }

  grouping LDP-NBR-ADDR-INFO {
    description
      "MPLS LDP Neighbor Bound Address Information";
    container address {
      description
        "Neighbor Address";
      uses LDP-IP-ADDR-T-UNION;
    }
  }

  grouping LDP-TCP-INFO {
    description
      "MPLS LDP Neighbor TCP Information";
    container foreign-host {
      description
        "Foreign host address";
      uses LDP-IP-ADDR-T-UNION;
    }
    container local-host {
      description
        "Local host address";
      uses LDP-IP-ADDR-T-UNION;
    }
    leaf foreign-port {
      type uint16;
      description
        "Foreign port number";
    }
    leaf local-port {
      type uint16;
      description
        "Local port number";
    }
    leaf is-md5-on {
      type boolean;
      description
        "Is MD5 Digest on";
    }
  }

  grouping LDP-GR-ADJ-INFO {
    description
      "MPLS LDP Neighbor Graceful Restart Adjacency
       Information";
    leaf is-graceful-restartable {
      type boolean;
      description
        "Is graceful restartable";
    }
    leaf reconnect-timeout {
      type uint32;
      description
        "Reconnect timeout";
    }
    leaf recovery-time {
      type uint32;
      description
        "Recovery time";
    }
  }

  grouping LDP-PTCL-ADJ-INFO {
    description
      "MPLS LDP PTCL Adjacency Information";
    container ta-graceful-restart-adjacency {
      description
        "Graceful restart information";
      uses LDP-GR-ADJ-INFO;
    }
    leaf ta-holdtime {
      type uint32;
      description
        "Session holdtime in sec";
    }
    leaf ta-state {
      type string;
      description
        "State";
    }
    leaf ta-pies-sent {
      type uint32;
      description
        "Number of pies sent";
    }
    leaf ta-pies-rcvd {
      type uint32;
      description
        "Number of pies received";
    }
    leaf ta-up-time-seconds {
      type uint32;
      units "second";
      description
        "Up time in seconds";
    }
    leaf downstream-on-demand {
      type boolean;
      description
        "Is Label advertisment mode in Downstream On
         Demand mode or Not";
    }
  }

  grouping LDP-NEIGHBOR-INFO {
    description
      "MPLS LDP Neighbor Information";
    container protocol-information {
      description
        "Protocol Information";
      uses LDP-PTCL-ADJ-INFO;
    }
    container tcp-information {
      description
        "TCP Information";
      uses LDP-TCP-INFO;
    }
    container detailed-information {
      description
        "Detailed information with regards to holdtime,
         KA, inbound filtering, and Session protection";
      uses LDP-NBR-DETAILED-INFO;
    }
    list ldp-nbr-bound-ipv4-address-info {
      description
        "Neighbor IPv4 Address Info";
      uses LDP-NBR-ADDR-INFO;
    }
    list ldp-nbr-bound-ipv6-address-info {
      description
        "Neighbor IPv6 Address Info";
      uses LDP-NBR-ADDR-INFO;
    }
    list ldp-nbr-ipv4-adj-info {
      description
        "Neighbor's IPv4 Adjacency Information";
      uses LDP-NBR-ADJ-INFO;
    }
    list ldp-nbr-ipv6-adj-info {
      description
        "Neighbor's IPv6 Adjacency Information";
      uses LDP-NBR-ADJ-INFO;
    }
  }

  grouping LDP-NBR-CAP-INFO {
    description
      "MPLS LDP Neighbor Capability Information";
    list sent {
      description
        "List of sent capabilities";
      uses LDP-CAP-DESC;
    }
    list received {
      description
        "List of received capabilities";
      uses LDP-CAP-DESC;
    }
  }

  grouping LDP-PARAMETERS-AF {
    description
      "MPLS LDP per AF Parameters Information";
    container discovery-transport-address {
      description
        "Discovery transport address";
      uses LDP-IP-ADDR-T-UNION;
    }
    leaf address-family {
      type Ldp-af;
      description
        "Address Family";
    }
    leaf null-label {
      type string;
      description
        "Null label";
    }
    leaf label-imp-null-override-acl {
      type string;
      description
        "ACL to override local label to use implicit-null";
    }
    leaf is-accepting-targeted-hellos {
      type boolean;
      description
        "Accepting targeted Hellos";
    }
    leaf targeted-hello-acl {
      type string;
      description
        "Targeted Hello ACL";
    }
  }

  grouping LDP-GRACEFUL-RESTART-INFO {
    description
      "MPLS LDP Global Graceful Restart Information";
    leaf is-graceful-restart-configured {
      type boolean;
      description
        "Is graceful restart configured";
    }
    leaf graceful-restart-reconnect-timeout {
      type uint32;
      description
        "Reconnect timeout value";
    }
    leaf graceful-restart-forwarding-state-hold-time {
      type uint32;
      description
        "Graceful restart forward state hold time";
    }
  }

  grouping LDP-PARAMETERS {
    description
      "MPLS LDP Global Parameters";
    container graceful-restart-information {
      description
        "Graceful restart information";
      uses LDP-GRACEFUL-RESTART-INFO;
    }
    leaf role-is-active {
      type boolean;
      description
        "Is process role active or standby";
    }
    leaf global-md5-password-enabled {
      type boolean;
      description
        "Global MD5 password enabled";
    }
    leaf protocol-version {
      type uint32;
      description
        "Protocol version";
    }
    leaf router-id {
      type inet:ipv4-address;
      description
        "Router ID";
    }
    leaf keepalive-interval {
      type uint32;
      description
        "Keepalive interval";
    }
    leaf hello-hold-time {
      type uint32;
      description
        "Hello hold time";
    }
    leaf hello-interval {
      type uint32;
      description
        "Hello interval";
    }
    leaf targeted-hello-hold-time {
      type uint32;
      description
        "Targeted hello hold time";
    }
    leaf targeted-hello-interval {
      type uint32;
      description
        "Targeted hello interval";
    }
    leaf session-hold-time {
      type uint32;
      description
        "Session hold time";
    }
    leaf housekeeping-timer-interval {
      type uint32;
      description
        "Housekeeping periodic timer interval";
    }
    leaf le-no-route-timeout {
      type uint32;
      description
        "LIB entry no route timeout";
    }
    leaf ldp-recovery-timeout {
      type uint32;
      description
        "LDP recovery timeout with LSD";
    }
    leaf af-binding-withdraw-delay {
      type uint32;
      description
        "Delay (sec) in Binding Withdrawal for an Address
         Family";
    }
    leaf max-intf-attached {
      type uint32;
      description
        "Maximum number of LDP enabled attached
         interfaces";
    }
    leaf max-intf-te {
      type uint32;
      description
        "Maximum number of LDP enabled TE interfaces";
    }
    leaf max-peer {
      type uint32;
      description
        "Maximum number of LDP peers";
    }
    leaf ldp-out-of-mem-state {
      type uint32;
      description
        "LDP Out of memory state";
    }
    leaf nsr-enabled {
      type boolean;
      description
        "TRUE if NSR is enabled";
    }
    leaf nsr-synced {
      type boolean;
      description
        "TRUE if LDP is standby and is NSR Sync-ed with
         active";
    }
    leaf igp-sync-delay-time-for-interface {
      type uint32;
      units "second";
      description
        "Interface IGP sync delay time in seconds";
    }
    leaf igp-sync-delay-time-on-restart {
      type uint32;
      units "second";
      description
        "IGP sync delay time on process restart in
         seconds";
    }
    leaf global-discovery-quick-start-disabled {
      type boolean;
      description
        "Discovery quick-start globally disabled";
    }
    leaf discovery-quick-start-disabled-on-interfaces {
      type boolean;
      description
        "Discovery quick-start disabled on some
         LDP-enabled interfaces";
    }
    list address-family-parameter {
      description
        "Per AF parameters";
      uses LDP-PARAMETERS-AF;
    }
  }

  grouping LDP-NSR-SUM-SESS {
    description
      "MPLS LDP NSR session summary";
    leaf total {
      type uint32;
      description
        "Total sessions";
    }
    leaf nsr-eligible {
      type uint32;
      description
        "NSR eligible sessions";
    }
    leaf nsr-state-none {
      type uint32;
      description
        "Number of sessions in NSR none state";
    }
    leaf nsr-state-wait {
      type uint32;
      description
        "Number of sessions in NSR wait state";
    }
    leaf nsr-state-ready {
      type uint32;
      description
        "Number of sessions in NSR ready state";
    }
    leaf nsr-state-prepare {
      type uint32;
      description
        "Number of sessions in NSR prepare state";
    }
    leaf nsr-state-app-wait {
      type uint32;
      description
        "Number of sessions in NSR app-wait state";
    }
    leaf nsr-state-operational {
      type uint32;
      description
        "Number of sessions in NSR operational state";
    }
    leaf nsr-state-tcp-phase1 {
      type uint32;
      description
        "Number of sessions in NSR TCP phase 1 state";
    }
    leaf nsr-state-tcp-phase2 {
      type uint32;
      description
        "Number of sessions in NSR TCP phase 2 state";
    }
  }

  grouping LDP-NSR-SUM {
    description
      "MPLS LDP NSR summary";
    container vrf {
      description
        "VRF information";
      uses LDP-VRF-INFO;
    }
    container sessions {
      description
        "Session summary";
      uses LDP-NSR-SUM-SESS;
    }
  }

  grouping LDP-BACKOFF-ENTRY-INFO {
    description
      "MPLS LDP Session Backoff Entry Information";
    leaf backoff-seconds {
      type uint32;
      units "second";
      description
        "Backoff seconds";
    }
    leaf waiting-seconds {
      type uint32;
      units "second";
      description
        "Backoff waiting seconds";
    }
  }

  grouping LDP-BACKOFF-INFO {
    description
      "MPLS LDP Session Backoff Information";
    leaf initial-seconds {
      type uint32;
      units "second";
      description
        "Initial backoff value in seconds";
    }
    leaf maximum-seconds {
      type uint32;
      units "second";
      description
        "Maximum backoff value in seconds";
    }
  }

  grouping LDP-NEIGHBOR-BRIEF-AF-INFO {
    description
      "MPLS LDP Neighbor Brief AF information";
    leaf address-family {
      type Ldp-af;
      description
        "Neighbor Brief Address Family";
    }
    leaf num-of-nbr-discovery {
      type uint32;
      description
        "Number of neighbor discovery sources";
    }
    leaf num-of-nbr-addresses {
      type uint32;
      description
        "Number of neighbor addresses";
    }
    leaf num-of-nbr-lbl {
      type uint32;
      description
        "Number of neighbor labels";
    }
  }

  grouping LDP-NEIGHBOR-BRIEF-INFO {
    description
      "MPLS LDP Neighbor Brief Information";
    container vrf {
      description
        "VRF information";
      uses LDP-VRF-INFO;
    }
    leaf is-graceful-restartable {
      type boolean;
      description
        "Is graceful restartable";
    }
    leaf nsr-state {
      type Show-nsr-state;
      description
        "NSR readiness state";
    }
    leaf up-time-seconds {
      type uint32;
      units "second";
      description
        "Up time in seconds";
    }
    list nbr-br-af-info {
      max-elements 2;
      description
        "Neighbor Brief AF Info";
      uses LDP-NEIGHBOR-BRIEF-AF-INFO;
    }
  }

  grouping LDP-FWD-RW-PATH-SUMM {
    description
      "MPLS LDP fowarding rewrite nexthop/path summary";
    leaf total-paths {
      type uint32;
      description
        "Total path count";
    }
    leaf protected-paths {
      type uint32;
      description
        "Count of FRR protected paths";
    }
    leaf backup-paths {
      type uint32;
      description
        "Count of non-primary backup paths";
    }
    leaf remote-backup-paths {
      type uint32;
      description
        "Count of non-primary remote backup paths";
    }
    leaf labeled-paths {
      type uint32;
      description
        "Count of all labeled paths";
    }
    leaf labeled-backup-paths {
      type uint32;
      description
        "Count of labeled backup paths";
    }
  }

  grouping LDP-FWD-RW-PFX-LBL-SUMM {
    description
      "MPLS LDP forwarding rewrite prefix nexthops
       labeled summary";
    leaf labeled-pfxs {
      type uint16;
      description
        "Count of labeled prefixes with 1 or more paths
         labeled";
    }
    leaf labeled-pfxs-partial {
      type uint16;
      description
        "Count of labeled prefixes with some (but not
         ALL) paths labeled";
    }
    leaf unlabeled-pfxs {
      type uint16;
      description
        "Count of labeled prefixes with ALL paths
         unlabeled";
    }
  }

  grouping LDP-FWD-RW-PFX-SUMM {
    description
      "MPLS LDP fowarding rewrite prefix summary";
    container labeled-pfxs-aggr {
      description
        "Labeled prefix count for all paths";
      uses LDP-FWD-RW-PFX-LBL-SUMM;
    }
    container labeled-pfxs-primary {
      description
        "Labeled prefix count related to primary paths
         only";
      uses LDP-FWD-RW-PFX-LBL-SUMM;
    }
    container labeled-pfxs-backup {
      description
        "Labeled prefix count related to backup paths
         only";
      uses LDP-FWD-RW-PFX-LBL-SUMM;
    }
    leaf total-pfxs {
      type uint16;
      description
        "Total Prefix count";
    }
    leaf ecmp-pfxs {
      type uint16;
      description
        "Count of prefixes with ECMP";
    }
    leaf protected-pfxs {
      type uint16;
      description
        "Count of FRR protected prefixes";
    }
  }

  grouping LDP-FWD-RW-SUMM {
    description
      "MPLS LDP fowarding rewrite summary";
    container pfxs {
      description
        "Forwarding rewrites prefix summary";
      uses LDP-FWD-RW-PFX-SUMM;
    }
    container nhs {
      description
        "Forwarding rewrites nexthops (paths) summary";
      uses LDP-FWD-RW-PATH-SUMM;
    }
  }

  grouping LDP-FWD-SUMM-INFO {
    description
      "MPLS LDP fowarding summary";
    container vrf {
      description
        "VRF information";
      uses LDP-VRF-INFO;
    }
    container rws {
      description
        "Forwarding rewrites summary";
      uses LDP-FWD-RW-SUMM;
    }
    leaf is-lsd-bound {
      type boolean;
      description
        "LDP is connected to LSD server";
    }
    leaf fsht {
      type uint16;
      description
        "Forwarding state hold time registered with LSD";
    }
    leaf intfs {
      type uint16;
      description
        "MPLS forwarding enabled interface count";
    }
    leaf lbls {
      type uint16;
      description
        "Local label allocated count";
    }
  }

  grouping LDP-BINDING-ALLOC {
    description
      "MPLS LDP Binding local label allocation filter";
    leaf has-acl {
      type boolean;
      description
        "Has ACL filter?";
    }
    leaf prefix-acl {
      type string {
        length "0..64";
      }
      description
        "Prefix ACL";
    }
    leaf is-host-route-only {
      type boolean;
      description
        "Host-routes only?";
    }
  }

  grouping LDP-BINDING-ADVT-ACL-PAIR {
    description
      "MPLS LDP Binding advertisement ACL pair";
    leaf prefix-acl {
      type string {
        length "0..64";
      }
      description
        "Prefix ACL";
    }
    leaf peer-acl {
      type string {
        length "0..64";
      }
      description
        "Peer ACL";
    }
  }

  grouping LDP-BINDING-ADVT-SPEC {
    description
      "MPLS LDP Binding advertisement specification ACLs";
    container allocation-acl {
      description
        "Local label Allocation filter";
      uses LDP-BINDING-ALLOC;
    }
    list advt-acl {
      description
        "Advertisement ACLs";
      uses LDP-BINDING-ADVT-ACL-PAIR;
    }
  }

  grouping LDP-FWD-PATH-RLFA-MOI-INFO {
    description
      "MPLS LDP Forwarding Path Remote LFA-FRR backup
       MPLS MOI info";
    list stack {
      description
        "Inner label stack info";
      uses LDP-FWD-PATH-MPLS-NH-INFO;
    }
  }

  grouping LDP-FWD-PATH-RLFA-MPLS-INFO {
    description
      "MPLS LDP Forwarding Path Remote LFA-FRR backup
       MPLS info";
    container mpls-outgoing-info {
      description
        "Remote LFA MPLS nexthop(s_ info";
      uses LDP-FWD-PATH-RLFA-MOI-INFO;
    }
    leaf has-remote-lfa-bkup {
      type boolean;
      description
        "Whether path has remote LFA backup";
    }
  }

  grouping LDP-FWD-PATH-MPLS-NH-INFO {
    description
      "Forwarding Path MPLS nexthop info";
    container nexthop-peer-ldp-ident {
      description
        "Nexthop LDP peer";
      uses LDP-LDPID-INFO;
    }
    leaf out-label {
      type uint32;
      description
        "Outgoing label";
    }
    leaf out-label-rsn {
      type Ldp-fwd-unlbl-rsn;
      description
        "Outgoing label reason";
    }
    leaf out-label-type {
      type Label-value;
      description
        "Outgoing Label Type";
    }
    leaf out-label-owner {
      type Ldp-route-path-lbl-owner;
      description
        "Outgoing label owner";
    }
    leaf is-from-graceful-restartable-neighbor {
      type boolean;
      description
        "Is from a GR neighbor";
    }
    leaf is-stale {
      type boolean;
      description
        "Is the entry stale";
    }
    leaf entropy-label-capability {
      type boolean;
      description
        "Entropy Label Capability";
    }
  }

  grouping LDP-FWD-PATH-MPLS-INFO {
    description
      "MPLS LDP Forwarding Path MPLS information";
    container mpls-outgoing-info {
      description
        "MPLS nexthop info";
      uses LDP-FWD-PATH-MPLS-NH-INFO;
    }
    container remote-lfa {
      description
        "Remote LFA-FRR backup info";
      uses LDP-FWD-PATH-RLFA-MPLS-INFO;
    }
  }

  grouping LDP-FWD-PATH-RLFA-ROUTING-INFO {
    description
      "MPLS LDP Forwarding Path Remote LFA-FRR backup
       routing info";
    container remote-p-node-id {
      description
        "Remote/P node address";
      uses LDP-IP-ADDR-T-UNION;
    }
    container remote-q-node-id {
      description
        "Remote/Q node address";
      uses LDP-IP-ADDR-T-UNION;
    }
    leaf has-remote-lfa-bkup {
      type boolean;
      description
        "Whether path has remote LFA backup";
    }
    leaf needs-tldp {
      type boolean;
      description
        "Whether TLDP is needed with remote PQ node";
    }
    leaf has-q-node {
      type boolean;
      description
        "Whether remote LFA path has a Q node associated";
    }
  }

  grouping LDP-FWD-PATH-ROUTING-INFO {
    description
      "MPLS LDP Forwarding Path IP Routing information";
    container next-hop {
      description
        "Next Hop";
      uses LDP-IP-ADDR-T-UNION;
    }
    container remote-lfa {
      description
        "Remote LFA-FRR backup info";
      uses LDP-FWD-PATH-RLFA-ROUTING-INFO;
    }
    leaf interface {
      type xr:Interface-name;
      description
        "Interface name";
    }
    leaf interface-name {
      type string;
      description
        "Interface Name";
    }
    leaf nh-is-overriden {
      type boolean;
      description
        "Nexthop is overriden by LDP";
    }
    leaf nexthop-id {
      type uint32;
      description
        "Nexthop Identifier";
    }
    leaf next-hop-table-id {
      type uint32;
      description
        "Table ID for nexthop address";
    }
    leaf flags {
      type uint32;
      description
        "Route path flags";
    }
    leaf load-metric {
      type uint32;
      description
        "Path's load metric for load balancing";
    }
    leaf binding-label {
      type uint32;
      description
        "Binding label obtained via RIB";
    }
    leaf path-id {
      type uint8;
      description
        "path Id";
    }
    leaf bkup-path-id {
      type uint8;
      description
        "Backup path Id";
    }
    leaf path-flags {
      type Ldp-route-path-flags;
      description
        "Routing path flags decoded";
    }
  }

  grouping LDP-FWD-PATH-INFO {
    description
      "MPLS LDP Forwarding Path info";
    container routing {
      description
        "IP routing information";
      uses LDP-FWD-PATH-ROUTING-INFO;
    }
    container mpls {
      description
        "MPLS information";
      uses LDP-FWD-PATH-MPLS-INFO;
    }
  }

  grouping LDP-FWD-ROUTE-MPLS-INFO {
    description
      "MPLS LDP Forwarding Route LDP information";
    leaf local-label {
      type uint32;
      description
        "Local label";
    }
    leaf forwarding-update-count {
      type uint32;
      description
        "Number of forwarding updates";
    }
    leaf forwarding-update-timestamp {
      type uint64;
      description
        "Last Forwarding update nanosec timestamp";
    }
    leaf forwarding-update-age {
      type uint64;
      description
        "Last Forwarding update nanosec age";
    }
  }

  grouping LDP-FWD-ROUTE-ROUTING-INFO {
    description
      "MPLS LDP Forwarding Route IP Routing information";
    leaf version {
      type uint32;
      description
        "Route RIB ersion";
    }
    leaf priority {
      type uint8;
      description
        "Route priority";
    }
    leaf source {
      type uint16;
      description
        "Route source protol Id";
    }
    leaf type {
      type uint16;
      description
        "Route type";
    }
    leaf flags {
      type uint32;
      description
        "Route RIB flags";
    }
    leaf metric {
      type uint32;
      description
        "Route metric";
    }
    leaf is-local-vrf-leaked {
      type boolean;
      description
        "Is route leaked across local VRFs?";
    }
    leaf routing-update-count {
      type uint32;
      description
        "Number of routing updates";
    }
    leaf routing-update-timestamp {
      type uint64;
      description
        "Last Routing update nanosec timestamp";
    }
    leaf routing-update-age {
      type uint64;
      description
        "Last Routing update nanosec age";
    }
    leaf sr-local-label {
      type uint32;
      description
        "SR Local-label";
    }
  }

  grouping LDP-FWD-ROUTE-INFO {
    description
      "MPLS LDP Forwarding Route information";
    container routing {
      description
        "IP routing information";
      uses LDP-FWD-ROUTE-ROUTING-INFO;
    }
    container mpls {
      description
        "MPLS information";
      uses LDP-FWD-ROUTE-MPLS-INFO;
    }
  }

  grouping LDP-FWD-PFX-INFO {
    description
      "MPLS LDP Forwarding Prefix Information";
    container vrf {
      description
        "VRF information";
      uses LDP-VRF-INFO;
    }
    container prefix-xr {
      description
        "IP Prefix";
      uses LDP-IP-ADDR-T-UNION;
    }
    container route {
      description
        "Route";
      uses LDP-FWD-ROUTE-INFO;
    }
    leaf table-id {
      type uint32;
      description
        "Table ID associated with IP prefix";
    }
    leaf prefix-length {
      type uint8;
      description
        "Prefix length";
    }
    list paths {
      description
        "Paths";
      uses LDP-FWD-PATH-INFO;
    }
  }

  grouping LDP-DISCOVERY-ADJ-GRP-INFO {
    description
      "MPLS LDP Discovery Adjacency Group Information";
    leaf adjacency-group-up-time {
      type uint32;
      units "second";
      description
        "Adjacency group up time in seconds";
    }
    leaf tcp-open-count {
      type uint32;
      description
        "Count of attempted TCP opens";
    }
    leaf tcp-arb-chg-count {
      type uint32;
      description
        "Count of changes in TCP arbitration";
    }
    leaf tcp-role {
      type uint32;
      description
        "TCP Role";
    }
  }

  grouping LDP-TARGETED-HELLO-BRIEF-INFO {
    description
      "MPLS LDP Discovery Targeted Brief Information";
    container vrf {
      description
        "VRF information";
      uses LDP-VRF-INFO;
    }
    container dhcb-target-address {
      description
        "DHCB target address";
      uses LDP-IP-ADDR-T-UNION;
    }
    leaf address-family {
      type Ldp-af;
      description
        "Targeted Discovery Address Family";
    }
    list hello-information {
      description
        "LDP hello info";
      uses LDP-HELLO-BRIEF-INFO;
    }
  }

  grouping LDP-HELLO-BRIEF-INFO {
    description
      "MPLS LDP Hello Brief Information";
    leaf neighbor-ldp-identifier {
      type string;
      description
        "Neighbor LDP Identifier";
    }
    leaf hold-time {
      type uint32;
      description
        "Session hold time in sec";
    }
    leaf session-up {
      type boolean;
      description
        "Is session up for this adj";
    }
  }

  grouping LDP-DISCOVERY-LINK-BRIEF-INFO {
    description
      "MPLS LDP Discovery Link Brief Information";
    container vrf {
      description
        "VRF information";
      uses LDP-VRF-INFO;
    }
    leaf address-family {
      type Ldp-af;
      description
        "Discovery Brief Address Family";
    }
    leaf address-family-set {
      type Ldp-af;
      description
        "Discovery Brief Address Family Set";
    }
    leaf interface {
      type xr:Interface-name;
      description
        "Interface name";
    }
    leaf interface-name-xr {
      type string;
      description
        "Interface name";
    }
    list hello-information {
      description
        "LDP hello info";
      uses LDP-HELLO-BRIEF-INFO;
    }
  }

  grouping LDP-TARGETED-HELLO-INFO {
    description
      "MPLS LDP Targeted Hello Information";
    container dhcb-local-address {
      description
        "DHCB local address";
      uses LDP-IP-ADDR-T-UNION;
    }
    container dhcb-target-address {
      description
        "DHCB target address";
      uses LDP-IP-ADDR-T-UNION;
    }
    leaf state {
      type Dhcb-state;
      description
        "Targeted hello state";
    }
    leaf adjacency-ldp-identifier {
      type string;
      description
        "Adjacency LDP Identifier";
    }
    leaf interval {
      type uint32;
      description
        "Hello interval in sec";
    }
    leaf next-hello {
      type uint32;
      description
        "Next hello due time in msec";
    }
    leaf hold-time {
      type uint32;
      description
        "Targeted hello hold time";
    }
    leaf local-hold-time {
      type uint32;
      description
        "Local hold time";
    }
    leaf neighbor-hold-time {
      type uint32;
      description
        "Neighbor hold time";
    }
    leaf disc-expiry {
      type uint32;
      description
        "Discovery expiry time in msec";
    }
    leaf quick-start-disabled {
      type boolean;
      description
        "Quick-start disabled";
    }
    leaf established-time {
      type uint64;
      description
        "Hello adjacency estabished time in nanosec";
    }
    leaf established-age {
      type uint64;
      description
        "Hello adjacency estabished age in nanosec";
    }
    leaf session-up {
      type boolean;
      description
        "Is session up for this adj";
    }
    leaf session-bringup-failure-reason {
      type string;
      description
        "session bringup failure reason";
    }
    list last-session-down-info {
      description
        "Last session down information";
      uses LDP-LAST-SESS-INFO;
    }
  }

  grouping LDP-DISCOVERY-SUMMARY-INFO {
    description
      "MPLS LDP Discovery Summary Information";
    container vrf {
      description
        "VRF information";
      uses LDP-VRF-INFO;
    }
    leaf local-ldp-id {
      type string;
      description
        "Local LDP identifier";
    }
    leaf num-of-ldp-interfaces {
      type uint32;
      description
        "Total Number of LDP configured interfaces";
    }
    leaf num-of-active-ldp-interfaces {
      type uint32;
      description
        "Number of active LDP enabled interfaces";
    }
    leaf num-of-lnk-disc-xmit {
      type uint32;
      description
        "Number of link hello discoveries in xmit state";
    }
    leaf num-of-tgt-disc-xmit {
      type uint32;
      description
        "Number of targeted hello discoveries in xmit
         state";
    }
    leaf num-of-lnk-disc-recv {
      type uint32;
      description
        "Number of link hello discoveries in recv state";
    }
    leaf num-of-tgt-disc-recv {
      type uint32;
      description
        "Number of targeted hello discoveries in recv
         state";
    }
    leaf num-of-disc-with-bad-addr-recv {
      type uint32;
      description
        "Number of hello discoveries received with bad
         source address";
    }
    leaf num-of-disc-with-bad-hello-pdu {
      type uint32;
      description
        "Number of hello discoveries received with bad
         hello PDU";
    }
    leaf num-of-disc-with-bad-xport-addr {
      type uint32;
      description
        "Number of hello discoveries received with bad
         export address";
    }
    leaf num-of-disc-with-same-router-id {
      type uint32;
      description
        "Number of hello discoveries received with the
         same router id as this router";
    }
    leaf num-of-disc-with-wrong-router-id {
      type uint32;
      description
        "Number of hello discoveries received with the
         router id that is not destined for this router";
    }
  }

  grouping LDP-DISCOVERY-LINK-AF-INFO {
    description
      "MPLS LDP Discovery Link Address Family
       Information";
    container local-src-address {
      description
        "Local source address";
      uses LDP-IP-ADDR-T-UNION;
    }
    container local-transport-address {
      description
        "Local transport address";
      uses LDP-IP-ADDR-T-UNION;
    }
    leaf interval {
      type uint32;
      description
        "Hello interval in sec";
    }
  }

  grouping LDP-LAST-SESS-INFO {
    description
      "LDP last down session information";
    leaf last-session-down-reason {
      type string;
      description
        "The reason of last socket failure";
    }
    leaf last-session-down-time {
      type uint64;
      description
        "Timestamp of when the last session went down";
    }
    leaf last-session-up-time {
      type uint32;
      description
        "The time duration the last session was up";
    }
  }

  grouping LDP-HELLO-INFO {
    description
      "MPLS LDP Hello Information";
    container neighbor-src-address {
      description
        "Neighbor source address";
      uses LDP-IP-ADDR-T-UNION;
    }
    container neighbor-transport-address {
      description
        "Neighbor transport address";
      uses LDP-IP-ADDR-T-UNION;
    }
    container target {
      description
        "Target address";
      uses LDP-IP-ADDR-T-UNION;
    }
    leaf neighbor-ldp-identifier {
      type string;
      description
        "Neighbor LDP Identifier";
    }
    leaf is-no-route {
      type boolean;
      description
        "Is route valid";
    }
    leaf hold-time {
      type uint32;
      units "second";
      description
        "Session hold time in seconds";
    }
    leaf local-hold-time {
      type uint32;
      units "second";
      description
        "Local hold time in seconds";
    }
    leaf neighbor-hold-time {
      type uint32;
      units "second";
      description
        "Neighbor hold time in seconds";
    }
    leaf disc-expiry {
      type uint32;
      description
        "Discovery expiry time in sec";
    }
    leaf is-targeted {
      type boolean;
      description
        "Is session a targeted session";
    }
    leaf session-up {
      type boolean;
      description
        "Is session up for this adj";
    }
    leaf established-time {
      type uint64;
      description
        "Hello adjacency estabished time in nanosec";
    }
    leaf established-age {
      type uint64;
      description
        "Hello adjacency estabished age in nanosec";
    }
    leaf session-bringup-failure-reason {
      type string;
      description
        "session bringup failure reason";
    }
    list last-session-down-info {
      description
        "Last session down information";
      uses LDP-LAST-SESS-INFO;
    }
  }

  grouping LDP-DISCOVERY-LINK-INFO {
    description
      "MPLS LDP Discovery Link Information";
    container vrf {
      description
        "VRF information";
      uses LDP-VRF-INFO;
    }
    leaf next-hello {
      type uint32;
      description
        "Next hello due time in msec";
    }
    leaf interface {
      type xr:Interface-name;
      description
        "Interface name";
    }
    leaf interface-name-xr {
      type string;
      description
        "Interface name";
    }
    leaf quick-start-disabled {
      type boolean;
      description
        "Quick-start disabled";
    }
    list hello-information {
      description
        "LDP hello info";
      uses LDP-HELLO-INFO;
    }
    list discovery-link-af {
      max-elements 2;
      description
        "LDP hello AF info";
      uses LDP-DISCOVERY-LINK-AF-INFO;
    }
  }

  grouping LDP-INTF-AUTOCFG {
    description
      "MPLS LDP auto configure";
    leaf tuple {
      type string;
      description
        "Tuple";
    }
  }

  grouping LDP-INTF-TE-MESH-GRP {
    description
      "MPLS LDP interface tunnel mesh group";
    leaf ldp-te-mesh-group-all-cfgd {
      type boolean;
      description
        "LDP has enabled all TE mesh-groups";
    }
    leaf ldp-mesh-group-enabled {
      type boolean;
      description
        "LDP has enabled this TE mesh-group";
    }
    leaf te-mesh-group-id {
      type uint32;
      description
        "TE tunnel Mesh Group ID";
    }
  }

  grouping LDP-INTF {
    description
      "MPLS LDP interface information";
    container vrf {
      description
        "VRF information";
      uses LDP-VRF-INFO;
    }
    leaf interface {
      type xr:Interface-name;
      description
        "Interface name";
    }
    leaf interface-name-xr {
      type string;
      description
        "Interface name";
    }
    leaf ldp-enabled {
      type boolean;
      description
        "LDP enabled";
    }
    leaf is-im-stale {
      type boolean;
      description
        "Is IM information stale";
    }
    leaf ldp-config-mode {
      type boolean;
      description
        "LDP config mode";
    }
    leaf ldp-autoconfig-disable {
      type boolean;
      description
        "LDP autoconfig disable";
    }
    list te-mesh-grp {
      description
        "TE tunnel mesh-group";
      uses LDP-INTF-TE-MESH-GRP;
    }
    list auto-config {
      description
        "Auto config";
      uses LDP-INTF-AUTOCFG;
    }
  }

  grouping LDP-BINDING-SUMMARY-AF {
    description
      "MPLS LDP Binding Summary AF Information";
    leaf address-family {
      type Ldp-af;
      description
        "Binding Summary Address Family";
    }
    leaf last-lib-update {
      type uint32;
      description
        "Last update to LIB local binding";
    }
    leaf lib-minimum-revision-sent-all {
      type uint32;
      description
        "Last update sent to all peers";
    }
    leaf binding-total {
      type uint32;
      description
        "Total bindings";
    }
    leaf binding-local {
      type uint32;
      description
        "Number of local bindings";
    }
    leaf binding-remote {
      type uint32;
      description
        "Number of remote bindings";
    }
  }

  grouping LDP-BINDING-SUMMARY {
    description
      "MPLS LDP Binding Summary Information";
    container vrf {
      description
        "VRF information";
      uses LDP-VRF-INFO;
    }
    leaf address-family {
      type Ldp-af;
      description
        "Address Family";
    }
    leaf binding-no-route {
      type uint32;
      description
        "Bindings with no route";
    }
    leaf binding-local-no-route {
      type uint32;
      description
        "Local bindings with no route";
    }
    leaf binding-local-null {
      type uint32;
      description
        "Number of local null bindings";
    }
    leaf binding-local-implicit-null {
      type uint32;
      description
        "Number of local implicit null bindings";
    }
    leaf binding-local-explicit-null {
      type uint32;
      description
        "Number of local explicit null bindings";
    }
    leaf binding-local-non-null {
      type uint32;
      description
        "Number of local non-null bindings";
    }
    leaf binding-local-oor {
      type uint32;
      description
        "Number of local bindings        needing label -
         OOR";
    }
    leaf lowest-allocated-label {
      type uint32;
      description
        "Lowest allocated label";
    }
    leaf highest-allocated-label {
      type uint32;
      description
        "Highest allocated label";
    }
    list bind-af {
      max-elements 2;
      description
        "bind af";
      uses LDP-BINDING-SUMMARY-AF;
    }
  }

  grouping LDP-IGP-SYNC-DELAY-RESTART-INFO {
    description
      "MPLS LDP IGP Sync Restart Delay Information";
    leaf configured {
      type boolean;
      description
        "Is restart delay configured";
    }
    leaf delay-secs {
      type uint32;
      description
        "Delay time";
    }
    leaf timer-running {
      type boolean;
      description
        "Is restart delay timer running";
    }
    leaf remaining-secs {
      type uint32;
      description
        "Delay timer remaining time";
    }
  }

  grouping LDP-IGP-SYNC-INTF-GR-ONLY {
    description
      "MPLS LDP IGP Sync Interface GR-only reachable
       Peer Information";
    leaf peer-id {
      type String-td2;
      description
        "Peer Identifier";
    }
    leaf is-chkpt-created {
      type boolean;
      description
        "Is created due to checkpointing";
    }
  }

  grouping LDP-IGP-SYNC-INTF-PEER {
    description
      "MPLS LDP IGP Sync Interface Peer Information";
    leaf peer-id {
      type String-td2;
      description
        "Peer Identifier";
    }
    leaf is-gr-enabled {
      type boolean;
      description
        "Is GR enabled session";
    }
  }

  grouping LDP-IGP-SYNC-INFO {
    description
      "MPLS LDP IGP Sync Information";
    container vrf {
      description
        "VRF information";
      uses LDP-VRF-INFO;
    }
    leaf interface-name-xr {
      type string;
      description
        "Interface name";
    }
    leaf igp-sync-state {
      type Ldp-igp-sync-state;
      description
        "IGP Sync state";
    }
    leaf igp-sync-delay {
      type uint32;
      units "second";
      description
        "IGP sync delay in seconds";
    }
    leaf is-delay-timer-running {
      type boolean;
      description
        "Is sync delay timer running";
    }
    leaf delay-timer-remaining {
      type uint32;
      units "second";
      description
        "Remaining timer (seconds) till expiry of sync
         delay timer";
    }
    leaf igp-sync-down-reason {
      type Ldp-igp-sync-down-reason;
      description
        "Reason IGP Sync Not Achieved";
    }
    list peers {
      description
        "Interface Peers";
      uses LDP-IGP-SYNC-INTF-PEER;
    }
    list gr-only-peer {
      description
        "Interface GR-only reachable peers";
      uses LDP-IGP-SYNC-INTF-GR-ONLY;
    }
  }

  grouping LDP-TIB-ENTRY-REMOTE {
    description
      "MPLS LDP Remote Binding Information";
    container assigning-peer-ldp-ident {
      description
        "Assigning peer";
      uses LDP-LDPID-INFO;
    }
    leaf remote-label {
      type uint32;
      description
        "Remote Label";
    }
    leaf is-stale {
      type boolean;
      description
        "Is the entry stale";
    }
    leaf is-elc {
      type boolean;
      description
        "Is the entry entropy label capable";
    }
  }

  grouping LDP-TIB-ENTRY-DETAIL {
    description
      "MPLS LDP Binding Detail Information";
    container vrf {
      description
        "VRF information";
      uses LDP-VRF-INFO;
    }
    container prefix-xr {
      description
        "IP Prefix";
      uses LDP-IP-ADDR-T-UNION;
    }
    leaf prefix-length {
      type uint8;
      description
        "Prefix Length";
    }
    leaf local-label {
      type uint32;
      description
        "Local label";
    }
    leaf le-local-binding-revision {
      type uint32;
      description
        "Local Binding revision";
    }
    leaf le-local-label-state {
      type Local-label-state;
      description
        "Local label state";
    }
    leaf is-no-route {
      type boolean;
      description
        "No route";
    }
    leaf label-oor {
      type boolean;
      description
        "Label space depletion OOR";
    }
    leaf advertise-prefix-acl {
      type string;
      description
        "Advertise Prerfix ACL";
    }
    leaf advertise-tsr-acl {
      type string;
      description
        "Advertise TSR ACL";
    }
    leaf config-enforced-local-label-value {
      type boolean;
      description
        "Config/User enforced local label value";
    }
    leaf is-elc {
      type boolean;
      description
        "Is the entry entropy label capable";
    }
    list remote-binding {
      description
        "Remote binding";
      uses LDP-TIB-ENTRY-REMOTE;
    }
    list peers-advertised-to {
      description
        "Peers this entry is advertised to";
      uses LDP-LDPID-INFO;
    }
    list peers-acked {
      description
        "Peers that have ACKed this entry";
      uses LDP-LDPID-INFO;
    }
  }

  grouping LDP-INTF-SUM {
    description
      "MPLS LDP interface summary";
    leaf known-ip-interface-count {
      type uint32;
      description
        "Number of known IP Interfaces";
    }
    leaf known-ip-interface-ldp-enabled {
      type uint32;
      description
        "Number of known IP Interfaces with LDP Enabled";
    }
    leaf ldp-configured-attached-interface {
      type uint32;
      description
        "Number of attached interfaces configured in LDP";
    }
    leaf ldp-configured-te-interface {
      type uint32;
      description
        "Number of TE tunnel interfaces configured in LDP";
    }
    leaf forward-references {
      type uint32;
      description
        "Number of forward referenced interfaces";
    }
    leaf auto-config-disabled {
      type uint32;
      description
        "Autoconfigure disabled";
    }
    leaf auto-config {
      type uint32;
      description
        "Auto-configured interfaces";
    }
    leaf auto-config-forward-reference-interfaces {
      type uint32;
      description
        "Auto-configured forward references";
    }
  }

  grouping LDP-SUMMARY-COMMON {
    description
      "MPLS LDP common summary Information";
    leaf address-families {
      type Ldp-af;
      description
        "Address Families enabled";
    }
    leaf number-of-ipv4af {
      type uint32;
      description
        "Number of IPv4 address-families enabled";
    }
    leaf number-of-ipv6af {
      type uint32;
      description
        "Number of IPv6 address-families enabled";
    }
    leaf number-of-neighbors {
      type uint32;
      description
        "Number of neighbors";
    }
    leaf number-of-adj-grps {
      type uint32;
      description
        "Number of Adjacency Groups";
    }
    leaf number-of-nsr-synced-neighbors {
      type uint32;
      description
        "Number of NSR-synced/operational neighbors";
    }
    leaf number-of-graceful-restart-neighbors {
      type uint32;
      description
        "Number of Graceful Restart neighbors";
    }
    leaf number-of-downstream-on-demand-neighbors {
      type uint32;
      description
        "Number of Downstream-On-Demand neighbors";
    }
    leaf number-of-ipv4-hello-adj {
      type uint32;
      description
        "Number of LDP discovery IPv4 hello adjacencies";
    }
    leaf number-of-ipv6-hello-adj {
      type uint32;
      description
        "Number of LDP discovery IPv6 hello adjacencies";
    }
    leaf number-of-ipv4-routes {
      type uint32;
      description
        "Number of resolved IPv4 routes";
    }
    leaf number-of-ipv6-routes {
      type uint32;
      description
        "Number of resolved IPv6 routes";
    }
    leaf number-of-ipv4-local-addresses {
      type uint32;
      description
        "Number of IPv4 local addresses";
    }
    leaf number-of-ipv6-local-addresses {
      type uint32;
      description
        "Number of IPv6 local addresses";
    }
    leaf number-of-ldp-interfaces {
      type uint32;
      description
        "Number of LDP configured interfaces";
    }
    leaf number-of-ipv4ldp-interfaces {
      type uint32;
      description
        "Number of LDP IPv4 configured interfaces";
    }
    leaf number-of-ipv6ldp-interfaces {
      type uint32;
      description
        "Number of LDP IPv6 configured interfaces";
    }
    leaf number-of-bindings-ipv4 {
      type uint32;
      description
        "Total number of ipv4 bindings";
    }
    leaf number-of-bindings-ipv6 {
      type uint32;
      description
        "Total number of ipv6 bindings";
    }
    leaf number-of-local-bindings-ipv4 {
      type uint32;
      description
        "Total number of ipv4 local label bindings";
    }
    leaf number-of-local-bindings-ipv6 {
      type uint32;
      description
        "Total number of ipv6 local label bindings";
    }
    leaf number-of-remote-bindings-ipv4 {
      type uint32;
      description
        "Total number of ipv4 remote label bindings";
    }
    leaf number-of-remote-bindings-ipv6 {
      type uint32;
      description
        "Total number of ipv6 remote label bindings";
    }
  }

  grouping LDP-SUMMARY-VRF {
    description
      "MPLS LDP per VRF summarized Information";
    container vrf {
      description
        "VRF information";
      uses LDP-VRF-INFO;
    }
    container common {
      description
        "Common Summary information";
      uses LDP-SUMMARY-COMMON;
    }
  }

  grouping LDP-CAP-DESC {
    description
      "MPLS LDP Capability Description";
    leaf type {
      type uint16;
      description
        "Capability type (IANA assigned)";
    }
    leaf description {
      type string {
        length "0..80";
      }
      description
        "Capability description";
    }
    leaf capability-data-length {
      type uint16;
      description
        "Capability data length";
    }
    leaf capability-data {
      type string;
      description
        "Capability data";
    }
  }

  grouping LDP-CAP-INFO {
    description
      "MPLS LDP Capability Information";
    container capability {
      description
        "Capability information";
      uses LDP-CAP-DESC;
    }
    leaf capability-owner {
      type string;
      description
        "Capability owner";
    }
  }

  grouping LDP-IP-ADDR-T-UNION {
    description
      "LDP IP ADDR T UNION";
    leaf afi {
      type Ldp-af-id;
      description
        "AFI";
    }
    leaf dummy {
      when "../afi = 'ldp-af-id-none'" {
        tailf:xpath-root 3;
        description
          "../AFI = 'LDP_AF_ID_NONE'";
      }
      type uint8;
      description
        "No Address";
    }
    leaf ipv4 {
      when "../afi = 'ldp-af-id-ipv4'" {
        tailf:xpath-root 3;
        description
          "../AFI = 'LDP_AF_ID_IPV4'";
      }
      type Ldp-in-addr;
      description
        "IPv4 address type";
    }
    leaf ipv6 {
      when "../afi = 'ldp-af-id-ipv6'" {
        tailf:xpath-root 3;
        description
          "../AFI = 'LDP_AF_ID_IPV6'";
      }
      type Ldp-in6-addr;
      description
        "IPv6 address type";
    }
  }

  grouping LDP-GR-DNBR-INTF-INFO {
    description
      "MPLS LDP GR DownNbr Interface Info";
    leaf address-family {
      type Ldp-af-id;
      description
        "Interface adj Address Family";
    }
    leaf interface-handle {
      type xr:Interface-name;
      description
        "Interfaces handle";
    }
  }

  grouping LDP-LDPID-INFO {
    description
      "MPLS LDP Identifier Information";
    leaf lsr-id {
      type inet:ipv4-address;
      description
        "LSR identifier";
    }
    leaf label-space-id {
      type uint16;
      description
        "Label space identifier";
    }
    leaf ldp-id {
      type string;
      description
        "LDP identifier";
    }
  }

  grouping LDP-GR-NBR-INFO {
    description
      "MPLS LDP Graceful Restart Neighbor Information";
    container gr-peer {
      description
        "GR peer LDP Id";
      uses LDP-LDPID-INFO;
    }
    leaf connect-count {
      type uint32;
      description
        "ConnectCount";
    }
    leaf is-neighbor-up {
      type boolean;
      description
        "Is neighbor up";
    }
    leaf is-liveness-timer-running {
      type boolean;
      description
        "Is liveness timer running";
    }
    leaf liveness-timer-remaining-seconds {
      type uint32;
      description
        "Remaining time from liveness timer";
    }
    leaf is-recovery-timer-running {
      type boolean;
      description
        "Is recovery timer running";
    }
    leaf recovery-timer-remaining-seconds {
      type uint32;
      description
        "Recovery timer remining time";
    }
    leaf down-nbr-flap-count {
      type uint8;
      description
        "Count of back2back flaps";
    }
    leaf down-nbr-flags {
      type uint32;
      description
        "Flags";
    }
    leaf down-nbr-down-reason {
      type uint32;
      description
        "Session down reason code";
    }
    list down-nbr-interface {
      description
        "Interfaces bound to GR down Nbr";
      uses LDP-GR-DNBR-INTF-INFO;
    }
    list down-nbr-address {
      description
        "Addresses bound to GR down Nbr";
      uses LDP-IP-ADDR-T-UNION;
    }
  }

  grouping LDP-VRF-INFO {
    description
      "MPLS LDP VRF information";
    leaf name {
      type string;
      description
        "VRF Name";
    }
    leaf id {
      type uint32;
      description
        "VRF Id";
    }
  }

  grouping LDP-GR-GLOBAL-INFO {
    description
      "MPLS LDP Graceful Restart Information";
    container vrf {
      description
        "VRF information";
      uses LDP-VRF-INFO;
    }
    leaf is-forwarding-state-hold-timer-running {
      type boolean;
      description
        "Is graceful restart forwarding state hold timer
         running";
    }
    leaf forwarding-state-hold-timer-remaining-seconds {
      type uint32;
      units "second";
      description
        "Forwarding state hold timer remaining time in
         seconds";
    }
    list graceful-restartable-neighbor {
      description
        "Vector of graceful restart neighbor information";
      uses LDP-GR-NBR-INFO;
    }
  }
}

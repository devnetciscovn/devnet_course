submodule Cisco-IOS-XR-gnss-oper-sub1 {
  // Generated by yanger -t ncs
  tailf:mount-id "cisco-iosxr-nc-7.3:cisco-iosxr-nc-7.3";

  belongs-to Cisco-IOS-XR-gnss-oper {
    prefix Cisco-IOS-XR-gnss-oper;
  }

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR gnss package operational data.

     Copyright (c) 2013-2019 by Cisco Systems, Inc.
     All rights reserved.";

  revision 2019-09-30 {
    description
      "Removed enum usage from alarms, added elevation, azimuth and time locked by gnss receiver";
    semver:module-version "2.0.0";
  }
  revision 2019-04-05 {
    description
      "Establish semantic version baseline.";
    semver:module-version "1.0.0";
  }
  revision 2017-09-07 {
    description
      "Fixed type translation error.";
  }
  revision 2015-11-09 {
    description
      "IOS XR 6.0 revision.";
  }

  typedef ncs_template_Gnssmgr-bag-sat-sv {
    type string;
    description
      "Space vehicle (SV) type";
  }

  typedef ncs_template_Gnssmgr-bag-optional-string {
    type string;
    description
      "Gnssmgr bag optional string";
  }

  typedef ncs_template_Gnssmgr-bag-rx-mode {
    type string;
    description
      "Receiver mode";
  }

  typedef ncs_template_Gnssmgr-bag-lock-status {
    type string;
    description
      "Lock status";
  }

  typedef ncs_template_Gnssmgr-bag-1pps-polarity {
    type string;
    description
      "1PPS polarity";
  }

  typedef ncs_template_Gnssmgr-bag-constellation {
    type string;
    description
      "Consetellation";
  }

  typedef ncs_rpc_notif_Gnssmgr-bag-sat-sv {
    type enumeration {
      enum "gps" {
        value 0;
        description
          "GPS";
      }
      enum "glonass" {
        value 1;
        description
          "GLONASS";
      }
      enum "sbas" {
        value 2;
        description
          "SBAS (WAAS)";
      }
      enum "qzss" {
        value 3;
        description
          "QZSS";
      }
      enum "bei-dou" {
        value 4;
        description
          "BeiDou";
      }
      enum "galileo" {
        value 5;
        description
          "Galileo";
      }
      enum "irnss" {
        value 6;
        description
          "IRNSS";
      }
      enum "gnss" {
        value 7;
        description
          "GNSS";
      }
      enum "unknown" {
        value 8;
        description
          "Unknown";
      }
      enum "reserved" {
        value 9;
        description
          "Reserved";
      }
    }
    description
      "Space vehicle (SV) type";
  }

  typedef ncs_rpc_notif_Gnssmgr-bag-optional-string {
    type string;
    description
      "Gnssmgr bag optional string";
  }

  typedef ncs_rpc_notif_Gnssmgr-bag-rx-mode {
    type enumeration {
      enum "no-fix" {
        value 0;
        description
          "No fix";
      }
      enum "dead-reckoning-only" {
        value 1;
        description
          "Dead Reckoning only";
      }
      enum "fix-2d" {
        value 2;
        description
          "2D fix";
      }
      enum "fix-3d" {
        value 3;
        description
          "3D fix";
      }
      enum "gnss-and-dead-reckoning" {
        value 4;
        description
          "GNSS and Dead Reckoning";
      }
      enum "time-fix-only" {
        value 5;
        description
          "Time fix only";
      }
      enum "a-gnss" {
        value 6;
        description
          "A GNSS";
      }
      enum "gnss-and-sbas" {
        value 7;
        description
          "GNSS and SBAS";
      }
      enum "gnss-and-gbas" {
        value 8;
        description
          "GNSS and GBAS";
      }
      enum "reserved" {
        value 9;
        description
          "Reserved";
      }
    }
    description
      "Receiver mode";
  }

  typedef ncs_rpc_notif_Gnssmgr-bag-lock-status {
    type enumeration {
      enum "phase-locked" {
        value 0;
        description
          "Phase locked";
      }
      enum "frequency-locked" {
        value 1;
        description
          "Frequency locked";
      }
      enum "initializing" {
        value 2;
        description
          "Initializing";
      }
      enum "auto-holdover" {
        value 3;
        description
          "Auto holdover";
      }
      enum "manual-holdover" {
        value 4;
        description
          "Manual holdover";
      }
      enum "recovery" {
        value 5;
        description
          "Recovery";
      }
      enum "inactive" {
        value 6;
        description
          "Inactive";
      }
    }
    description
      "Lock status";
  }

  typedef ncs_rpc_notif_Gnssmgr-bag-1pps-polarity {
    type enumeration {
      enum "positive" {
        value 0;
        description
          "Positive";
      }
      enum "negative" {
        value 1;
        description
          "Negative";
      }
    }
    description
      "1PPS polarity";
  }

  typedef ncs_rpc_notif_Gnssmgr-bag-constellation {
    type enumeration {
      enum "auto" {
        value 0;
        description
          "Auto choose constellation";
      }
      enum "gps" {
        value 1;
        description
          "GPS";
      }
      enum "galileo" {
        value 2;
        description
          "Galileo";
      }
      enum "bei-dou" {
        value 3;
        description
          "BeiDou";
      }
      enum "qzss" {
        value 4;
        description
          "QZSS";
      }
      enum "glonass" {
        value 5;
        description
          "GLONASS";
      }
      enum "sbas" {
        value 6;
        description
          "SBAS (WAAS)";
      }
      enum "irnss" {
        value 7;
        description
          "IRNSS";
      }
    }
    description
      "Consetellation";
  }

  typedef live_ncs_Gnssmgr-bag-sat-sv {
    type enumeration {
      enum "gps" {
        value 0;
        description
          "GPS";
      }
      enum "glonass" {
        value 1;
        description
          "GLONASS";
      }
      enum "sbas" {
        value 2;
        description
          "SBAS (WAAS)";
      }
      enum "qzss" {
        value 3;
        description
          "QZSS";
      }
      enum "bei-dou" {
        value 4;
        description
          "BeiDou";
      }
      enum "galileo" {
        value 5;
        description
          "Galileo";
      }
      enum "irnss" {
        value 6;
        description
          "IRNSS";
      }
      enum "gnss" {
        value 7;
        description
          "GNSS";
      }
      enum "unknown" {
        value 8;
        description
          "Unknown";
      }
      enum "reserved" {
        value 9;
        description
          "Reserved";
      }
    }
    description
      "Space vehicle (SV) type";
  }

  typedef live_ncs_Gnssmgr-bag-optional-string {
    type string;
    description
      "Gnssmgr bag optional string";
  }

  typedef live_ncs_Gnssmgr-bag-rx-mode {
    type enumeration {
      enum "no-fix" {
        value 0;
        description
          "No fix";
      }
      enum "dead-reckoning-only" {
        value 1;
        description
          "Dead Reckoning only";
      }
      enum "fix-2d" {
        value 2;
        description
          "2D fix";
      }
      enum "fix-3d" {
        value 3;
        description
          "3D fix";
      }
      enum "gnss-and-dead-reckoning" {
        value 4;
        description
          "GNSS and Dead Reckoning";
      }
      enum "time-fix-only" {
        value 5;
        description
          "Time fix only";
      }
      enum "a-gnss" {
        value 6;
        description
          "A GNSS";
      }
      enum "gnss-and-sbas" {
        value 7;
        description
          "GNSS and SBAS";
      }
      enum "gnss-and-gbas" {
        value 8;
        description
          "GNSS and GBAS";
      }
      enum "reserved" {
        value 9;
        description
          "Reserved";
      }
    }
    description
      "Receiver mode";
  }

  typedef live_ncs_Gnssmgr-bag-lock-status {
    type enumeration {
      enum "phase-locked" {
        value 0;
        description
          "Phase locked";
      }
      enum "frequency-locked" {
        value 1;
        description
          "Frequency locked";
      }
      enum "initializing" {
        value 2;
        description
          "Initializing";
      }
      enum "auto-holdover" {
        value 3;
        description
          "Auto holdover";
      }
      enum "manual-holdover" {
        value 4;
        description
          "Manual holdover";
      }
      enum "recovery" {
        value 5;
        description
          "Recovery";
      }
      enum "inactive" {
        value 6;
        description
          "Inactive";
      }
    }
    description
      "Lock status";
  }

  typedef live_ncs_Gnssmgr-bag-1pps-polarity {
    type enumeration {
      enum "positive" {
        value 0;
        description
          "Positive";
      }
      enum "negative" {
        value 1;
        description
          "Negative";
      }
    }
    description
      "1PPS polarity";
  }

  typedef live_ncs_Gnssmgr-bag-constellation {
    type enumeration {
      enum "auto" {
        value 0;
        description
          "Auto choose constellation";
      }
      enum "gps" {
        value 1;
        description
          "GPS";
      }
      enum "galileo" {
        value 2;
        description
          "Galileo";
      }
      enum "bei-dou" {
        value 3;
        description
          "BeiDou";
      }
      enum "qzss" {
        value 4;
        description
          "QZSS";
      }
      enum "glonass" {
        value 5;
        description
          "GLONASS";
      }
      enum "sbas" {
        value 6;
        description
          "SBAS (WAAS)";
      }
      enum "irnss" {
        value 7;
        description
          "IRNSS";
      }
    }
    description
      "Consetellation";
  }

  typedef Gnssmgr-bag-sat-sv {
    type enumeration {
      enum "gps" {
        value 0;
        description
          "GPS";
      }
      enum "glonass" {
        value 1;
        description
          "GLONASS";
      }
      enum "sbas" {
        value 2;
        description
          "SBAS (WAAS)";
      }
      enum "qzss" {
        value 3;
        description
          "QZSS";
      }
      enum "bei-dou" {
        value 4;
        description
          "BeiDou";
      }
      enum "galileo" {
        value 5;
        description
          "Galileo";
      }
      enum "irnss" {
        value 6;
        description
          "IRNSS";
      }
      enum "gnss" {
        value 7;
        description
          "GNSS";
      }
      enum "unknown" {
        value 8;
        description
          "Unknown";
      }
      enum "reserved" {
        value 9;
        description
          "Reserved";
      }
    }
    description
      "Space vehicle (SV) type";
  }

  typedef Gnssmgr-bag-optional-string {
    type string;
    description
      "Gnssmgr bag optional string";
  }

  typedef Gnssmgr-bag-rx-mode {
    type enumeration {
      enum "no-fix" {
        value 0;
        description
          "No fix";
      }
      enum "dead-reckoning-only" {
        value 1;
        description
          "Dead Reckoning only";
      }
      enum "fix-2d" {
        value 2;
        description
          "2D fix";
      }
      enum "fix-3d" {
        value 3;
        description
          "3D fix";
      }
      enum "gnss-and-dead-reckoning" {
        value 4;
        description
          "GNSS and Dead Reckoning";
      }
      enum "time-fix-only" {
        value 5;
        description
          "Time fix only";
      }
      enum "a-gnss" {
        value 6;
        description
          "A GNSS";
      }
      enum "gnss-and-sbas" {
        value 7;
        description
          "GNSS and SBAS";
      }
      enum "gnss-and-gbas" {
        value 8;
        description
          "GNSS and GBAS";
      }
      enum "reserved" {
        value 9;
        description
          "Reserved";
      }
    }
    description
      "Receiver mode";
  }

  typedef Gnssmgr-bag-lock-status {
    type enumeration {
      enum "phase-locked" {
        value 0;
        description
          "Phase locked";
      }
      enum "frequency-locked" {
        value 1;
        description
          "Frequency locked";
      }
      enum "initializing" {
        value 2;
        description
          "Initializing";
      }
      enum "auto-holdover" {
        value 3;
        description
          "Auto holdover";
      }
      enum "manual-holdover" {
        value 4;
        description
          "Manual holdover";
      }
      enum "recovery" {
        value 5;
        description
          "Recovery";
      }
      enum "inactive" {
        value 6;
        description
          "Inactive";
      }
    }
    description
      "Lock status";
  }

  typedef Gnssmgr-bag-1pps-polarity {
    type enumeration {
      enum "positive" {
        value 0;
        description
          "Positive";
      }
      enum "negative" {
        value 1;
        description
          "Negative";
      }
    }
    description
      "1PPS polarity";
  }

  typedef Gnssmgr-bag-constellation {
    type enumeration {
      enum "auto" {
        value 0;
        description
          "Auto choose constellation";
      }
      enum "gps" {
        value 1;
        description
          "GPS";
      }
      enum "galileo" {
        value 2;
        description
          "Galileo";
      }
      enum "bei-dou" {
        value 3;
        description
          "BeiDou";
      }
      enum "qzss" {
        value 4;
        description
          "QZSS";
      }
      enum "glonass" {
        value 5;
        description
          "GLONASS";
      }
      enum "sbas" {
        value 6;
        description
          "SBAS (WAAS)";
      }
      enum "irnss" {
        value 7;
        description
          "IRNSS";
      }
    }
    description
      "Consetellation";
  }

  grouping ncs_template_GNSSMGR-BAG-SATELLITE {
    description
      "Satellite information";
    leaf prn-number {
      type string;
      description
        "PRN number";
    }
    leaf channel-number {
      type string;
      description
        "Channel number";
    }
    leaf acquisition-flag {
      type string;
      description
        "Acquisition flag";
    }
    leaf ephemeris-flag {
      type string;
      description
        "Ephemeris flag";
    }
    leaf sv-type {
      type ncs_template_Gnssmgr-bag-sat-sv;
      description
        "Space vehicle (SV) type";
    }
    leaf signal-strength {
      type string;
      description
        "Signal strength (0.001 dB-Hz)";
    }
    leaf elevation {
      type string;
      description
        "Elevation (0.001 degrees)";
    }
    leaf azimuth {
      type string;
      description
        "Azimuth (0.001 degrees)";
    }
  }

  grouping ncs_template_GNSSMGR-RX-INFO {
    description
      "GNSS receiver information";
    leaf receiver-number {
      type string;
      description
        "Receiver number";
    }
    leaf node {
      type xr:ncs_template_Node-id;
      description
        "Node the receiver is on";
    }
    leaf enabled {
      type string;
      description
        "Whether the receiver is enabled";
    }
    leaf shutdown {
      type string;
      description
        "Whether the receiver is shutdown";
    }
    leaf anti-jam-disable {
      type string;
      description
        "Whether anti-jam mode is disabled";
    }
    leaf constellation {
      type ncs_template_Gnssmgr-bag-constellation;
      description
        "Constellation used by the receiver";
    }
    leaf snr-threshold {
      type string;
      description
        "Satellite SNR threshold";
    }
    leaf elevation-threshold {
      type string;
      description
        "Satellite elevation threshold";
    }
    leaf pdop-threshold {
      type string;
      description
        "Satellite position (3D) dilution of precision
         (PDOP) threshold";
    }
    leaf traim-threshold {
      type string;
      description
        "Satellite TRAIM threshold";
    }
    leaf cable-delay-compensation {
      type string;
      description
        "Cable delay compensation";
    }
    leaf polarity1pps {
      type ncs_template_Gnssmgr-bag-1pps-polarity;
      description
        "1PPS polarity";
    }
    leaf available {
      type string;
      description
        "Whether the receiver is available";
    }
    leaf lock-status {
      type ncs_template_Gnssmgr-bag-lock-status;
      description
        "The lock status of the receiver";
    }
    leaf receiver-mode {
      type ncs_template_Gnssmgr-bag-rx-mode;
      description
        "The receiver mode of the receiver";
    }
    leaf survey-progress {
      type string;
      description
        "The survey progress of the receiver";
    }
    leaf holdover-duration {
      type string;
      description
        "The holdover duration of the receier";
    }
    leaf major-alarm {
      type string;
      description
        "The status of the receiver's major alarm";
    }
    leaf minor-alarm {
      type string;
      description
        "The status of the receiver's minor alarm";
    }
    leaf pdop {
      type string;
      description
        "Position (3D) dilution of precision (in
         thousandths)";
    }
    leaf hdop {
      type string;
      description
        "Horizontal dilution of precision (in
         thousandths)";
    }
    leaf vdop {
      type string;
      description
        "Vertical dilution of precision (in thousandths)";
    }
    leaf tdop {
      type string;
      description
        "Time dilution of precision (in thousandths)";
    }
    leaf latitude {
      type string;
      units "centisecond";
      description
        "Latitude of the receiver (arcseconds)";
    }
    leaf longitude {
      type string;
      units "centisecond";
      description
        "Longitude of the receiver (arcseconds)";
    }
    leaf altitude {
      type string;
      description
        "Altitude of the receiver (m)";
    }
    leaf time {
      type string;
      units "second";
      description
        "Current time recovered by the receiver (secs
         since epoch)";
    }
    leaf utc-offset {
      type string;
      description
        "UTC offset of the receiver";
    }
    leaf firmware-version {
      type ncs_template_Gnssmgr-bag-optional-string;
      description
        "Firmware version of the receiver";
    }
    leaf locked-time {
      type string;
      units "second";
      description
        "Locked time recovered by the receiver (secs
         since epoch)";
    }
    leaf satellite-data-known {
      type string;
      description
        "Is the satellite data known?";
    }
    list satellite {
      // NCS patched for predictable order
      ordered-by user;
      description
        "Satellites visible to the receiver";
      uses ncs_template_GNSSMGR-BAG-SATELLITE;
    }
  }

  grouping ncs_rpc_notif_GNSSMGR-BAG-SATELLITE {
    description
      "Satellite information";
    leaf prn-number {
      type uint8;
      description
        "PRN number";
    }
    leaf channel-number {
      type uint8;
      description
        "Channel number";
    }
    leaf acquisition-flag {
      type boolean;
      description
        "Acquisition flag";
    }
    leaf ephemeris-flag {
      type boolean;
      description
        "Ephemeris flag";
    }
    leaf sv-type {
      type ncs_rpc_notif_Gnssmgr-bag-sat-sv;
      description
        "Space vehicle (SV) type";
    }
    leaf signal-strength {
      type uint32;
      description
        "Signal strength (0.001 dB-Hz)";
    }
    leaf elevation {
      type uint32;
      description
        "Elevation (0.001 degrees)";
    }
    leaf azimuth {
      type uint32;
      description
        "Azimuth (0.001 degrees)";
    }
  }

  grouping ncs_rpc_notif_GNSSMGR-RX-INFO {
    description
      "GNSS receiver information";
    leaf receiver-number {
      type uint32;
      description
        "Receiver number";
    }
    leaf node {
      type xr:ncs_rpc_notif_Node-id;
      description
        "Node the receiver is on";
    }
    leaf enabled {
      type boolean;
      description
        "Whether the receiver is enabled";
    }
    leaf shutdown {
      type boolean;
      description
        "Whether the receiver is shutdown";
    }
    leaf anti-jam-disable {
      type boolean;
      description
        "Whether anti-jam mode is disabled";
    }
    leaf constellation {
      type ncs_rpc_notif_Gnssmgr-bag-constellation;
      description
        "Constellation used by the receiver";
    }
    leaf snr-threshold {
      type uint32;
      description
        "Satellite SNR threshold";
    }
    leaf elevation-threshold {
      type uint32;
      description
        "Satellite elevation threshold";
    }
    leaf pdop-threshold {
      type uint32;
      description
        "Satellite position (3D) dilution of precision
         (PDOP) threshold";
    }
    leaf traim-threshold {
      type uint32;
      description
        "Satellite TRAIM threshold";
    }
    leaf cable-delay-compensation {
      type int32;
      description
        "Cable delay compensation";
    }
    leaf polarity1pps {
      type ncs_rpc_notif_Gnssmgr-bag-1pps-polarity;
      description
        "1PPS polarity";
    }
    leaf available {
      type boolean;
      description
        "Whether the receiver is available";
    }
    leaf lock-status {
      type ncs_rpc_notif_Gnssmgr-bag-lock-status;
      description
        "The lock status of the receiver";
    }
    leaf receiver-mode {
      type ncs_rpc_notif_Gnssmgr-bag-rx-mode;
      description
        "The receiver mode of the receiver";
    }
    leaf survey-progress {
      type uint32;
      description
        "The survey progress of the receiver";
    }
    leaf holdover-duration {
      type uint32;
      description
        "The holdover duration of the receier";
    }
    leaf major-alarm {
      type uint32;
      description
        "The status of the receiver's major alarm";
    }
    leaf minor-alarm {
      type uint32;
      description
        "The status of the receiver's minor alarm";
    }
    leaf pdop {
      type uint32;
      description
        "Position (3D) dilution of precision (in
         thousandths)";
    }
    leaf hdop {
      type uint32;
      description
        "Horizontal dilution of precision (in
         thousandths)";
    }
    leaf vdop {
      type uint32;
      description
        "Vertical dilution of precision (in thousandths)";
    }
    leaf tdop {
      type uint32;
      description
        "Time dilution of precision (in thousandths)";
    }
    leaf latitude {
      type int32;
      units "centisecond";
      description
        "Latitude of the receiver (arcseconds)";
    }
    leaf longitude {
      type int32;
      units "centisecond";
      description
        "Longitude of the receiver (arcseconds)";
    }
    leaf altitude {
      type int64;
      description
        "Altitude of the receiver (m)";
    }
    leaf time {
      type uint32;
      units "second";
      description
        "Current time recovered by the receiver (secs
         since epoch)";
    }
    leaf utc-offset {
      type int16;
      description
        "UTC offset of the receiver";
    }
    leaf firmware-version {
      type ncs_rpc_notif_Gnssmgr-bag-optional-string;
      description
        "Firmware version of the receiver";
    }
    leaf locked-time {
      type uint32;
      units "second";
      description
        "Locked time recovered by the receiver (secs
         since epoch)";
    }
    leaf satellite-data-known {
      type boolean;
      description
        "Is the satellite data known?";
    }
    list satellite {
      description
        "Satellites visible to the receiver";
      uses ncs_rpc_notif_GNSSMGR-BAG-SATELLITE;
    }
  }

  grouping live_ncs_GNSSMGR-BAG-SATELLITE {
    description
      "Satellite information";
    leaf prn-number {
      type uint8;
      description
        "PRN number";
    }
    leaf channel-number {
      type uint8;
      description
        "Channel number";
    }
    leaf acquisition-flag {
      type boolean;
      description
        "Acquisition flag";
    }
    leaf ephemeris-flag {
      type boolean;
      description
        "Ephemeris flag";
    }
    leaf sv-type {
      type live_ncs_Gnssmgr-bag-sat-sv;
      description
        "Space vehicle (SV) type";
    }
    leaf signal-strength {
      type uint32;
      description
        "Signal strength (0.001 dB-Hz)";
    }
    leaf elevation {
      type uint32;
      description
        "Elevation (0.001 degrees)";
    }
    leaf azimuth {
      type uint32;
      description
        "Azimuth (0.001 degrees)";
    }
  }

  grouping live_ncs_GNSSMGR-RX-INFO {
    description
      "GNSS receiver information";
    leaf receiver-number {
      type uint32;
      description
        "Receiver number";
    }
    leaf node {
      type xr:live_ncs_Node-id;
      description
        "Node the receiver is on";
    }
    leaf enabled {
      type boolean;
      description
        "Whether the receiver is enabled";
    }
    leaf shutdown {
      type boolean;
      description
        "Whether the receiver is shutdown";
    }
    leaf anti-jam-disable {
      type boolean;
      description
        "Whether anti-jam mode is disabled";
    }
    leaf constellation {
      type live_ncs_Gnssmgr-bag-constellation;
      description
        "Constellation used by the receiver";
    }
    leaf snr-threshold {
      type uint32;
      description
        "Satellite SNR threshold";
    }
    leaf elevation-threshold {
      type uint32;
      description
        "Satellite elevation threshold";
    }
    leaf pdop-threshold {
      type uint32;
      description
        "Satellite position (3D) dilution of precision
         (PDOP) threshold";
    }
    leaf traim-threshold {
      type uint32;
      description
        "Satellite TRAIM threshold";
    }
    leaf cable-delay-compensation {
      type int32;
      description
        "Cable delay compensation";
    }
    leaf polarity1pps {
      type live_ncs_Gnssmgr-bag-1pps-polarity;
      description
        "1PPS polarity";
    }
    leaf available {
      type boolean;
      description
        "Whether the receiver is available";
    }
    leaf lock-status {
      type live_ncs_Gnssmgr-bag-lock-status;
      description
        "The lock status of the receiver";
    }
    leaf receiver-mode {
      type live_ncs_Gnssmgr-bag-rx-mode;
      description
        "The receiver mode of the receiver";
    }
    leaf survey-progress {
      type uint32;
      description
        "The survey progress of the receiver";
    }
    leaf holdover-duration {
      type uint32;
      description
        "The holdover duration of the receier";
    }
    leaf major-alarm {
      type uint32;
      description
        "The status of the receiver's major alarm";
    }
    leaf minor-alarm {
      type uint32;
      description
        "The status of the receiver's minor alarm";
    }
    leaf pdop {
      type uint32;
      description
        "Position (3D) dilution of precision (in
         thousandths)";
    }
    leaf hdop {
      type uint32;
      description
        "Horizontal dilution of precision (in
         thousandths)";
    }
    leaf vdop {
      type uint32;
      description
        "Vertical dilution of precision (in thousandths)";
    }
    leaf tdop {
      type uint32;
      description
        "Time dilution of precision (in thousandths)";
    }
    leaf latitude {
      type int32;
      units "centisecond";
      description
        "Latitude of the receiver (arcseconds)";
    }
    leaf longitude {
      type int32;
      units "centisecond";
      description
        "Longitude of the receiver (arcseconds)";
    }
    leaf altitude {
      type int64;
      description
        "Altitude of the receiver (m)";
    }
    leaf time {
      type uint32;
      units "second";
      description
        "Current time recovered by the receiver (secs
         since epoch)";
    }
    leaf utc-offset {
      type int16;
      description
        "UTC offset of the receiver";
    }
    leaf firmware-version {
      type live_ncs_Gnssmgr-bag-optional-string;
      description
        "Firmware version of the receiver";
    }
    leaf locked-time {
      type uint32;
      units "second";
      description
        "Locked time recovered by the receiver (secs
         since epoch)";
    }
    leaf satellite-data-known {
      type boolean;
      description
        "Is the satellite data known?";
    }
    list satellite {
      description
        "Satellites visible to the receiver";
      uses live_ncs_GNSSMGR-BAG-SATELLITE;
    }
  }

  grouping GNSSMGR-BAG-SATELLITE {
    description
      "Satellite information";
    leaf prn-number {
      type uint8;
      description
        "PRN number";
    }
    leaf channel-number {
      type uint8;
      description
        "Channel number";
    }
    leaf acquisition-flag {
      type boolean;
      description
        "Acquisition flag";
    }
    leaf ephemeris-flag {
      type boolean;
      description
        "Ephemeris flag";
    }
    leaf sv-type {
      type Gnssmgr-bag-sat-sv;
      description
        "Space vehicle (SV) type";
    }
    leaf signal-strength {
      type uint32;
      description
        "Signal strength (0.001 dB-Hz)";
    }
    leaf elevation {
      type uint32;
      description
        "Elevation (0.001 degrees)";
    }
    leaf azimuth {
      type uint32;
      description
        "Azimuth (0.001 degrees)";
    }
  }

  grouping GNSSMGR-RX-INFO {
    description
      "GNSS receiver information";
    leaf receiver-number {
      type uint32;
      description
        "Receiver number";
    }
    leaf node {
      type xr:Node-id;
      description
        "Node the receiver is on";
    }
    leaf enabled {
      type boolean;
      description
        "Whether the receiver is enabled";
    }
    leaf shutdown {
      type boolean;
      description
        "Whether the receiver is shutdown";
    }
    leaf anti-jam-disable {
      type boolean;
      description
        "Whether anti-jam mode is disabled";
    }
    leaf constellation {
      type Gnssmgr-bag-constellation;
      description
        "Constellation used by the receiver";
    }
    leaf snr-threshold {
      type uint32;
      description
        "Satellite SNR threshold";
    }
    leaf elevation-threshold {
      type uint32;
      description
        "Satellite elevation threshold";
    }
    leaf pdop-threshold {
      type uint32;
      description
        "Satellite position (3D) dilution of precision
         (PDOP) threshold";
    }
    leaf traim-threshold {
      type uint32;
      description
        "Satellite TRAIM threshold";
    }
    leaf cable-delay-compensation {
      type int32;
      description
        "Cable delay compensation";
    }
    leaf polarity1pps {
      type Gnssmgr-bag-1pps-polarity;
      description
        "1PPS polarity";
    }
    leaf available {
      type boolean;
      description
        "Whether the receiver is available";
    }
    leaf lock-status {
      type Gnssmgr-bag-lock-status;
      description
        "The lock status of the receiver";
    }
    leaf receiver-mode {
      type Gnssmgr-bag-rx-mode;
      description
        "The receiver mode of the receiver";
    }
    leaf survey-progress {
      type uint32;
      description
        "The survey progress of the receiver";
    }
    leaf holdover-duration {
      type uint32;
      description
        "The holdover duration of the receier";
    }
    leaf major-alarm {
      type uint32;
      description
        "The status of the receiver's major alarm";
    }
    leaf minor-alarm {
      type uint32;
      description
        "The status of the receiver's minor alarm";
    }
    leaf pdop {
      type uint32;
      description
        "Position (3D) dilution of precision (in
         thousandths)";
    }
    leaf hdop {
      type uint32;
      description
        "Horizontal dilution of precision (in
         thousandths)";
    }
    leaf vdop {
      type uint32;
      description
        "Vertical dilution of precision (in thousandths)";
    }
    leaf tdop {
      type uint32;
      description
        "Time dilution of precision (in thousandths)";
    }
    leaf latitude {
      type int32;
      units "centisecond";
      description
        "Latitude of the receiver (arcseconds)";
    }
    leaf longitude {
      type int32;
      units "centisecond";
      description
        "Longitude of the receiver (arcseconds)";
    }
    leaf altitude {
      type int64;
      description
        "Altitude of the receiver (m)";
    }
    leaf time {
      type uint32;
      units "second";
      description
        "Current time recovered by the receiver (secs
         since epoch)";
    }
    leaf utc-offset {
      type int16;
      description
        "UTC offset of the receiver";
    }
    leaf firmware-version {
      type Gnssmgr-bag-optional-string;
      description
        "Firmware version of the receiver";
    }
    leaf locked-time {
      type uint32;
      units "second";
      description
        "Locked time recovered by the receiver (secs
         since epoch)";
    }
    leaf satellite-data-known {
      type boolean;
      description
        "Is the satellite data known?";
    }
    list satellite {
      description
        "Satellites visible to the receiver";
      uses GNSSMGR-BAG-SATELLITE;
    }
  }
}

module Cisco-IOS-XR-sysadmin-clear-ncs5502 {
  // Generated by yanger -t ncs
  tailf:mount-id "cisco-iosxr-nc-7.3:cisco-iosxr-nc-7.3";
  tailf:ncs-device-type "netconf";

  namespace "http://www.cisco.com/ns/yang/Cisco-IOS-XR-sysadmin-clear-ncs5502";
  prefix calvados_clear;

  import tailf-common {
    prefix tailf;
  }
  import Cisco-IOS-XR-sysadmin-ethsw-esdma-cli-ncs5500 {
    prefix esdma;
  }
  import Cisco-IOS-XR-sysadmin-asic-errors-ael {
    prefix aelclear;
  }
  import Cisco-IOS-XR-sysadmin-fabric-ncs5502 {
    prefix fabric;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the top level container for
     all 'clear' commands for Sysadmin.

     Copyright (c) 2015-2020 by Cisco Systems, Inc.
     All rights reserved.";

  revision 2019-04-15 {
    description
      "Establish semantic version baseline.";
    semver:module-version "1.0.0";
  }
  revision 2019-01-30 {
    description
      "Changed the namespace to be consistent with module name";
  }
  revision 2017-10-11 {
    description
      "Changed the namespace to unique namespace per unique model";
  }
  revision 2017-01-31 {
    description
      "Changed the namespace and module name";
  }
  revision 2015-03-20 {
    description
      "Created initial 'clear' implementation for Fretta";
  }

  grouping ncs_template_asic_clear;

  grouping ncs_rpc_notif_asic_clear;

  grouping live_ncs_asic_clear;

  grouping asic_clear;

  augment "/ncs:devices/ncs:device/ncs:config" {
    container clear {
      tailf:ncs-device-type "netconf";
      tailf:display-when "not(../../ncs:module) or ../../ncs:module[ncs:name='Cisco-IOS-XR-sysadmin-clear-ncs5502']";
      container controller {
        container switch {
          uses esdma:switch_clear;
        }
        uses fabric:fabric_clear;
      }
      uses aelclear:ael-clear-asic-errors-grp;
    }
  }
  augment "/ncs:devices/ncs:device/ncs:live-status" {
    container clear {
      tailf:ncs-device-type "netconf";
      tailf:display-when "not(../../ncs:module) or ../../ncs:module[ncs:name='Cisco-IOS-XR-sysadmin-clear-ncs5502'] or (../../ncs:live-status-protocol[not(ncs:capability)]) or (../../ncs:live-status-protocol/ncs:capability/ncs:module[.='Cisco-IOS-XR-sysadmin-clear-ncs5502'])";
      container controller {
        container switch {
          uses esdma:live_ncs_switch_clear;
        }
        uses fabric:live_ncs_fabric_clear;
      }
      uses aelclear:live_ncs_ael-clear-asic-errors-grp;
    }
  }
  augment "/ncs:devices/ncs:template/ncs:ned-id/ncs:config" {
    container clear {
      container controller {
        container switch {
          uses esdma:ncs_template_switch_clear;
        }
        uses fabric:ncs_template_fabric_clear;
      }
      uses aelclear:ncs_template_ael-clear-asic-errors-grp;
    }
  }
}

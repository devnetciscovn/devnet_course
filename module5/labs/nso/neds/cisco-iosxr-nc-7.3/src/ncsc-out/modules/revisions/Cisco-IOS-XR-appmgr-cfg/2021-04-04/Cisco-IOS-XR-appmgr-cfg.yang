module Cisco-IOS-XR-appmgr-cfg {
  // Generated by yanger -t ncs
  tailf:mount-id "cisco-iosxr-nc-7.3:cisco-iosxr-nc-7.3";
  tailf:ncs-device-type "netconf";

  namespace "http://cisco.com/ns/yang/Cisco-IOS-XR-appmgr-cfg";
  prefix appmgr-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR appmgr package configuration.

     This module contains definitions
     for the following management objects:
       appmgr: Appmgr configuration data

     Copyright (c) 2013-2021 by Cisco Systems, Inc.
     All rights reserved.";

  revision 2021-04-04 {
    description
      "Support for secure vault tuple.
       2021-02-15
         Support for process scripts.
       2021-02-15
         Support for process scripts added.";
    semver:module-version "1.1.0";
  }
  revision 2019-04-05 {
    description
      "Establish semantic version baseline.";
    semver:module-version "1.0.0";
  }
  revision 2015-11-09 {
    description
      "IOS XR 6.0 revision.";
  }

  typedef ncs_template_App-restart-policy {
    type string;
    description
      "App restart policy";
  }

  typedef ncs_template_App {
    type string;
    description
      "App";
  }

  typedef ncs_rpc_notif_App-restart-policy {
    type enumeration {
      enum "never" {
        value 1;
        description
          "Do not automatically restart the app.";
      }
      enum "on-failure" {
        value 2;
        description
          "Restart the app if it exits due to an error.";
      }
      enum "always" {
        value 3;
        description
          "Always restart the app if it stops. (the
           default)";
      }
      enum "unless-stopped" {
        value 4;
        description
          "Similar to always, except that when the app is
           stopped (manually or otherwise), it is not
           restarted.";
      }
      enum "unless-errored" {
        value 5;
        description
          "Similar to always, except that when the app is
           in error state, it is not restarted.";
      }
    }
    description
      "App restart policy";
  }

  typedef ncs_rpc_notif_App {
    type enumeration {
      enum "docker" {
        value 1;
        description
          "Docker application";
      }
    }
    description
      "App";
  }

  typedef live_ncs_App-restart-policy {
    type enumeration {
      enum "never" {
        value 1;
        description
          "Do not automatically restart the app.";
      }
      enum "on-failure" {
        value 2;
        description
          "Restart the app if it exits due to an error.";
      }
      enum "always" {
        value 3;
        description
          "Always restart the app if it stops. (the
           default)";
      }
      enum "unless-stopped" {
        value 4;
        description
          "Similar to always, except that when the app is
           stopped (manually or otherwise), it is not
           restarted.";
      }
      enum "unless-errored" {
        value 5;
        description
          "Similar to always, except that when the app is
           in error state, it is not restarted.";
      }
    }
    description
      "App restart policy";
  }

  typedef live_ncs_App {
    type enumeration {
      enum "docker" {
        value 1;
        description
          "Docker application";
      }
    }
    description
      "App";
  }

  typedef App-restart-policy {
    type enumeration {
      enum "never" {
        value 1;
        description
          "Do not automatically restart the app.";
      }
      enum "on-failure" {
        value 2;
        description
          "Restart the app if it exits due to an error.";
      }
      enum "always" {
        value 3;
        description
          "Always restart the app if it stops. (the
           default)";
      }
      enum "unless-stopped" {
        value 4;
        description
          "Similar to always, except that when the app is
           stopped (manually or otherwise), it is not
           restarted.";
      }
      enum "unless-errored" {
        value 5;
        description
          "Similar to always, except that when the app is
           in error state, it is not restarted.";
      }
    }
    description
      "App restart policy";
  }

  typedef App {
    type enumeration {
      enum "docker" {
        value 1;
        description
          "Docker application";
      }
    }
    description
      "App";
  }

  augment "/ncs:devices/ncs:device/ncs:config" {
    container appmgr {
      tailf:ncs-device-type "netconf";
      tailf:display-when "not(../../ncs:module) or ../../ncs:module[ncs:name='Cisco-IOS-XR-appmgr-cfg']";
      description
        "Appmgr configuration data";
      container process-scripts {
        description
          "Table of process scripts";
        list process-script {
          key "name";
          description
            "Process script configuration";
          container restart-policy {
            description
              "Application restart policy";
            leaf restart {
              type App-restart-policy;
              description
                "Appliction restart policy";
            }
            leaf max-retries {
              when "../restart = 'on-failure'" {
                tailf:xpath-root 3;
                description
                  "../Restart = on-failure";
              }
              type uint32 {
                range "1..10";
              }
              description
                "Maximum retries to attempt";
            }
          }
          leaf arguments {
            type string {
              length "1..1024";
            }
            description
              "Process script argument string";
          }
          leaf executable {
            type string {
              length "1..255";
            }
            description
              "Process script executable name";
          }
          leaf name {
            type string {
              length "1..255";
            }
            description
              "Application identifier";
          }
        }
      }
      container applications {
        description
          "Table of applications";
        list application {
          key "name";
          description
            "Application configuration";
          container activate {
            description
              "Application activation";
            leaf type {
              type App;
              default "docker";
              description
                "Appliction type - type of application to be
                 deployed";
            }
            leaf source {
              type string {
                length "1..255";
              }
              default "none";
              description
                "Appliction source - name of source";
            }
            leaf command {
              type string {
                length "1..1024";
              }
              default "none";
              description
                "Command to be run inside the container -
                 Docker Only ";
            }
            leaf run-options {
              type string {
                length "1..1024";
              }
              default "none";
              description
                "Docker run options as a string - Docker Only";
            }
          }
          leaf name {
            type string {
              length "1..255";
            }
            description
              "Application identifier";
          }
        }
      }
    }
  }
  augment "/ncs:devices/ncs:device/ncs:live-status" {
    container appmgr {
      tailf:ncs-device-type "netconf";
      tailf:display-when "not(../../ncs:module) or ../../ncs:module[ncs:name='Cisco-IOS-XR-appmgr-cfg'] or (../../ncs:live-status-protocol[not(ncs:capability)]) or (../../ncs:live-status-protocol/ncs:capability/ncs:module[.='Cisco-IOS-XR-appmgr-cfg'])";
      description
        "Appmgr configuration data";
      container process-scripts {
        description
          "Table of process scripts";
        list process-script {
          key "name";
          description
            "Process script configuration";
          container restart-policy {
            description
              "Application restart policy";
            leaf restart {
              type live_ncs_App-restart-policy;
              description
                "Appliction restart policy";
            }
            leaf max-retries {
              // NCS drop when statement
              type uint32 {
                range "1..10";
              }
              description
                "Maximum retries to attempt";
            }
          }
          leaf arguments {
            type string {
              length "1..1024";
            }
            description
              "Process script argument string";
          }
          leaf executable {
            type string {
              length "1..255";
            }
            description
              "Process script executable name";
          }
          leaf name {
            type string {
              length "1..255";
            }
            description
              "Application identifier";
          }
        }
      }
      container applications {
        description
          "Table of applications";
        list application {
          key "name";
          description
            "Application configuration";
          container activate {
            description
              "Application activation";
            leaf type {
              type live_ncs_App;
              // NCS drop default statement
              description
                "Appliction type - type of application to be
                 deployed";
            }
            leaf source {
              type string {
                length "1..255";
              }
              // NCS drop default statement
              description
                "Appliction source - name of source";
            }
            leaf command {
              type string {
                length "1..1024";
              }
              // NCS drop default statement
              description
                "Command to be run inside the container -
                 Docker Only ";
            }
            leaf run-options {
              type string {
                length "1..1024";
              }
              // NCS drop default statement
              description
                "Docker run options as a string - Docker Only";
            }
          }
          leaf name {
            type string {
              length "1..255";
            }
            description
              "Application identifier";
          }
        }
      }
    }
  }
  augment "/ncs:devices/ncs:template/ncs:ned-id/ncs:config" {
    container appmgr {
      description
        "Appmgr configuration data";
      container process-scripts {
        description
          "Table of process scripts";
        list process-script {
          // NCS patched for predictable order
          ordered-by user;
          key "name";
          description
            "Process script configuration";
          container restart-policy {
            description
              "Application restart policy";
            leaf restart {
              type ncs_template_App-restart-policy;
              description
                "Appliction restart policy";
            }
            leaf max-retries {
              // NCS drop when statement
              type string;
              description
                "Maximum retries to attempt";
            }
          }
          leaf arguments {
            type string;
            description
              "Process script argument string";
          }
          leaf executable {
            type string;
            description
              "Process script executable name";
          }
          leaf name {
            type string;
            description
              "Application identifier";
          }
        }
      }
      container applications {
        description
          "Table of applications";
        list application {
          // NCS patched for predictable order
          ordered-by user;
          key "name";
          description
            "Application configuration";
          container activate {
            description
              "Application activation";
            leaf type {
              type ncs_template_App;
              // NCS drop default statement
              description
                "Appliction type - type of application to be
                 deployed";
            }
            leaf source {
              type string;
              // NCS drop default statement
              description
                "Appliction source - name of source";
            }
            leaf command {
              type string;
              // NCS drop default statement
              description
                "Command to be run inside the container -
                 Docker Only ";
            }
            leaf run-options {
              type string;
              // NCS drop default statement
              description
                "Docker run options as a string - Docker Only";
            }
          }
          leaf name {
            type string;
            description
              "Application identifier";
          }
        }
      }
    }
  }
}

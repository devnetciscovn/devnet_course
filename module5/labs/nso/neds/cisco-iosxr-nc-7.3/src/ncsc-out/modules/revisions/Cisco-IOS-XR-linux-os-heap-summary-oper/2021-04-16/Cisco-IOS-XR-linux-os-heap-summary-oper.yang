module Cisco-IOS-XR-linux-os-heap-summary-oper {
  // Generated by yanger -t ncs
  tailf:mount-id "cisco-iosxr-nc-7.3:cisco-iosxr-nc-7.3";
  tailf:ncs-device-type "netconf";

  namespace "http://cisco.com/ns/yang/Cisco-IOS-XR-linux-os-heap-summary-oper";
  prefix linux-os-heap-summary-oper;

  import Cisco-IOS-XR-types {
    prefix xr;
  }
  import cisco-semver {
    prefix semver;
  }
  include Cisco-IOS-XR-linux-os-heap-summary-oper-sub1 {
    revision-date 2021-04-16;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-os-heap-summary package operational data.

     This module contains definitions
     for the following management objects:
       heap-summary: Heap Summary

     Copyright (c) 2013-2021 by Cisco Systems, Inc.
     All rights reserved.";

  revision 2021-04-16 {
    description
      "Structuring the yang response of show memory heap summary all.";
    semver:module-version "2.0.0";
  }
  revision 2019-04-05 {
    description
      "Establish semantic version baseline.";
    semver:module-version "1.0.1";
  }
  revision 2015-11-09 {
    description
      "IOS XR 6.0 revision.";
  }

  grouping ncs_template_PROCESS {
    description
      "Common node of process-table, all";
    list process {
      // NCS patched for predictable order
      ordered-by user;
      key "process-name";
      description
        "Process Name";
      leaf process-name {
        type xr:ncs_template_Cisco-ios-xr-string;
        description
          "Process name";
      }
      uses ncs_template_SHOW-MEM-HEAP-SUM-YANG;
    }
  }

  grouping ncs_rpc_notif_PROCESS {
    description
      "Common node of process-table, all";
    list process {
      key "process-name";
      description
        "Process Name";
      leaf process-name {
        type xr:ncs_rpc_notif_Cisco-ios-xr-string;
        description
          "Process name";
      }
      uses ncs_rpc_notif_SHOW-MEM-HEAP-SUM-YANG;
    }
  }

  grouping live_ncs_PROCESS {
    description
      "Common node of process-table, all";
    list process {
      key "process-name";
      description
        "Process Name";
      leaf process-name {
        type xr:live_ncs_Cisco-ios-xr-string;
        description
          "Process name";
      }
      uses live_ncs_SHOW-MEM-HEAP-SUM-YANG;
    }
  }

  grouping PROCESS {
    description
      "Common node of process-table, all";
    list process {
      key "process-name";
      description
        "Process Name";
      leaf process-name {
        type xr:Cisco-ios-xr-string;
        description
          "Process name";
      }
      uses SHOW-MEM-HEAP-SUM-YANG;
    }
  }

  augment "/ncs:devices/ncs:device/ncs:config" {
    // NCS drop config false container 'heap-summary'
  }
  augment "/ncs:devices/ncs:device/ncs:live-status" {
    container heap-summary {
      tailf:ncs-device-type "netconf";
      tailf:display-when "not(../../ncs:module) or ../../ncs:module[ncs:name='Cisco-IOS-XR-linux-os-heap-summary-oper'] or (../../ncs:live-status-protocol[not(ncs:capability)]) or (../../ncs:live-status-protocol/ncs:capability/ncs:module[.='Cisco-IOS-XR-linux-os-heap-summary-oper'])";
      description
        "Heap Summary";
      container location-descriptions {
        description
          "Location";
        list location-description {
          key "node";
          description
            "Location specified in location";
          container process-table {
            description
              "List of processes";
            uses live_ncs_PROCESS;
          }
          leaf node {
            type xr:live_ncs_Node-id;
            description
              "Node location";
          }
        }
      }
      container all {
        description
          "All processes";
        uses live_ncs_PROCESS;
      }
    }
  }
  augment "/ncs:devices/ncs:template/ncs:ned-id/ncs:config" {
    // NCS drop config false container 'heap-summary'
  }
}

module Cisco-IOS-XR-sysadmin-tacacs-tacacs-server {
  // Generated by yanger -t ncs
  tailf:mount-id "cisco-iosxr-nc-7.3:cisco-iosxr-nc-7.3";
  tailf:ncs-device-type "netconf";

  namespace "http://www.cisco.com/ns/yang/Cisco-IOS-XR-sysadmin-tacacs-tacacs-server";
  prefix tacacs-server;

  import tailf-common {
    prefix tailf;
  }
  import ietf-inet-types {
    prefix inet;
  }
  import cisco-semver {
    prefix semver;
  }
  import tailf-ncs {
    prefix ncs;
  }

  organization
    "Cisco Systems";
  contact
    "aaa-ng-tacacs-dev@cisco.com";
  description
    "This module defines the TACACS+ data model.

     Copyright (c) 2012-2020 by Cisco Systems, Inc.
     All rights reserved.";

  revision 2019-04-15 {
    description
      "Establish semantic version baseline.";
    semver:module-version "1.0.0";
  }
  revision 2017-05-10 {
    description
      "Namespace changed from tacacs to Cisco-IOS-XR-sysadmin-tacacs-tacacs-server";
  }
  revision 2015-06-06 {
    description
      "Initial creation";
  }

  typedef ncs_template_passwdStr {
    type string;
  }

  typedef ncs_rpc_notif_passwdStr {
    type tailf:aes-cfb-128-encrypted-string;
  }

  typedef live_ncs_passwdStr {
    type tailf:aes-cfb-128-encrypted-string;
  }

  typedef passwdStr {
    type tailf:aes-cfb-128-encrypted-string;
  }

  augment "/ncs:devices/ncs:device/ncs:config" {
    container tacacs-server {
      tailf:ncs-device-type "netconf";
      tailf:display-when "not(../../ncs:module) or ../../ncs:module[ncs:name='Cisco-IOS-XR-sysadmin-tacacs-tacacs-server']";
      list host {
        key "ip port";
        max-elements 10;
        ordered-by user;
        leaf ip {
          type inet:ip-address;
        }
        leaf port {
          type inet:port-number {
            range "1 .. 65535";
          }
        }
        leaf timeout {
          type uint32 {
            range "1 .. 1000";
          }
        }
        leaf key {
          type passwdStr;
        }
      }
      leaf timeout {
        type uint32 {
          range "1 .. 1000";
        }
      }
      leaf key {
        type passwdStr;
      }
    }
  }
  augment "/ncs:devices/ncs:device/ncs:live-status" {
    container tacacs-server {
      tailf:ncs-device-type "netconf";
      tailf:display-when "not(../../ncs:module) or ../../ncs:module[ncs:name='Cisco-IOS-XR-sysadmin-tacacs-tacacs-server'] or (../../ncs:live-status-protocol[not(ncs:capability)]) or (../../ncs:live-status-protocol/ncs:capability/ncs:module[.='Cisco-IOS-XR-sysadmin-tacacs-tacacs-server'])";
      list host {
        key "ip port";
        // NCS drop max-elements statement
        ordered-by user;
        leaf ip {
          type inet:ip-address;
        }
        leaf port {
          type inet:port-number {
            range "1 .. 65535";
          }
        }
        leaf timeout {
          type uint32 {
            range "1 .. 1000";
          }
        }
        leaf key {
          type live_ncs_passwdStr;
        }
      }
      leaf timeout {
        type uint32 {
          range "1 .. 1000";
        }
      }
      leaf key {
        type live_ncs_passwdStr;
      }
    }
  }
  augment "/ncs:devices/ncs:template/ncs:ned-id/ncs:config" {
    container tacacs-server {
      list host {
        // NCS patched for predictable order
        ordered-by user;
        key "ip port";
        // NCS drop max-elements statement
        leaf ip {
          type string;
        }
        leaf port {
          type string;
        }
        leaf timeout {
          type string;
        }
        leaf key {
          type ncs_template_passwdStr;
        }
      }
      leaf timeout {
        type string;
      }
      leaf key {
        type ncs_template_passwdStr;
      }
    }
  }
}

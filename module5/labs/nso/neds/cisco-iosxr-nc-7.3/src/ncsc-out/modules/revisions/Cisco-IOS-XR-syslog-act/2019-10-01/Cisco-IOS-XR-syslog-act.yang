module Cisco-IOS-XR-syslog-act {
  // Generated by yanger -t ncs
  tailf:mount-id "cisco-iosxr-nc-7.3:cisco-iosxr-nc-7.3";
  tailf:ncs-device-type "netconf";

  namespace "http://cisco.com/ns/yang/Cisco-IOS-XR-syslog-act";
  prefix syslog-act;

  import cisco-semver {
    prefix semver;
  }
  import ietf-syslog-types {
    prefix log;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     This module contains definitions
     for the following management objects:
     syslog: Global Syslog messaging data

     Copyright (c) 2016-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2016-04-17 {
    description
      "IOS XR 6.1.1 revision.";
  }

  augment "/ncs:devices/ncs:device/ncs:rpc" {
    container rpc-logmsg {
      tailf:ncs-device-type "netconf";
      tailf:display-when "not(../../ncs:module) or ../../ncs:module[ncs:name='Cisco-IOS-XR-syslog-act']";
      tailf:action logmsg {
        tailf:actionpoint ncsproxy {
          tailf:internal;
        }
        description
          "Log message";
        input {
          leaf severity {
            type log:ncs_rpc_notif_severity;
            mandatory true;
            description
              "Set serverity level";
          }
          leaf message {
            type string;
            mandatory true;
            description
              "Message body.";
          }
        }
      }
    }
  }
  augment "/ncs:devices/ncs:device-group/ncs:ned-id/ncs:rpc" {
    container rpc-logmsg {
      tailf:ncs-device-type "netconf";
      tailf:display-when "/ncs:devices/ncs:device[ncs:name=current()/../../../ncs:member]/ncs:module[ncs:name='Cisco-IOS-XR-syslog-act']";
      tailf:action logmsg {
        tailf:actionpoint ncsproxy {
          tailf:internal;
        }
        description
          "Log message";
        input {
          leaf severity {
            type log:ncs_rpc_notif_severity;
            mandatory true;
            description
              "Set serverity level";
          }
          leaf message {
            type string;
            mandatory true;
            description
              "Message body.";
          }
        }
      }
    }
  }
}

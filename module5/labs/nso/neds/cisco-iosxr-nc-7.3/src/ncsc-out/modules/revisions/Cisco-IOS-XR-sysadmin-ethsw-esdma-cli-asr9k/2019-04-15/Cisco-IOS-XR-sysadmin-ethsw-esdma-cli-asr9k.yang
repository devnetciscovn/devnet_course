module Cisco-IOS-XR-sysadmin-ethsw-esdma-cli-asr9k {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-cli-asr9k";
  prefix esdma;

  import Cisco-IOS-XR-sysadmin-ethsw-esdma-admin-exec {
    prefix esdma_admin_exec;
  }
  import Cisco-IOS-XR-sysadmin-ethsw-esdma-bridge {
    prefix esdma_bridge;
  }
  import Cisco-IOS-XR-sysadmin-ethsw-esdma-clear {
    prefix esdma_clear;
  }
  import Cisco-IOS-XR-sysadmin-ethsw-esdma-fdb {
    prefix esdma_fdb;
  }
  import Cisco-IOS-XR-sysadmin-ethsw-esdma-mac {
    prefix esdma_mac;
  }
  import Cisco-IOS-XR-sysadmin-ethsw-esdma-mgmt-agent {
    prefix esdma_mgmt_agent;
  }
  import Cisco-IOS-XR-sysadmin-ethsw-esdma-reachable {
    prefix esdma_reachable;
  }
  import Cisco-IOS-XR-sysadmin-ethsw-esdma-statistics {
    prefix esdma_statistics;
  }
  import Cisco-IOS-XR-sysadmin-ethsw-esdma-summary {
    prefix esdma_summary;
  }
  import Cisco-IOS-XR-sysadmin-ethsw-esdma-trace {
    prefix esdma_trace;
  }
  import Cisco-IOS-XR-sysadmin-ethsw-esdma-trunk {
    prefix esdma_trunk;
  }
  import Cisco-IOS-XR-sysadmin-ethsw-esdma-vlan {
    prefix esdma_vlan;
  }
  import Cisco-IOS-XR-sysadmin-ethsw-esdma-debug {
    prefix esdma_debug;
  }
  import Cisco-IOS-XR-sysadmin-ethsw-esdma-sdr {
    prefix esdma_sdr;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     The 'switch' module provides support for configuring and
     monitoring the control Ethernet switches and ports.
     Support includes basic switch and port statistics.

     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-09-20 {
    description
      "Created separate asr9k yang file.";
  }
  revision 2016-07-06 {
    description
      "Moved command implementations to separate yang module files.";
  }
  revision 2013-02-04 {
    description
      "Initial revision.";
  }

  grouping ncs_template_switch_clear {
    // NCS drop config false container oper
  }

  grouping ncs_template_switch {
    // NCS drop config false container oper
  }

  grouping ncs_rpc_notif_switch_clear {
    container oper {
      config false;
      description
        "Control Ethernet switch operational data.";
      uses esdma_clear:ncs_rpc_notif_switch-clear-fdb;
      uses esdma_clear:ncs_rpc_notif_switch-clear-statistics;
    }
  }

  grouping ncs_rpc_notif_switch {
    container oper {
      config false;
      description
        "Control Ethernet switch operational data.";
      uses esdma_reachable:ncs_rpc_notif_switch-reachable-data;
      uses esdma_summary:ncs_rpc_notif_switch-summary-group;
      uses esdma_statistics:ncs_rpc_notif_switch-statistics-group;
      uses esdma_mac:ncs_rpc_notif_switch-mac-group;
      uses esdma_bridge:ncs_rpc_notif_switch-bridge-group;
      uses esdma_fdb:ncs_rpc_notif_switch-fdb-group;
      uses esdma_vlan:ncs_rpc_notif_switch-vlan-group;
      uses esdma_trace:ncs_rpc_notif_esd-ctrace;
      uses esdma_mgmt_agent:ncs_rpc_notif_esdma-mgmt-group;
      uses esdma_sdr:ncs_rpc_notif_switch-sdr-group;
      uses esdma_admin_exec:ncs_rpc_notif_switch-exec-admin;
      uses esdma_trunk:ncs_rpc_notif_switch-trunk-group;
      uses esdma_debug:ncs_rpc_notif_switch-debug-group;
    }
  }

  grouping live_ncs_switch_clear {
    container oper {
      description
        "Control Ethernet switch operational data.";
      uses esdma_clear:live_ncs_switch-clear-fdb;
      uses esdma_clear:live_ncs_switch-clear-statistics;
    }
  }

  grouping live_ncs_switch {
    container oper {
      description
        "Control Ethernet switch operational data.";
      uses esdma_reachable:live_ncs_switch-reachable-data;
      uses esdma_summary:live_ncs_switch-summary-group;
      uses esdma_statistics:live_ncs_switch-statistics-group;
      uses esdma_mac:live_ncs_switch-mac-group;
      uses esdma_bridge:live_ncs_switch-bridge-group;
      uses esdma_fdb:live_ncs_switch-fdb-group;
      uses esdma_vlan:live_ncs_switch-vlan-group;
      uses esdma_trace:live_ncs_esd-ctrace;
      uses esdma_mgmt_agent:live_ncs_esdma-mgmt-group;
      uses esdma_sdr:live_ncs_switch-sdr-group;
      uses esdma_admin_exec:live_ncs_switch-exec-admin;
      uses esdma_trunk:live_ncs_switch-trunk-group;
      uses esdma_debug:live_ncs_switch-debug-group;
    }
  }

  grouping switch_clear {
    // NCS drop config false container oper
  }

  grouping switch {
    // NCS drop config false container oper
  }
}

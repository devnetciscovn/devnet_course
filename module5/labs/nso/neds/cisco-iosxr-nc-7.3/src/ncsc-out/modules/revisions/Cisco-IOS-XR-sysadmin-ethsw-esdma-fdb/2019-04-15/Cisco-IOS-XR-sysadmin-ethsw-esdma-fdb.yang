module Cisco-IOS-XR-sysadmin-ethsw-esdma-fdb {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-fdb";
  prefix esdma_fdb;

  import ietf-yang-types {
    prefix ietf;
  }
  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch fdb' commands.

     Copyright (c) 2011-2020 by Cisco Systems, Inc.
     All rights reserved.";

  revision 2019-04-15 {
    description
      "Establish semantic version baseline.";
    semver:module-version "1.0.0";
  }
  revision 2018-10-26 {
    description
      "Modified FDB port leaf to use new ESDMA type esdma-switch-fdb-ports";
  }
  revision 2017-05-01 {
    description
      "Namespace change to comply with Cisco guidelines on namespace";
  }
  revision 2016-07-06 {
    description
      "Initial revision with content extracted from esdma_cli.yang.";
  }

  grouping ncs_template_switch-fdb-location {
    container switch-fdb-common {
      list location {
        // NCS patched for predictable order
        ordered-by user;
        key "rack card switch-id";
        leaf rack {
          type esdma_types:ncs_template_esdma-rack-num-enum;
        }
        leaf card {
          type esdma_types:ncs_template_esdma-cpu;
          description
            "Card to list the switch FDB information for";
        }
        leaf switch-id {
          type esdma_types:ncs_template_esdma-switch-type-enum;
          description
            "Switch type";
        }
        leaf num-entries {
          type string;
          description
            "Number of FDB entries in the table.";
        }
        leaf has-trunk-entry {
          type string;
          description
            "FDB entries contain an entry from the trunk";
        }
        leaf trunk-entry-message {
          type string;
          description
            "Message displayed when an FDB entry contains an entry for a trunk member port";
        }
        container fdb-block {
          list fdb-entry {
            // NCS patched for predictable order
            ordered-by user;
            key "fdb-index";
            leaf fdb-index {
              type string;
            }
            leaf fdb-mac-addr {
              type string;
            }
            leaf fdb-vlan {
              type esdma_types:ncs_template_vlan-id-type;
            }
            leaf fdb-vlan-hex {
              type string;
            }
            leaf fdb-port {
              type esdma_types:ncs_template_esdma-switch-fdb-ports;
              description
                "Switch port MAC address learned on.";
            }
            leaf fdb-trap-entry {
              type esdma_types:ncs_template_esdma-switch-yes-no-enum;
            }
            leaf fdb-static-entry {
              type esdma_types:ncs_template_esdma-switch-yes-no-enum;
            }
            leaf-list fdb-synced-cores {
              // NCS patched for predictable order
              ordered-by user;
              type string;
            }
          }
        }
      }
    }
  }

  grouping ncs_template_switch-fdb-group {
    container fdb {
      container vlan {
        list vlan-iter {
          // NCS patched for predictable order
          ordered-by user;
          key "vlan";
          leaf vlan {
            type esdma_types:ncs_template_vlan-id-type;
          }
          uses ncs_template_switch-fdb-location;
        }
      }
      container mac {
        list mac-iter {
          // NCS patched for predictable order
          ordered-by user;
          key "mac";
          leaf mac {
            type string;
          }
          uses ncs_template_switch-fdb-location;
        }
      }
      container port {
        list port-iter {
          // NCS patched for predictable order
          ordered-by user;
          key "port";
          leaf port {
            type esdma_types:ncs_template_esdma-switch-port-type;
            description
              "Switch port used for filtering";
          }
          uses ncs_template_switch-fdb-location;
        }
      }
      container statistics {
        list location {
          // NCS patched for predictable order
          ordered-by user;
          key "rack card switch-id";
          leaf rack {
            type esdma_types:ncs_template_esdma-rack-num-enum;
          }
          leaf card {
            type esdma_types:ncs_template_esdma-cpu;
            description
              "Card";
          }
          leaf switch-id {
            type esdma_types:ncs_template_esdma-switch-type-enum;
            description
              "Switch type";
          }
          container counter-info {
            leaf fdb-shadow-entries {
              type string;
            }
            leaf fdb-max-shadow-entries {
              type string;
            }
            leaf fdb-max-hash-chain {
              type string;
            }
            leaf fdb-entries-added {
              type string;
            }
            leaf fdb-entries-deleted {
              type string;
            }
            leaf fdb-entries-updated {
              type string;
            }
            leaf fdb-flushes {
              type string;
            }
            leaf fdb-address-updates {
              type string;
            }
            leaf fdb-new-addresses {
              type string;
            }
            leaf fdb-aged-updates {
              type string;
            }
            leaf fdb-transplant-updates {
              type string;
            }
            leaf fdb-forwarding-updates {
              type string;
            }
            leaf fdb-address-insert-errors {
              type string;
            }
            leaf fdb-address-update-errors {
              type string;
            }
            leaf fdb-memory-errors {
              type string;
            }
            leaf fdb-allocation-errors {
              type string;
            }
            leaf fdb-address-updates-queued {
              type string;
            }
            leaf fdb-address-queue-full {
              type esdma_types:ncs_template_esdma-switch-yes-no-enum;
            }
            leaf fdb-forwarding-updates-queued {
              type string;
            }
            leaf fdb-forwarding-queue-full {
              type esdma_types:ncs_template_esdma-switch-yes-no-enum;
            }
          }
          list core-id {
            // NCS patched for predictable order
            ordered-by user;
            key "core";
            leaf core {
              type string;
            }
            leaf core-entries {
              type string;
            }
            leaf core-static-entries {
              type string;
            }
          }
        }
      }
      uses ncs_template_switch-fdb-location;
    }
  }

  grouping ncs_rpc_notif_switch-fdb-location {
    container switch-fdb-common {
      list location {
        key "rack card switch-id";
        leaf rack {
          type esdma_types:ncs_rpc_notif_esdma-rack-num-enum;
        }
        leaf card {
          type esdma_types:ncs_rpc_notif_esdma-cpu;
          description
            "Card to list the switch FDB information for";
        }
        leaf switch-id {
          type esdma_types:ncs_rpc_notif_esdma-switch-type-enum;
          description
            "Switch type";
        }
        leaf num-entries {
          type uint32;
          description
            "Number of FDB entries in the table.";
        }
        leaf has-trunk-entry {
          type uint8;
          description
            "FDB entries contain an entry from the trunk";
        }
        leaf trunk-entry-message {
          type string;
          description
            "Message displayed when an FDB entry contains an entry for a trunk member port";
        }
        container fdb-block {
          list fdb-entry {
            key "fdb-index";
            leaf fdb-index {
              type uint32;
            }
            leaf fdb-mac-addr {
              type ietf:mac-address;
            }
            leaf fdb-vlan {
              type esdma_types:ncs_rpc_notif_vlan-id-type;
            }
            leaf fdb-vlan-hex {
              type leafref {
                path "../fdb-vlan";
              }
            }
            leaf fdb-port {
              type esdma_types:ncs_rpc_notif_esdma-switch-fdb-ports;
              description
                "Switch port MAC address learned on.";
            }
            leaf fdb-trap-entry {
              type esdma_types:ncs_rpc_notif_esdma-switch-yes-no-enum;
            }
            leaf fdb-static-entry {
              type esdma_types:ncs_rpc_notif_esdma-switch-yes-no-enum;
            }
            leaf-list fdb-synced-cores {
              type uint8;
            }
          }
        }
      }
    }
  }

  grouping ncs_rpc_notif_switch-fdb-group {
    container fdb {
      container vlan {
        list vlan-iter {
          key "vlan";
          leaf vlan {
            type esdma_types:ncs_rpc_notif_vlan-id-type;
          }
          uses ncs_rpc_notif_switch-fdb-location;
        }
      }
      container mac {
        list mac-iter {
          key "mac";
          leaf mac {
            type ietf:mac-address;
          }
          uses ncs_rpc_notif_switch-fdb-location;
        }
      }
      container port {
        list port-iter {
          key "port";
          leaf port {
            type esdma_types:ncs_rpc_notif_esdma-switch-port-type;
            description
              "Switch port used for filtering";
          }
          uses ncs_rpc_notif_switch-fdb-location;
        }
      }
      container statistics {
        list location {
          key "rack card switch-id";
          leaf rack {
            type esdma_types:ncs_rpc_notif_esdma-rack-num-enum;
          }
          leaf card {
            type esdma_types:ncs_rpc_notif_esdma-cpu;
            description
              "Card";
          }
          leaf switch-id {
            type esdma_types:ncs_rpc_notif_esdma-switch-type-enum;
            description
              "Switch type";
          }
          container counter-info {
            leaf fdb-shadow-entries {
              type uint32;
            }
            leaf fdb-max-shadow-entries {
              type uint32;
            }
            leaf fdb-max-hash-chain {
              type uint32;
            }
            leaf fdb-entries-added {
              type uint32;
            }
            leaf fdb-entries-deleted {
              type uint32;
            }
            leaf fdb-entries-updated {
              type uint32;
            }
            leaf fdb-flushes {
              type uint32;
            }
            leaf fdb-address-updates {
              type uint32;
            }
            leaf fdb-new-addresses {
              type uint32;
            }
            leaf fdb-aged-updates {
              type uint32;
            }
            leaf fdb-transplant-updates {
              type uint32;
            }
            leaf fdb-forwarding-updates {
              type uint32;
            }
            leaf fdb-address-insert-errors {
              type uint32;
            }
            leaf fdb-address-update-errors {
              type uint32;
            }
            leaf fdb-memory-errors {
              type uint32;
            }
            leaf fdb-allocation-errors {
              type uint32;
            }
            leaf fdb-address-updates-queued {
              type uint32;
            }
            leaf fdb-address-queue-full {
              type esdma_types:ncs_rpc_notif_esdma-switch-yes-no-enum;
            }
            leaf fdb-forwarding-updates-queued {
              type uint32;
            }
            leaf fdb-forwarding-queue-full {
              type esdma_types:ncs_rpc_notif_esdma-switch-yes-no-enum;
            }
          }
          list core-id {
            key "core";
            leaf core {
              type int32;
            }
            leaf core-entries {
              type uint32;
            }
            leaf core-static-entries {
              type uint32;
            }
          }
        }
      }
      uses ncs_rpc_notif_switch-fdb-location;
    }
  }

  grouping live_ncs_switch-fdb-location {
    container switch-fdb-common {
      list location {
        key "rack card switch-id";
        leaf rack {
          type esdma_types:live_ncs_esdma-rack-num-enum;
        }
        leaf card {
          type esdma_types:live_ncs_esdma-cpu;
          description
            "Card to list the switch FDB information for";
        }
        leaf switch-id {
          type esdma_types:live_ncs_esdma-switch-type-enum;
          description
            "Switch type";
        }
        leaf num-entries {
          type uint32;
          description
            "Number of FDB entries in the table.";
        }
        leaf has-trunk-entry {
          type uint8;
          description
            "FDB entries contain an entry from the trunk";
        }
        leaf trunk-entry-message {
          type string;
          description
            "Message displayed when an FDB entry contains an entry for a trunk member port";
        }
        container fdb-block {
          list fdb-entry {
            key "fdb-index";
            leaf fdb-index {
              type uint32;
            }
            leaf fdb-mac-addr {
              type ietf:mac-address;
            }
            leaf fdb-vlan {
              type esdma_types:live_ncs_vlan-id-type;
            }
            leaf fdb-vlan-hex {
              type leafref {
                path "../fdb-vlan";
              }
            }
            leaf fdb-port {
              type esdma_types:live_ncs_esdma-switch-fdb-ports;
              description
                "Switch port MAC address learned on.";
            }
            leaf fdb-trap-entry {
              type esdma_types:live_ncs_esdma-switch-yes-no-enum;
            }
            leaf fdb-static-entry {
              type esdma_types:live_ncs_esdma-switch-yes-no-enum;
            }
            leaf-list fdb-synced-cores {
              type uint8;
            }
          }
        }
      }
    }
  }

  grouping live_ncs_switch-fdb-group {
    container fdb {
      container vlan {
        list vlan-iter {
          key "vlan";
          leaf vlan {
            type esdma_types:live_ncs_vlan-id-type;
          }
          uses live_ncs_switch-fdb-location;
        }
      }
      container mac {
        list mac-iter {
          key "mac";
          leaf mac {
            type ietf:mac-address;
          }
          uses live_ncs_switch-fdb-location;
        }
      }
      container port {
        list port-iter {
          key "port";
          leaf port {
            type esdma_types:live_ncs_esdma-switch-port-type;
            description
              "Switch port used for filtering";
          }
          uses live_ncs_switch-fdb-location;
        }
      }
      container statistics {
        list location {
          key "rack card switch-id";
          leaf rack {
            type esdma_types:live_ncs_esdma-rack-num-enum;
          }
          leaf card {
            type esdma_types:live_ncs_esdma-cpu;
            description
              "Card";
          }
          leaf switch-id {
            type esdma_types:live_ncs_esdma-switch-type-enum;
            description
              "Switch type";
          }
          container counter-info {
            leaf fdb-shadow-entries {
              type uint32;
            }
            leaf fdb-max-shadow-entries {
              type uint32;
            }
            leaf fdb-max-hash-chain {
              type uint32;
            }
            leaf fdb-entries-added {
              type uint32;
            }
            leaf fdb-entries-deleted {
              type uint32;
            }
            leaf fdb-entries-updated {
              type uint32;
            }
            leaf fdb-flushes {
              type uint32;
            }
            leaf fdb-address-updates {
              type uint32;
            }
            leaf fdb-new-addresses {
              type uint32;
            }
            leaf fdb-aged-updates {
              type uint32;
            }
            leaf fdb-transplant-updates {
              type uint32;
            }
            leaf fdb-forwarding-updates {
              type uint32;
            }
            leaf fdb-address-insert-errors {
              type uint32;
            }
            leaf fdb-address-update-errors {
              type uint32;
            }
            leaf fdb-memory-errors {
              type uint32;
            }
            leaf fdb-allocation-errors {
              type uint32;
            }
            leaf fdb-address-updates-queued {
              type uint32;
            }
            leaf fdb-address-queue-full {
              type esdma_types:live_ncs_esdma-switch-yes-no-enum;
            }
            leaf fdb-forwarding-updates-queued {
              type uint32;
            }
            leaf fdb-forwarding-queue-full {
              type esdma_types:live_ncs_esdma-switch-yes-no-enum;
            }
          }
          list core-id {
            key "core";
            leaf core {
              type int32;
            }
            leaf core-entries {
              type uint32;
            }
            leaf core-static-entries {
              type uint32;
            }
          }
        }
      }
      uses live_ncs_switch-fdb-location;
    }
  }

  grouping switch-fdb-location {
    container switch-fdb-common {
      list location {
        key "rack card switch-id";
        leaf rack {
          type esdma_types:esdma-rack-num-enum;
        }
        leaf card {
          type esdma_types:esdma-cpu;
          description
            "Card to list the switch FDB information for";
        }
        leaf switch-id {
          type esdma_types:esdma-switch-type-enum;
          description
            "Switch type";
        }
        leaf num-entries {
          type uint32;
          description
            "Number of FDB entries in the table.";
        }
        leaf has-trunk-entry {
          type uint8;
          description
            "FDB entries contain an entry from the trunk";
        }
        leaf trunk-entry-message {
          type string;
          description
            "Message displayed when an FDB entry contains an entry for a trunk member port";
        }
        container fdb-block {
          list fdb-entry {
            key "fdb-index";
            leaf fdb-index {
              type uint32;
            }
            leaf fdb-mac-addr {
              type ietf:mac-address;
            }
            leaf fdb-vlan {
              type esdma_types:vlan-id-type;
            }
            leaf fdb-vlan-hex {
              type leafref {
                path "../fdb-vlan";
              }
            }
            leaf fdb-port {
              type esdma_types:esdma-switch-fdb-ports;
              description
                "Switch port MAC address learned on.";
            }
            leaf fdb-trap-entry {
              type esdma_types:esdma-switch-yes-no-enum;
            }
            leaf fdb-static-entry {
              type esdma_types:esdma-switch-yes-no-enum;
            }
            leaf-list fdb-synced-cores {
              type uint8;
            }
          }
        }
      }
    }
  }

  grouping switch-fdb-group {
    container fdb {
      container vlan {
        list vlan-iter {
          key "vlan";
          leaf vlan {
            type esdma_types:vlan-id-type;
          }
          uses switch-fdb-location;
        }
      }
      container mac {
        list mac-iter {
          key "mac";
          leaf mac {
            type ietf:mac-address;
          }
          uses switch-fdb-location;
        }
      }
      container port {
        list port-iter {
          key "port";
          leaf port {
            type esdma_types:esdma-switch-port-type;
            description
              "Switch port used for filtering";
          }
          uses switch-fdb-location;
        }
      }
      container statistics {
        list location {
          key "rack card switch-id";
          leaf rack {
            type esdma_types:esdma-rack-num-enum;
          }
          leaf card {
            type esdma_types:esdma-cpu;
            description
              "Card";
          }
          leaf switch-id {
            type esdma_types:esdma-switch-type-enum;
            description
              "Switch type";
          }
          container counter-info {
            leaf fdb-shadow-entries {
              type uint32;
            }
            leaf fdb-max-shadow-entries {
              type uint32;
            }
            leaf fdb-max-hash-chain {
              type uint32;
            }
            leaf fdb-entries-added {
              type uint32;
            }
            leaf fdb-entries-deleted {
              type uint32;
            }
            leaf fdb-entries-updated {
              type uint32;
            }
            leaf fdb-flushes {
              type uint32;
            }
            leaf fdb-address-updates {
              type uint32;
            }
            leaf fdb-new-addresses {
              type uint32;
            }
            leaf fdb-aged-updates {
              type uint32;
            }
            leaf fdb-transplant-updates {
              type uint32;
            }
            leaf fdb-forwarding-updates {
              type uint32;
            }
            leaf fdb-address-insert-errors {
              type uint32;
            }
            leaf fdb-address-update-errors {
              type uint32;
            }
            leaf fdb-memory-errors {
              type uint32;
            }
            leaf fdb-allocation-errors {
              type uint32;
            }
            leaf fdb-address-updates-queued {
              type uint32;
            }
            leaf fdb-address-queue-full {
              type esdma_types:esdma-switch-yes-no-enum;
            }
            leaf fdb-forwarding-updates-queued {
              type uint32;
            }
            leaf fdb-forwarding-queue-full {
              type esdma_types:esdma-switch-yes-no-enum;
            }
          }
          list core-id {
            key "core";
            leaf core {
              type int32;
            }
            leaf core-entries {
              type uint32;
            }
            leaf core-static-entries {
              type uint32;
            }
          }
        }
      }
      uses switch-fdb-location;
    }
  }
}

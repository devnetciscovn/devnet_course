module Cisco-IOS-XR-appmgr-act {
  // Generated by yanger -t ncs
  tailf:mount-id "cisco-iosxr-nc-7.3:cisco-iosxr-nc-7.3";
  tailf:ncs-device-type "netconf";

  namespace "http://cisco.com/ns/yang/Cisco-IOS-XR-appmgr-act";
  prefix appmgr-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2020-2021 by Cisco Systems, Inc.
     All rights reserved.";

  revision 2021-03-01 {
    description
      "Adding support for uninstall by source.
       2021-02-15
         Support for process script actions added.";
    semver:module-version "1.1.0";
  }
  revision 2020-07-14 {
    description
      "IOS XR 6.6.4 revision.";
    semver:module-version "1.0.0";
  }

  augment "/ncs:devices/ncs:device/ncs:rpc" {
    container rpc-appmgr-process-script-restart {
      tailf:ncs-device-type "netconf";
      tailf:display-when "not(../../ncs:module) or ../../ncs:module[ncs:name='Cisco-IOS-XR-appmgr-act']";
      tailf:action appmgr-process-script-restart {
        tailf:actionpoint ncsproxy {
          tailf:internal;
        }
        description
          "Restart a process-script";
        input {
          leaf name {
            type string;
            mandatory true;
            description
              "Process script name";
          }
        }
      }
    }
  }
  augment "/ncs:devices/ncs:device-group/ncs:ned-id/ncs:rpc" {
    container rpc-appmgr-process-script-restart {
      tailf:ncs-device-type "netconf";
      tailf:display-when "/ncs:devices/ncs:device[ncs:name=current()/../../../ncs:member]/ncs:module[ncs:name='Cisco-IOS-XR-appmgr-act']";
      tailf:action appmgr-process-script-restart {
        tailf:actionpoint ncsproxy {
          tailf:internal;
        }
        description
          "Restart a process-script";
        input {
          leaf name {
            type string;
            mandatory true;
            description
              "Process script name";
          }
        }
      }
    }
  }
  augment "/ncs:devices/ncs:device/ncs:rpc" {
    container rpc-appmgr-process-script-kill {
      tailf:ncs-device-type "netconf";
      tailf:display-when "not(../../ncs:module) or ../../ncs:module[ncs:name='Cisco-IOS-XR-appmgr-act']";
      tailf:action appmgr-process-script-kill {
        tailf:actionpoint ncsproxy {
          tailf:internal;
        }
        description
          "Kill a process-script";
        input {
          leaf name {
            type string;
            mandatory true;
            description
              "Process script name";
          }
        }
      }
    }
  }
  augment "/ncs:devices/ncs:device-group/ncs:ned-id/ncs:rpc" {
    container rpc-appmgr-process-script-kill {
      tailf:ncs-device-type "netconf";
      tailf:display-when "/ncs:devices/ncs:device[ncs:name=current()/../../../ncs:member]/ncs:module[ncs:name='Cisco-IOS-XR-appmgr-act']";
      tailf:action appmgr-process-script-kill {
        tailf:actionpoint ncsproxy {
          tailf:internal;
        }
        description
          "Kill a process-script";
        input {
          leaf name {
            type string;
            mandatory true;
            description
              "Process script name";
          }
        }
      }
    }
  }
  augment "/ncs:devices/ncs:device/ncs:rpc" {
    container rpc-appmgr-process-script-stop {
      tailf:ncs-device-type "netconf";
      tailf:display-when "not(../../ncs:module) or ../../ncs:module[ncs:name='Cisco-IOS-XR-appmgr-act']";
      tailf:action appmgr-process-script-stop {
        tailf:actionpoint ncsproxy {
          tailf:internal;
        }
        description
          "Stop a process-script";
        input {
          leaf name {
            type string;
            mandatory true;
            description
              "Process script name";
          }
        }
      }
    }
  }
  augment "/ncs:devices/ncs:device-group/ncs:ned-id/ncs:rpc" {
    container rpc-appmgr-process-script-stop {
      tailf:ncs-device-type "netconf";
      tailf:display-when "/ncs:devices/ncs:device[ncs:name=current()/../../../ncs:member]/ncs:module[ncs:name='Cisco-IOS-XR-appmgr-act']";
      tailf:action appmgr-process-script-stop {
        tailf:actionpoint ncsproxy {
          tailf:internal;
        }
        description
          "Stop a process-script";
        input {
          leaf name {
            type string;
            mandatory true;
            description
              "Process script name";
          }
        }
      }
    }
  }
  augment "/ncs:devices/ncs:device/ncs:rpc" {
    container rpc-appmgr-process-script-start {
      tailf:ncs-device-type "netconf";
      tailf:display-when "not(../../ncs:module) or ../../ncs:module[ncs:name='Cisco-IOS-XR-appmgr-act']";
      tailf:action appmgr-process-script-start {
        tailf:actionpoint ncsproxy {
          tailf:internal;
        }
        description
          "Start a process-script";
        input {
          leaf name {
            type string;
            mandatory true;
            description
              "Process script name";
          }
        }
      }
    }
  }
  augment "/ncs:devices/ncs:device-group/ncs:ned-id/ncs:rpc" {
    container rpc-appmgr-process-script-start {
      tailf:ncs-device-type "netconf";
      tailf:display-when "/ncs:devices/ncs:device[ncs:name=current()/../../../ncs:member]/ncs:module[ncs:name='Cisco-IOS-XR-appmgr-act']";
      tailf:action appmgr-process-script-start {
        tailf:actionpoint ncsproxy {
          tailf:internal;
        }
        description
          "Start a process-script";
        input {
          leaf name {
            type string;
            mandatory true;
            description
              "Process script name";
          }
        }
      }
    }
  }
  augment "/ncs:devices/ncs:device/ncs:rpc" {
    container rpc-appmgr-process-script-deactivate {
      tailf:ncs-device-type "netconf";
      tailf:display-when "not(../../ncs:module) or ../../ncs:module[ncs:name='Cisco-IOS-XR-appmgr-act']";
      tailf:action appmgr-process-script-deactivate {
        tailf:actionpoint ncsproxy {
          tailf:internal;
        }
        description
          "Deactivate a process-script";
        input {
          leaf name {
            type string;
            mandatory true;
            description
              "Process script name";
          }
        }
      }
    }
  }
  augment "/ncs:devices/ncs:device-group/ncs:ned-id/ncs:rpc" {
    container rpc-appmgr-process-script-deactivate {
      tailf:ncs-device-type "netconf";
      tailf:display-when "/ncs:devices/ncs:device[ncs:name=current()/../../../ncs:member]/ncs:module[ncs:name='Cisco-IOS-XR-appmgr-act']";
      tailf:action appmgr-process-script-deactivate {
        tailf:actionpoint ncsproxy {
          tailf:internal;
        }
        description
          "Deactivate a process-script";
        input {
          leaf name {
            type string;
            mandatory true;
            description
              "Process script name";
          }
        }
      }
    }
  }
  augment "/ncs:devices/ncs:device/ncs:rpc" {
    container rpc-appmgr-process-script-activate {
      tailf:ncs-device-type "netconf";
      tailf:display-when "not(../../ncs:module) or ../../ncs:module[ncs:name='Cisco-IOS-XR-appmgr-act']";
      tailf:action appmgr-process-script-activate {
        tailf:actionpoint ncsproxy {
          tailf:internal;
        }
        description
          "Activate a process-script";
        input {
          leaf name {
            type string;
            mandatory true;
            description
              "Process script name";
          }
        }
      }
    }
  }
  augment "/ncs:devices/ncs:device-group/ncs:ned-id/ncs:rpc" {
    container rpc-appmgr-process-script-activate {
      tailf:ncs-device-type "netconf";
      tailf:display-when "/ncs:devices/ncs:device[ncs:name=current()/../../../ncs:member]/ncs:module[ncs:name='Cisco-IOS-XR-appmgr-act']";
      tailf:action appmgr-process-script-activate {
        tailf:actionpoint ncsproxy {
          tailf:internal;
        }
        description
          "Activate a process-script";
        input {
          leaf name {
            type string;
            mandatory true;
            description
              "Process script name";
          }
        }
      }
    }
  }
  augment "/ncs:devices/ncs:device/ncs:rpc" {
    container rpc-appmgr-package-uninstall-source {
      tailf:ncs-device-type "netconf";
      tailf:display-when "not(../../ncs:module) or ../../ncs:module[ncs:name='Cisco-IOS-XR-appmgr-act']";
      tailf:action appmgr-package-uninstall-source {
        tailf:actionpoint ncsproxy {
          tailf:internal;
        }
        description
          "Uninstall a package by source name.";
        input {
          leaf source {
            type string;
            mandatory true;
            description
              "Source name";
          }
        }
      }
    }
  }
  augment "/ncs:devices/ncs:device-group/ncs:ned-id/ncs:rpc" {
    container rpc-appmgr-package-uninstall-source {
      tailf:ncs-device-type "netconf";
      tailf:display-when "/ncs:devices/ncs:device[ncs:name=current()/../../../ncs:member]/ncs:module[ncs:name='Cisco-IOS-XR-appmgr-act']";
      tailf:action appmgr-package-uninstall-source {
        tailf:actionpoint ncsproxy {
          tailf:internal;
        }
        description
          "Uninstall a package by source name.";
        input {
          leaf source {
            type string;
            mandatory true;
            description
              "Source name";
          }
        }
      }
    }
  }
  augment "/ncs:devices/ncs:device/ncs:rpc" {
    container rpc-appmgr-package-uninstall {
      tailf:ncs-device-type "netconf";
      tailf:display-when "not(../../ncs:module) or ../../ncs:module[ncs:name='Cisco-IOS-XR-appmgr-act']";
      tailf:action appmgr-package-uninstall {
        tailf:actionpoint ncsproxy {
          tailf:internal;
        }
        description
          "Uninstall a package.";
        input {
          leaf package {
            type string;
            mandatory true;
            description
              "Package name";
          }
        }
      }
    }
  }
  augment "/ncs:devices/ncs:device-group/ncs:ned-id/ncs:rpc" {
    container rpc-appmgr-package-uninstall {
      tailf:ncs-device-type "netconf";
      tailf:display-when "/ncs:devices/ncs:device[ncs:name=current()/../../../ncs:member]/ncs:module[ncs:name='Cisco-IOS-XR-appmgr-act']";
      tailf:action appmgr-package-uninstall {
        tailf:actionpoint ncsproxy {
          tailf:internal;
        }
        description
          "Uninstall a package.";
        input {
          leaf package {
            type string;
            mandatory true;
            description
              "Package name";
          }
        }
      }
    }
  }
  augment "/ncs:devices/ncs:device/ncs:rpc" {
    container rpc-appmgr-package-install {
      tailf:ncs-device-type "netconf";
      tailf:display-when "not(../../ncs:module) or ../../ncs:module[ncs:name='Cisco-IOS-XR-appmgr-act']";
      tailf:action appmgr-package-install {
        tailf:actionpoint ncsproxy {
          tailf:internal;
        }
        description
          "Install an rpm.";
        input {
          leaf rpm {
            type string;
            mandatory true;
            description
              "Path to package rpm";
          }
        }
      }
    }
  }
  augment "/ncs:devices/ncs:device-group/ncs:ned-id/ncs:rpc" {
    container rpc-appmgr-package-install {
      tailf:ncs-device-type "netconf";
      tailf:display-when "/ncs:devices/ncs:device[ncs:name=current()/../../../ncs:member]/ncs:module[ncs:name='Cisco-IOS-XR-appmgr-act']";
      tailf:action appmgr-package-install {
        tailf:actionpoint ncsproxy {
          tailf:internal;
        }
        description
          "Install an rpm.";
        input {
          leaf rpm {
            type string;
            mandatory true;
            description
              "Path to package rpm";
          }
        }
      }
    }
  }
  augment "/ncs:devices/ncs:device/ncs:rpc" {
    container rpc-appmgr-app-copy {
      tailf:ncs-device-type "netconf";
      tailf:display-when "not(../../ncs:module) or ../../ncs:module[ncs:name='Cisco-IOS-XR-appmgr-act']";
      tailf:action appmgr-app-copy {
        tailf:actionpoint ncsproxy {
          tailf:internal;
        }
        description
          "Copy files/folders between an application and an XR filesystem";
        input {
          leaf source {
            type string;
            mandatory true;
            description
              "SOURCE-FILESYSTEM:PATH or SOURCE-APPLICATION:PATH (eg. harddisk:foo/bar or myapp:foo/bar)";
          }
          leaf destination {
            type string;
            mandatory true;
            description
              "DESTINATION-FILESYSTEM:PATH or DESTINATION-APPLICATION:PATH (eg. harddisk:foo/bar or myapp:foo/bar)";
          }
        }
      }
    }
  }
  augment "/ncs:devices/ncs:device-group/ncs:ned-id/ncs:rpc" {
    container rpc-appmgr-app-copy {
      tailf:ncs-device-type "netconf";
      tailf:display-when "/ncs:devices/ncs:device[ncs:name=current()/../../../ncs:member]/ncs:module[ncs:name='Cisco-IOS-XR-appmgr-act']";
      tailf:action appmgr-app-copy {
        tailf:actionpoint ncsproxy {
          tailf:internal;
        }
        description
          "Copy files/folders between an application and an XR filesystem";
        input {
          leaf source {
            type string;
            mandatory true;
            description
              "SOURCE-FILESYSTEM:PATH or SOURCE-APPLICATION:PATH (eg. harddisk:foo/bar or myapp:foo/bar)";
          }
          leaf destination {
            type string;
            mandatory true;
            description
              "DESTINATION-FILESYSTEM:PATH or DESTINATION-APPLICATION:PATH (eg. harddisk:foo/bar or myapp:foo/bar)";
          }
        }
      }
    }
  }
  augment "/ncs:devices/ncs:device/ncs:rpc" {
    container rpc-appmgr-app-kill {
      tailf:ncs-device-type "netconf";
      tailf:display-when "not(../../ncs:module) or ../../ncs:module[ncs:name='Cisco-IOS-XR-appmgr-act']";
      tailf:action appmgr-app-kill {
        tailf:actionpoint ncsproxy {
          tailf:internal;
        }
        description
          "Kill an application";
        input {
          leaf name {
            type string;
            mandatory true;
            description
              "App name";
          }
        }
      }
    }
  }
  augment "/ncs:devices/ncs:device-group/ncs:ned-id/ncs:rpc" {
    container rpc-appmgr-app-kill {
      tailf:ncs-device-type "netconf";
      tailf:display-when "/ncs:devices/ncs:device[ncs:name=current()/../../../ncs:member]/ncs:module[ncs:name='Cisco-IOS-XR-appmgr-act']";
      tailf:action appmgr-app-kill {
        tailf:actionpoint ncsproxy {
          tailf:internal;
        }
        description
          "Kill an application";
        input {
          leaf name {
            type string;
            mandatory true;
            description
              "App name";
          }
        }
      }
    }
  }
  augment "/ncs:devices/ncs:device/ncs:rpc" {
    container rpc-appmgr-app-stop {
      tailf:ncs-device-type "netconf";
      tailf:display-when "not(../../ncs:module) or ../../ncs:module[ncs:name='Cisco-IOS-XR-appmgr-act']";
      tailf:action appmgr-app-stop {
        tailf:actionpoint ncsproxy {
          tailf:internal;
        }
        description
          "Stop an application";
        input {
          leaf name {
            type string;
            mandatory true;
            description
              "App name";
          }
        }
      }
    }
  }
  augment "/ncs:devices/ncs:device-group/ncs:ned-id/ncs:rpc" {
    container rpc-appmgr-app-stop {
      tailf:ncs-device-type "netconf";
      tailf:display-when "/ncs:devices/ncs:device[ncs:name=current()/../../../ncs:member]/ncs:module[ncs:name='Cisco-IOS-XR-appmgr-act']";
      tailf:action appmgr-app-stop {
        tailf:actionpoint ncsproxy {
          tailf:internal;
        }
        description
          "Stop an application";
        input {
          leaf name {
            type string;
            mandatory true;
            description
              "App name";
          }
        }
      }
    }
  }
  augment "/ncs:devices/ncs:device/ncs:rpc" {
    container rpc-appmgr-app-start {
      tailf:ncs-device-type "netconf";
      tailf:display-when "not(../../ncs:module) or ../../ncs:module[ncs:name='Cisco-IOS-XR-appmgr-act']";
      tailf:action appmgr-app-start {
        tailf:actionpoint ncsproxy {
          tailf:internal;
        }
        description
          "Start an application";
        input {
          leaf name {
            type string;
            mandatory true;
            description
              "App name";
          }
        }
      }
    }
  }
  augment "/ncs:devices/ncs:device-group/ncs:ned-id/ncs:rpc" {
    container rpc-appmgr-app-start {
      tailf:ncs-device-type "netconf";
      tailf:display-when "/ncs:devices/ncs:device[ncs:name=current()/../../../ncs:member]/ncs:module[ncs:name='Cisco-IOS-XR-appmgr-act']";
      tailf:action appmgr-app-start {
        tailf:actionpoint ncsproxy {
          tailf:internal;
        }
        description
          "Start an application";
        input {
          leaf name {
            type string;
            mandatory true;
            description
              "App name";
          }
        }
      }
    }
  }
}

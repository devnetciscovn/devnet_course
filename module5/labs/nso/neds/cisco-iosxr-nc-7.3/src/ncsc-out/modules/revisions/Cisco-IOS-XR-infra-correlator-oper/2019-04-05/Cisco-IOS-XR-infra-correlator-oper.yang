module Cisco-IOS-XR-infra-correlator-oper {
  // Generated by yanger -t ncs
  tailf:mount-id "cisco-iosxr-nc-7.3:cisco-iosxr-nc-7.3";
  tailf:ncs-device-type "netconf";

  namespace "http://cisco.com/ns/yang/Cisco-IOS-XR-infra-correlator-oper";
  prefix infra-correlator-oper;

  import cisco-semver {
    prefix semver;
  }
  include Cisco-IOS-XR-infra-correlator-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-correlator package operational data.

     This module contains definitions
     for the following management objects:
       suppression: Suppression operational data
       correlator: Correlator operational data

     Copyright (c) 2013-2019 by Cisco Systems, Inc.
     All rights reserved.";

  revision 2019-04-05 {
    description
      "Establish semantic version baseline.";
    semver:module-version "1.0.1";
  }
  revision 2017-09-07 {
    description
      "Fixed type translation error.";
  }
  revision 2017-05-01 {
    description
      "Fixing backward compatibility error in module.";
  }
  revision 2015-11-09 {
    description
      "IOS XR 6.0 revision.";
  }

  augment "/ncs:devices/ncs:device/ncs:config" {
    // NCS drop config false container suppression
    // NCS drop config false container correlator
  }
  augment "/ncs:devices/ncs:device/ncs:live-status" {
    container suppression {
      tailf:ncs-device-type "netconf";
      tailf:display-when "not(../../ncs:module) or ../../ncs:module[ncs:name='Cisco-IOS-XR-infra-correlator-oper'] or (../../ncs:live-status-protocol[not(ncs:capability)]) or (../../ncs:live-status-protocol/ncs:capability/ncs:module[.='Cisco-IOS-XR-infra-correlator-oper'])";
      description
        "Suppression operational data";
      container rule-summaries {
        description
          "Table that contains the database of suppression
           rule summary";
        list rule-summary {
          key "rule-name";
          description
            "One of the suppression rules";
          leaf rule-name {
            type string {
              length "1..32";
            }
            description
              "Suppression Rule Name";
          }
          uses live_ncs_AC-SUPPR-RULE-SUMMARY-BAG;
        }
      }
      container rule-details {
        description
          "Table that contains the database of suppression
           rule details";
        list rule-detail {
          key "rule-name";
          description
            "Details of one of the suppression rules";
          leaf rule-name {
            type string {
              length "1..32";
            }
            description
              "Suppression Rule Name";
          }
          uses live_ncs_AC-SUPPR-RULE-DETAIL-BAG;
        }
      }
    }
    container correlator {
      tailf:ncs-device-type "netconf";
      tailf:display-when "not(../../ncs:module) or ../../ncs:module[ncs:name='Cisco-IOS-XR-infra-correlator-oper'] or (../../ncs:live-status-protocol[not(ncs:capability)]) or (../../ncs:live-status-protocol/ncs:capability/ncs:module[.='Cisco-IOS-XR-infra-correlator-oper'])";
      description
        "Correlator operational data";
      container rules {
        description
          "Table that contains the database of correlation
           rules";
        list rule {
          key "rule-name";
          description
            "One of the correlation rules";
          leaf rule-name {
            type string {
              length "1..32";
            }
            description
              "Correlation Rule Name";
          }
          uses live_ncs_AC-RULE-INFO-BAG;
        }
      }
      container buffer-status {
        description
          "Describes buffer utilization and parameters
           configured";
        uses live_ncs_AC-BUFFER-INFO-BAG;
      }
      container alarms {
        description
          "Correlated alarms Table";
        list alarm {
          key "alarm-id";
          description
            "One of the correlated alarms";
          leaf alarm-id {
            type uint32;
            description
              "Alarm ID";
          }
          uses live_ncs_AC-ALDEMS-ALARM-BAG;
        }
      }
      container rule-set-summaries {
        description
          "Table that contains the ruleset summary info";
        list rule-set-summary {
          key "rule-set-name";
          description
            "Summary of one of the correlation rulesets";
          leaf rule-set-name {
            type string {
              length "1..32";
            }
            description
              "Ruleset Name";
          }
          uses live_ncs_AC-RULESET-SUMMARY-BAG;
        }
      }
      container rule-set-details {
        description
          "Table that contains the ruleset detail info";
        list rule-set-detail {
          key "rule-set-name";
          description
            "Detail of one of the correlation rulesets";
          leaf rule-set-name {
            type string {
              length "1..32";
            }
            description
              "Ruleset Name";
          }
          uses live_ncs_AC-RULESET-DETAIL-BAG;
        }
      }
      container rule-details {
        description
          "Table that contains the database of correlation
           rule details";
        list rule-detail {
          key "rule-name";
          description
            "Details of one of the correlation rules";
          leaf rule-name {
            type string {
              length "1..32";
            }
            description
              "Correlation Rule Name";
          }
          uses live_ncs_AC-RULE-DETAIL-BAG;
        }
      }
      container rule-summaries {
        description
          "Table that contains the database of correlation
           rule summary";
        list rule-summary {
          key "rule-name";
          description
            "One of the correlation rules";
          leaf rule-name {
            type string {
              length "1..32";
            }
            description
              "Correlation Rule Name";
          }
          uses live_ncs_AC-RULE-SUMMARY-BAG;
        }
      }
    }
  }
  augment "/ncs:devices/ncs:template/ncs:ned-id/ncs:config" {
    // NCS drop config false container suppression
    // NCS drop config false container correlator
  }
}

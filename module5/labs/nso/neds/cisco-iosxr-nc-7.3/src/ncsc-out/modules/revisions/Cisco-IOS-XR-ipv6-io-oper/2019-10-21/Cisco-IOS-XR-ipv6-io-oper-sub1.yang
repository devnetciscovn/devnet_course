submodule Cisco-IOS-XR-ipv6-io-oper-sub1 {
  // Generated by yanger -t ncs
  tailf:mount-id "cisco-iosxr-nc-7.3:cisco-iosxr-nc-7.3";

  belongs-to Cisco-IOS-XR-ipv6-io-oper {
    prefix Cisco-IOS-XR-ipv6-io-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv6-io package operational data.

     Copyright (c) 2013-2019 by Cisco Systems, Inc.
     All rights reserved.";

  revision 2019-10-21 {
    description
      "Added List of VRF IDs for path-mtu cache.";
    semver:module-version "1.1.0";
  }
  revision 2019-04-05 {
    description
      "Establish semantic version baseline.";
    semver:module-version "1.0.1";
  }
  revision 2015-11-09 {
    description
      "IOS XR 6.0 revision.";
  }
  revision 2015-08-27 {
    description
      "IOS XR 6.0.0 revision.";
  }

  grouping ncs_template_IPV6-PMTU-CACHE {
    description
      "PMTU Cache";
    leaf interface-handle {
      type string;
      description
        "Interface name";
    }
    leaf address {
      type string;
      description
        "IPv6 Address of Destination";
    }
    leaf vrf-name {
      type string;
      description
        "VRF NAME";
    }
    leaf pmtu {
      type string;
      description
        "Pmtu value";
    }
    leaf age {
      type string;
      description
        "Time remaining for this entry";
    }
  }

  grouping ncs_template_IPV6-PMTU-CACHE-LIST {
    description
      "IPv6 PMTU Cache Information";
    list pmtu-cache {
      // NCS patched for predictable order
      ordered-by user;
      description
        "Pmtu Cache list";
      uses ncs_template_IPV6-PMTU-CACHE;
    }
  }

  grouping ncs_template_IPV6-ND-TRAFFIC {
    description
      "IPV6 ND Traffic";
    leaf sent-router-solicitation-messages {
      type string;
      description
        "ICMP Router Solicitations Sent";
    }
    leaf sent-router-advertisement-messages {
      type string;
      description
        "ICMP Router Advertisements Sent";
    }
    leaf sent-neighbor-solicitation-messages {
      type string;
      description
        "ICMP Neighbor Solicitations Sent";
    }
    leaf sent-neighbor-advertisement-messages {
      type string;
      description
        "ICMP Neighbor Advertisements Sent";
    }
    leaf sent-redirect-messages {
      type string;
      description
        "ICMP Redirect Sent";
    }
    leaf received-router-solicitation-messages {
      type string;
      description
        "ICMP Router Solicitations Received";
    }
    leaf received-router-advertisement-messages {
      type string;
      description
        "ICMP Router Advertisements Received";
    }
    leaf received-neighbor-solicitation-messages {
      type string;
      description
        "ICMP Neighbor Solicitations Received";
    }
    leaf received-neighbor-advertisement-messages {
      type string;
      description
        "ICMP Neighbor Advertisements Received";
    }
    leaf received-redirect-messages {
      type string;
      description
        "ICMP Redirect Received";
    }
  }

  grouping ncs_template_IPV6-IO-ICMP-TRAFFIC {
    description
      "ICMPv6 Traffic Information";
    leaf total-messages {
      type string;
      description
        "ICMP Received";
    }
    leaf too-short-error-messages {
      type string;
      description
        "ICMP Too Short Errors";
    }
    leaf checksum-error-messages {
      type string;
      description
        "ICMP Checksum Errors";
    }
    leaf unknown-error-type-messages {
      type string;
      description
        "ICMP Unknown Error";
    }
    leaf output-messages {
      type string;
      description
        "ICMP Transmitted";
    }
    leaf sent-rate-limited-packets {
      type string;
      description
        "ICMP Sent Packets Ratelimited";
    }
    leaf sent-unreachable-routing-messages {
      type string;
      description
        "ICMP Route Unreachable Sent";
    }
    leaf sent-unreachable-admin-messages {
      type string;
      description
        "ICMP Admin Unreachable Sent";
    }
    leaf sent-unreachable-neighbor-messages {
      type string;
      description
        "ICMP Host Unreachable Sent";
    }
    leaf sent-unreachable-address-messages {
      type string;
      description
        "ICMP Addr Unreachable Sent";
    }
    leaf sent-unreachable-port-messages {
      type string;
      description
        "ICMP Port Unreachable Sent";
    }
    leaf received-unreachable-routing-messages {
      type string;
      description
        "ICMP Route Unreachable Received";
    }
    leaf received-unreachable-admin-messages {
      type string;
      description
        "ICMP Admin Unreachable Received";
    }
    leaf received-unreachable-neighbor-messages {
      type string;
      description
        "ICMP Host Unreachable Received";
    }
    leaf received-unreachable-address-messages {
      type string;
      description
        "ICMP Addr Unreachable Received";
    }
    leaf received-unreachable-port-messages {
      type string;
      description
        "ICMP Port Unreachable Received";
    }
    leaf sent-hop-count-expired-messages {
      type string;
      description
        "ICMP Hop Count Expired Sent";
    }
    leaf sent-reassembly-timeouts {
      type string;
      description
        "ICMP Reassembly Timeouts";
    }
    leaf received-hop-count-expired-messages {
      type string;
      description
        "ICMP Hop Count Expired Received";
    }
    leaf received-reassembly-timeouts {
      type string;
      description
        "ICMP Reassembly Timeouts";
    }
    leaf sent-too-big-messages {
      type string;
      description
        "ICMP Too Big Messages Sent";
    }
    leaf received-too-big-messages {
      type string;
      description
        "ICMP Too Big Messages Received";
    }
    leaf sent-parameter-error-messages {
      type string;
      description
        "ICMP Parameter Error Messages Sent";
    }
    leaf sent-parameter-header-messages {
      type string;
      description
        "ICMP Parameter Next Header Messages Sent";
    }
    leaf sent-parameter-option-messages {
      type string;
      description
        "ICMP Parameter Option Messages Sent";
    }
    leaf received-parameter-error-messages {
      type string;
      description
        "ICMP Parameter Error Messages Received";
    }
    leaf received-parameter-header-messages {
      type string;
      description
        "ICMP Parameter Next Header Messages Received";
    }
    leaf received-parameter-option-messages {
      type string;
      description
        "ICMP Parameter Option Problem Received";
    }
    leaf sent-echo-request-messages {
      type string;
      description
        "ICMP Echo Request Sent";
    }
    leaf sent-echo-reply-messages {
      type string;
      description
        "ICMP Echo Reply Sent";
    }
    leaf received-echo-request-messages {
      type string;
      description
        "ICMP Echo Request Received";
    }
    leaf received-echo-reply-messages {
      type string;
      description
        "ICMP Echo Reply Received";
    }
    leaf sent-unknown-timeout-messages {
      type string;
      description
        "ICMP Unknown Timeout Messages Sent";
    }
    leaf received-unknown-timeout-messages {
      type string;
      description
        "ICMP Unknown Timeout Messages Received";
    }
    leaf sent-parameter-unknown-type-messages {
      type string;
      description
        "ICMP Parameter Unknown Type Messages Sent";
    }
    leaf received-parameter-unknown-type-messages {
      type string;
      description
        "ICMP Parameter Unknown Type Messages Received";
    }
    leaf sent-unreachable-unknown-type-messages {
      type string;
      description
        "ICMP Unreachable Unknown Messages Sent";
    }
    leaf received-unreachable-unknown-type-messages {
      type string;
      description
        "ICMP Unreachable Unknown Messages Received";
    }
  }

  grouping ncs_template_IPV6-IO-TRAFFIC {
    description
      "IPv6 Traffic Information";
    leaf total-packets {
      type string;
      description
        "Total number of IPv6 input Packets";
    }
    leaf local-destination-packets {
      type string;
      description
        "Number of Local IPv6 Destination Packets";
    }
    leaf format-errors {
      type string;
      description
        "Number of IPv6 Format Errors";
    }
    leaf truncated-packets {
      type string;
      description
        "Number of Truncated IPv6 Packets";
    }
    leaf hop-count-exceeded-packets {
      type string;
      description
        "Number of IPv6 Hop Count Exceeded Packets";
    }
    leaf bad-source-address-packets {
      type string;
      description
        "Number of IPv6 Bad Source Address Packets";
    }
    leaf bad-header-packets {
      type string;
      description
        "Number of IPv6 Bad Header Packets";
    }
    leaf unknown-option-type-packets {
      type string;
      description
        "Number of IPv6 Unknown Option Type Packets";
    }
    leaf unknown-protocol-packets {
      type string;
      description
        "Number of IPv6 Unknown Protocol Packets";
    }
    leaf fragments {
      type string;
      description
        "Number of IPv6 Packets to be Fragmented";
    }
    leaf reassembled-packets {
      type string;
      description
        "Number of IPv6 Reassembled Packets";
    }
    leaf reassembly-timeouts {
      type string;
      description
        "Number of IPv6 Reassembly Timedout packets";
    }
    leaf reassembly-failures {
      type string;
      description
        "Number of IPv6 Reassembly Failures";
    }
    leaf reassembly-maximum-drops {
      type string;
      description
        "Reassembly Reach Maximum Drop";
    }
    leaf overlap-frag-drops {
      type string;
      description
        "Reassembly drop overlap frags";
    }
    leaf generated-packets {
      type string;
      description
        "Packets Output";
    }
    leaf forwarded-packets {
      type string;
      description
        "Packets Forwarded";
    }
    leaf source-routed-packets {
      type string;
      description
        "Packets Source Routed";
    }
    leaf fragmented-packets {
      type string;
      description
        "Packets Fragmented";
    }
    leaf fragment-count {
      type string;
      description
        "Fragmented Packet Count";
    }
    leaf fragment-failures {
      type string;
      description
        "Number of IPv6 Fragment Packet  Failures";
    }
    leaf no-route-packets {
      type string;
      description
        "Number of No Route IPv6 Packets";
    }
    leaf too-big-packets {
      type string;
      description
        "Packet Too Big";
    }
    leaf received-multicast-packets {
      type string;
      description
        "Multicast In";
    }
    leaf sent-multicast-packets {
      type string;
      description
        "Multicast Out";
    }
    leaf miscellaneous-drops {
      type string;
      description
        "Misc. drops";
    }
    leaf lisp-v4-encap-packets {
      type string;
      description
        "Locator ID Separation Protocol IPv4 Encapped
         packets";
    }
    leaf lisp-v4-decap-packets {
      type string;
      description
        "Locator ID Separation Protocol IPv4 Decapped
         packets";
    }
    leaf lisp-v6-encap-packets {
      type string;
      description
        "Locator ID Separation Protocol IPv6 Encapped
         packets";
    }
    leaf lisp-v6-decap-packets {
      type string;
      description
        "Locator ID Separation Protocol IPv6 Decapped
         packets";
    }
    leaf lisp-encap-errors {
      type string;
      description
        "Locator ID Separation Protocol Encap errors";
    }
    leaf lisp-decap-errors {
      type string;
      description
        "Locator ID Separation Protocol Decap errors";
    }
    leaf io-puntback {
      type string;
      description
        "IPv6 IO Puntback";
    }
  }

  grouping ncs_template_IPV6-TRAFFIC {
    description
      "IPv6 and ICMPv6 Traffic Information";
    container ipv6 {
      description
        "IPv6 Statistics";
      uses ncs_template_IPV6-IO-TRAFFIC;
    }
    container icmp {
      description
        "ICMP Statistics";
      uses ncs_template_IPV6-IO-ICMP-TRAFFIC;
    }
    container ipv6-node-discovery {
      description
        "IPv6 Node Discovery Statistics";
      uses ncs_template_IPV6-ND-TRAFFIC;
    }
  }

  grouping ncs_rpc_notif_IPV6-PMTU-CACHE {
    description
      "PMTU Cache";
    leaf interface-handle {
      type uint32;
      description
        "Interface name";
    }
    leaf address {
      type inet:ipv6-address;
      description
        "IPv6 Address of Destination";
    }
    leaf vrf-name {
      type string {
        length "0..32";
      }
      description
        "VRF NAME";
    }
    leaf pmtu {
      type uint32;
      description
        "Pmtu value";
    }
    leaf age {
      type uint64;
      description
        "Time remaining for this entry";
    }
  }

  grouping ncs_rpc_notif_IPV6-PMTU-CACHE-LIST {
    description
      "IPv6 PMTU Cache Information";
    list pmtu-cache {
      description
        "Pmtu Cache list";
      uses ncs_rpc_notif_IPV6-PMTU-CACHE;
    }
  }

  grouping ncs_rpc_notif_IPV6-ND-TRAFFIC {
    description
      "IPV6 ND Traffic";
    leaf sent-router-solicitation-messages {
      type uint32;
      description
        "ICMP Router Solicitations Sent";
    }
    leaf sent-router-advertisement-messages {
      type uint32;
      description
        "ICMP Router Advertisements Sent";
    }
    leaf sent-neighbor-solicitation-messages {
      type uint32;
      description
        "ICMP Neighbor Solicitations Sent";
    }
    leaf sent-neighbor-advertisement-messages {
      type uint32;
      description
        "ICMP Neighbor Advertisements Sent";
    }
    leaf sent-redirect-messages {
      type uint32;
      description
        "ICMP Redirect Sent";
    }
    leaf received-router-solicitation-messages {
      type uint32;
      description
        "ICMP Router Solicitations Received";
    }
    leaf received-router-advertisement-messages {
      type uint32;
      description
        "ICMP Router Advertisements Received";
    }
    leaf received-neighbor-solicitation-messages {
      type uint32;
      description
        "ICMP Neighbor Solicitations Received";
    }
    leaf received-neighbor-advertisement-messages {
      type uint32;
      description
        "ICMP Neighbor Advertisements Received";
    }
    leaf received-redirect-messages {
      type uint32;
      description
        "ICMP Redirect Received";
    }
  }

  grouping ncs_rpc_notif_IPV6-IO-ICMP-TRAFFIC {
    description
      "ICMPv6 Traffic Information";
    leaf total-messages {
      type uint32;
      description
        "ICMP Received";
    }
    leaf too-short-error-messages {
      type uint32;
      description
        "ICMP Too Short Errors";
    }
    leaf checksum-error-messages {
      type uint32;
      description
        "ICMP Checksum Errors";
    }
    leaf unknown-error-type-messages {
      type uint32;
      description
        "ICMP Unknown Error";
    }
    leaf output-messages {
      type uint32;
      description
        "ICMP Transmitted";
    }
    leaf sent-rate-limited-packets {
      type uint32;
      description
        "ICMP Sent Packets Ratelimited";
    }
    leaf sent-unreachable-routing-messages {
      type uint32;
      description
        "ICMP Route Unreachable Sent";
    }
    leaf sent-unreachable-admin-messages {
      type uint32;
      description
        "ICMP Admin Unreachable Sent";
    }
    leaf sent-unreachable-neighbor-messages {
      type uint32;
      description
        "ICMP Host Unreachable Sent";
    }
    leaf sent-unreachable-address-messages {
      type uint32;
      description
        "ICMP Addr Unreachable Sent";
    }
    leaf sent-unreachable-port-messages {
      type uint32;
      description
        "ICMP Port Unreachable Sent";
    }
    leaf received-unreachable-routing-messages {
      type uint32;
      description
        "ICMP Route Unreachable Received";
    }
    leaf received-unreachable-admin-messages {
      type uint32;
      description
        "ICMP Admin Unreachable Received";
    }
    leaf received-unreachable-neighbor-messages {
      type uint32;
      description
        "ICMP Host Unreachable Received";
    }
    leaf received-unreachable-address-messages {
      type uint32;
      description
        "ICMP Addr Unreachable Received";
    }
    leaf received-unreachable-port-messages {
      type uint32;
      description
        "ICMP Port Unreachable Received";
    }
    leaf sent-hop-count-expired-messages {
      type uint32;
      description
        "ICMP Hop Count Expired Sent";
    }
    leaf sent-reassembly-timeouts {
      type uint32;
      description
        "ICMP Reassembly Timeouts";
    }
    leaf received-hop-count-expired-messages {
      type uint32;
      description
        "ICMP Hop Count Expired Received";
    }
    leaf received-reassembly-timeouts {
      type uint32;
      description
        "ICMP Reassembly Timeouts";
    }
    leaf sent-too-big-messages {
      type uint32;
      description
        "ICMP Too Big Messages Sent";
    }
    leaf received-too-big-messages {
      type uint32;
      description
        "ICMP Too Big Messages Received";
    }
    leaf sent-parameter-error-messages {
      type uint32;
      description
        "ICMP Parameter Error Messages Sent";
    }
    leaf sent-parameter-header-messages {
      type uint32;
      description
        "ICMP Parameter Next Header Messages Sent";
    }
    leaf sent-parameter-option-messages {
      type uint32;
      description
        "ICMP Parameter Option Messages Sent";
    }
    leaf received-parameter-error-messages {
      type uint32;
      description
        "ICMP Parameter Error Messages Received";
    }
    leaf received-parameter-header-messages {
      type uint32;
      description
        "ICMP Parameter Next Header Messages Received";
    }
    leaf received-parameter-option-messages {
      type uint32;
      description
        "ICMP Parameter Option Problem Received";
    }
    leaf sent-echo-request-messages {
      type uint32;
      description
        "ICMP Echo Request Sent";
    }
    leaf sent-echo-reply-messages {
      type uint32;
      description
        "ICMP Echo Reply Sent";
    }
    leaf received-echo-request-messages {
      type uint32;
      description
        "ICMP Echo Request Received";
    }
    leaf received-echo-reply-messages {
      type uint32;
      description
        "ICMP Echo Reply Received";
    }
    leaf sent-unknown-timeout-messages {
      type uint32;
      description
        "ICMP Unknown Timeout Messages Sent";
    }
    leaf received-unknown-timeout-messages {
      type uint32;
      description
        "ICMP Unknown Timeout Messages Received";
    }
    leaf sent-parameter-unknown-type-messages {
      type uint32;
      description
        "ICMP Parameter Unknown Type Messages Sent";
    }
    leaf received-parameter-unknown-type-messages {
      type uint32;
      description
        "ICMP Parameter Unknown Type Messages Received";
    }
    leaf sent-unreachable-unknown-type-messages {
      type uint32;
      description
        "ICMP Unreachable Unknown Messages Sent";
    }
    leaf received-unreachable-unknown-type-messages {
      type uint32;
      description
        "ICMP Unreachable Unknown Messages Received";
    }
  }

  grouping ncs_rpc_notif_IPV6-IO-TRAFFIC {
    description
      "IPv6 Traffic Information";
    leaf total-packets {
      type uint32;
      description
        "Total number of IPv6 input Packets";
    }
    leaf local-destination-packets {
      type uint32;
      description
        "Number of Local IPv6 Destination Packets";
    }
    leaf format-errors {
      type uint32;
      description
        "Number of IPv6 Format Errors";
    }
    leaf truncated-packets {
      type uint32;
      description
        "Number of Truncated IPv6 Packets";
    }
    leaf hop-count-exceeded-packets {
      type uint32;
      description
        "Number of IPv6 Hop Count Exceeded Packets";
    }
    leaf bad-source-address-packets {
      type uint32;
      description
        "Number of IPv6 Bad Source Address Packets";
    }
    leaf bad-header-packets {
      type uint32;
      description
        "Number of IPv6 Bad Header Packets";
    }
    leaf unknown-option-type-packets {
      type uint32;
      description
        "Number of IPv6 Unknown Option Type Packets";
    }
    leaf unknown-protocol-packets {
      type uint32;
      description
        "Number of IPv6 Unknown Protocol Packets";
    }
    leaf fragments {
      type uint32;
      description
        "Number of IPv6 Packets to be Fragmented";
    }
    leaf reassembled-packets {
      type uint32;
      description
        "Number of IPv6 Reassembled Packets";
    }
    leaf reassembly-timeouts {
      type uint32;
      description
        "Number of IPv6 Reassembly Timedout packets";
    }
    leaf reassembly-failures {
      type uint32;
      description
        "Number of IPv6 Reassembly Failures";
    }
    leaf reassembly-maximum-drops {
      type uint32;
      description
        "Reassembly Reach Maximum Drop";
    }
    leaf overlap-frag-drops {
      type uint32;
      description
        "Reassembly drop overlap frags";
    }
    leaf generated-packets {
      type uint32;
      description
        "Packets Output";
    }
    leaf forwarded-packets {
      type uint32;
      description
        "Packets Forwarded";
    }
    leaf source-routed-packets {
      type uint32;
      description
        "Packets Source Routed";
    }
    leaf fragmented-packets {
      type uint32;
      description
        "Packets Fragmented";
    }
    leaf fragment-count {
      type uint32;
      description
        "Fragmented Packet Count";
    }
    leaf fragment-failures {
      type uint32;
      description
        "Number of IPv6 Fragment Packet  Failures";
    }
    leaf no-route-packets {
      type uint32;
      description
        "Number of No Route IPv6 Packets";
    }
    leaf too-big-packets {
      type uint32;
      description
        "Packet Too Big";
    }
    leaf received-multicast-packets {
      type uint32;
      description
        "Multicast In";
    }
    leaf sent-multicast-packets {
      type uint32;
      description
        "Multicast Out";
    }
    leaf miscellaneous-drops {
      type uint32;
      description
        "Misc. drops";
    }
    leaf lisp-v4-encap-packets {
      type uint32;
      description
        "Locator ID Separation Protocol IPv4 Encapped
         packets";
    }
    leaf lisp-v4-decap-packets {
      type uint32;
      description
        "Locator ID Separation Protocol IPv4 Decapped
         packets";
    }
    leaf lisp-v6-encap-packets {
      type uint32;
      description
        "Locator ID Separation Protocol IPv6 Encapped
         packets";
    }
    leaf lisp-v6-decap-packets {
      type uint32;
      description
        "Locator ID Separation Protocol IPv6 Decapped
         packets";
    }
    leaf lisp-encap-errors {
      type uint32;
      description
        "Locator ID Separation Protocol Encap errors";
    }
    leaf lisp-decap-errors {
      type uint32;
      description
        "Locator ID Separation Protocol Decap errors";
    }
    leaf io-puntback {
      type uint32;
      description
        "IPv6 IO Puntback";
    }
  }

  grouping ncs_rpc_notif_IPV6-TRAFFIC {
    description
      "IPv6 and ICMPv6 Traffic Information";
    container ipv6 {
      description
        "IPv6 Statistics";
      uses ncs_rpc_notif_IPV6-IO-TRAFFIC;
    }
    container icmp {
      description
        "ICMP Statistics";
      uses ncs_rpc_notif_IPV6-IO-ICMP-TRAFFIC;
    }
    container ipv6-node-discovery {
      description
        "IPv6 Node Discovery Statistics";
      uses ncs_rpc_notif_IPV6-ND-TRAFFIC;
    }
  }

  grouping live_ncs_IPV6-PMTU-CACHE {
    description
      "PMTU Cache";
    leaf interface-handle {
      type uint32;
      description
        "Interface name";
    }
    leaf address {
      type inet:ipv6-address;
      description
        "IPv6 Address of Destination";
    }
    leaf vrf-name {
      type string {
        length "0..32";
      }
      description
        "VRF NAME";
    }
    leaf pmtu {
      type uint32;
      description
        "Pmtu value";
    }
    leaf age {
      type uint64;
      description
        "Time remaining for this entry";
    }
  }

  grouping live_ncs_IPV6-PMTU-CACHE-LIST {
    description
      "IPv6 PMTU Cache Information";
    list pmtu-cache {
      description
        "Pmtu Cache list";
      uses live_ncs_IPV6-PMTU-CACHE;
    }
  }

  grouping live_ncs_IPV6-ND-TRAFFIC {
    description
      "IPV6 ND Traffic";
    leaf sent-router-solicitation-messages {
      type uint32;
      description
        "ICMP Router Solicitations Sent";
    }
    leaf sent-router-advertisement-messages {
      type uint32;
      description
        "ICMP Router Advertisements Sent";
    }
    leaf sent-neighbor-solicitation-messages {
      type uint32;
      description
        "ICMP Neighbor Solicitations Sent";
    }
    leaf sent-neighbor-advertisement-messages {
      type uint32;
      description
        "ICMP Neighbor Advertisements Sent";
    }
    leaf sent-redirect-messages {
      type uint32;
      description
        "ICMP Redirect Sent";
    }
    leaf received-router-solicitation-messages {
      type uint32;
      description
        "ICMP Router Solicitations Received";
    }
    leaf received-router-advertisement-messages {
      type uint32;
      description
        "ICMP Router Advertisements Received";
    }
    leaf received-neighbor-solicitation-messages {
      type uint32;
      description
        "ICMP Neighbor Solicitations Received";
    }
    leaf received-neighbor-advertisement-messages {
      type uint32;
      description
        "ICMP Neighbor Advertisements Received";
    }
    leaf received-redirect-messages {
      type uint32;
      description
        "ICMP Redirect Received";
    }
  }

  grouping live_ncs_IPV6-IO-ICMP-TRAFFIC {
    description
      "ICMPv6 Traffic Information";
    leaf total-messages {
      type uint32;
      description
        "ICMP Received";
    }
    leaf too-short-error-messages {
      type uint32;
      description
        "ICMP Too Short Errors";
    }
    leaf checksum-error-messages {
      type uint32;
      description
        "ICMP Checksum Errors";
    }
    leaf unknown-error-type-messages {
      type uint32;
      description
        "ICMP Unknown Error";
    }
    leaf output-messages {
      type uint32;
      description
        "ICMP Transmitted";
    }
    leaf sent-rate-limited-packets {
      type uint32;
      description
        "ICMP Sent Packets Ratelimited";
    }
    leaf sent-unreachable-routing-messages {
      type uint32;
      description
        "ICMP Route Unreachable Sent";
    }
    leaf sent-unreachable-admin-messages {
      type uint32;
      description
        "ICMP Admin Unreachable Sent";
    }
    leaf sent-unreachable-neighbor-messages {
      type uint32;
      description
        "ICMP Host Unreachable Sent";
    }
    leaf sent-unreachable-address-messages {
      type uint32;
      description
        "ICMP Addr Unreachable Sent";
    }
    leaf sent-unreachable-port-messages {
      type uint32;
      description
        "ICMP Port Unreachable Sent";
    }
    leaf received-unreachable-routing-messages {
      type uint32;
      description
        "ICMP Route Unreachable Received";
    }
    leaf received-unreachable-admin-messages {
      type uint32;
      description
        "ICMP Admin Unreachable Received";
    }
    leaf received-unreachable-neighbor-messages {
      type uint32;
      description
        "ICMP Host Unreachable Received";
    }
    leaf received-unreachable-address-messages {
      type uint32;
      description
        "ICMP Addr Unreachable Received";
    }
    leaf received-unreachable-port-messages {
      type uint32;
      description
        "ICMP Port Unreachable Received";
    }
    leaf sent-hop-count-expired-messages {
      type uint32;
      description
        "ICMP Hop Count Expired Sent";
    }
    leaf sent-reassembly-timeouts {
      type uint32;
      description
        "ICMP Reassembly Timeouts";
    }
    leaf received-hop-count-expired-messages {
      type uint32;
      description
        "ICMP Hop Count Expired Received";
    }
    leaf received-reassembly-timeouts {
      type uint32;
      description
        "ICMP Reassembly Timeouts";
    }
    leaf sent-too-big-messages {
      type uint32;
      description
        "ICMP Too Big Messages Sent";
    }
    leaf received-too-big-messages {
      type uint32;
      description
        "ICMP Too Big Messages Received";
    }
    leaf sent-parameter-error-messages {
      type uint32;
      description
        "ICMP Parameter Error Messages Sent";
    }
    leaf sent-parameter-header-messages {
      type uint32;
      description
        "ICMP Parameter Next Header Messages Sent";
    }
    leaf sent-parameter-option-messages {
      type uint32;
      description
        "ICMP Parameter Option Messages Sent";
    }
    leaf received-parameter-error-messages {
      type uint32;
      description
        "ICMP Parameter Error Messages Received";
    }
    leaf received-parameter-header-messages {
      type uint32;
      description
        "ICMP Parameter Next Header Messages Received";
    }
    leaf received-parameter-option-messages {
      type uint32;
      description
        "ICMP Parameter Option Problem Received";
    }
    leaf sent-echo-request-messages {
      type uint32;
      description
        "ICMP Echo Request Sent";
    }
    leaf sent-echo-reply-messages {
      type uint32;
      description
        "ICMP Echo Reply Sent";
    }
    leaf received-echo-request-messages {
      type uint32;
      description
        "ICMP Echo Request Received";
    }
    leaf received-echo-reply-messages {
      type uint32;
      description
        "ICMP Echo Reply Received";
    }
    leaf sent-unknown-timeout-messages {
      type uint32;
      description
        "ICMP Unknown Timeout Messages Sent";
    }
    leaf received-unknown-timeout-messages {
      type uint32;
      description
        "ICMP Unknown Timeout Messages Received";
    }
    leaf sent-parameter-unknown-type-messages {
      type uint32;
      description
        "ICMP Parameter Unknown Type Messages Sent";
    }
    leaf received-parameter-unknown-type-messages {
      type uint32;
      description
        "ICMP Parameter Unknown Type Messages Received";
    }
    leaf sent-unreachable-unknown-type-messages {
      type uint32;
      description
        "ICMP Unreachable Unknown Messages Sent";
    }
    leaf received-unreachable-unknown-type-messages {
      type uint32;
      description
        "ICMP Unreachable Unknown Messages Received";
    }
  }

  grouping live_ncs_IPV6-IO-TRAFFIC {
    description
      "IPv6 Traffic Information";
    leaf total-packets {
      type uint32;
      description
        "Total number of IPv6 input Packets";
    }
    leaf local-destination-packets {
      type uint32;
      description
        "Number of Local IPv6 Destination Packets";
    }
    leaf format-errors {
      type uint32;
      description
        "Number of IPv6 Format Errors";
    }
    leaf truncated-packets {
      type uint32;
      description
        "Number of Truncated IPv6 Packets";
    }
    leaf hop-count-exceeded-packets {
      type uint32;
      description
        "Number of IPv6 Hop Count Exceeded Packets";
    }
    leaf bad-source-address-packets {
      type uint32;
      description
        "Number of IPv6 Bad Source Address Packets";
    }
    leaf bad-header-packets {
      type uint32;
      description
        "Number of IPv6 Bad Header Packets";
    }
    leaf unknown-option-type-packets {
      type uint32;
      description
        "Number of IPv6 Unknown Option Type Packets";
    }
    leaf unknown-protocol-packets {
      type uint32;
      description
        "Number of IPv6 Unknown Protocol Packets";
    }
    leaf fragments {
      type uint32;
      description
        "Number of IPv6 Packets to be Fragmented";
    }
    leaf reassembled-packets {
      type uint32;
      description
        "Number of IPv6 Reassembled Packets";
    }
    leaf reassembly-timeouts {
      type uint32;
      description
        "Number of IPv6 Reassembly Timedout packets";
    }
    leaf reassembly-failures {
      type uint32;
      description
        "Number of IPv6 Reassembly Failures";
    }
    leaf reassembly-maximum-drops {
      type uint32;
      description
        "Reassembly Reach Maximum Drop";
    }
    leaf overlap-frag-drops {
      type uint32;
      description
        "Reassembly drop overlap frags";
    }
    leaf generated-packets {
      type uint32;
      description
        "Packets Output";
    }
    leaf forwarded-packets {
      type uint32;
      description
        "Packets Forwarded";
    }
    leaf source-routed-packets {
      type uint32;
      description
        "Packets Source Routed";
    }
    leaf fragmented-packets {
      type uint32;
      description
        "Packets Fragmented";
    }
    leaf fragment-count {
      type uint32;
      description
        "Fragmented Packet Count";
    }
    leaf fragment-failures {
      type uint32;
      description
        "Number of IPv6 Fragment Packet  Failures";
    }
    leaf no-route-packets {
      type uint32;
      description
        "Number of No Route IPv6 Packets";
    }
    leaf too-big-packets {
      type uint32;
      description
        "Packet Too Big";
    }
    leaf received-multicast-packets {
      type uint32;
      description
        "Multicast In";
    }
    leaf sent-multicast-packets {
      type uint32;
      description
        "Multicast Out";
    }
    leaf miscellaneous-drops {
      type uint32;
      description
        "Misc. drops";
    }
    leaf lisp-v4-encap-packets {
      type uint32;
      description
        "Locator ID Separation Protocol IPv4 Encapped
         packets";
    }
    leaf lisp-v4-decap-packets {
      type uint32;
      description
        "Locator ID Separation Protocol IPv4 Decapped
         packets";
    }
    leaf lisp-v6-encap-packets {
      type uint32;
      description
        "Locator ID Separation Protocol IPv6 Encapped
         packets";
    }
    leaf lisp-v6-decap-packets {
      type uint32;
      description
        "Locator ID Separation Protocol IPv6 Decapped
         packets";
    }
    leaf lisp-encap-errors {
      type uint32;
      description
        "Locator ID Separation Protocol Encap errors";
    }
    leaf lisp-decap-errors {
      type uint32;
      description
        "Locator ID Separation Protocol Decap errors";
    }
    leaf io-puntback {
      type uint32;
      description
        "IPv6 IO Puntback";
    }
  }

  grouping live_ncs_IPV6-TRAFFIC {
    description
      "IPv6 and ICMPv6 Traffic Information";
    container ipv6 {
      description
        "IPv6 Statistics";
      uses live_ncs_IPV6-IO-TRAFFIC;
    }
    container icmp {
      description
        "ICMP Statistics";
      uses live_ncs_IPV6-IO-ICMP-TRAFFIC;
    }
    container ipv6-node-discovery {
      description
        "IPv6 Node Discovery Statistics";
      uses live_ncs_IPV6-ND-TRAFFIC;
    }
  }

  grouping IPV6-PMTU-CACHE {
    description
      "PMTU Cache";
    leaf interface-handle {
      type uint32;
      description
        "Interface name";
    }
    leaf address {
      type inet:ipv6-address;
      description
        "IPv6 Address of Destination";
    }
    leaf vrf-name {
      type string {
        length "0..32";
      }
      description
        "VRF NAME";
    }
    leaf pmtu {
      type uint32;
      description
        "Pmtu value";
    }
    leaf age {
      type uint64;
      description
        "Time remaining for this entry";
    }
  }

  grouping IPV6-PMTU-CACHE-LIST {
    description
      "IPv6 PMTU Cache Information";
    list pmtu-cache {
      description
        "Pmtu Cache list";
      uses IPV6-PMTU-CACHE;
    }
  }

  grouping IPV6-ND-TRAFFIC {
    description
      "IPV6 ND Traffic";
    leaf sent-router-solicitation-messages {
      type uint32;
      description
        "ICMP Router Solicitations Sent";
    }
    leaf sent-router-advertisement-messages {
      type uint32;
      description
        "ICMP Router Advertisements Sent";
    }
    leaf sent-neighbor-solicitation-messages {
      type uint32;
      description
        "ICMP Neighbor Solicitations Sent";
    }
    leaf sent-neighbor-advertisement-messages {
      type uint32;
      description
        "ICMP Neighbor Advertisements Sent";
    }
    leaf sent-redirect-messages {
      type uint32;
      description
        "ICMP Redirect Sent";
    }
    leaf received-router-solicitation-messages {
      type uint32;
      description
        "ICMP Router Solicitations Received";
    }
    leaf received-router-advertisement-messages {
      type uint32;
      description
        "ICMP Router Advertisements Received";
    }
    leaf received-neighbor-solicitation-messages {
      type uint32;
      description
        "ICMP Neighbor Solicitations Received";
    }
    leaf received-neighbor-advertisement-messages {
      type uint32;
      description
        "ICMP Neighbor Advertisements Received";
    }
    leaf received-redirect-messages {
      type uint32;
      description
        "ICMP Redirect Received";
    }
  }

  grouping IPV6-IO-ICMP-TRAFFIC {
    description
      "ICMPv6 Traffic Information";
    leaf total-messages {
      type uint32;
      description
        "ICMP Received";
    }
    leaf too-short-error-messages {
      type uint32;
      description
        "ICMP Too Short Errors";
    }
    leaf checksum-error-messages {
      type uint32;
      description
        "ICMP Checksum Errors";
    }
    leaf unknown-error-type-messages {
      type uint32;
      description
        "ICMP Unknown Error";
    }
    leaf output-messages {
      type uint32;
      description
        "ICMP Transmitted";
    }
    leaf sent-rate-limited-packets {
      type uint32;
      description
        "ICMP Sent Packets Ratelimited";
    }
    leaf sent-unreachable-routing-messages {
      type uint32;
      description
        "ICMP Route Unreachable Sent";
    }
    leaf sent-unreachable-admin-messages {
      type uint32;
      description
        "ICMP Admin Unreachable Sent";
    }
    leaf sent-unreachable-neighbor-messages {
      type uint32;
      description
        "ICMP Host Unreachable Sent";
    }
    leaf sent-unreachable-address-messages {
      type uint32;
      description
        "ICMP Addr Unreachable Sent";
    }
    leaf sent-unreachable-port-messages {
      type uint32;
      description
        "ICMP Port Unreachable Sent";
    }
    leaf received-unreachable-routing-messages {
      type uint32;
      description
        "ICMP Route Unreachable Received";
    }
    leaf received-unreachable-admin-messages {
      type uint32;
      description
        "ICMP Admin Unreachable Received";
    }
    leaf received-unreachable-neighbor-messages {
      type uint32;
      description
        "ICMP Host Unreachable Received";
    }
    leaf received-unreachable-address-messages {
      type uint32;
      description
        "ICMP Addr Unreachable Received";
    }
    leaf received-unreachable-port-messages {
      type uint32;
      description
        "ICMP Port Unreachable Received";
    }
    leaf sent-hop-count-expired-messages {
      type uint32;
      description
        "ICMP Hop Count Expired Sent";
    }
    leaf sent-reassembly-timeouts {
      type uint32;
      description
        "ICMP Reassembly Timeouts";
    }
    leaf received-hop-count-expired-messages {
      type uint32;
      description
        "ICMP Hop Count Expired Received";
    }
    leaf received-reassembly-timeouts {
      type uint32;
      description
        "ICMP Reassembly Timeouts";
    }
    leaf sent-too-big-messages {
      type uint32;
      description
        "ICMP Too Big Messages Sent";
    }
    leaf received-too-big-messages {
      type uint32;
      description
        "ICMP Too Big Messages Received";
    }
    leaf sent-parameter-error-messages {
      type uint32;
      description
        "ICMP Parameter Error Messages Sent";
    }
    leaf sent-parameter-header-messages {
      type uint32;
      description
        "ICMP Parameter Next Header Messages Sent";
    }
    leaf sent-parameter-option-messages {
      type uint32;
      description
        "ICMP Parameter Option Messages Sent";
    }
    leaf received-parameter-error-messages {
      type uint32;
      description
        "ICMP Parameter Error Messages Received";
    }
    leaf received-parameter-header-messages {
      type uint32;
      description
        "ICMP Parameter Next Header Messages Received";
    }
    leaf received-parameter-option-messages {
      type uint32;
      description
        "ICMP Parameter Option Problem Received";
    }
    leaf sent-echo-request-messages {
      type uint32;
      description
        "ICMP Echo Request Sent";
    }
    leaf sent-echo-reply-messages {
      type uint32;
      description
        "ICMP Echo Reply Sent";
    }
    leaf received-echo-request-messages {
      type uint32;
      description
        "ICMP Echo Request Received";
    }
    leaf received-echo-reply-messages {
      type uint32;
      description
        "ICMP Echo Reply Received";
    }
    leaf sent-unknown-timeout-messages {
      type uint32;
      description
        "ICMP Unknown Timeout Messages Sent";
    }
    leaf received-unknown-timeout-messages {
      type uint32;
      description
        "ICMP Unknown Timeout Messages Received";
    }
    leaf sent-parameter-unknown-type-messages {
      type uint32;
      description
        "ICMP Parameter Unknown Type Messages Sent";
    }
    leaf received-parameter-unknown-type-messages {
      type uint32;
      description
        "ICMP Parameter Unknown Type Messages Received";
    }
    leaf sent-unreachable-unknown-type-messages {
      type uint32;
      description
        "ICMP Unreachable Unknown Messages Sent";
    }
    leaf received-unreachable-unknown-type-messages {
      type uint32;
      description
        "ICMP Unreachable Unknown Messages Received";
    }
  }

  grouping IPV6-IO-TRAFFIC {
    description
      "IPv6 Traffic Information";
    leaf total-packets {
      type uint32;
      description
        "Total number of IPv6 input Packets";
    }
    leaf local-destination-packets {
      type uint32;
      description
        "Number of Local IPv6 Destination Packets";
    }
    leaf format-errors {
      type uint32;
      description
        "Number of IPv6 Format Errors";
    }
    leaf truncated-packets {
      type uint32;
      description
        "Number of Truncated IPv6 Packets";
    }
    leaf hop-count-exceeded-packets {
      type uint32;
      description
        "Number of IPv6 Hop Count Exceeded Packets";
    }
    leaf bad-source-address-packets {
      type uint32;
      description
        "Number of IPv6 Bad Source Address Packets";
    }
    leaf bad-header-packets {
      type uint32;
      description
        "Number of IPv6 Bad Header Packets";
    }
    leaf unknown-option-type-packets {
      type uint32;
      description
        "Number of IPv6 Unknown Option Type Packets";
    }
    leaf unknown-protocol-packets {
      type uint32;
      description
        "Number of IPv6 Unknown Protocol Packets";
    }
    leaf fragments {
      type uint32;
      description
        "Number of IPv6 Packets to be Fragmented";
    }
    leaf reassembled-packets {
      type uint32;
      description
        "Number of IPv6 Reassembled Packets";
    }
    leaf reassembly-timeouts {
      type uint32;
      description
        "Number of IPv6 Reassembly Timedout packets";
    }
    leaf reassembly-failures {
      type uint32;
      description
        "Number of IPv6 Reassembly Failures";
    }
    leaf reassembly-maximum-drops {
      type uint32;
      description
        "Reassembly Reach Maximum Drop";
    }
    leaf overlap-frag-drops {
      type uint32;
      description
        "Reassembly drop overlap frags";
    }
    leaf generated-packets {
      type uint32;
      description
        "Packets Output";
    }
    leaf forwarded-packets {
      type uint32;
      description
        "Packets Forwarded";
    }
    leaf source-routed-packets {
      type uint32;
      description
        "Packets Source Routed";
    }
    leaf fragmented-packets {
      type uint32;
      description
        "Packets Fragmented";
    }
    leaf fragment-count {
      type uint32;
      description
        "Fragmented Packet Count";
    }
    leaf fragment-failures {
      type uint32;
      description
        "Number of IPv6 Fragment Packet  Failures";
    }
    leaf no-route-packets {
      type uint32;
      description
        "Number of No Route IPv6 Packets";
    }
    leaf too-big-packets {
      type uint32;
      description
        "Packet Too Big";
    }
    leaf received-multicast-packets {
      type uint32;
      description
        "Multicast In";
    }
    leaf sent-multicast-packets {
      type uint32;
      description
        "Multicast Out";
    }
    leaf miscellaneous-drops {
      type uint32;
      description
        "Misc. drops";
    }
    leaf lisp-v4-encap-packets {
      type uint32;
      description
        "Locator ID Separation Protocol IPv4 Encapped
         packets";
    }
    leaf lisp-v4-decap-packets {
      type uint32;
      description
        "Locator ID Separation Protocol IPv4 Decapped
         packets";
    }
    leaf lisp-v6-encap-packets {
      type uint32;
      description
        "Locator ID Separation Protocol IPv6 Encapped
         packets";
    }
    leaf lisp-v6-decap-packets {
      type uint32;
      description
        "Locator ID Separation Protocol IPv6 Decapped
         packets";
    }
    leaf lisp-encap-errors {
      type uint32;
      description
        "Locator ID Separation Protocol Encap errors";
    }
    leaf lisp-decap-errors {
      type uint32;
      description
        "Locator ID Separation Protocol Decap errors";
    }
    leaf io-puntback {
      type uint32;
      description
        "IPv6 IO Puntback";
    }
  }

  grouping IPV6-TRAFFIC {
    description
      "IPv6 and ICMPv6 Traffic Information";
    container ipv6 {
      description
        "IPv6 Statistics";
      uses IPV6-IO-TRAFFIC;
    }
    container icmp {
      description
        "ICMP Statistics";
      uses IPV6-IO-ICMP-TRAFFIC;
    }
    container ipv6-node-discovery {
      description
        "IPv6 Node Discovery Statistics";
      uses IPV6-ND-TRAFFIC;
    }
  }
}

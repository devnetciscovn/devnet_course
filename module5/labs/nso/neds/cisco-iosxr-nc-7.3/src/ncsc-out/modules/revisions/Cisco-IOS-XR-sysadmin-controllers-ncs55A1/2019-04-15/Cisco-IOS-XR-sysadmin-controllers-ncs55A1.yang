module Cisco-IOS-XR-sysadmin-controllers-ncs55A1 {
  // Generated by yanger -t ncs
  tailf:mount-id "cisco-iosxr-nc-7.3:cisco-iosxr-nc-7.3";
  tailf:ncs-device-type "netconf";

  namespace "http://www.cisco.com/ns/yang/Cisco-IOS-XR-sysadmin-controllers-NCS55A1";
  prefix calvados_controllers;

  import Cisco-IOS-XR-sysadmin-fabric-ncs5502 {
    prefix fabric;
  }
  import fit {
    prefix fit;
  }
  import Cisco-IOS-XR-sysadmin-card-mgr {
    prefix card_mgr;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the top level container for
     all hardware devices managed in Sysadmin.

     Copyright (c) 2015-2020 by Cisco Systems, Inc.
     All rights reserved.";

  revision 2019-04-15 {
    description
      "Establish semantic version baseline.";
    semver:module-version "1.0.0";
  }
  revision 2017-10-11 {
    description
      "Changed the namespace to unique namespace per unique model";
  }
  revision 2015-03-20 {
    description
      "Created initial 'controller' implementation for Fretta";
  }

  augment "/ncs:devices/ncs:device/ncs:config" {
    container set {
      tailf:ncs-device-type "netconf";
      tailf:display-when "not(../../ncs:module) or ../../ncs:module[ncs:name='Cisco-IOS-XR-sysadmin-controllers-ncs55A1']";
      container controller {
        uses fit:fit-grp;
      }
    }
    container controller {
      tailf:ncs-device-type "netconf";
      tailf:display-when "not(../../ncs:module) or ../../ncs:module[ncs:name='Cisco-IOS-XR-sysadmin-controllers-ncs55A1']";
      uses fabric:fabric;
      uses fabric:fabric_action_cmds;
      uses card_mgr:card_mgr-group;
    }
  }
  augment "/ncs:devices/ncs:device/ncs:live-status" {
    container set {
      tailf:ncs-device-type "netconf";
      tailf:display-when "not(../../ncs:module) or ../../ncs:module[ncs:name='Cisco-IOS-XR-sysadmin-controllers-ncs55A1'] or (../../ncs:live-status-protocol[not(ncs:capability)]) or (../../ncs:live-status-protocol/ncs:capability/ncs:module[.='Cisco-IOS-XR-sysadmin-controllers-ncs55A1'])";
      container controller {
        uses fit:live_ncs_fit-grp;
      }
    }
    container controller {
      tailf:ncs-device-type "netconf";
      tailf:display-when "not(../../ncs:module) or ../../ncs:module[ncs:name='Cisco-IOS-XR-sysadmin-controllers-ncs55A1'] or (../../ncs:live-status-protocol[not(ncs:capability)]) or (../../ncs:live-status-protocol/ncs:capability/ncs:module[.='Cisco-IOS-XR-sysadmin-controllers-ncs55A1'])";
      uses fabric:live_ncs_fabric;
      uses fabric:live_ncs_fabric_action_cmds;
      uses card_mgr:live_ncs_card_mgr-group;
    }
  }
  augment "/ncs:devices/ncs:template/ncs:ned-id/ncs:config" {
    container set {
      container controller {
        uses fit:ncs_template_fit-grp;
      }
    }
    container controller {
      uses fabric:ncs_template_fabric;
      uses fabric:ncs_template_fabric_action_cmds;
      uses card_mgr:ncs_template_card_mgr-group;
    }
  }
}

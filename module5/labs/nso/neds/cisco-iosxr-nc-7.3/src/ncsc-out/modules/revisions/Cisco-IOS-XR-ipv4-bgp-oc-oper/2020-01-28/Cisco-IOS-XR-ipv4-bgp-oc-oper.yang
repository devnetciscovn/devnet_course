module Cisco-IOS-XR-ipv4-bgp-oc-oper {
  // Generated by yanger -t ncs
  tailf:mount-id "cisco-iosxr-nc-7.3:cisco-iosxr-nc-7.3";
  tailf:ncs-device-type "netconf";

  namespace "http://cisco.com/ns/yang/Cisco-IOS-XR-ipv4-bgp-oc-oper";
  prefix ipv4-bgp-oc-oper;

  import ietf-inet-types {
    prefix inet;
  }
  import cisco-semver {
    prefix semver;
  }
  include Cisco-IOS-XR-ipv4-bgp-oc-oper-sub1 {
    revision-date 2020-01-28;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-bgp-oc package operational data.

     This module contains definitions
     for the following management objects:
       oc-bgp: OC-BGP operational data

     Copyright (c) 2013-2020 by Cisco Systems, Inc.
     All rights reserved.";

  revision 2020-01-28 {
    description
      "Removing unsupported InvalidReason";
    semver:module-version "3.0.0";
  }
  revision 2019-08-31 {
    description
      "Fixing revision error in module.";
    semver:module-version "2.0.0";
  }
  revision 2019-04-05 {
    description
      "Fixing backward compatibility error in module";
    semver:module-version "1.0.0";
  }
  revision 2019-04-05 {
    description
      "Establish semantic version baseline.";
  }
  revision 2017-09-07 {
    description
      "Fixed type translation error.";
  }
  revision 2017-05-01 {
    description
      "Fixing backward compatibility error in module.";
  }
  revision 2015-11-09 {
    description
      "IOS XR 6.0 revision.";
  }

  grouping ncs_template_ROUTE-TABLE {
    description
      "Common node of loc-rib, adj-rib-in-pre,
       adj-rib-in-post, adj-rib-out-pre,
       adj-rib-out-post";
    container routes {
      description
        "routes table";
      list route {
        // NCS patched for predictable order
        ordered-by user;
        description
          "route entry";
        leaf route {
          type string;
          description
            "Network in prefix/length format";
        }
        leaf neighbor-address {
          type string;
          description
            "IP address of the BGP Neighbor";
        }
        leaf path-id {
          type string;
          description
            "Received Path ID";
        }
        uses ncs_template_BGP-OC-ROUTE-BAG;
      }
    }
  }

  grouping ncs_template_LOC-RIB {
    description
      "Common node of ipv4-unicast, ipv6-unicast";
    container loc-rib {
      description
        "Local rib route table";
      uses ncs_template_ROUTE-TABLE;
      uses ncs_template_NUM-ROUTES;
    }
  }

  grouping ncs_template_NUM-ROUTES {
    description
      "Common node of loc-rib, adj-rib-in-pre,
       adj-rib-in-post, adj-rib-out-pre,
       adj-rib-out-post";
    container num-routes {
      description
        "Number of routes in adjacency rib out-bound
         post-policy table";
      uses ncs_template_BGP-OC-RIB-COMMON-BAG;
    }
  }

  grouping ncs_template_OPEN-CONFIG-NEIGHBOR-TABLE {
    description
      "Common node of ipv4-unicast, ipv6-unicast";
    container open-config-neighbors {
      description
        "Neighbor list";
      list open-config-neighbor {
        // NCS patched for predictable order
        ordered-by user;
        key "neighbor-address";
        description
          "Neighbor name";
        container adj-rib-in-post {
          description
            "Adjacency rib in-bound post-policy table";
          uses ncs_template_ROUTE-TABLE;
          uses ncs_template_NUM-ROUTES;
        }
        container adj-rib-out-post {
          description
            "Adjacency rib out-bound post-policy table";
          uses ncs_template_ROUTE-TABLE;
          uses ncs_template_NUM-ROUTES;
        }
        container adj-rib-out-pre {
          description
            "Adjacency rib out-bound pre-policy table";
          uses ncs_template_ROUTE-TABLE;
          uses ncs_template_NUM-ROUTES;
        }
        container adj-rib-in-pre {
          description
            "Adjacency rib in-bound pre-policy table";
          uses ncs_template_ROUTE-TABLE;
          uses ncs_template_NUM-ROUTES;
        }
        leaf neighbor-address {
          type string;
          description
            "Neighbor Address";
        }
      }
    }
  }

  grouping ncs_rpc_notif_ROUTE-TABLE {
    description
      "Common node of loc-rib, adj-rib-in-pre,
       adj-rib-in-post, adj-rib-out-pre,
       adj-rib-out-post";
    container routes {
      description
        "routes table";
      list route {
        description
          "route entry";
        leaf route {
          type inet:ip-prefix;
          description
            "Network in prefix/length format";
        }
        leaf neighbor-address {
          type inet:ip-address-no-zone;
          description
            "IP address of the BGP Neighbor";
        }
        leaf path-id {
          type uint32 {
            range "0..4294967295";
          }
          description
            "Received Path ID";
        }
        uses ncs_rpc_notif_BGP-OC-ROUTE-BAG;
      }
    }
  }

  grouping ncs_rpc_notif_LOC-RIB {
    description
      "Common node of ipv4-unicast, ipv6-unicast";
    container loc-rib {
      description
        "Local rib route table";
      uses ncs_rpc_notif_ROUTE-TABLE;
      uses ncs_rpc_notif_NUM-ROUTES;
    }
  }

  grouping ncs_rpc_notif_NUM-ROUTES {
    description
      "Common node of loc-rib, adj-rib-in-pre,
       adj-rib-in-post, adj-rib-out-pre,
       adj-rib-out-post";
    container num-routes {
      description
        "Number of routes in adjacency rib out-bound
         post-policy table";
      uses ncs_rpc_notif_BGP-OC-RIB-COMMON-BAG;
    }
  }

  grouping ncs_rpc_notif_OPEN-CONFIG-NEIGHBOR-TABLE {
    description
      "Common node of ipv4-unicast, ipv6-unicast";
    container open-config-neighbors {
      description
        "Neighbor list";
      list open-config-neighbor {
        key "neighbor-address";
        description
          "Neighbor name";
        container adj-rib-in-post {
          description
            "Adjacency rib in-bound post-policy table";
          uses ncs_rpc_notif_ROUTE-TABLE;
          uses ncs_rpc_notif_NUM-ROUTES;
        }
        container adj-rib-out-post {
          description
            "Adjacency rib out-bound post-policy table";
          uses ncs_rpc_notif_ROUTE-TABLE;
          uses ncs_rpc_notif_NUM-ROUTES;
        }
        container adj-rib-out-pre {
          description
            "Adjacency rib out-bound pre-policy table";
          uses ncs_rpc_notif_ROUTE-TABLE;
          uses ncs_rpc_notif_NUM-ROUTES;
        }
        container adj-rib-in-pre {
          description
            "Adjacency rib in-bound pre-policy table";
          uses ncs_rpc_notif_ROUTE-TABLE;
          uses ncs_rpc_notif_NUM-ROUTES;
        }
        leaf neighbor-address {
          type inet:ip-address-no-zone;
          description
            "Neighbor Address";
        }
      }
    }
  }

  grouping live_ncs_ROUTE-TABLE {
    description
      "Common node of loc-rib, adj-rib-in-pre,
       adj-rib-in-post, adj-rib-out-pre,
       adj-rib-out-post";
    container routes {
      description
        "routes table";
      list route {
        description
          "route entry";
        leaf route {
          type inet:ip-prefix;
          description
            "Network in prefix/length format";
        }
        leaf neighbor-address {
          type inet:ip-address-no-zone;
          description
            "IP address of the BGP Neighbor";
        }
        leaf path-id {
          type uint32 {
            range "0..4294967295";
          }
          description
            "Received Path ID";
        }
        uses live_ncs_BGP-OC-ROUTE-BAG;
      }
    }
  }

  grouping live_ncs_LOC-RIB {
    description
      "Common node of ipv4-unicast, ipv6-unicast";
    container loc-rib {
      description
        "Local rib route table";
      uses live_ncs_ROUTE-TABLE;
      uses live_ncs_NUM-ROUTES;
    }
  }

  grouping live_ncs_NUM-ROUTES {
    description
      "Common node of loc-rib, adj-rib-in-pre,
       adj-rib-in-post, adj-rib-out-pre,
       adj-rib-out-post";
    container num-routes {
      description
        "Number of routes in adjacency rib out-bound
         post-policy table";
      uses live_ncs_BGP-OC-RIB-COMMON-BAG;
    }
  }

  grouping live_ncs_OPEN-CONFIG-NEIGHBOR-TABLE {
    description
      "Common node of ipv4-unicast, ipv6-unicast";
    container open-config-neighbors {
      description
        "Neighbor list";
      list open-config-neighbor {
        key "neighbor-address";
        description
          "Neighbor name";
        container adj-rib-in-post {
          description
            "Adjacency rib in-bound post-policy table";
          uses live_ncs_ROUTE-TABLE;
          uses live_ncs_NUM-ROUTES;
        }
        container adj-rib-out-post {
          description
            "Adjacency rib out-bound post-policy table";
          uses live_ncs_ROUTE-TABLE;
          uses live_ncs_NUM-ROUTES;
        }
        container adj-rib-out-pre {
          description
            "Adjacency rib out-bound pre-policy table";
          uses live_ncs_ROUTE-TABLE;
          uses live_ncs_NUM-ROUTES;
        }
        container adj-rib-in-pre {
          description
            "Adjacency rib in-bound pre-policy table";
          uses live_ncs_ROUTE-TABLE;
          uses live_ncs_NUM-ROUTES;
        }
        leaf neighbor-address {
          type inet:ip-address-no-zone;
          description
            "Neighbor Address";
        }
      }
    }
  }

  grouping ROUTE-TABLE {
    description
      "Common node of loc-rib, adj-rib-in-pre,
       adj-rib-in-post, adj-rib-out-pre,
       adj-rib-out-post";
    container routes {
      description
        "routes table";
      list route {
        description
          "route entry";
        leaf route {
          type inet:ip-prefix;
          description
            "Network in prefix/length format";
        }
        leaf neighbor-address {
          type inet:ip-address-no-zone;
          description
            "IP address of the BGP Neighbor";
        }
        leaf path-id {
          type uint32 {
            range "0..4294967295";
          }
          description
            "Received Path ID";
        }
        uses BGP-OC-ROUTE-BAG;
      }
    }
  }

  grouping LOC-RIB {
    description
      "Common node of ipv4-unicast, ipv6-unicast";
    container loc-rib {
      description
        "Local rib route table";
      uses ROUTE-TABLE;
      uses NUM-ROUTES;
    }
  }

  grouping NUM-ROUTES {
    description
      "Common node of loc-rib, adj-rib-in-pre,
       adj-rib-in-post, adj-rib-out-pre,
       adj-rib-out-post";
    container num-routes {
      description
        "Number of routes in adjacency rib out-bound
         post-policy table";
      uses BGP-OC-RIB-COMMON-BAG;
    }
  }

  grouping OPEN-CONFIG-NEIGHBOR-TABLE {
    description
      "Common node of ipv4-unicast, ipv6-unicast";
    container open-config-neighbors {
      description
        "Neighbor list";
      list open-config-neighbor {
        key "neighbor-address";
        description
          "Neighbor name";
        container adj-rib-in-post {
          description
            "Adjacency rib in-bound post-policy table";
          uses ROUTE-TABLE;
          uses NUM-ROUTES;
        }
        container adj-rib-out-post {
          description
            "Adjacency rib out-bound post-policy table";
          uses ROUTE-TABLE;
          uses NUM-ROUTES;
        }
        container adj-rib-out-pre {
          description
            "Adjacency rib out-bound pre-policy table";
          uses ROUTE-TABLE;
          uses NUM-ROUTES;
        }
        container adj-rib-in-pre {
          description
            "Adjacency rib in-bound pre-policy table";
          uses ROUTE-TABLE;
          uses NUM-ROUTES;
        }
        leaf neighbor-address {
          type inet:ip-address-no-zone;
          description
            "Neighbor Address";
        }
      }
    }
  }

  augment "/ncs:devices/ncs:device/ncs:config" {
    // NCS drop config false container 'oc-bgp'
  }
  augment "/ncs:devices/ncs:device/ncs:live-status" {
    container oc-bgp {
      tailf:ncs-device-type "netconf";
      tailf:display-when "not(../../ncs:module) or ../../ncs:module[ncs:name='Cisco-IOS-XR-ipv4-bgp-oc-oper'] or (../../ncs:live-status-protocol[not(ncs:capability)]) or (../../ncs:live-status-protocol/ncs:capability/ncs:module[.='Cisco-IOS-XR-ipv4-bgp-oc-oper'])";
      description
        "OC-BGP operational data";
      container bgp-rib {
        description
          "BGP-RIB operational data";
        container afi-safi-table {
          description
            "AFI-SAFIs information";
          container ipv4-unicast {
            description
              "IPv4 Unicast";
            uses live_ncs_LOC-RIB;
            uses live_ncs_OPEN-CONFIG-NEIGHBOR-TABLE;
          }
          container ipv6-unicast {
            description
              "IPv6 Unicast";
            uses live_ncs_LOC-RIB;
            uses live_ncs_OPEN-CONFIG-NEIGHBOR-TABLE;
          }
        }
      }
    }
  }
  augment "/ncs:devices/ncs:template/ncs:ned-id/ncs:config" {
    // NCS drop config false container 'oc-bgp'
  }
}

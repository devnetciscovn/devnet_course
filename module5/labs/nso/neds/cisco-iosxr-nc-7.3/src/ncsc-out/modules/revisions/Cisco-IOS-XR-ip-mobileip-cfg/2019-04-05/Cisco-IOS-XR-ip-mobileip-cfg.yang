module Cisco-IOS-XR-ip-mobileip-cfg {
  // Generated by yanger -t ncs
  tailf:mount-id "cisco-iosxr-nc-7.3:cisco-iosxr-nc-7.3";
  tailf:ncs-device-type "netconf";

  namespace "http://cisco.com/ns/yang/Cisco-IOS-XR-ip-mobileip-cfg";
  prefix ip-mobileip-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-mobileip package configuration.

     This module contains definitions
     for the following management objects:
       mobile-ip: MobileIP configuration

     Copyright (c) 2013-2019 by Cisco Systems, Inc.
     All rights reserved.";

  revision 2019-04-05 {
    description
      "Establish semantic version baseline.";
    semver:module-version "1.0.1";
  }
  revision 2015-11-09 {
    description
      "IOS XR 6.0 revision.";
  }
  revision 2015-09-02 {
    description
      "Initial version";
  }

  typedef ncs_template_Gre-key-type {
    type string;
    description
      "Gre key type";
  }

  typedef ncs_template_Service-type {
    type string;
    description
      "Service type";
  }

  typedef ncs_template_Lma-service {
    type string;
    description
      "Lma service";
  }

  typedef ncs_template_Redist-type {
    type string;
    description
      "Redist type";
  }

  typedef ncs_template_Redist-sub-type {
    type string;
    description
      "Redist sub type";
  }

  typedef ncs_template_Lma-role {
    type string;
    description
      "Lma role";
  }

  typedef ncs_template_Lma-rat {
    type string;
    description
      "Lma rat";
  }

  typedef ncs_template_Encap-opt {
    type string;
    description
      "Encap opt";
  }

  typedef ncs_rpc_notif_Gre-key-type {
    type enumeration {
      enum "symmetric" {
        value 1;
        description
          "Symmetric GRE Key (same Uplink and Downlink
           key)";
      }
    }
    description
      "Gre key type";
  }

  typedef ncs_rpc_notif_Service-type {
    type enumeration {
      enum "ipv4" {
        value 1;
        description
          "ipv4 service type";
      }
      enum "ipv6" {
        value 2;
        description
          "ipv6 service type";
      }
      enum "dual" {
        value 3;
        description
          "dual service type";
      }
    }
    description
      "Service type";
  }

  typedef ncs_rpc_notif_Lma-service {
    type enumeration {
      enum "service-mll" {
        value 1;
        description
          "Wireless Private Routing service";
      }
    }
    description
      "Lma service";
  }

  typedef ncs_rpc_notif_Redist-type {
    type enumeration {
      enum "home-address" {
        value 1;
        description
          "Redistribute HoA/HNP routes";
      }
    }
    description
      "Redist type";
  }

  typedef ncs_rpc_notif_Redist-sub-type {
    type enumeration {
      enum "host-prefix" {
        value 1;
        description
          "Redistribute HoA/HNP host prefix routes";
      }
      enum "disable" {
        value 2;
        description
          "Disable redistribution of HoA/HNP host and pool
           refix routes";
      }
    }
    description
      "Redist sub type";
  }

  typedef ncs_rpc_notif_Lma-role {
    type enumeration {
      enum "3gma" {
        value 0;
        description
          "3GMA mode";
      }
    }
    description
      "Lma role";
  }

  typedef ncs_rpc_notif_Lma-rat {
    type enumeration {
      enum "virtual" {
        value 0;
        description
          "VIRTUAL rat";
      }
      enum "ppp" {
        value 1;
        description
          "PPP rat";
      }
      enum "ethernet" {
        value 2;
        description
          "ETHERNET rat";
      }
      enum "wlan" {
        value 3;
        description
          "WLAN rat";
      }
      enum "wi-max" {
        value 4;
        description
          "WIMAX rat";
      }
      enum "3gppgeran" {
        value 5;
        description
          "3GPP_GERAN rat";
      }
      enum "3gpputran" {
        value 6;
        description
          "3GPP_UTRAN rat";
      }
      enum "3gppeutran" {
        value 7;
        description
          "3GPP_E_UTRAN rat";
      }
      enum "3gpp2ehrpd" {
        value 8;
        description
          "3GPP2_EHRPD rat";
      }
      enum "3gpp2hrpd" {
        value 9;
        description
          "3GPP2_HRPD rat";
      }
      enum "3gpp21rtt" {
        value 10;
        description
          "3GPP2_1RTT rat";
      }
      enum "3gpp2umb" {
        value 11;
        description
          "3GPP2_UMB rat";
      }
    }
    description
      "Lma rat";
  }

  typedef ncs_rpc_notif_Encap-opt {
    type enumeration {
      enum "greipv4" {
        value 4;
        description
          "GRE IPv4 tunnel encap";
      }
      enum "greipv6" {
        value 5;
        description
          "GRE IPv6 tunnel encap";
      }
      enum "mgreipv4" {
        value 7;
        description
          "mGRE IPv4 tunnel encap";
      }
      enum "mgreipv6" {
        value 8;
        description
          "mGRE IPv6 tunnel encap";
      }
    }
    description
      "Encap opt";
  }

  typedef live_ncs_Gre-key-type {
    type enumeration {
      enum "symmetric" {
        value 1;
        description
          "Symmetric GRE Key (same Uplink and Downlink
           key)";
      }
    }
    description
      "Gre key type";
  }

  typedef live_ncs_Service-type {
    type enumeration {
      enum "ipv4" {
        value 1;
        description
          "ipv4 service type";
      }
      enum "ipv6" {
        value 2;
        description
          "ipv6 service type";
      }
      enum "dual" {
        value 3;
        description
          "dual service type";
      }
    }
    description
      "Service type";
  }

  typedef live_ncs_Lma-service {
    type enumeration {
      enum "service-mll" {
        value 1;
        description
          "Wireless Private Routing service";
      }
    }
    description
      "Lma service";
  }

  typedef live_ncs_Redist-type {
    type enumeration {
      enum "home-address" {
        value 1;
        description
          "Redistribute HoA/HNP routes";
      }
    }
    description
      "Redist type";
  }

  typedef live_ncs_Redist-sub-type {
    type enumeration {
      enum "host-prefix" {
        value 1;
        description
          "Redistribute HoA/HNP host prefix routes";
      }
      enum "disable" {
        value 2;
        description
          "Disable redistribution of HoA/HNP host and pool
           refix routes";
      }
    }
    description
      "Redist sub type";
  }

  typedef live_ncs_Lma-role {
    type enumeration {
      enum "3gma" {
        value 0;
        description
          "3GMA mode";
      }
    }
    description
      "Lma role";
  }

  typedef live_ncs_Lma-rat {
    type enumeration {
      enum "virtual" {
        value 0;
        description
          "VIRTUAL rat";
      }
      enum "ppp" {
        value 1;
        description
          "PPP rat";
      }
      enum "ethernet" {
        value 2;
        description
          "ETHERNET rat";
      }
      enum "wlan" {
        value 3;
        description
          "WLAN rat";
      }
      enum "wi-max" {
        value 4;
        description
          "WIMAX rat";
      }
      enum "3gppgeran" {
        value 5;
        description
          "3GPP_GERAN rat";
      }
      enum "3gpputran" {
        value 6;
        description
          "3GPP_UTRAN rat";
      }
      enum "3gppeutran" {
        value 7;
        description
          "3GPP_E_UTRAN rat";
      }
      enum "3gpp2ehrpd" {
        value 8;
        description
          "3GPP2_EHRPD rat";
      }
      enum "3gpp2hrpd" {
        value 9;
        description
          "3GPP2_HRPD rat";
      }
      enum "3gpp21rtt" {
        value 10;
        description
          "3GPP2_1RTT rat";
      }
      enum "3gpp2umb" {
        value 11;
        description
          "3GPP2_UMB rat";
      }
    }
    description
      "Lma rat";
  }

  typedef live_ncs_Encap-opt {
    type enumeration {
      enum "greipv4" {
        value 4;
        description
          "GRE IPv4 tunnel encap";
      }
      enum "greipv6" {
        value 5;
        description
          "GRE IPv6 tunnel encap";
      }
      enum "mgreipv4" {
        value 7;
        description
          "mGRE IPv4 tunnel encap";
      }
      enum "mgreipv6" {
        value 8;
        description
          "mGRE IPv6 tunnel encap";
      }
    }
    description
      "Encap opt";
  }

  typedef Gre-key-type {
    type enumeration {
      enum "symmetric" {
        value 1;
        description
          "Symmetric GRE Key (same Uplink and Downlink
           key)";
      }
    }
    description
      "Gre key type";
  }

  typedef Service-type {
    type enumeration {
      enum "ipv4" {
        value 1;
        description
          "ipv4 service type";
      }
      enum "ipv6" {
        value 2;
        description
          "ipv6 service type";
      }
      enum "dual" {
        value 3;
        description
          "dual service type";
      }
    }
    description
      "Service type";
  }

  typedef Lma-service {
    type enumeration {
      enum "service-mll" {
        value 1;
        description
          "Wireless Private Routing service";
      }
    }
    description
      "Lma service";
  }

  typedef Redist-type {
    type enumeration {
      enum "home-address" {
        value 1;
        description
          "Redistribute HoA/HNP routes";
      }
    }
    description
      "Redist type";
  }

  typedef Redist-sub-type {
    type enumeration {
      enum "host-prefix" {
        value 1;
        description
          "Redistribute HoA/HNP host prefix routes";
      }
      enum "disable" {
        value 2;
        description
          "Disable redistribution of HoA/HNP host and pool
           refix routes";
      }
    }
    description
      "Redist sub type";
  }

  typedef Lma-role {
    type enumeration {
      enum "3gma" {
        value 0;
        description
          "3GMA mode";
      }
    }
    description
      "Lma role";
  }

  typedef Lma-rat {
    type enumeration {
      enum "virtual" {
        value 0;
        description
          "VIRTUAL rat";
      }
      enum "ppp" {
        value 1;
        description
          "PPP rat";
      }
      enum "ethernet" {
        value 2;
        description
          "ETHERNET rat";
      }
      enum "wlan" {
        value 3;
        description
          "WLAN rat";
      }
      enum "wi-max" {
        value 4;
        description
          "WIMAX rat";
      }
      enum "3gppgeran" {
        value 5;
        description
          "3GPP_GERAN rat";
      }
      enum "3gpputran" {
        value 6;
        description
          "3GPP_UTRAN rat";
      }
      enum "3gppeutran" {
        value 7;
        description
          "3GPP_E_UTRAN rat";
      }
      enum "3gpp2ehrpd" {
        value 8;
        description
          "3GPP2_EHRPD rat";
      }
      enum "3gpp2hrpd" {
        value 9;
        description
          "3GPP2_HRPD rat";
      }
      enum "3gpp21rtt" {
        value 10;
        description
          "3GPP2_1RTT rat";
      }
      enum "3gpp2umb" {
        value 11;
        description
          "3GPP2_UMB rat";
      }
    }
    description
      "Lma rat";
  }

  typedef Encap-opt {
    type enumeration {
      enum "greipv4" {
        value 4;
        description
          "GRE IPv4 tunnel encap";
      }
      enum "greipv6" {
        value 5;
        description
          "GRE IPv6 tunnel encap";
      }
      enum "mgreipv4" {
        value 7;
        description
          "mGRE IPv4 tunnel encap";
      }
      enum "mgreipv6" {
        value 8;
        description
          "mGRE IPv6 tunnel encap";
      }
    }
    description
      "Encap opt";
  }

  augment "/ncs:devices/ncs:device/ncs:config" {
    container mobile-ip {
      tailf:ncs-device-type "netconf";
      tailf:display-when "not(../../ncs:module) or ../../ncs:module[ncs:name='Cisco-IOS-XR-ip-mobileip-cfg']";
      description
        "MobileIP configuration";
      container domains {
        description
          "Table of Domain";
        list domain {
          key "domain-name";
          description
            "PMIPv6 domain configuration";
          container mags {
            description
              "Table of MAG";
            list mag {
              key "mag-name";
              description
                "MAG within domain";
              leaf mag-name {
                type xr:Cisco-ios-xr-string {
                  length "1..125";
                }
                description
                  "MAG Identifier";
              }
            }
          }
          container nais {
            description
              "Table of NAI";
            list nai {
              key "nai-name";
              description
                "Network access identifier or Realm";
              leaf lma {
                type string {
                  length "1..125";
                }
                description
                  "LMA for this MN";
              }
              leaf apn {
                type string {
                  length "1..125";
                }
                description
                  "Access point network for this MN";
              }
              leaf customer {
                type xr:Cisco-ios-xr-string {
                  length "1..125";
                }
                description
                  "Customer name for this MN";
              }
              leaf service {
                type Service-type;
                description
                  "Service type for this MN";
              }
              leaf network {
                type string {
                  length "1..125";
                }
                description
                  "Network name (Address pool) for this MN";
              }
              leaf nai-name {
                type string {
                  length "1..125";
                }
                description
                  "MN Identifier";
              }
            }
          }
          container authenticate-option {
            description
              "Authentication option between PMIPV6 entities";
            leaf spi {
              type xr:Hex-integer;
              description
                "SPI in hex value";
            }
            leaf key {
              type string {
                length "1..125";
              }
              description
                "ASCII string";
            }
          }
          container lmas {
            description
              "Table of LMA";
            list lma {
              key "lma-name";
              description
                "LMA within domain";
              leaf lma-name {
                type xr:Cisco-ios-xr-string {
                  length "1..125";
                }
                description
                  "LMA Identifier";
              }
            }
          }
          leaf enable {
            type empty;
            description
              "Enable PMIPv6 domain configuration. Deletion
               of this object also causes deletion of all
               associated objects under Domain.";
          }
          leaf domain-name {
            type xr:Cisco-ios-xr-string {
              length "1..125";
            }
            description
              "Domain Name";
          }
        }
      }
      container lmas {
        description
          "Table of LMA";
        list lma {
          key "lma-name domain-name";
          description
            "PMIPv6 LMA configuration";
          container binding-revocation-attributes {
            description
              "LMA Binding Revocation Attributes";
            container delay {
              description
                "Time to wait before Retransmitting BRI
                 Message";
              leaf br-min {
                type uint32 {
                  range "500..65535";
                }
                description
                  "Specify in millisec";
              }
              leaf br-max {
                type uint32 {
                  range "500..65535";
                }
                description
                  "Specify in millisec";
              }
            }
            leaf retry {
              type uint32 {
                range "1..10";
              }
              description
                "Number of Retransmissons Allowed for BRI
                 Message";
            }
          }
          container rat-attributes {
            description
              "Radio access technology type config  this LMA";
            leaf lma-rat {
              type Lma-rat;
              description
                "LMA rat type";
            }
            leaf priority-value {
              type uint32 {
                range "1..255";
              }
              description
                "Specify the priority value";
            }
          }
          container heart-beat-attributes {
            description
              "heartbeat config for this LMA";
            leaf interval {
              type uint32 {
                range "10..3600";
              }
              description
                "Specify the interval value in second";
            }
            leaf retries {
              type uint32 {
                range "1..10";
              }
              description
                "Specify the retry value";
            }
            leaf timeout {
              type uint32 {
                range "1..3600";
              }
              description
                "Specify the timeout value";
            }
          }
          container lmaipv6-addresses {
            description
              "Table of LMAIPv6Address";
            list lmaipv6-address {
              key "address";
              description
                "Configure IPv6 address for this LMA";
              leaf address {
                type inet:ipv6-address-no-zone;
                description
                  "LMA IPv6 address";
              }
            }
          }
          container hnp {
            description
              "LMA HNP options";
            leaf maximum {
              type uint32 {
                range "1..3";
              }
              description
                "maximum HNPs allowed per MN interface";
            }
          }
          container redistribute {
            description
              "Redistribute routes";
            leaf redist-type {
              type Redist-type;
              description
                "Redistribute type";
            }
            leaf redist-sub-type {
              type Redist-sub-type;
              description
                "Redistribute sub-type";
            }
          }
          container aaa {
            description
              "AAA configuration for this LMA";
            container accounting {
              description
                "AAA accounting for this LMA";
              leaf enable {
                type empty;
                description
                  "Set constant integer";
              }
              leaf interim-interval {
                type uint32 {
                  range "1..86400";
                }
                units "minute";
                description
                  "Interim acounting interval (in minutes)";
              }
            }
          }
          container dscp {
            description
              "DSCP for packets originating from this LMA";
            leaf value {
              type uint32 {
                range "1..63";
              }
              description
                "Specify the DSCP value";
            }
            leaf force {
              type empty;
              description
                "Set constant integer";
            }
          }
          container lmaipv4-addresses {
            description
              "Table of LMAIPv4Address";
            list lmaipv4-address {
              key "address";
              description
                "Configure IPv4 address for this LMA";
              leaf address {
                type inet:ipv4-address-no-zone;
                description
                  "LMA IPv4 address";
              }
            }
          }
          container roles {
            description
              "Table of Role";
            list role {
              key "lma-role";
              description
                "Role of this LMA";
              leaf lma-role {
                type Lma-role;
                description
                  "LMA role mode";
              }
            }
          }
          container binding-attributes {
            description
              "LMA binding attributes";
            leaf refresh-time {
              type uint32 {
                range "4..65000";
              }
              units "second";
              description
                "Specify in seconds, (multiples of 4)";
            }
            leaf delete-wait-interval {
              type uint32 {
                range "100..65535";
              }
              description
                "bce delete wait time interval";
            }
            leaf create-wait-interval {
              type uint32 {
                range "100..65535";
              }
              description
                "bce create wait time interval";
            }
            leaf max-life-time {
              type uint32 {
                range "10..65535";
              }
              units "second";
              description
                "Maximum bce lifetime permitted";
            }
            leaf maximum {
              type uint32 {
                range "1..128000";
              }
              description
                "Specify max. number of bindings";
            }
          }
          container mags {
            description
              "Table of MAG";
            list mag {
              key "mag-name domain-name";
              description
                "MAG within LMA";
              container authenticate-option {
                description
                  "Authentication option between PMIPV6
                   entities";
                leaf spi {
                  type xr:Hex-integer;
                  description
                    "SPI in hex value";
                }
                leaf key {
                  type string {
                    length "1..125";
                  }
                  description
                    "ASCII string";
                }
              }
              container dscp {
                description
                  "DSCP for packets originating from this MAG";
                leaf value {
                  type uint32 {
                    range "1..63";
                  }
                  description
                    "Specify the DSCP value";
                }
                leaf force {
                  type empty;
                  description
                    "Set constant integer";
                }
              }
              leaf encap-option {
                type Encap-opt;
                description
                  "Encapsulation option between PMIPV6 entities";
              }
              leaf ipv4-address {
                type inet:ipv4-address-no-zone;
                description
                  "Configure IPv4 address for this MAG";
              }
              leaf ipv6-address {
                type inet:ipv6-address-no-zone;
                description
                  "Configure IPv6 address for this MAG";
              }
              leaf tunnel {
                type xr:Interface-name;
                description
                  "static tunnel for this peer MAG";
              }
              leaf mag-name {
                type string {
                  length "1..125";
                }
                description
                  "MAG identifier";
              }
              leaf domain-name {
                type string {
                  length "1..125";
                }
                description
                  "Domain name";
              }
            }
          }
          container tunnel-attributes {
            description
              "tunnel attributes";
            leaf mtu {
              type uint32 {
                range "68..17916";
              }
              description
                "maximum transmission unit for tunnel";
            }
            leaf acl {
              type string {
                length "1..125";
              }
              description
                "access list to apply for tunnel";
            }
          }
          container services {
            description
              "Table of Service";
            list service {
              key "lma-service";
              description
                "Service of this LMA";
              container customers {
                description
                  "Table of Customer";
                list customer {
                  key "customer-name vrf-name";
                  description
                    "customer configuration on this mobile local
                     loop service";
                  container authenticate-option {
                    description
                      "Authentication option between PMIPV6
                       entities";
                    leaf spi {
                      type xr:Hex-integer;
                      description
                        "SPI in hex value";
                    }
                    leaf key {
                      type string {
                        length "1..125";
                      }
                      description
                        "ASCII string";
                    }
                  }
                  container heart-beat-attributes {
                    description
                      "heartbeat config for this Customer";
                    leaf interval {
                      type uint32 {
                        range "10..3600";
                      }
                      description
                        "Specify the interval value in second";
                    }
                    leaf retries {
                      type uint32 {
                        range "1..10";
                      }
                      description
                        "Specify the retry value";
                    }
                    leaf timeout {
                      type uint32 {
                        range "1..3600";
                      }
                      description
                        "Specify the timeout value";
                    }
                  }
                  container transports {
                    description
                      "Table of Transport";
                    list transport {
                      key "vrf-name";
                      description
                        "Customer transport attributes";
                      leaf ipv4-address {
                        type inet:ipv4-address-no-zone;
                        description
                          "Configure IPv4 address for this LMA";
                      }
                      leaf ipv6-address {
                        type inet:ipv6-address-no-zone;
                        description
                          "Configure IPv6 address for this LMA";
                      }
                      leaf vrf-name {
                        type string {
                          length "1..125";
                        }
                        description
                          "VRF Name";
                      }
                    }
                  }
                  container network-attributes {
                    description
                      "network parameters for the customer";
                    container authorizes {
                      description
                        "Table of Authorize";
                      list authorize {
                        key "name";
                        description
                          "not authorize the network prefixes";
                        container pool-attributes {
                          description
                            "Pool configs for this network";
                          container mobile-node {
                            description
                              "pool configs for the mobile nodes";
                            container ipv4-pool {
                              description
                                "None";
                              leaf start-address {
                                type inet:ipv4-address-no-zone;
                                description
                                  "Pool IPv4 start address";
                              }
                              leaf pool-prefix {
                                type uint32 {
                                  range "8..30";
                                }
                                description
                                  "IPv4 Pool Prefix value";
                              }
                            }
                            container ipv6-pool {
                              description
                                "None";
                              leaf start-address {
                                type inet:ipv6-address-no-zone;
                                description
                                  "Pool IPv6 start address";
                              }
                              leaf pool-prefix {
                                type uint32 {
                                  range "8..62";
                                }
                                description
                                  "IPv6 Pool Prefix value";
                              }
                            }
                          }
                          container mobile-network {
                            description
                              "pool configs for the mobile network";
                            container mripv6-pools {
                              description
                                "Table of MRIPV6Pool";
                              list mripv6-pool {
                                key "start-address";
                                description
                                  "ipv6 pool";
                                leaf start-address {
                                  type inet:ipv6-address-no-zone;
                                  description
                                    "Pool IPv6 start address";
                                }
                                leaf pool-prefix {
                                  type uint32 {
                                    range "8..64";
                                  }
                                  description
                                    "IPv6 Pool Prefix value";
                                }
                                leaf network-prefix {
                                  type uint32 {
                                    range "8..64";
                                  }
                                  description
                                    "IPv4 Network Prefix value";
                                }
                              }
                            }
                            container mripv4-pools {
                              description
                                "Table of MRIPV4Pool";
                              list mripv4-pool {
                                key "start-address";
                                description
                                  "ipv4 pool";
                                leaf start-address {
                                  type inet:ipv4-address-no-zone;
                                  description
                                    "Pool IPv4 start address";
                                }
                                leaf pool-prefix {
                                  type uint32 {
                                    range "8..30";
                                  }
                                  description
                                    "IPv4 Pool Prefix value";
                                }
                                leaf network-prefix {
                                  type uint32 {
                                    range "8..32";
                                  }
                                  description
                                    "IPv4 Network Prefix value";
                                }
                              }
                            }
                          }
                        }
                        leaf name {
                          type string {
                            length "1..125";
                          }
                          description
                            "ASCII string";
                        }
                      }
                    }
                    leaf unauthorize {
                      type empty;
                      description
                        "not authorize the network prefixes";
                    }
                  }
                  container gre-key {
                    description
                      "Customer specific GRE key";
                    leaf gre-key-type {
                      type Gre-key-type;
                      description
                        "GRE key type";
                    }
                    leaf gre-key-value {
                      type uint32 {
                        range "1..4294967295";
                      }
                      description
                        "GRE key value";
                    }
                  }
                  container binding-attributes {
                    description
                      "Customer specific binding attributes";
                    leaf max-life-time {
                      type uint32 {
                        range "10..65535";
                      }
                      units "second";
                      description
                        "Maximum bce lifetime permitted";
                    }
                  }
                  leaf mnp-customer {
                    type uint32 {
                      range "1..4000000";
                    }
                    description
                      "mnp limit config for customer";
                  }
                  leaf mnp-ipv4-lmn {
                    type uint32 {
                      range "1..32";
                    }
                    description
                      "mnp limit config for customer specific
                       logical mn";
                  }
                  leaf mnp-ipv6-lmn {
                    type uint32 {
                      range "1..32";
                    }
                    description
                      "mnp limit config for customer specific
                       logical mn";
                  }
                  leaf mnp-lmn {
                    type uint32 {
                      range "1..32";
                    }
                    description
                      "mnp limit config for customer specific
                       logical mn";
                  }
                  leaf mnp-ipv4-customer {
                    type uint32 {
                      range "1..4000000";
                    }
                    description
                      "mnp limit config for customer";
                  }
                  leaf mnp-ipv6-customer {
                    type uint32 {
                      range "1..4000000";
                    }
                    description
                      "mnp limit config for customer";
                  }
                  leaf mobile-route-ad {
                    type uint32 {
                      range "1..254";
                    }
                    description
                      "Specify the Admin Distance value";
                  }
                  leaf bandwidth-aggregate {
                    type uint32 {
                      range "1..4294967295";
                    }
                    units "kbit/s";
                    description
                      "Aggregate bandwidth across all logical MNs";
                  }
                  leaf customer-name {
                    type string {
                      length "1..32";
                    }
                    description
                      "Customer name";
                  }
                  leaf vrf-name {
                    type string {
                      length "1..32";
                    }
                    description
                      "VRF name";
                  }
                }
              }
              leaf mnp-customer {
                type uint32 {
                  range "1..4000000";
                }
                description
                  "mnp limit config for all customer's";
              }
              leaf mnp-ipv4-lmn {
                type uint32 {
                  range "1..32";
                }
                description
                  "mnp limit config for all logical mn's";
              }
              leaf mnp-ipv6-lmn {
                type uint32 {
                  range "1..32";
                }
                description
                  "mnp limit config for all logical mn's";
              }
              leaf mnp-lmn {
                type uint32 {
                  range "1..32";
                }
                description
                  "mnp limit config for all logical mn's";
              }
              leaf ignore-home-address {
                type empty;
                description
                  "Ignore HoA/HNP option";
              }
              leaf mnp-ipv4-customer {
                type uint32 {
                  range "1..4000000";
                }
                description
                  "mnp limit config for all customer's";
              }
              leaf mnp-ipv6-customer {
                type uint32 {
                  range "1..4000000";
                }
                description
                  "mnp limit config for all customer's";
              }
              leaf lma-service {
                type Lma-service;
                description
                  "LMA service mode";
              }
            }
          }
          container networks {
            description
              "Table of Network";
            list network {
              key "lma-network";
              description
                "network for this LMA";
              container pool-attributes {
                description
                  "Pool configs for this network";
                container mobile-node {
                  description
                    "pool configs for the mobile nodes";
                  container ipv4-pool {
                    description
                      "None";
                    leaf start-address {
                      type inet:ipv4-address-no-zone;
                      description
                        "Pool IPv4 start address";
                    }
                    leaf pool-prefix {
                      type uint32 {
                        range "8..30";
                      }
                      description
                        "IPv4 Pool Prefix value";
                    }
                  }
                  container ipv6-pool {
                    description
                      "None";
                    leaf start-address {
                      type inet:ipv6-address-no-zone;
                      description
                        "Pool IPv6 start address";
                    }
                    leaf pool-prefix {
                      type uint32 {
                        range "8..62";
                      }
                      description
                        "IPv6 Pool Prefix value";
                    }
                  }
                }
                container mobile-network {
                  description
                    "pool configs for the mobile network";
                  container mripv6-pools {
                    description
                      "Table of MRIPV6Pool";
                    list mripv6-pool {
                      key "start-address";
                      description
                        "ipv6 pool";
                      leaf start-address {
                        type inet:ipv6-address-no-zone;
                        description
                          "Pool IPv6 start address";
                      }
                      leaf pool-prefix {
                        type uint32 {
                          range "8..64";
                        }
                        description
                          "IPv6 Pool Prefix value";
                      }
                      leaf network-prefix {
                        type uint32 {
                          range "8..64";
                        }
                        description
                          "IPv4 Network Prefix value";
                      }
                    }
                  }
                  container mripv4-pools {
                    description
                      "Table of MRIPV4Pool";
                    list mripv4-pool {
                      key "start-address";
                      description
                        "ipv4 pool";
                      leaf start-address {
                        type inet:ipv4-address-no-zone;
                        description
                          "Pool IPv4 start address";
                      }
                      leaf pool-prefix {
                        type uint32 {
                          range "8..30";
                        }
                        description
                          "IPv4 Pool Prefix value";
                      }
                      leaf network-prefix {
                        type uint32 {
                          range "8..32";
                        }
                        description
                          "IPv4 Network Prefix value";
                      }
                    }
                  }
                }
              }
              leaf lma-network {
                type string {
                  length "1..125";
                }
                description
                  "Network name";
              }
            }
          }
          container replay-protection {
            description
              "Replay Protection Method";
            leaf timestamp-window {
              type uint32 {
                range "1..255";
              }
              units "second";
              description
                "Specify timestamp window value in seconds";
            }
          }
          leaf generate {
            type empty;
            description
              "generate gre key for LMA bindings";
          }
          leaf mobile-route-ad {
            type uint32 {
              range "1..254";
            }
            description
              "Specify the Admin Distance value";
          }
          leaf ani {
            type empty;
            description
              "enable ani option processing in LMA";
          }
          leaf multipath {
            type empty;
            description
              "enable multipath support for LMA";
          }
          leaf dynamic {
            type empty;
            description
              "enable dynamic mag learning for LMA";
          }
          leaf enforce {
            type empty;
            description
              "enforce heartbeat values to MAG";
          }
          leaf default-profile {
            type string {
              length "1..125";
            }
            description
              "Default MN profile for LMA";
          }
          leaf interface {
            type xr:Interface-name;
            description
              "CN facing interface name";
          }
          leaf mobile-map {
            type string {
              length "1..125";
            }
            description
              "Mobile Map for this LMA";
          }
          leaf pgw-subs-cont {
            type empty;
            description
              "Feature related to interface with PGW";
          }
          leaf lma-name {
            type string {
              length "1..125";
            }
            description
              "LMA name";
          }
          leaf domain-name {
            type string {
              length "1..125";
            }
            description
              "Domain name";
          }
        }
      }
    }
  }
  augment "/ncs:devices/ncs:device/ncs:live-status" {
    container mobile-ip {
      tailf:ncs-device-type "netconf";
      tailf:display-when "not(../../ncs:module) or ../../ncs:module[ncs:name='Cisco-IOS-XR-ip-mobileip-cfg'] or (../../ncs:live-status-protocol[not(ncs:capability)]) or (../../ncs:live-status-protocol/ncs:capability/ncs:module[.='Cisco-IOS-XR-ip-mobileip-cfg'])";
      description
        "MobileIP configuration";
      container domains {
        description
          "Table of Domain";
        list domain {
          key "domain-name";
          description
            "PMIPv6 domain configuration";
          container mags {
            description
              "Table of MAG";
            list mag {
              key "mag-name";
              description
                "MAG within domain";
              leaf mag-name {
                type xr:live_ncs_Cisco-ios-xr-string;
                description
                  "MAG Identifier";
              }
            }
          }
          container nais {
            description
              "Table of NAI";
            list nai {
              key "nai-name";
              description
                "Network access identifier or Realm";
              leaf lma {
                type string {
                  length "1..125";
                }
                description
                  "LMA for this MN";
              }
              leaf apn {
                type string {
                  length "1..125";
                }
                description
                  "Access point network for this MN";
              }
              leaf customer {
                type xr:live_ncs_Cisco-ios-xr-string;
                description
                  "Customer name for this MN";
              }
              leaf service {
                type live_ncs_Service-type;
                description
                  "Service type for this MN";
              }
              leaf network {
                type string {
                  length "1..125";
                }
                description
                  "Network name (Address pool) for this MN";
              }
              leaf nai-name {
                type string {
                  length "1..125";
                }
                description
                  "MN Identifier";
              }
            }
          }
          container authenticate-option {
            description
              "Authentication option between PMIPV6 entities";
            leaf spi {
              type xr:live_ncs_Hex-integer;
              description
                "SPI in hex value";
            }
            leaf key {
              type string {
                length "1..125";
              }
              description
                "ASCII string";
            }
          }
          container lmas {
            description
              "Table of LMA";
            list lma {
              key "lma-name";
              description
                "LMA within domain";
              leaf lma-name {
                type xr:live_ncs_Cisco-ios-xr-string;
                description
                  "LMA Identifier";
              }
            }
          }
          leaf enable {
            type empty;
            description
              "Enable PMIPv6 domain configuration. Deletion
               of this object also causes deletion of all
               associated objects under Domain.";
          }
          leaf domain-name {
            type xr:live_ncs_Cisco-ios-xr-string;
            description
              "Domain Name";
          }
        }
      }
      container lmas {
        description
          "Table of LMA";
        list lma {
          key "lma-name domain-name";
          description
            "PMIPv6 LMA configuration";
          container binding-revocation-attributes {
            description
              "LMA Binding Revocation Attributes";
            container delay {
              description
                "Time to wait before Retransmitting BRI
                 Message";
              leaf br-min {
                type uint32 {
                  range "500..65535";
                }
                description
                  "Specify in millisec";
              }
              leaf br-max {
                type uint32 {
                  range "500..65535";
                }
                description
                  "Specify in millisec";
              }
            }
            leaf retry {
              type uint32 {
                range "1..10";
              }
              description
                "Number of Retransmissons Allowed for BRI
                 Message";
            }
          }
          container rat-attributes {
            description
              "Radio access technology type config  this LMA";
            leaf lma-rat {
              type live_ncs_Lma-rat;
              description
                "LMA rat type";
            }
            leaf priority-value {
              type uint32 {
                range "1..255";
              }
              description
                "Specify the priority value";
            }
          }
          container heart-beat-attributes {
            description
              "heartbeat config for this LMA";
            leaf interval {
              type uint32 {
                range "10..3600";
              }
              description
                "Specify the interval value in second";
            }
            leaf retries {
              type uint32 {
                range "1..10";
              }
              description
                "Specify the retry value";
            }
            leaf timeout {
              type uint32 {
                range "1..3600";
              }
              description
                "Specify the timeout value";
            }
          }
          container lmaipv6-addresses {
            description
              "Table of LMAIPv6Address";
            list lmaipv6-address {
              key "address";
              description
                "Configure IPv6 address for this LMA";
              leaf address {
                type inet:ipv6-address-no-zone;
                description
                  "LMA IPv6 address";
              }
            }
          }
          container hnp {
            description
              "LMA HNP options";
            leaf maximum {
              type uint32 {
                range "1..3";
              }
              description
                "maximum HNPs allowed per MN interface";
            }
          }
          container redistribute {
            description
              "Redistribute routes";
            leaf redist-type {
              type live_ncs_Redist-type;
              description
                "Redistribute type";
            }
            leaf redist-sub-type {
              type live_ncs_Redist-sub-type;
              description
                "Redistribute sub-type";
            }
          }
          container aaa {
            description
              "AAA configuration for this LMA";
            container accounting {
              description
                "AAA accounting for this LMA";
              leaf enable {
                type empty;
                description
                  "Set constant integer";
              }
              leaf interim-interval {
                type uint32 {
                  range "1..86400";
                }
                units "minute";
                description
                  "Interim acounting interval (in minutes)";
              }
            }
          }
          container dscp {
            description
              "DSCP for packets originating from this LMA";
            leaf value {
              type uint32 {
                range "1..63";
              }
              description
                "Specify the DSCP value";
            }
            leaf force {
              type empty;
              description
                "Set constant integer";
            }
          }
          container lmaipv4-addresses {
            description
              "Table of LMAIPv4Address";
            list lmaipv4-address {
              key "address";
              description
                "Configure IPv4 address for this LMA";
              leaf address {
                type inet:ipv4-address-no-zone;
                description
                  "LMA IPv4 address";
              }
            }
          }
          container roles {
            description
              "Table of Role";
            list role {
              key "lma-role";
              description
                "Role of this LMA";
              leaf lma-role {
                type live_ncs_Lma-role;
                description
                  "LMA role mode";
              }
            }
          }
          container binding-attributes {
            description
              "LMA binding attributes";
            leaf refresh-time {
              type uint32 {
                range "4..65000";
              }
              units "second";
              description
                "Specify in seconds, (multiples of 4)";
            }
            leaf delete-wait-interval {
              type uint32 {
                range "100..65535";
              }
              description
                "bce delete wait time interval";
            }
            leaf create-wait-interval {
              type uint32 {
                range "100..65535";
              }
              description
                "bce create wait time interval";
            }
            leaf max-life-time {
              type uint32 {
                range "10..65535";
              }
              units "second";
              description
                "Maximum bce lifetime permitted";
            }
            leaf maximum {
              type uint32 {
                range "1..128000";
              }
              description
                "Specify max. number of bindings";
            }
          }
          container mags {
            description
              "Table of MAG";
            list mag {
              key "mag-name domain-name";
              description
                "MAG within LMA";
              container authenticate-option {
                description
                  "Authentication option between PMIPV6
                   entities";
                leaf spi {
                  type xr:live_ncs_Hex-integer;
                  description
                    "SPI in hex value";
                }
                leaf key {
                  type string {
                    length "1..125";
                  }
                  description
                    "ASCII string";
                }
              }
              container dscp {
                description
                  "DSCP for packets originating from this MAG";
                leaf value {
                  type uint32 {
                    range "1..63";
                  }
                  description
                    "Specify the DSCP value";
                }
                leaf force {
                  type empty;
                  description
                    "Set constant integer";
                }
              }
              leaf encap-option {
                type live_ncs_Encap-opt;
                description
                  "Encapsulation option between PMIPV6 entities";
              }
              leaf ipv4-address {
                type inet:ipv4-address-no-zone;
                description
                  "Configure IPv4 address for this MAG";
              }
              leaf ipv6-address {
                type inet:ipv6-address-no-zone;
                description
                  "Configure IPv6 address for this MAG";
              }
              leaf tunnel {
                type xr:live_ncs_Interface-name;
                description
                  "static tunnel for this peer MAG";
              }
              leaf mag-name {
                type string {
                  length "1..125";
                }
                description
                  "MAG identifier";
              }
              leaf domain-name {
                type string {
                  length "1..125";
                }
                description
                  "Domain name";
              }
            }
          }
          container tunnel-attributes {
            description
              "tunnel attributes";
            leaf mtu {
              type uint32 {
                range "68..17916";
              }
              description
                "maximum transmission unit for tunnel";
            }
            leaf acl {
              type string {
                length "1..125";
              }
              description
                "access list to apply for tunnel";
            }
          }
          container services {
            description
              "Table of Service";
            list service {
              key "lma-service";
              description
                "Service of this LMA";
              container customers {
                description
                  "Table of Customer";
                list customer {
                  key "customer-name vrf-name";
                  description
                    "customer configuration on this mobile local
                     loop service";
                  container authenticate-option {
                    description
                      "Authentication option between PMIPV6
                       entities";
                    leaf spi {
                      type xr:live_ncs_Hex-integer;
                      description
                        "SPI in hex value";
                    }
                    leaf key {
                      type string {
                        length "1..125";
                      }
                      description
                        "ASCII string";
                    }
                  }
                  container heart-beat-attributes {
                    description
                      "heartbeat config for this Customer";
                    leaf interval {
                      type uint32 {
                        range "10..3600";
                      }
                      description
                        "Specify the interval value in second";
                    }
                    leaf retries {
                      type uint32 {
                        range "1..10";
                      }
                      description
                        "Specify the retry value";
                    }
                    leaf timeout {
                      type uint32 {
                        range "1..3600";
                      }
                      description
                        "Specify the timeout value";
                    }
                  }
                  container transports {
                    description
                      "Table of Transport";
                    list transport {
                      key "vrf-name";
                      description
                        "Customer transport attributes";
                      leaf ipv4-address {
                        type inet:ipv4-address-no-zone;
                        description
                          "Configure IPv4 address for this LMA";
                      }
                      leaf ipv6-address {
                        type inet:ipv6-address-no-zone;
                        description
                          "Configure IPv6 address for this LMA";
                      }
                      leaf vrf-name {
                        type string {
                          length "1..125";
                        }
                        description
                          "VRF Name";
                      }
                    }
                  }
                  container network-attributes {
                    description
                      "network parameters for the customer";
                    container authorizes {
                      description
                        "Table of Authorize";
                      list authorize {
                        key "name";
                        description
                          "not authorize the network prefixes";
                        container pool-attributes {
                          description
                            "Pool configs for this network";
                          container mobile-node {
                            description
                              "pool configs for the mobile nodes";
                            container ipv4-pool {
                              description
                                "None";
                              leaf start-address {
                                type inet:ipv4-address-no-zone;
                                description
                                  "Pool IPv4 start address";
                              }
                              leaf pool-prefix {
                                type uint32 {
                                  range "8..30";
                                }
                                description
                                  "IPv4 Pool Prefix value";
                              }
                            }
                            container ipv6-pool {
                              description
                                "None";
                              leaf start-address {
                                type inet:ipv6-address-no-zone;
                                description
                                  "Pool IPv6 start address";
                              }
                              leaf pool-prefix {
                                type uint32 {
                                  range "8..62";
                                }
                                description
                                  "IPv6 Pool Prefix value";
                              }
                            }
                          }
                          container mobile-network {
                            description
                              "pool configs for the mobile network";
                            container mripv6-pools {
                              description
                                "Table of MRIPV6Pool";
                              list mripv6-pool {
                                key "start-address";
                                description
                                  "ipv6 pool";
                                leaf start-address {
                                  type inet:ipv6-address-no-zone;
                                  description
                                    "Pool IPv6 start address";
                                }
                                leaf pool-prefix {
                                  type uint32 {
                                    range "8..64";
                                  }
                                  description
                                    "IPv6 Pool Prefix value";
                                }
                                leaf network-prefix {
                                  type uint32 {
                                    range "8..64";
                                  }
                                  description
                                    "IPv4 Network Prefix value";
                                }
                              }
                            }
                            container mripv4-pools {
                              description
                                "Table of MRIPV4Pool";
                              list mripv4-pool {
                                key "start-address";
                                description
                                  "ipv4 pool";
                                leaf start-address {
                                  type inet:ipv4-address-no-zone;
                                  description
                                    "Pool IPv4 start address";
                                }
                                leaf pool-prefix {
                                  type uint32 {
                                    range "8..30";
                                  }
                                  description
                                    "IPv4 Pool Prefix value";
                                }
                                leaf network-prefix {
                                  type uint32 {
                                    range "8..32";
                                  }
                                  description
                                    "IPv4 Network Prefix value";
                                }
                              }
                            }
                          }
                        }
                        leaf name {
                          type string {
                            length "1..125";
                          }
                          description
                            "ASCII string";
                        }
                      }
                    }
                    leaf unauthorize {
                      type empty;
                      description
                        "not authorize the network prefixes";
                    }
                  }
                  container gre-key {
                    description
                      "Customer specific GRE key";
                    leaf gre-key-type {
                      type live_ncs_Gre-key-type;
                      description
                        "GRE key type";
                    }
                    leaf gre-key-value {
                      type uint32 {
                        range "1..4294967295";
                      }
                      description
                        "GRE key value";
                    }
                  }
                  container binding-attributes {
                    description
                      "Customer specific binding attributes";
                    leaf max-life-time {
                      type uint32 {
                        range "10..65535";
                      }
                      units "second";
                      description
                        "Maximum bce lifetime permitted";
                    }
                  }
                  leaf mnp-customer {
                    type uint32 {
                      range "1..4000000";
                    }
                    description
                      "mnp limit config for customer";
                  }
                  leaf mnp-ipv4-lmn {
                    type uint32 {
                      range "1..32";
                    }
                    description
                      "mnp limit config for customer specific
                       logical mn";
                  }
                  leaf mnp-ipv6-lmn {
                    type uint32 {
                      range "1..32";
                    }
                    description
                      "mnp limit config for customer specific
                       logical mn";
                  }
                  leaf mnp-lmn {
                    type uint32 {
                      range "1..32";
                    }
                    description
                      "mnp limit config for customer specific
                       logical mn";
                  }
                  leaf mnp-ipv4-customer {
                    type uint32 {
                      range "1..4000000";
                    }
                    description
                      "mnp limit config for customer";
                  }
                  leaf mnp-ipv6-customer {
                    type uint32 {
                      range "1..4000000";
                    }
                    description
                      "mnp limit config for customer";
                  }
                  leaf mobile-route-ad {
                    type uint32 {
                      range "1..254";
                    }
                    description
                      "Specify the Admin Distance value";
                  }
                  leaf bandwidth-aggregate {
                    type uint32 {
                      range "1..4294967295";
                    }
                    units "kbit/s";
                    description
                      "Aggregate bandwidth across all logical MNs";
                  }
                  leaf customer-name {
                    type string {
                      length "1..32";
                    }
                    description
                      "Customer name";
                  }
                  leaf vrf-name {
                    type string {
                      length "1..32";
                    }
                    description
                      "VRF name";
                  }
                }
              }
              leaf mnp-customer {
                type uint32 {
                  range "1..4000000";
                }
                description
                  "mnp limit config for all customer's";
              }
              leaf mnp-ipv4-lmn {
                type uint32 {
                  range "1..32";
                }
                description
                  "mnp limit config for all logical mn's";
              }
              leaf mnp-ipv6-lmn {
                type uint32 {
                  range "1..32";
                }
                description
                  "mnp limit config for all logical mn's";
              }
              leaf mnp-lmn {
                type uint32 {
                  range "1..32";
                }
                description
                  "mnp limit config for all logical mn's";
              }
              leaf ignore-home-address {
                type empty;
                description
                  "Ignore HoA/HNP option";
              }
              leaf mnp-ipv4-customer {
                type uint32 {
                  range "1..4000000";
                }
                description
                  "mnp limit config for all customer's";
              }
              leaf mnp-ipv6-customer {
                type uint32 {
                  range "1..4000000";
                }
                description
                  "mnp limit config for all customer's";
              }
              leaf lma-service {
                type live_ncs_Lma-service;
                description
                  "LMA service mode";
              }
            }
          }
          container networks {
            description
              "Table of Network";
            list network {
              key "lma-network";
              description
                "network for this LMA";
              container pool-attributes {
                description
                  "Pool configs for this network";
                container mobile-node {
                  description
                    "pool configs for the mobile nodes";
                  container ipv4-pool {
                    description
                      "None";
                    leaf start-address {
                      type inet:ipv4-address-no-zone;
                      description
                        "Pool IPv4 start address";
                    }
                    leaf pool-prefix {
                      type uint32 {
                        range "8..30";
                      }
                      description
                        "IPv4 Pool Prefix value";
                    }
                  }
                  container ipv6-pool {
                    description
                      "None";
                    leaf start-address {
                      type inet:ipv6-address-no-zone;
                      description
                        "Pool IPv6 start address";
                    }
                    leaf pool-prefix {
                      type uint32 {
                        range "8..62";
                      }
                      description
                        "IPv6 Pool Prefix value";
                    }
                  }
                }
                container mobile-network {
                  description
                    "pool configs for the mobile network";
                  container mripv6-pools {
                    description
                      "Table of MRIPV6Pool";
                    list mripv6-pool {
                      key "start-address";
                      description
                        "ipv6 pool";
                      leaf start-address {
                        type inet:ipv6-address-no-zone;
                        description
                          "Pool IPv6 start address";
                      }
                      leaf pool-prefix {
                        type uint32 {
                          range "8..64";
                        }
                        description
                          "IPv6 Pool Prefix value";
                      }
                      leaf network-prefix {
                        type uint32 {
                          range "8..64";
                        }
                        description
                          "IPv4 Network Prefix value";
                      }
                    }
                  }
                  container mripv4-pools {
                    description
                      "Table of MRIPV4Pool";
                    list mripv4-pool {
                      key "start-address";
                      description
                        "ipv4 pool";
                      leaf start-address {
                        type inet:ipv4-address-no-zone;
                        description
                          "Pool IPv4 start address";
                      }
                      leaf pool-prefix {
                        type uint32 {
                          range "8..30";
                        }
                        description
                          "IPv4 Pool Prefix value";
                      }
                      leaf network-prefix {
                        type uint32 {
                          range "8..32";
                        }
                        description
                          "IPv4 Network Prefix value";
                      }
                    }
                  }
                }
              }
              leaf lma-network {
                type string {
                  length "1..125";
                }
                description
                  "Network name";
              }
            }
          }
          container replay-protection {
            description
              "Replay Protection Method";
            leaf timestamp-window {
              type uint32 {
                range "1..255";
              }
              units "second";
              description
                "Specify timestamp window value in seconds";
            }
          }
          leaf generate {
            type empty;
            description
              "generate gre key for LMA bindings";
          }
          leaf mobile-route-ad {
            type uint32 {
              range "1..254";
            }
            description
              "Specify the Admin Distance value";
          }
          leaf ani {
            type empty;
            description
              "enable ani option processing in LMA";
          }
          leaf multipath {
            type empty;
            description
              "enable multipath support for LMA";
          }
          leaf dynamic {
            type empty;
            description
              "enable dynamic mag learning for LMA";
          }
          leaf enforce {
            type empty;
            description
              "enforce heartbeat values to MAG";
          }
          leaf default-profile {
            type string {
              length "1..125";
            }
            description
              "Default MN profile for LMA";
          }
          leaf interface {
            type xr:live_ncs_Interface-name;
            description
              "CN facing interface name";
          }
          leaf mobile-map {
            type string {
              length "1..125";
            }
            description
              "Mobile Map for this LMA";
          }
          leaf pgw-subs-cont {
            type empty;
            description
              "Feature related to interface with PGW";
          }
          leaf lma-name {
            type string {
              length "1..125";
            }
            description
              "LMA name";
          }
          leaf domain-name {
            type string {
              length "1..125";
            }
            description
              "Domain name";
          }
        }
      }
    }
  }
  augment "/ncs:devices/ncs:template/ncs:ned-id/ncs:config" {
    container mobile-ip {
      description
        "MobileIP configuration";
      container domains {
        description
          "Table of Domain";
        list domain {
          // NCS patched for predictable order
          ordered-by user;
          key "domain-name";
          description
            "PMIPv6 domain configuration";
          container mags {
            description
              "Table of MAG";
            list mag {
              // NCS patched for predictable order
              ordered-by user;
              key "mag-name";
              description
                "MAG within domain";
              leaf mag-name {
                type xr:ncs_template_Cisco-ios-xr-string;
                description
                  "MAG Identifier";
              }
            }
          }
          container nais {
            description
              "Table of NAI";
            list nai {
              // NCS patched for predictable order
              ordered-by user;
              key "nai-name";
              description
                "Network access identifier or Realm";
              leaf lma {
                type string;
                description
                  "LMA for this MN";
              }
              leaf apn {
                type string;
                description
                  "Access point network for this MN";
              }
              leaf customer {
                type xr:ncs_template_Cisco-ios-xr-string;
                description
                  "Customer name for this MN";
              }
              leaf service {
                type ncs_template_Service-type;
                description
                  "Service type for this MN";
              }
              leaf network {
                type string;
                description
                  "Network name (Address pool) for this MN";
              }
              leaf nai-name {
                type string;
                description
                  "MN Identifier";
              }
            }
          }
          container authenticate-option {
            description
              "Authentication option between PMIPV6 entities";
            leaf spi {
              type xr:ncs_template_Hex-integer;
              description
                "SPI in hex value";
            }
            leaf key {
              type string;
              description
                "ASCII string";
            }
          }
          container lmas {
            description
              "Table of LMA";
            list lma {
              // NCS patched for predictable order
              ordered-by user;
              key "lma-name";
              description
                "LMA within domain";
              leaf lma-name {
                type xr:ncs_template_Cisco-ios-xr-string;
                description
                  "LMA Identifier";
              }
            }
          }
          leaf enable {
            type empty;
            description
              "Enable PMIPv6 domain configuration. Deletion
               of this object also causes deletion of all
               associated objects under Domain.";
          }
          leaf domain-name {
            type xr:ncs_template_Cisco-ios-xr-string;
            description
              "Domain Name";
          }
        }
      }
      container lmas {
        description
          "Table of LMA";
        list lma {
          // NCS patched for predictable order
          ordered-by user;
          key "lma-name domain-name";
          description
            "PMIPv6 LMA configuration";
          container binding-revocation-attributes {
            description
              "LMA Binding Revocation Attributes";
            container delay {
              description
                "Time to wait before Retransmitting BRI
                 Message";
              leaf br-min {
                type string;
                description
                  "Specify in millisec";
              }
              leaf br-max {
                type string;
                description
                  "Specify in millisec";
              }
            }
            leaf retry {
              type string;
              description
                "Number of Retransmissons Allowed for BRI
                 Message";
            }
          }
          container rat-attributes {
            description
              "Radio access technology type config  this LMA";
            leaf lma-rat {
              type ncs_template_Lma-rat;
              description
                "LMA rat type";
            }
            leaf priority-value {
              type string;
              description
                "Specify the priority value";
            }
          }
          container heart-beat-attributes {
            description
              "heartbeat config for this LMA";
            leaf interval {
              type string;
              description
                "Specify the interval value in second";
            }
            leaf retries {
              type string;
              description
                "Specify the retry value";
            }
            leaf timeout {
              type string;
              description
                "Specify the timeout value";
            }
          }
          container lmaipv6-addresses {
            description
              "Table of LMAIPv6Address";
            list lmaipv6-address {
              // NCS patched for predictable order
              ordered-by user;
              key "address";
              description
                "Configure IPv6 address for this LMA";
              leaf address {
                type string;
                description
                  "LMA IPv6 address";
              }
            }
          }
          container hnp {
            description
              "LMA HNP options";
            leaf maximum {
              type string;
              description
                "maximum HNPs allowed per MN interface";
            }
          }
          container redistribute {
            description
              "Redistribute routes";
            leaf redist-type {
              type ncs_template_Redist-type;
              description
                "Redistribute type";
            }
            leaf redist-sub-type {
              type ncs_template_Redist-sub-type;
              description
                "Redistribute sub-type";
            }
          }
          container aaa {
            description
              "AAA configuration for this LMA";
            container accounting {
              description
                "AAA accounting for this LMA";
              leaf enable {
                type empty;
                description
                  "Set constant integer";
              }
              leaf interim-interval {
                type string;
                units "minute";
                description
                  "Interim acounting interval (in minutes)";
              }
            }
          }
          container dscp {
            description
              "DSCP for packets originating from this LMA";
            leaf value {
              type string;
              description
                "Specify the DSCP value";
            }
            leaf force {
              type empty;
              description
                "Set constant integer";
            }
          }
          container lmaipv4-addresses {
            description
              "Table of LMAIPv4Address";
            list lmaipv4-address {
              // NCS patched for predictable order
              ordered-by user;
              key "address";
              description
                "Configure IPv4 address for this LMA";
              leaf address {
                type string;
                description
                  "LMA IPv4 address";
              }
            }
          }
          container roles {
            description
              "Table of Role";
            list role {
              // NCS patched for predictable order
              ordered-by user;
              key "lma-role";
              description
                "Role of this LMA";
              leaf lma-role {
                type ncs_template_Lma-role;
                description
                  "LMA role mode";
              }
            }
          }
          container binding-attributes {
            description
              "LMA binding attributes";
            leaf refresh-time {
              type string;
              units "second";
              description
                "Specify in seconds, (multiples of 4)";
            }
            leaf delete-wait-interval {
              type string;
              description
                "bce delete wait time interval";
            }
            leaf create-wait-interval {
              type string;
              description
                "bce create wait time interval";
            }
            leaf max-life-time {
              type string;
              units "second";
              description
                "Maximum bce lifetime permitted";
            }
            leaf maximum {
              type string;
              description
                "Specify max. number of bindings";
            }
          }
          container mags {
            description
              "Table of MAG";
            list mag {
              // NCS patched for predictable order
              ordered-by user;
              key "mag-name domain-name";
              description
                "MAG within LMA";
              container authenticate-option {
                description
                  "Authentication option between PMIPV6
                   entities";
                leaf spi {
                  type xr:ncs_template_Hex-integer;
                  description
                    "SPI in hex value";
                }
                leaf key {
                  type string;
                  description
                    "ASCII string";
                }
              }
              container dscp {
                description
                  "DSCP for packets originating from this MAG";
                leaf value {
                  type string;
                  description
                    "Specify the DSCP value";
                }
                leaf force {
                  type empty;
                  description
                    "Set constant integer";
                }
              }
              leaf encap-option {
                type ncs_template_Encap-opt;
                description
                  "Encapsulation option between PMIPV6 entities";
              }
              leaf ipv4-address {
                type string;
                description
                  "Configure IPv4 address for this MAG";
              }
              leaf ipv6-address {
                type string;
                description
                  "Configure IPv6 address for this MAG";
              }
              leaf tunnel {
                type xr:ncs_template_Interface-name;
                description
                  "static tunnel for this peer MAG";
              }
              leaf mag-name {
                type string;
                description
                  "MAG identifier";
              }
              leaf domain-name {
                type string;
                description
                  "Domain name";
              }
            }
          }
          container tunnel-attributes {
            description
              "tunnel attributes";
            leaf mtu {
              type string;
              description
                "maximum transmission unit for tunnel";
            }
            leaf acl {
              type string;
              description
                "access list to apply for tunnel";
            }
          }
          container services {
            description
              "Table of Service";
            list service {
              // NCS patched for predictable order
              ordered-by user;
              key "lma-service";
              description
                "Service of this LMA";
              container customers {
                description
                  "Table of Customer";
                list customer {
                  // NCS patched for predictable order
                  ordered-by user;
                  key "customer-name vrf-name";
                  description
                    "customer configuration on this mobile local
                     loop service";
                  container authenticate-option {
                    description
                      "Authentication option between PMIPV6
                       entities";
                    leaf spi {
                      type xr:ncs_template_Hex-integer;
                      description
                        "SPI in hex value";
                    }
                    leaf key {
                      type string;
                      description
                        "ASCII string";
                    }
                  }
                  container heart-beat-attributes {
                    description
                      "heartbeat config for this Customer";
                    leaf interval {
                      type string;
                      description
                        "Specify the interval value in second";
                    }
                    leaf retries {
                      type string;
                      description
                        "Specify the retry value";
                    }
                    leaf timeout {
                      type string;
                      description
                        "Specify the timeout value";
                    }
                  }
                  container transports {
                    description
                      "Table of Transport";
                    list transport {
                      // NCS patched for predictable order
                      ordered-by user;
                      key "vrf-name";
                      description
                        "Customer transport attributes";
                      leaf ipv4-address {
                        type string;
                        description
                          "Configure IPv4 address for this LMA";
                      }
                      leaf ipv6-address {
                        type string;
                        description
                          "Configure IPv6 address for this LMA";
                      }
                      leaf vrf-name {
                        type string;
                        description
                          "VRF Name";
                      }
                    }
                  }
                  container network-attributes {
                    description
                      "network parameters for the customer";
                    container authorizes {
                      description
                        "Table of Authorize";
                      list authorize {
                        // NCS patched for predictable order
                        ordered-by user;
                        key "name";
                        description
                          "not authorize the network prefixes";
                        container pool-attributes {
                          description
                            "Pool configs for this network";
                          container mobile-node {
                            description
                              "pool configs for the mobile nodes";
                            container ipv4-pool {
                              description
                                "None";
                              leaf start-address {
                                type string;
                                description
                                  "Pool IPv4 start address";
                              }
                              leaf pool-prefix {
                                type string;
                                description
                                  "IPv4 Pool Prefix value";
                              }
                            }
                            container ipv6-pool {
                              description
                                "None";
                              leaf start-address {
                                type string;
                                description
                                  "Pool IPv6 start address";
                              }
                              leaf pool-prefix {
                                type string;
                                description
                                  "IPv6 Pool Prefix value";
                              }
                            }
                          }
                          container mobile-network {
                            description
                              "pool configs for the mobile network";
                            container mripv6-pools {
                              description
                                "Table of MRIPV6Pool";
                              list mripv6-pool {
                                // NCS patched for predictable order
                                ordered-by user;
                                key "start-address";
                                description
                                  "ipv6 pool";
                                leaf start-address {
                                  type string;
                                  description
                                    "Pool IPv6 start address";
                                }
                                leaf pool-prefix {
                                  type string;
                                  description
                                    "IPv6 Pool Prefix value";
                                }
                                leaf network-prefix {
                                  type string;
                                  description
                                    "IPv4 Network Prefix value";
                                }
                              }
                            }
                            container mripv4-pools {
                              description
                                "Table of MRIPV4Pool";
                              list mripv4-pool {
                                // NCS patched for predictable order
                                ordered-by user;
                                key "start-address";
                                description
                                  "ipv4 pool";
                                leaf start-address {
                                  type string;
                                  description
                                    "Pool IPv4 start address";
                                }
                                leaf pool-prefix {
                                  type string;
                                  description
                                    "IPv4 Pool Prefix value";
                                }
                                leaf network-prefix {
                                  type string;
                                  description
                                    "IPv4 Network Prefix value";
                                }
                              }
                            }
                          }
                        }
                        leaf name {
                          type string;
                          description
                            "ASCII string";
                        }
                      }
                    }
                    leaf unauthorize {
                      type empty;
                      description
                        "not authorize the network prefixes";
                    }
                  }
                  container gre-key {
                    description
                      "Customer specific GRE key";
                    leaf gre-key-type {
                      type ncs_template_Gre-key-type;
                      description
                        "GRE key type";
                    }
                    leaf gre-key-value {
                      type string;
                      description
                        "GRE key value";
                    }
                  }
                  container binding-attributes {
                    description
                      "Customer specific binding attributes";
                    leaf max-life-time {
                      type string;
                      units "second";
                      description
                        "Maximum bce lifetime permitted";
                    }
                  }
                  leaf mnp-customer {
                    type string;
                    description
                      "mnp limit config for customer";
                  }
                  leaf mnp-ipv4-lmn {
                    type string;
                    description
                      "mnp limit config for customer specific
                       logical mn";
                  }
                  leaf mnp-ipv6-lmn {
                    type string;
                    description
                      "mnp limit config for customer specific
                       logical mn";
                  }
                  leaf mnp-lmn {
                    type string;
                    description
                      "mnp limit config for customer specific
                       logical mn";
                  }
                  leaf mnp-ipv4-customer {
                    type string;
                    description
                      "mnp limit config for customer";
                  }
                  leaf mnp-ipv6-customer {
                    type string;
                    description
                      "mnp limit config for customer";
                  }
                  leaf mobile-route-ad {
                    type string;
                    description
                      "Specify the Admin Distance value";
                  }
                  leaf bandwidth-aggregate {
                    type string;
                    units "kbit/s";
                    description
                      "Aggregate bandwidth across all logical MNs";
                  }
                  leaf customer-name {
                    type string;
                    description
                      "Customer name";
                  }
                  leaf vrf-name {
                    type string;
                    description
                      "VRF name";
                  }
                }
              }
              leaf mnp-customer {
                type string;
                description
                  "mnp limit config for all customer's";
              }
              leaf mnp-ipv4-lmn {
                type string;
                description
                  "mnp limit config for all logical mn's";
              }
              leaf mnp-ipv6-lmn {
                type string;
                description
                  "mnp limit config for all logical mn's";
              }
              leaf mnp-lmn {
                type string;
                description
                  "mnp limit config for all logical mn's";
              }
              leaf ignore-home-address {
                type empty;
                description
                  "Ignore HoA/HNP option";
              }
              leaf mnp-ipv4-customer {
                type string;
                description
                  "mnp limit config for all customer's";
              }
              leaf mnp-ipv6-customer {
                type string;
                description
                  "mnp limit config for all customer's";
              }
              leaf lma-service {
                type ncs_template_Lma-service;
                description
                  "LMA service mode";
              }
            }
          }
          container networks {
            description
              "Table of Network";
            list network {
              // NCS patched for predictable order
              ordered-by user;
              key "lma-network";
              description
                "network for this LMA";
              container pool-attributes {
                description
                  "Pool configs for this network";
                container mobile-node {
                  description
                    "pool configs for the mobile nodes";
                  container ipv4-pool {
                    description
                      "None";
                    leaf start-address {
                      type string;
                      description
                        "Pool IPv4 start address";
                    }
                    leaf pool-prefix {
                      type string;
                      description
                        "IPv4 Pool Prefix value";
                    }
                  }
                  container ipv6-pool {
                    description
                      "None";
                    leaf start-address {
                      type string;
                      description
                        "Pool IPv6 start address";
                    }
                    leaf pool-prefix {
                      type string;
                      description
                        "IPv6 Pool Prefix value";
                    }
                  }
                }
                container mobile-network {
                  description
                    "pool configs for the mobile network";
                  container mripv6-pools {
                    description
                      "Table of MRIPV6Pool";
                    list mripv6-pool {
                      // NCS patched for predictable order
                      ordered-by user;
                      key "start-address";
                      description
                        "ipv6 pool";
                      leaf start-address {
                        type string;
                        description
                          "Pool IPv6 start address";
                      }
                      leaf pool-prefix {
                        type string;
                        description
                          "IPv6 Pool Prefix value";
                      }
                      leaf network-prefix {
                        type string;
                        description
                          "IPv4 Network Prefix value";
                      }
                    }
                  }
                  container mripv4-pools {
                    description
                      "Table of MRIPV4Pool";
                    list mripv4-pool {
                      // NCS patched for predictable order
                      ordered-by user;
                      key "start-address";
                      description
                        "ipv4 pool";
                      leaf start-address {
                        type string;
                        description
                          "Pool IPv4 start address";
                      }
                      leaf pool-prefix {
                        type string;
                        description
                          "IPv4 Pool Prefix value";
                      }
                      leaf network-prefix {
                        type string;
                        description
                          "IPv4 Network Prefix value";
                      }
                    }
                  }
                }
              }
              leaf lma-network {
                type string;
                description
                  "Network name";
              }
            }
          }
          container replay-protection {
            description
              "Replay Protection Method";
            leaf timestamp-window {
              type string;
              units "second";
              description
                "Specify timestamp window value in seconds";
            }
          }
          leaf generate {
            type empty;
            description
              "generate gre key for LMA bindings";
          }
          leaf mobile-route-ad {
            type string;
            description
              "Specify the Admin Distance value";
          }
          leaf ani {
            type empty;
            description
              "enable ani option processing in LMA";
          }
          leaf multipath {
            type empty;
            description
              "enable multipath support for LMA";
          }
          leaf dynamic {
            type empty;
            description
              "enable dynamic mag learning for LMA";
          }
          leaf enforce {
            type empty;
            description
              "enforce heartbeat values to MAG";
          }
          leaf default-profile {
            type string;
            description
              "Default MN profile for LMA";
          }
          leaf interface {
            type xr:ncs_template_Interface-name;
            description
              "CN facing interface name";
          }
          leaf mobile-map {
            type string;
            description
              "Mobile Map for this LMA";
          }
          leaf pgw-subs-cont {
            type empty;
            description
              "Feature related to interface with PGW";
          }
          leaf lma-name {
            type string;
            description
              "LMA name";
          }
          leaf domain-name {
            type string;
            description
              "Domain name";
          }
        }
      }
    }
  }
}

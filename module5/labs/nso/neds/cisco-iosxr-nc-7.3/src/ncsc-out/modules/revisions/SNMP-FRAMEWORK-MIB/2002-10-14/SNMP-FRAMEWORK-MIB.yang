module SNMP-FRAMEWORK-MIB {
  // Generated by yanger -t ncs
  tailf:mount-id "cisco-iosxr-nc-7.3:cisco-iosxr-nc-7.3";
  tailf:ncs-device-type "netconf";

  namespace "http://tail-f.com/ns/mibs/SNMP-FRAMEWORK-MIB/200210140000Z";
  prefix SNMP_FRAMEWORK_MIB;

  import tailf-common {
    prefix tailf;
  }
  import tailf-ncs {
    prefix ncs;
  }

  revision 2002-10-14 {
    description
      "";
  }

  typedef ncs_template_SnmpEngineID {
    type string;
  }

  typedef ncs_template_SnmpSecurityModel {
    type string;
  }

  typedef ncs_template_SnmpMessageProcessingModel {
    type string;
  }

  typedef ncs_template_SnmpSecurityLevel {
    type string;
  }

  typedef ncs_template_SnmpAdminString {
    type string;
  }

  typedef ncs_template_snmpEngineBootsType {
    type string;
  }

  typedef ncs_template_snmpEngineTimeType {
    type string;
  }

  typedef ncs_template_snmpEngineMaxMessageSizeType {
    type string;
  }

  typedef ncs_rpc_notif_SnmpEngineID {
    type tailf:hex-list {
      pattern '(((([0-9A-Fa-f]{2}):){4,31})([0-9A-Fa-f]{2}))';
      tailf:value-length "5 .. 32";
    }
  }

  typedef ncs_rpc_notif_SnmpSecurityModel {
    type int32 {
      range "0 .. 2147483647";
    }
  }

  typedef ncs_rpc_notif_SnmpMessageProcessingModel {
    type int32 {
      range "0 .. 2147483647";
    }
  }

  typedef ncs_rpc_notif_SnmpSecurityLevel {
    type enumeration {
      enum "noAuthNoPriv" {
        value 1;
      }
      enum "authNoPriv" {
        value 2;
      }
      enum "authPriv" {
        value 3;
      }
    }
  }

  typedef ncs_rpc_notif_SnmpAdminString {
    type string {
      length "min .. 255";
    }
  }

  typedef ncs_rpc_notif_snmpEngineBootsType {
    type int32 {
      range "1 .. 2147483647";
    }
  }

  typedef ncs_rpc_notif_snmpEngineTimeType {
    type int32 {
      range "0 .. 2147483647";
    }
  }

  typedef ncs_rpc_notif_snmpEngineMaxMessageSizeType {
    type int32 {
      range "484 .. 2147483647";
    }
  }

  typedef live_ncs_SnmpEngineID {
    type tailf:hex-list {
      pattern '(((([0-9A-Fa-f]{2}):){4,31})([0-9A-Fa-f]{2}))';
      tailf:value-length "5 .. 32";
    }
  }

  typedef live_ncs_SnmpSecurityModel {
    type int32 {
      range "0 .. 2147483647";
    }
  }

  typedef live_ncs_SnmpMessageProcessingModel {
    type int32 {
      range "0 .. 2147483647";
    }
  }

  typedef live_ncs_SnmpSecurityLevel {
    type enumeration {
      enum "noAuthNoPriv" {
        value 1;
      }
      enum "authNoPriv" {
        value 2;
      }
      enum "authPriv" {
        value 3;
      }
    }
  }

  typedef live_ncs_SnmpAdminString {
    type string {
      length "min .. 255";
    }
  }

  typedef live_ncs_snmpEngineBootsType {
    type int32 {
      range "1 .. 2147483647";
    }
  }

  typedef live_ncs_snmpEngineTimeType {
    type int32 {
      range "0 .. 2147483647";
    }
  }

  typedef live_ncs_snmpEngineMaxMessageSizeType {
    type int32 {
      range "484 .. 2147483647";
    }
  }

  typedef SnmpEngineID {
    type tailf:hex-list {
      pattern '(((([0-9A-Fa-f]{2}):){4,31})([0-9A-Fa-f]{2}))';
      tailf:value-length "5 .. 32";
    }
  }

  typedef SnmpSecurityModel {
    type int32 {
      range "0 .. 2147483647";
    }
  }

  typedef SnmpMessageProcessingModel {
    type int32 {
      range "0 .. 2147483647";
    }
  }

  typedef SnmpSecurityLevel {
    type enumeration {
      enum "noAuthNoPriv" {
        value 1;
      }
      enum "authNoPriv" {
        value 2;
      }
      enum "authPriv" {
        value 3;
      }
    }
  }

  typedef SnmpAdminString {
    type string {
      length "min .. 255";
    }
  }

  typedef snmpEngineBootsType {
    type int32 {
      range "1 .. 2147483647";
    }
  }

  typedef snmpEngineTimeType {
    type int32 {
      range "0 .. 2147483647";
    }
  }

  typedef snmpEngineMaxMessageSizeType {
    type int32 {
      range "484 .. 2147483647";
    }
  }

  augment "/ncs:devices/ncs:device/ncs:config" {
    // NCS drop config false container 'SNMP-FRAMEWORK-MIB'
  }
  augment "/ncs:devices/ncs:device/ncs:live-status" {
    container SNMP-FRAMEWORK-MIB {
      tailf:ncs-device-type "netconf";
      tailf:display-when "not(../../ncs:module) or ../../ncs:module[ncs:name='SNMP-FRAMEWORK-MIB'] or (../../ncs:live-status-protocol[not(ncs:capability)]) or (../../ncs:live-status-protocol/ncs:capability/ncs:module[.='SNMP-FRAMEWORK-MIB'])";
      container snmpEngine {
        leaf snmpEngineID {
          type live_ncs_SnmpEngineID;
        }
        leaf snmpEngineBoots {
          type live_ncs_snmpEngineBootsType;
        }
        leaf snmpEngineTime {
          type live_ncs_snmpEngineTimeType;
        }
        leaf snmpEngineMaxMessageSize {
          type live_ncs_snmpEngineMaxMessageSizeType;
        }
      }
    }
  }
  augment "/ncs:devices/ncs:template/ncs:ned-id/ncs:config" {
    // NCS drop config false container 'SNMP-FRAMEWORK-MIB'
  }
}

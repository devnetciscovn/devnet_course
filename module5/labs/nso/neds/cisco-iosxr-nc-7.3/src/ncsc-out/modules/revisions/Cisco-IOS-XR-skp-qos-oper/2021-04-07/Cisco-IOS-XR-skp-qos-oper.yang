module Cisco-IOS-XR-skp-qos-oper {
  // Generated by yanger -t ncs
  tailf:mount-id "cisco-iosxr-nc-7.3:cisco-iosxr-nc-7.3";
  tailf:ncs-device-type "netconf";

  namespace "http://cisco.com/ns/yang/Cisco-IOS-XR-skp-qos-oper";
  prefix skp-qos-oper;

  import Cisco-IOS-XR-types {
    prefix xr;
  }
  import cisco-semver {
    prefix semver;
  }
  include Cisco-IOS-XR-skp-qos-oper-sub2 {
    revision-date 2021-04-07;
  }
  include Cisco-IOS-XR-skp-qos-oper-sub1 {
    revision-date 2021-04-07;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR skp-qos package operational data.

     This module contains definitions
     for the following management objects:
       platform-qos: QoS Skywarp platform operational data
       platform-qos-ea: QoS-EA Skywarp platform operational data

     Copyright (c) 2013-2021 by Cisco Systems, Inc.
     All rights reserved.";

  revision 2021-04-07 {
    description
      "Added new policy param unit for inverse ratio";
    semver:module-version "1.1.0";
  }
  revision 2019-04-05 {
    description
      "Establish semantic version baseline.";
    semver:module-version "1.0.1";
  }
  revision 2016-02-18 {
    description
      "Implementing Oper Yang Model";
  }
  revision 2015-11-09 {
    description
      "IOS XR 6.0 revision.";
  }

  grouping ncs_template_NV-SATELLITE-INPUT {
    description
      "Common node of nv-satellite-interface,
       satellite-id, member-interface";
    container nv-satellite-input {
      description
        "A piece of Satellite QoS policy-map operational
         data for input";
      uses ncs_template_NV-SAT-STATISTICS;
    }
  }

  grouping ncs_template_DETAILS {
    description
      "Common node of output, input, bundle-input,
       bundle-output";
    container details {
      description
        "QoS-EA policy details";
      uses ncs_template_QOS-SHOW-EA-POLICY-ST;
    }
  }

  grouping ncs_template_STATISTICS {
    description
      "Common node of input, output, policy-name";
    container statistics {
      description
        "Policy-map statistics operational data for an
         interface";
      uses ncs_template_QOS-STATS;
    }
  }

  grouping ncs_template_INTERFACE {
    description
      "Common node of interface-table,
       nv-interface-table";
    list interface {
      // NCS patched for predictable order
      ordered-by user;
      key "interface-name";
      description
        "QoS policy-map operational data for a particular
         interface";
      leaf interface-name {
        type xr:ncs_template_Interface-name;
        description
          "Name of the interface";
      }
      uses ncs_template_OUTPUT;
      uses ncs_template_INPUT;
      uses ncs_template_MEMBER-INTERFACE-TABLE;
      uses ncs_template_SATELLITE-ID-TABLE;
    }
  }

  grouping ncs_template_INPUT {
    description
      "Common node of shared-policy-instance,
       member-interface, interface";
    container input {
      description
        "A piece of QoS policy-map operational data for
         an interface";
      uses ncs_template_POLICY-NAME-TABLE;
      uses ncs_template_STATISTICS;
    }
  }

  grouping ncs_template_MEMBER-INTERFACE-TABLE {
    description
      "Common node of interface, nv-satellite-interface,
       shared-policy-instance";
    container member-interfaces {
      description
        "QoS policy-map member interface table";
      list member-interface {
        // NCS patched for predictable order
        ordered-by user;
        key "interface-name";
        description
          "QoS policy-map member interface statistics";
        leaf interface-name {
          type xr:ncs_template_Interface-name;
          description
            "Name of member interface";
        }
        uses ncs_template_OUTPUT;
        uses ncs_template_NV-SATELLITE-OUTPUT;
        uses ncs_template_INPUT;
        uses ncs_template_NV-SATELLITE-INPUT;
        uses ncs_template_SATELLITE-ID-TABLE;
      }
    }
  }

  grouping ncs_template_POLICY-NAME-TABLE {
    description
      "Common node of input, output";
    container policy-names {
      description
        "Policy-map statistics operational data for an
         interface";
      list policy-name {
        // NCS patched for predictable order
        ordered-by user;
        key "service-policy-name";
        description
          "Policy-map statistics operational data for an
           interface";
        leaf service-policy-name {
          type xr:ncs_template_Cisco-ios-xr-string;
          description
            "Name of the policy";
        }
        uses ncs_template_STATISTICS;
      }
    }
  }

  grouping ncs_template_NV-SATELLITE-OUTPUT {
    description
      "Common node of nv-satellite-interface,
       satellite-id, member-interface";
    container nv-satellite-output {
      description
        "A piece of Satellite QoS policy-map operational
         data for an interface";
      uses ncs_template_NV-SAT-STATISTICS;
    }
  }

  grouping ncs_template_OUTPUT {
    description
      "Common node of shared-policy-instance,
       member-interface, interface";
    container output {
      description
        "A piece of QoS policy-map operational data for
         an interface";
      uses ncs_template_POLICY-NAME-TABLE;
      uses ncs_template_STATISTICS;
    }
  }

  grouping ncs_template_NV-SAT-STATISTICS {
    description
      "Common node of nv-satellite-input,
       nv-satellite-output";
    container nv-sat-statistics {
      description
        "Policy-map statistics operational data for
         satellite interface";
      uses ncs_template_QOS-STATS;
    }
  }

  grouping ncs_template_SATELLITE-ID-TABLE {
    description
      "Common node of interface, member-interface";
    container satellite-ids {
      description
        "Satellite ID information";
      list satellite-id {
        // NCS patched for predictable order
        ordered-by user;
        key "nv-satellite-id";
        description
          "Satellite ID information";
        leaf nv-satellite-id {
          type string;
          description
            "Satellite ID";
        }
        uses ncs_template_NV-SATELLITE-OUTPUT;
        uses ncs_template_NV-SATELLITE-INPUT;
      }
    }
  }

  grouping ncs_rpc_notif_NV-SATELLITE-INPUT {
    description
      "Common node of nv-satellite-interface,
       satellite-id, member-interface";
    container nv-satellite-input {
      description
        "A piece of Satellite QoS policy-map operational
         data for input";
      uses ncs_rpc_notif_NV-SAT-STATISTICS;
    }
  }

  grouping ncs_rpc_notif_DETAILS {
    description
      "Common node of output, input, bundle-input,
       bundle-output";
    container details {
      description
        "QoS-EA policy details";
      uses ncs_rpc_notif_QOS-SHOW-EA-POLICY-ST;
    }
  }

  grouping ncs_rpc_notif_STATISTICS {
    description
      "Common node of input, output, policy-name";
    container statistics {
      description
        "Policy-map statistics operational data for an
         interface";
      uses ncs_rpc_notif_QOS-STATS;
    }
  }

  grouping ncs_rpc_notif_INTERFACE {
    description
      "Common node of interface-table,
       nv-interface-table";
    list interface {
      key "interface-name";
      description
        "QoS policy-map operational data for a particular
         interface";
      leaf interface-name {
        type xr:ncs_rpc_notif_Interface-name;
        description
          "Name of the interface";
      }
      uses ncs_rpc_notif_OUTPUT;
      uses ncs_rpc_notif_INPUT;
      uses ncs_rpc_notif_MEMBER-INTERFACE-TABLE;
      uses ncs_rpc_notif_SATELLITE-ID-TABLE;
    }
  }

  grouping ncs_rpc_notif_INPUT {
    description
      "Common node of shared-policy-instance,
       member-interface, interface";
    container input {
      description
        "A piece of QoS policy-map operational data for
         an interface";
      uses ncs_rpc_notif_POLICY-NAME-TABLE;
      uses ncs_rpc_notif_STATISTICS;
    }
  }

  grouping ncs_rpc_notif_MEMBER-INTERFACE-TABLE {
    description
      "Common node of interface, nv-satellite-interface,
       shared-policy-instance";
    container member-interfaces {
      description
        "QoS policy-map member interface table";
      list member-interface {
        key "interface-name";
        description
          "QoS policy-map member interface statistics";
        leaf interface-name {
          type xr:ncs_rpc_notif_Interface-name;
          description
            "Name of member interface";
        }
        uses ncs_rpc_notif_OUTPUT;
        uses ncs_rpc_notif_NV-SATELLITE-OUTPUT;
        uses ncs_rpc_notif_INPUT;
        uses ncs_rpc_notif_NV-SATELLITE-INPUT;
        uses ncs_rpc_notif_SATELLITE-ID-TABLE;
      }
    }
  }

  grouping ncs_rpc_notif_POLICY-NAME-TABLE {
    description
      "Common node of input, output";
    container policy-names {
      description
        "Policy-map statistics operational data for an
         interface";
      list policy-name {
        key "service-policy-name";
        description
          "Policy-map statistics operational data for an
           interface";
        leaf service-policy-name {
          type xr:ncs_rpc_notif_Cisco-ios-xr-string;
          description
            "Name of the policy";
        }
        uses ncs_rpc_notif_STATISTICS;
      }
    }
  }

  grouping ncs_rpc_notif_NV-SATELLITE-OUTPUT {
    description
      "Common node of nv-satellite-interface,
       satellite-id, member-interface";
    container nv-satellite-output {
      description
        "A piece of Satellite QoS policy-map operational
         data for an interface";
      uses ncs_rpc_notif_NV-SAT-STATISTICS;
    }
  }

  grouping ncs_rpc_notif_OUTPUT {
    description
      "Common node of shared-policy-instance,
       member-interface, interface";
    container output {
      description
        "A piece of QoS policy-map operational data for
         an interface";
      uses ncs_rpc_notif_POLICY-NAME-TABLE;
      uses ncs_rpc_notif_STATISTICS;
    }
  }

  grouping ncs_rpc_notif_NV-SAT-STATISTICS {
    description
      "Common node of nv-satellite-input,
       nv-satellite-output";
    container nv-sat-statistics {
      description
        "Policy-map statistics operational data for
         satellite interface";
      uses ncs_rpc_notif_QOS-STATS;
    }
  }

  grouping ncs_rpc_notif_SATELLITE-ID-TABLE {
    description
      "Common node of interface, member-interface";
    container satellite-ids {
      description
        "Satellite ID information";
      list satellite-id {
        key "nv-satellite-id";
        description
          "Satellite ID information";
        leaf nv-satellite-id {
          type uint32;
          description
            "Satellite ID";
        }
        uses ncs_rpc_notif_NV-SATELLITE-OUTPUT;
        uses ncs_rpc_notif_NV-SATELLITE-INPUT;
      }
    }
  }

  grouping live_ncs_NV-SATELLITE-INPUT {
    description
      "Common node of nv-satellite-interface,
       satellite-id, member-interface";
    container nv-satellite-input {
      description
        "A piece of Satellite QoS policy-map operational
         data for input";
      uses live_ncs_NV-SAT-STATISTICS;
    }
  }

  grouping live_ncs_DETAILS {
    description
      "Common node of output, input, bundle-input,
       bundle-output";
    container details {
      description
        "QoS-EA policy details";
      uses live_ncs_QOS-SHOW-EA-POLICY-ST;
    }
  }

  grouping live_ncs_STATISTICS {
    description
      "Common node of input, output, policy-name";
    container statistics {
      description
        "Policy-map statistics operational data for an
         interface";
      uses live_ncs_QOS-STATS;
    }
  }

  grouping live_ncs_INTERFACE {
    description
      "Common node of interface-table,
       nv-interface-table";
    list interface {
      key "interface-name";
      description
        "QoS policy-map operational data for a particular
         interface";
      leaf interface-name {
        type xr:live_ncs_Interface-name;
        description
          "Name of the interface";
      }
      uses live_ncs_OUTPUT;
      uses live_ncs_INPUT;
      uses live_ncs_MEMBER-INTERFACE-TABLE;
      uses live_ncs_SATELLITE-ID-TABLE;
    }
  }

  grouping live_ncs_INPUT {
    description
      "Common node of shared-policy-instance,
       member-interface, interface";
    container input {
      description
        "A piece of QoS policy-map operational data for
         an interface";
      uses live_ncs_POLICY-NAME-TABLE;
      uses live_ncs_STATISTICS;
    }
  }

  grouping live_ncs_MEMBER-INTERFACE-TABLE {
    description
      "Common node of interface, nv-satellite-interface,
       shared-policy-instance";
    container member-interfaces {
      description
        "QoS policy-map member interface table";
      list member-interface {
        key "interface-name";
        description
          "QoS policy-map member interface statistics";
        leaf interface-name {
          type xr:live_ncs_Interface-name;
          description
            "Name of member interface";
        }
        uses live_ncs_OUTPUT;
        uses live_ncs_NV-SATELLITE-OUTPUT;
        uses live_ncs_INPUT;
        uses live_ncs_NV-SATELLITE-INPUT;
        uses live_ncs_SATELLITE-ID-TABLE;
      }
    }
  }

  grouping live_ncs_POLICY-NAME-TABLE {
    description
      "Common node of input, output";
    container policy-names {
      description
        "Policy-map statistics operational data for an
         interface";
      list policy-name {
        key "service-policy-name";
        description
          "Policy-map statistics operational data for an
           interface";
        leaf service-policy-name {
          type xr:live_ncs_Cisco-ios-xr-string;
          description
            "Name of the policy";
        }
        uses live_ncs_STATISTICS;
      }
    }
  }

  grouping live_ncs_NV-SATELLITE-OUTPUT {
    description
      "Common node of nv-satellite-interface,
       satellite-id, member-interface";
    container nv-satellite-output {
      description
        "A piece of Satellite QoS policy-map operational
         data for an interface";
      uses live_ncs_NV-SAT-STATISTICS;
    }
  }

  grouping live_ncs_OUTPUT {
    description
      "Common node of shared-policy-instance,
       member-interface, interface";
    container output {
      description
        "A piece of QoS policy-map operational data for
         an interface";
      uses live_ncs_POLICY-NAME-TABLE;
      uses live_ncs_STATISTICS;
    }
  }

  grouping live_ncs_NV-SAT-STATISTICS {
    description
      "Common node of nv-satellite-input,
       nv-satellite-output";
    container nv-sat-statistics {
      description
        "Policy-map statistics operational data for
         satellite interface";
      uses live_ncs_QOS-STATS;
    }
  }

  grouping live_ncs_SATELLITE-ID-TABLE {
    description
      "Common node of interface, member-interface";
    container satellite-ids {
      description
        "Satellite ID information";
      list satellite-id {
        key "nv-satellite-id";
        description
          "Satellite ID information";
        leaf nv-satellite-id {
          type uint32;
          description
            "Satellite ID";
        }
        uses live_ncs_NV-SATELLITE-OUTPUT;
        uses live_ncs_NV-SATELLITE-INPUT;
      }
    }
  }

  grouping NV-SATELLITE-INPUT {
    description
      "Common node of nv-satellite-interface,
       satellite-id, member-interface";
    container nv-satellite-input {
      description
        "A piece of Satellite QoS policy-map operational
         data for input";
      uses NV-SAT-STATISTICS;
    }
  }

  grouping DETAILS {
    description
      "Common node of output, input, bundle-input,
       bundle-output";
    container details {
      description
        "QoS-EA policy details";
      uses QOS-SHOW-EA-POLICY-ST;
    }
  }

  grouping STATISTICS {
    description
      "Common node of input, output, policy-name";
    container statistics {
      description
        "Policy-map statistics operational data for an
         interface";
      uses QOS-STATS;
    }
  }

  grouping INTERFACE {
    description
      "Common node of interface-table,
       nv-interface-table";
    list interface {
      key "interface-name";
      description
        "QoS policy-map operational data for a particular
         interface";
      leaf interface-name {
        type xr:Interface-name;
        description
          "Name of the interface";
      }
      uses OUTPUT;
      uses INPUT;
      uses MEMBER-INTERFACE-TABLE;
      uses SATELLITE-ID-TABLE;
    }
  }

  grouping INPUT {
    description
      "Common node of shared-policy-instance,
       member-interface, interface";
    container input {
      description
        "A piece of QoS policy-map operational data for
         an interface";
      uses POLICY-NAME-TABLE;
      uses STATISTICS;
    }
  }

  grouping MEMBER-INTERFACE-TABLE {
    description
      "Common node of interface, nv-satellite-interface,
       shared-policy-instance";
    container member-interfaces {
      description
        "QoS policy-map member interface table";
      list member-interface {
        key "interface-name";
        description
          "QoS policy-map member interface statistics";
        leaf interface-name {
          type xr:Interface-name;
          description
            "Name of member interface";
        }
        uses OUTPUT;
        uses NV-SATELLITE-OUTPUT;
        uses INPUT;
        uses NV-SATELLITE-INPUT;
        uses SATELLITE-ID-TABLE;
      }
    }
  }

  grouping POLICY-NAME-TABLE {
    description
      "Common node of input, output";
    container policy-names {
      description
        "Policy-map statistics operational data for an
         interface";
      list policy-name {
        key "service-policy-name";
        description
          "Policy-map statistics operational data for an
           interface";
        leaf service-policy-name {
          type xr:Cisco-ios-xr-string;
          description
            "Name of the policy";
        }
        uses STATISTICS;
      }
    }
  }

  grouping NV-SATELLITE-OUTPUT {
    description
      "Common node of nv-satellite-interface,
       satellite-id, member-interface";
    container nv-satellite-output {
      description
        "A piece of Satellite QoS policy-map operational
         data for an interface";
      uses NV-SAT-STATISTICS;
    }
  }

  grouping OUTPUT {
    description
      "Common node of shared-policy-instance,
       member-interface, interface";
    container output {
      description
        "A piece of QoS policy-map operational data for
         an interface";
      uses POLICY-NAME-TABLE;
      uses STATISTICS;
    }
  }

  grouping NV-SAT-STATISTICS {
    description
      "Common node of nv-satellite-input,
       nv-satellite-output";
    container nv-sat-statistics {
      description
        "Policy-map statistics operational data for
         satellite interface";
      uses QOS-STATS;
    }
  }

  grouping SATELLITE-ID-TABLE {
    description
      "Common node of interface, member-interface";
    container satellite-ids {
      description
        "Satellite ID information";
      list satellite-id {
        key "nv-satellite-id";
        description
          "Satellite ID information";
        leaf nv-satellite-id {
          type uint32;
          description
            "Satellite ID";
        }
        uses NV-SATELLITE-OUTPUT;
        uses NV-SATELLITE-INPUT;
      }
    }
  }

  augment "/ncs:devices/ncs:device/ncs:config" {
    // NCS drop config false container 'platform-qos'
    // NCS drop config false container 'platform-qos-ea'
  }
  augment "/ncs:devices/ncs:device/ncs:live-status" {
    container platform-qos {
      tailf:ncs-device-type "netconf";
      tailf:display-when "not(../../ncs:module) or ../../ncs:module[ncs:name='Cisco-IOS-XR-skp-qos-oper'] or (../../ncs:live-status-protocol[not(ncs:capability)]) or (../../ncs:live-status-protocol/ncs:capability/ncs:module[.='Cisco-IOS-XR-skp-qos-oper'])";
      description
        "QoS Skywarp platform operational data ";
      container nodes {
        description
          "List of nodes with platform specific QoS
           configuration";
        list node {
          key "node-name";
          description
            "Node with platform specific QoS configuration";
          container bundle-interfaces {
            description
              "QoS list of bundle interfaces";
            list bundle-interface {
              key "interface-name";
              description
                "QoS interface name";
              container member-interfaces {
                description
                  "QoS list of member interfaces";
                list member-interface {
                  key "interface-name";
                  description
                    "QoS interface name";
                  container bundle-input {
                    description
                      "QoS policy direction input";
                    uses live_ncs_QOS-SHOW-POLICY-ST;
                  }
                  container bundle-output {
                    description
                      "QoS policy direction output";
                    uses live_ncs_QOS-SHOW-POLICY-ST;
                  }
                  leaf interface-name {
                    type xr:live_ncs_Interface-name;
                    description
                      "Memeber interface";
                  }
                }
              }
              leaf interface-name {
                type xr:live_ncs_Interface-name;
                description
                  "Bundle interface name";
              }
            }
          }
          container capability {
            description
              "QoS system capability";
            uses live_ncs_QOS-EA-CAPABILITY;
          }
          container interfaces {
            description
              "QoS list of interfaces";
            list interface {
              key "interface-name";
              description
                "QoS interface name";
              container output {
                description
                  "QoS policy direction egress";
                uses live_ncs_QOS-SHOW-POLICY-ST;
              }
              container input {
                description
                  "QoS policy direction ingress";
                uses live_ncs_QOS-SHOW-POLICY-ST;
              }
              leaf interface-name {
                type xr:live_ncs_Interface-name;
                description
                  "The name of the interface";
              }
            }
          }
          leaf node-name {
            type xr:live_ncs_Node-id;
            description
              "Node name";
          }
        }
      }
    }
    container platform-qos-ea {
      tailf:ncs-device-type "netconf";
      tailf:display-when "not(../../ncs:module) or ../../ncs:module[ncs:name='Cisco-IOS-XR-skp-qos-oper'] or (../../ncs:live-status-protocol[not(ncs:capability)]) or (../../ncs:live-status-protocol/ncs:capability/ncs:module[.='Cisco-IOS-XR-skp-qos-oper'])";
      description
        "QoS-EA Skywarp platform operational data ";
      container nodes {
        description
          "List of nodes with platform specific QoS-EA
           configuration";
        list node {
          key "node-name";
          description
            "Node with platform specific QoS-EA
             configuration";
          container bundle-interfaces {
            description
              "QoS-EA list of bundle interfaces";
            list bundle-interface {
              key "interface-name";
              description
                "QoS-EA interface name";
              container member-interfaces {
                description
                  "QoS-EA list of member interfaces";
                list member-interface {
                  key "interface-name";
                  description
                    "QoS-EA interface name";
                  container bundle-output {
                    description
                      "QoS-EA policy direction output";
                    uses live_ncs_DETAILS;
                  }
                  container bundle-input {
                    description
                      "QoS-EA policy direction input";
                    uses live_ncs_DETAILS;
                  }
                  leaf interface-name {
                    type xr:live_ncs_Interface-name;
                    description
                      "Memeber interface";
                  }
                }
              }
              leaf interface-name {
                type xr:live_ncs_Interface-name;
                description
                  "Bundle interface name";
              }
            }
          }
          container interfaces {
            description
              "QoS-EA list of interfaces";
            list interface {
              key "interface-name";
              description
                "QoS-EA interface name";
              container output {
                description
                  "QoS-EA policy direction egress";
                uses live_ncs_DETAILS;
              }
              container input {
                description
                  "QoS-EA policy direction ingress";
                uses live_ncs_DETAILS;
              }
              leaf interface-name {
                type xr:live_ncs_Interface-name;
                description
                  "The name of the interface";
              }
            }
          }
          leaf node-name {
            type xr:live_ncs_Node-id;
            description
              "Node name";
          }
        }
      }
    }
  }
  augment "/ncs:devices/ncs:template/ncs:ned-id/ncs:config" {
    // NCS drop config false container 'platform-qos'
    // NCS drop config false container 'platform-qos-ea'
  }
}

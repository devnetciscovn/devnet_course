module Cisco-IOS-XR-ncs1k-mxp-headless-oper {
  // Generated by yanger -t ncs
  tailf:mount-id "cisco-iosxr-nc-7.3:cisco-iosxr-nc-7.3";
  tailf:ncs-device-type "netconf";

  namespace "http://cisco.com/ns/yang/Cisco-IOS-XR-ncs1k-mxp-headless-oper";
  prefix ncs1k-mxp-headless-oper;

  import Cisco-IOS-XR-types {
    prefix xr;
  }
  import cisco-semver {
    prefix semver;
  }
  include Cisco-IOS-XR-ncs1k-mxp-headless-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1k-mxp-headless package operational data.

     This module contains definitions
     for the following management objects:
       headless-func-data: Information related to headless
         functionality

     Copyright (c) 2013-2019 by Cisco Systems, Inc.
     All rights reserved.";

  revision 2019-04-05 {
    description
      "Establish semantic version baseline.";
    semver:module-version "1.0.0";
  }
  revision 2017-03-30 {
    description
      "PRBS stats added";
  }
  revision 2015-11-09 {
    description
      "IOS XR 6.0 revision.";
  }

  augment "/ncs:devices/ncs:device/ncs:config" {
    // NCS drop config false container 'headless-func-data'
  }
  augment "/ncs:devices/ncs:device/ncs:live-status" {
    container headless-func-data {
      tailf:ncs-device-type "netconf";
      tailf:display-when "not(../../ncs:module) or ../../ncs:module[ncs:name='Cisco-IOS-XR-ncs1k-mxp-headless-oper'] or (../../ncs:live-status-protocol[not(ncs:capability)]) or (../../ncs:live-status-protocol/ncs:capability/ncs:module[.='Cisco-IOS-XR-ncs1k-mxp-headless-oper'])";
      description
        "Information related to headless functionality";
      container otn-port-names {
        description
          "OTN Statistics collected during last headless
           operation";
        list otn-port-name {
          key "name";
          description
            "port Name";
          leaf name {
            type xr:live_ncs_Interface-name;
            description
              "Port name";
          }
          uses live_ncs_MXP-HEADLESS-OTN-CNT-INFO;
        }
      }
      container ethernet-port-names {
        description
          "Ethernet Statistics collected during last
           headless operation";
        list ethernet-port-name {
          key "name";
          description
            "Port Name";
          leaf name {
            type xr:live_ncs_Interface-name;
            description
              "Port name";
          }
          uses live_ncs_MXP-HEADLESS-ETHER-PRIM-INFO;
        }
      }
    }
  }
  augment "/ncs:devices/ncs:template/ncs:ned-id/ncs:config" {
    // NCS drop config false container 'headless-func-data'
  }
}

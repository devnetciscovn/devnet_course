module SNMPv2-TC {
  // Generated by yanger -t ncs
  tailf:mount-id "cisco-iosxr-nc-7.3:cisco-iosxr-nc-7.3";
  tailf:ncs-device-type "netconf";

  namespace "http://tail-f.com/ns/mibs/SNMPv2-TC/1.0";
  prefix SNMPv2_TC;

  import ietf-yang-types {
    prefix yang;
  }
  import tailf-common {
    prefix tailf;
  }
  import ietf-yang-smiv2 {
    prefix smiv2;
  }
  import tailf-ncs {
    prefix ncs;
  }

  revision 2016-08-18 {
    description
      "Initial revision";
  }

  typedef ncs_template_DisplayString {
    type string;
  }

  typedef ncs_template_PhysAddress {
    type string;
  }

  typedef ncs_template_MacAddress {
    type string;
  }

  typedef ncs_template_TruthValue {
    type string;
  }

  typedef ncs_template_TestAndIncr {
    type string;
  }

  typedef ncs_template_AutonomousType {
    type string;
  }

  typedef ncs_template_InstancePointer {
    type string;
  }

  typedef ncs_template_VariablePointer {
    type string;
  }

  typedef ncs_template_RowPointer {
    type string;
  }

  typedef ncs_template_RowStatus {
    type string;
  }

  typedef ncs_template_TimeStamp {
    type string;
  }

  typedef ncs_template_TimeInterval {
    type string;
  }

  typedef ncs_template_DateAndTime {
    type string;
  }

  typedef ncs_template_StorageType {
    type string;
  }

  typedef ncs_template_TDomain {
    type string;
  }

  typedef ncs_template_TAddress {
    type string;
  }

  typedef ncs_rpc_notif_DisplayString {
    type string {
      length "min .. 255";
    }
  }

  typedef ncs_rpc_notif_PhysAddress {
    type tailf:hex-list {
      pattern '(((([0-9A-Fa-f]{2}):)*([0-9A-Fa-f]{2}))){0,1}';
    }
  }

  typedef ncs_rpc_notif_MacAddress {
    type tailf:hex-list {
      pattern '(((([0-9A-Fa-f]{2}):){5,5})([0-9A-Fa-f]{2}))';
    }
  }

  typedef ncs_rpc_notif_TruthValue {
    type enumeration {
      enum "true" {
        value 1;
      }
      enum "false" {
        value 2;
      }
    }
  }

  typedef ncs_rpc_notif_TestAndIncr {
    type int32 {
      range "0 .. 2147483647";
    }
  }

  typedef ncs_rpc_notif_AutonomousType {
    type yang:object-identifier;
  }

  typedef ncs_rpc_notif_InstancePointer {
    type yang:object-identifier;
  }

  typedef ncs_rpc_notif_VariablePointer {
    type yang:object-identifier;
  }

  typedef ncs_rpc_notif_RowPointer {
    type yang:object-identifier;
  }

  typedef ncs_rpc_notif_RowStatus {
    type enumeration {
      enum "active" {
        value 1;
      }
      enum "notInService" {
        value 2;
      }
      enum "notReady" {
        value 3;
      }
      enum "createAndGo" {
        value 4;
      }
      enum "createAndWait" {
        value 5;
      }
      enum "destroy" {
        value 6;
      }
    }
  }

  typedef ncs_rpc_notif_TimeStamp {
    type uint32 {
      range "0 .. 4294967295";
    }
  }

  typedef ncs_rpc_notif_TimeInterval {
    type int32 {
      range "0 .. 2147483647";
    }
  }

  typedef ncs_rpc_notif_DateAndTime {
    smiv2:display-hint "2d-1d-1d,1d:1d:1d.1d,1a1d:1d";
    type string;
  }

  typedef ncs_rpc_notif_StorageType {
    type enumeration {
      enum "other" {
        value 1;
      }
      enum "volatile" {
        value 2;
      }
      enum "nonVolatile" {
        value 3;
      }
      enum "permanent" {
        value 4;
      }
      enum "readOnly" {
        value 5;
      }
    }
  }

  typedef ncs_rpc_notif_TDomain {
    type yang:object-identifier;
  }

  typedef ncs_rpc_notif_TAddress {
    type tailf:octet-list {
      tailf:value-length "1 .. 255";
    }
  }

  typedef live_ncs_DisplayString {
    type string {
      length "min .. 255";
    }
  }

  typedef live_ncs_PhysAddress {
    type tailf:hex-list {
      pattern '(((([0-9A-Fa-f]{2}):)*([0-9A-Fa-f]{2}))){0,1}';
    }
  }

  typedef live_ncs_MacAddress {
    type tailf:hex-list {
      pattern '(((([0-9A-Fa-f]{2}):){5,5})([0-9A-Fa-f]{2}))';
    }
  }

  typedef live_ncs_TruthValue {
    type enumeration {
      enum "true" {
        value 1;
      }
      enum "false" {
        value 2;
      }
    }
  }

  typedef live_ncs_TestAndIncr {
    type int32 {
      range "0 .. 2147483647";
    }
  }

  typedef live_ncs_AutonomousType {
    type yang:object-identifier;
  }

  typedef live_ncs_InstancePointer {
    type yang:object-identifier;
  }

  typedef live_ncs_VariablePointer {
    type yang:object-identifier;
  }

  typedef live_ncs_RowPointer {
    type yang:object-identifier;
  }

  typedef live_ncs_RowStatus {
    type enumeration {
      enum "active" {
        value 1;
      }
      enum "notInService" {
        value 2;
      }
      enum "notReady" {
        value 3;
      }
      enum "createAndGo" {
        value 4;
      }
      enum "createAndWait" {
        value 5;
      }
      enum "destroy" {
        value 6;
      }
    }
  }

  typedef live_ncs_TimeStamp {
    type uint32 {
      range "0 .. 4294967295";
    }
  }

  typedef live_ncs_TimeInterval {
    type int32 {
      range "0 .. 2147483647";
    }
  }

  typedef live_ncs_DateAndTime {
    smiv2:display-hint "2d-1d-1d,1d:1d:1d.1d,1a1d:1d";
    type string;
  }

  typedef live_ncs_StorageType {
    type enumeration {
      enum "other" {
        value 1;
      }
      enum "volatile" {
        value 2;
      }
      enum "nonVolatile" {
        value 3;
      }
      enum "permanent" {
        value 4;
      }
      enum "readOnly" {
        value 5;
      }
    }
  }

  typedef live_ncs_TDomain {
    type yang:object-identifier;
  }

  typedef live_ncs_TAddress {
    type tailf:octet-list {
      tailf:value-length "1 .. 255";
    }
  }

  typedef DisplayString {
    type string {
      length "min .. 255";
    }
  }

  typedef PhysAddress {
    type tailf:hex-list {
      pattern '(((([0-9A-Fa-f]{2}):)*([0-9A-Fa-f]{2}))){0,1}';
    }
  }

  typedef MacAddress {
    type tailf:hex-list {
      pattern '(((([0-9A-Fa-f]{2}):){5,5})([0-9A-Fa-f]{2}))';
    }
  }

  typedef TruthValue {
    type enumeration {
      enum "true" {
        value 1;
      }
      enum "false" {
        value 2;
      }
    }
  }

  typedef TestAndIncr {
    type int32 {
      range "0 .. 2147483647";
    }
  }

  typedef AutonomousType {
    type yang:object-identifier;
  }

  typedef InstancePointer {
    type yang:object-identifier;
  }

  typedef VariablePointer {
    type yang:object-identifier;
  }

  typedef RowPointer {
    type yang:object-identifier;
  }

  typedef RowStatus {
    type enumeration {
      enum "active" {
        value 1;
      }
      enum "notInService" {
        value 2;
      }
      enum "notReady" {
        value 3;
      }
      enum "createAndGo" {
        value 4;
      }
      enum "createAndWait" {
        value 5;
      }
      enum "destroy" {
        value 6;
      }
    }
  }

  typedef TimeStamp {
    type uint32 {
      range "0 .. 4294967295";
    }
  }

  typedef TimeInterval {
    type int32 {
      range "0 .. 2147483647";
    }
  }

  typedef DateAndTime {
    smiv2:display-hint "2d-1d-1d,1d:1d:1d.1d,1a1d:1d";
    type string;
  }

  typedef StorageType {
    type enumeration {
      enum "other" {
        value 1;
      }
      enum "volatile" {
        value 2;
      }
      enum "nonVolatile" {
        value 3;
      }
      enum "permanent" {
        value 4;
      }
      enum "readOnly" {
        value 5;
      }
    }
  }

  typedef TDomain {
    type yang:object-identifier;
  }

  typedef TAddress {
    type tailf:octet-list {
      tailf:value-length "1 .. 255";
    }
  }
}

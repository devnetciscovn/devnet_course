module Cisco-IOS-XR-ofa-netflow-oper {
  // Generated by yanger -t ncs
  tailf:mount-id "cisco-iosxr-nc-7.3:cisco-iosxr-nc-7.3";
  tailf:ncs-device-type "netconf";

  namespace "http://cisco.com/ns/yang/Cisco-IOS-XR-ofa-netflow-oper";
  prefix ofa-netflow-oper;

  import Cisco-IOS-XR-types {
    prefix xr;
  }
  import cisco-semver {
    prefix semver;
  }
  include Cisco-IOS-XR-ofa-netflow-oper-sub2 {
    revision-date 2019-08-26;
  }
  include Cisco-IOS-XR-ofa-netflow-oper-sub1 {
    revision-date 2019-08-26;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ofa-netflow package operational data.

     This module contains definitions
     for the following management objects:
       net-flow: NetFlow operational data

     Copyright (c) 2013-2019 by Cisco Systems, Inc.
     All rights reserved.";

  revision 2019-08-26 {
    description
      "Update leaf fields";
    semver:module-version "1.0.0";
  }
  revision 2019-04-05 {
    description
      "Establish semantic version baseline.";
  }
  revision 2015-11-09 {
    description
      "IOS XR 6.0 revision.";
  }

  augment "/ncs:devices/ncs:device/ncs:config" {
    // NCS drop config false container 'net-flow'
  }
  augment "/ncs:devices/ncs:device/ncs:live-status" {
    container net-flow {
      tailf:ncs-device-type "netconf";
      tailf:display-when "not(../../ncs:module) or ../../ncs:module[ncs:name='Cisco-IOS-XR-ofa-netflow-oper'] or (../../ncs:live-status-protocol[not(ncs:capability)]) or (../../ncs:live-status-protocol/ncs:capability/ncs:module[.='Cisco-IOS-XR-ofa-netflow-oper'])";
      description
        "NetFlow operational data";
      container statistics {
        description
          "Node-specific NetFlow statistics information";
        list statistic {
          key "node";
          description
            "NetFlow statistics information for a particular
             node";
          container producer {
            description
              "NetFlow producer statistics";
            container statistics {
              description
                "Statistics information";
              uses live_ncs_NF-PRODUCER-STATS;
            }
          }
          container server {
            description
              "NetFlow server statistics";
            container flow-exporters {
              description
                "Flow exporter information";
              list flow-exporter {
                key "exporter-name";
                description
                  "Exporter information";
                container exporter {
                  description
                    "Statistics information for the exporter";
                  uses live_ncs_NFSVR-SHOW-FLOW-EXPORTER-RESP-ARRAY;
                }
                leaf exporter-name {
                  type xr:live_ncs_Cisco-ios-xr-string;
                  description
                    "Exporter name";
                }
              }
            }
          }
          leaf node {
            type xr:live_ncs_Node-id;
            description
              "Node location";
          }
        }
      }
    }
  }
  augment "/ncs:devices/ncs:template/ncs:ned-id/ncs:config" {
    // NCS drop config false container 'net-flow'
  }
}

module Cisco-IOS-XR-snmp-test-trap-act {
  // Generated by yanger -t ncs
  tailf:mount-id "cisco-iosxr-nc-7.3:cisco-iosxr-nc-7.3";
  tailf:ncs-device-type "netconf";

  namespace "http://cisco.com/ns/yang/Cisco-IOS-XR-snmp-test-trap-act";
  prefix snmp-test-trap-act;

  import cisco-semver {
    prefix semver;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2017-2019 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2017-05-01 {
    description
      "Fixing backward compatibility error in module.";
  }
  revision 2016-10-25 {
    description
      "IOS XR 6.2.1 revision.";
  }

  augment "/ncs:devices/ncs:device/ncs:rpc" {
    container rpc-all {
      tailf:ncs-device-type "netconf";
      tailf:display-when "not(../../ncs:module) or ../../ncs:module[ncs:name='Cisco-IOS-XR-snmp-test-trap-act']";
      tailf:action all {
        tailf:actionpoint ncsproxy {
          tailf:internal;
        }
        description
          "generate all the supported traps";
      }
    }
  }
  augment "/ncs:devices/ncs:device-group/ncs:ned-id/ncs:rpc" {
    container rpc-all {
      tailf:ncs-device-type "netconf";
      tailf:display-when "/ncs:devices/ncs:device[ncs:name=current()/../../../ncs:member]/ncs:module[ncs:name='Cisco-IOS-XR-snmp-test-trap-act']";
      tailf:action all {
        tailf:actionpoint ncsproxy {
          tailf:internal;
        }
        description
          "generate all the supported traps";
      }
    }
  }
  augment "/ncs:devices/ncs:device/ncs:rpc" {
    container rpc-routing-mpls-tunnel-down-index {
      tailf:ncs-device-type "netconf";
      tailf:display-when "not(../../ncs:module) or ../../ncs:module[ncs:name='Cisco-IOS-XR-snmp-test-trap-act']";
      tailf:action routing-mpls-tunnel-down-index {
        tailf:actionpoint ncsproxy {
          tailf:internal;
        }
        description
          "Generate MPLS-TE-STD-MIB::mplsTunnelDown index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "src address";
          }
          leaf destination {
            type inet:ipv4-address-no-zone;
            mandatory true;
            description
              "destination address for which to generate the trap";
          }
        }
      }
    }
  }
  augment "/ncs:devices/ncs:device-group/ncs:ned-id/ncs:rpc" {
    container rpc-routing-mpls-tunnel-down-index {
      tailf:ncs-device-type "netconf";
      tailf:display-when "/ncs:devices/ncs:device[ncs:name=current()/../../../ncs:member]/ncs:module[ncs:name='Cisco-IOS-XR-snmp-test-trap-act']";
      tailf:action routing-mpls-tunnel-down-index {
        tailf:actionpoint ncsproxy {
          tailf:internal;
        }
        description
          "Generate MPLS-TE-STD-MIB::mplsTunnelDown index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "src address";
          }
          leaf destination {
            type inet:ipv4-address-no-zone;
            mandatory true;
            description
              "destination address for which to generate the trap";
          }
        }
      }
    }
  }
  augment "/ncs:devices/ncs:device/ncs:rpc" {
    container rpc-routing-mpls-tunnel-down {
      tailf:ncs-device-type "netconf";
      tailf:display-when "not(../../ncs:module) or ../../ncs:module[ncs:name='Cisco-IOS-XR-snmp-test-trap-act']";
      tailf:action routing-mpls-tunnel-down {
        tailf:actionpoint ncsproxy {
          tailf:internal;
        }
        description
          "Generate MPLS-TE-STD-MIB::mplsTunnelDown";
      }
    }
  }
  augment "/ncs:devices/ncs:device-group/ncs:ned-id/ncs:rpc" {
    container rpc-routing-mpls-tunnel-down {
      tailf:ncs-device-type "netconf";
      tailf:display-when "/ncs:devices/ncs:device[ncs:name=current()/../../../ncs:member]/ncs:module[ncs:name='Cisco-IOS-XR-snmp-test-trap-act']";
      tailf:action routing-mpls-tunnel-down {
        tailf:actionpoint ncsproxy {
          tailf:internal;
        }
        description
          "Generate MPLS-TE-STD-MIB::mplsTunnelDown";
      }
    }
  }
  augment "/ncs:devices/ncs:device/ncs:rpc" {
    container rpc-routing-mpls-tunnel-re-optimized-index {
      tailf:ncs-device-type "netconf";
      tailf:display-when "not(../../ncs:module) or ../../ncs:module[ncs:name='Cisco-IOS-XR-snmp-test-trap-act']";
      tailf:action routing-mpls-tunnel-re-optimized-index {
        tailf:actionpoint ncsproxy {
          tailf:internal;
        }
        description
          "Generate MPLS-TE-STD-MIB::mplsTunnelReoptimized index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "source address for which to generate the trap";
          }
          leaf destination {
            type inet:ipv4-address-no-zone;
            mandatory true;
            description
              "destination address for which to generate the trap";
          }
        }
      }
    }
  }
  augment "/ncs:devices/ncs:device-group/ncs:ned-id/ncs:rpc" {
    container rpc-routing-mpls-tunnel-re-optimized-index {
      tailf:ncs-device-type "netconf";
      tailf:display-when "/ncs:devices/ncs:device[ncs:name=current()/../../../ncs:member]/ncs:module[ncs:name='Cisco-IOS-XR-snmp-test-trap-act']";
      tailf:action routing-mpls-tunnel-re-optimized-index {
        tailf:actionpoint ncsproxy {
          tailf:internal;
        }
        description
          "Generate MPLS-TE-STD-MIB::mplsTunnelReoptimized index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "source address for which to generate the trap";
          }
          leaf destination {
            type inet:ipv4-address-no-zone;
            mandatory true;
            description
              "destination address for which to generate the trap";
          }
        }
      }
    }
  }
  augment "/ncs:devices/ncs:device/ncs:rpc" {
    container rpc-routing-mpls-tunnel-re-optimized {
      tailf:ncs-device-type "netconf";
      tailf:display-when "not(../../ncs:module) or ../../ncs:module[ncs:name='Cisco-IOS-XR-snmp-test-trap-act']";
      tailf:action routing-mpls-tunnel-re-optimized {
        tailf:actionpoint ncsproxy {
          tailf:internal;
        }
        description
          "Generate MPLS-TE-STD-MIB::mplsTunnelReoptimized";
      }
    }
  }
  augment "/ncs:devices/ncs:device-group/ncs:ned-id/ncs:rpc" {
    container rpc-routing-mpls-tunnel-re-optimized {
      tailf:ncs-device-type "netconf";
      tailf:display-when "/ncs:devices/ncs:device[ncs:name=current()/../../../ncs:member]/ncs:module[ncs:name='Cisco-IOS-XR-snmp-test-trap-act']";
      tailf:action routing-mpls-tunnel-re-optimized {
        tailf:actionpoint ncsproxy {
          tailf:internal;
        }
        description
          "Generate MPLS-TE-STD-MIB::mplsTunnelReoptimized";
      }
    }
  }
  augment "/ncs:devices/ncs:device/ncs:rpc" {
    container rpc-routing-mpls-tunnel-re-routed-index {
      tailf:ncs-device-type "netconf";
      tailf:display-when "not(../../ncs:module) or ../../ncs:module[ncs:name='Cisco-IOS-XR-snmp-test-trap-act']";
      tailf:action routing-mpls-tunnel-re-routed-index {
        tailf:actionpoint ncsproxy {
          tailf:internal;
        }
        description
          "Generate MPLS-TE-STD-MIB::mplsTunnelRerouted index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "source address for which to generate the trap";
          }
          leaf destination {
            type inet:ipv4-address-no-zone;
            mandatory true;
            description
              "destination address for which to generate the trap";
          }
        }
      }
    }
  }
  augment "/ncs:devices/ncs:device-group/ncs:ned-id/ncs:rpc" {
    container rpc-routing-mpls-tunnel-re-routed-index {
      tailf:ncs-device-type "netconf";
      tailf:display-when "/ncs:devices/ncs:device[ncs:name=current()/../../../ncs:member]/ncs:module[ncs:name='Cisco-IOS-XR-snmp-test-trap-act']";
      tailf:action routing-mpls-tunnel-re-routed-index {
        tailf:actionpoint ncsproxy {
          tailf:internal;
        }
        description
          "Generate MPLS-TE-STD-MIB::mplsTunnelRerouted index";
        input {
          leaf index {
            type uint32 {
              range "0..65535";
            }
            mandatory true;
            description
              "tunnel index for which to generate the trap";
          }
          leaf instance {
            type uint32 {
              range "0..65535";
            }
            mandatory true;
            description
              "tunnel instance for which to generate the trap";
          }
          leaf source {
            type inet:ipv4-address-no-zone;
            mandatory true;
            description
              "source address for which to generate the trap";
          }
          leaf destination {
            type inet:ipv4-address-no-zone;
            mandatory true;
            description
              "destination address for which to generate the trap";
          }
        }
      }
    }
  }
  augment "/ncs:devices/ncs:device/ncs:rpc" {
    container rpc-routing-mpls-tunnel-re-routed {
      tailf:ncs-device-type "netconf";
      tailf:display-when "not(../../ncs:module) or ../../ncs:module[ncs:name='Cisco-IOS-XR-snmp-test-trap-act']";
      tailf:action routing-mpls-tunnel-re-routed {
        tailf:actionpoint ncsproxy {
          tailf:internal;
        }
        description
          "Generate MPLS-TE-STD-MIB::mplsTunnelRerouted";
      }
    }
  }
  augment "/ncs:devices/ncs:device-group/ncs:ned-id/ncs:rpc" {
    container rpc-routing-mpls-tunnel-re-routed {
      tailf:ncs-device-type "netconf";
      tailf:display-when "/ncs:devices/ncs:device[ncs:name=current()/../../../ncs:member]/ncs:module[ncs:name='Cisco-IOS-XR-snmp-test-trap-act']";
      tailf:action routing-mpls-tunnel-re-routed {
        tailf:actionpoint ncsproxy {
          tailf:internal;
        }
        description
          "Generate MPLS-TE-STD-MIB::mplsTunnelRerouted";
      }
    }
  }
  augment "/ncs:devices/ncs:device/ncs:rpc" {
    container rpc-routing-mpls-ldp-session-down-entity-id {
      tailf:ncs-device-type "netconf";
      tailf:display-when "not(../../ncs:module) or ../../ncs:module[ncs:name='Cisco-IOS-XR-snmp-test-trap-act']";
      tailf:action routing-mpls-ldp-session-down-entity-id {
        tailf:actionpoint ncsproxy {
          tailf:internal;
        }
        description
          "Generate MPLS-LDP-STD-MIB::mplsLdpSessionDown entity-id";
        input {
          leaf entity-id {
            type string {
              length "23";
            }
            mandatory true;
            description
              "entity ldp-id in x.x.x.x.y.y format where x.x.x.x is the entity IP address and y.y is the label space";
          }
          leaf entity-index {
            type uint32 {
              range "1..4294967295";
            }
            mandatory true;
            description
              "entity index for which to generate the trap";
          }
          leaf peer-id {
            type string {
              length "23";
            }
            mandatory true;
            description
              "peer ldp-id in x.x.x.x.y.y format where x.x.x.x is the entity IP address and y.y is the label space";
          }
        }
      }
    }
  }
  augment "/ncs:devices/ncs:device-group/ncs:ned-id/ncs:rpc" {
    container rpc-routing-mpls-ldp-session-down-entity-id {
      tailf:ncs-device-type "netconf";
      tailf:display-when "/ncs:devices/ncs:device[ncs:name=current()/../../../ncs:member]/ncs:module[ncs:name='Cisco-IOS-XR-snmp-test-trap-act']";
      tailf:action routing-mpls-ldp-session-down-entity-id {
        tailf:actionpoint ncsproxy {
          tailf:internal;
        }
        description
          "Generate MPLS-LDP-STD-MIB::mplsLdpSessionDown entity-id";
        input {
          leaf entity-id {
            type string {
              length "23";
            }
            mandatory true;
            description
              "entity ldp-id in x.x.x.x.y.y format where x.x.x.x is the entity IP address and y.y is the label space";
          }
          leaf entity-index {
            type uint32 {
              range "1..4294967295";
            }
            mandatory true;
            description
              "entity index for which to generate the trap";
          }
          leaf peer-id {
            type string {
              length "23";
            }
            mandatory true;
            description
              "peer ldp-id in x.x.x.x.y.y format where x.x.x.x is the entity IP address and y.y is the label space";
          }
        }
      }
    }
  }
  augment "/ncs:devices/ncs:device/ncs:rpc" {
    container rpc-routing-mpls-ldp-session-down {
      tailf:ncs-device-type "netconf";
      tailf:display-when "not(../../ncs:module) or ../../ncs:module[ncs:name='Cisco-IOS-XR-snmp-test-trap-act']";
      tailf:action routing-mpls-ldp-session-down {
        tailf:actionpoint ncsproxy {
          tailf:internal;
        }
        description
          "Generate MPLS-LDP-STD-MIB::mplsLdpSessionDown";
      }
    }
  }
  augment "/ncs:devices/ncs:device-group/ncs:ned-id/ncs:rpc" {
    container rpc-routing-mpls-ldp-session-down {
      tailf:ncs-device-type "netconf";
      tailf:display-when "/ncs:devices/ncs:device[ncs:name=current()/../../../ncs:member]/ncs:module[ncs:name='Cisco-IOS-XR-snmp-test-trap-act']";
      tailf:action routing-mpls-ldp-session-down {
        tailf:actionpoint ncsproxy {
          tailf:internal;
        }
        description
          "Generate MPLS-LDP-STD-MIB::mplsLdpSessionDown";
      }
    }
  }
  augment "/ncs:devices/ncs:device/ncs:rpc" {
    container rpc-routing-ospf-neighbor-state-change-address {
      tailf:ncs-device-type "netconf";
      tailf:display-when "not(../../ncs:module) or ../../ncs:module[ncs:name='Cisco-IOS-XR-snmp-test-trap-act']";
      tailf:action routing-ospf-neighbor-state-change-address {
        tailf:actionpoint ncsproxy {
          tailf:internal;
        }
        description
          "Generate OSPF-TRAP-MIB::ospfNbrStateChange address";
        input {
          leaf address {
            type inet:ipv4-address-no-zone;
            mandatory true;
            description
              "neighbor's IP source address for which to generate the trap";
          }
          leaf ifindex {
            type uint32 {
              range "0..2147483647";
            }
            mandatory true;
            description
              "0 for interfaces having IP addresses or IF-MIB ifindex of addressless interface";
          }
        }
      }
    }
  }
  augment "/ncs:devices/ncs:device-group/ncs:ned-id/ncs:rpc" {
    container rpc-routing-ospf-neighbor-state-change-address {
      tailf:ncs-device-type "netconf";
      tailf:display-when "/ncs:devices/ncs:device[ncs:name=current()/../../../ncs:member]/ncs:module[ncs:name='Cisco-IOS-XR-snmp-test-trap-act']";
      tailf:action routing-ospf-neighbor-state-change-address {
        tailf:actionpoint ncsproxy {
          tailf:internal;
        }
        description
          "Generate OSPF-TRAP-MIB::ospfNbrStateChange address";
        input {
          leaf address {
            type inet:ipv4-address-no-zone;
            mandatory true;
            description
              "neighbor's IP source address for which to generate the trap";
          }
          leaf ifindex {
            type uint32 {
              range "0..2147483647";
            }
            mandatory true;
            description
              "0 for interfaces having IP addresses or IF-MIB ifindex of addressless interface";
          }
        }
      }
    }
  }
  augment "/ncs:devices/ncs:device/ncs:rpc" {
    container rpc-routing-ospf-neighbor-state-change {
      tailf:ncs-device-type "netconf";
      tailf:display-when "not(../../ncs:module) or ../../ncs:module[ncs:name='Cisco-IOS-XR-snmp-test-trap-act']";
      tailf:action routing-ospf-neighbor-state-change {
        tailf:actionpoint ncsproxy {
          tailf:internal;
        }
        description
          "Generate OSPF-TRAP-MIB::ospfNbrStateChange";
      }
    }
  }
  augment "/ncs:devices/ncs:device-group/ncs:ned-id/ncs:rpc" {
    container rpc-routing-ospf-neighbor-state-change {
      tailf:ncs-device-type "netconf";
      tailf:display-when "/ncs:devices/ncs:device[ncs:name=current()/../../../ncs:member]/ncs:module[ncs:name='Cisco-IOS-XR-snmp-test-trap-act']";
      tailf:action routing-ospf-neighbor-state-change {
        tailf:actionpoint ncsproxy {
          tailf:internal;
        }
        description
          "Generate OSPF-TRAP-MIB::ospfNbrStateChange";
      }
    }
  }
  augment "/ncs:devices/ncs:device/ncs:rpc" {
    container rpc-routing-bgp-state-change-remote-peer {
      tailf:ncs-device-type "netconf";
      tailf:display-when "not(../../ncs:module) or ../../ncs:module[ncs:name='Cisco-IOS-XR-snmp-test-trap-act']";
      tailf:action routing-bgp-state-change-remote-peer {
        tailf:actionpoint ncsproxy {
          tailf:internal;
        }
        description
          "Generate CISCO-BGP-MIB::cbgpBackwardTransition remote peer";
        input {
          leaf address {
            type inet:ipv4-address-no-zone;
            mandatory true;
            description
              "BGP remote peer IP address for which to generate the trap";
          }
        }
      }
    }
  }
  augment "/ncs:devices/ncs:device-group/ncs:ned-id/ncs:rpc" {
    container rpc-routing-bgp-state-change-remote-peer {
      tailf:ncs-device-type "netconf";
      tailf:display-when "/ncs:devices/ncs:device[ncs:name=current()/../../../ncs:member]/ncs:module[ncs:name='Cisco-IOS-XR-snmp-test-trap-act']";
      tailf:action routing-bgp-state-change-remote-peer {
        tailf:actionpoint ncsproxy {
          tailf:internal;
        }
        description
          "Generate CISCO-BGP-MIB::cbgpBackwardTransition remote peer";
        input {
          leaf address {
            type inet:ipv4-address-no-zone;
            mandatory true;
            description
              "BGP remote peer IP address for which to generate the trap";
          }
        }
      }
    }
  }
  augment "/ncs:devices/ncs:device/ncs:rpc" {
    container rpc-routing-bgp-state-change {
      tailf:ncs-device-type "netconf";
      tailf:display-when "not(../../ncs:module) or ../../ncs:module[ncs:name='Cisco-IOS-XR-snmp-test-trap-act']";
      tailf:action routing-bgp-state-change {
        tailf:actionpoint ncsproxy {
          tailf:internal;
        }
        description
          "Generate CISCO-BGP-MIB::cbgpBackwardTransition";
      }
    }
  }
  augment "/ncs:devices/ncs:device-group/ncs:ned-id/ncs:rpc" {
    container rpc-routing-bgp-state-change {
      tailf:ncs-device-type "netconf";
      tailf:display-when "/ncs:devices/ncs:device[ncs:name=current()/../../../ncs:member]/ncs:module[ncs:name='Cisco-IOS-XR-snmp-test-trap-act']";
      tailf:action routing-bgp-state-change {
        tailf:actionpoint ncsproxy {
          tailf:internal;
        }
        description
          "Generate CISCO-BGP-MIB::cbgpBackwardTransition";
      }
    }
  }
  augment "/ncs:devices/ncs:device/ncs:rpc" {
    container rpc-routing-bgp-established-remote-peer {
      tailf:ncs-device-type "netconf";
      tailf:display-when "not(../../ncs:module) or ../../ncs:module[ncs:name='Cisco-IOS-XR-snmp-test-trap-act']";
      tailf:action routing-bgp-established-remote-peer {
        tailf:actionpoint ncsproxy {
          tailf:internal;
        }
        description
          "Generate BGP4-MIB::bglEstablishedNotification remote peer";
        input {
          leaf address {
            type inet:ipv4-address-no-zone;
            mandatory true;
            description
              "BGP remote peer IP address for which to generate the trap";
          }
        }
      }
    }
  }
  augment "/ncs:devices/ncs:device-group/ncs:ned-id/ncs:rpc" {
    container rpc-routing-bgp-established-remote-peer {
      tailf:ncs-device-type "netconf";
      tailf:display-when "/ncs:devices/ncs:device[ncs:name=current()/../../../ncs:member]/ncs:module[ncs:name='Cisco-IOS-XR-snmp-test-trap-act']";
      tailf:action routing-bgp-established-remote-peer {
        tailf:actionpoint ncsproxy {
          tailf:internal;
        }
        description
          "Generate BGP4-MIB::bglEstablishedNotification remote peer";
        input {
          leaf address {
            type inet:ipv4-address-no-zone;
            mandatory true;
            description
              "BGP remote peer IP address for which to generate the trap";
          }
        }
      }
    }
  }
  augment "/ncs:devices/ncs:device/ncs:rpc" {
    container rpc-routing-bgp-established {
      tailf:ncs-device-type "netconf";
      tailf:display-when "not(../../ncs:module) or ../../ncs:module[ncs:name='Cisco-IOS-XR-snmp-test-trap-act']";
      tailf:action routing-bgp-established {
        tailf:actionpoint ncsproxy {
          tailf:internal;
        }
        description
          "Generate BGP4-MIB::bglEstablishedNotification";
      }
    }
  }
  augment "/ncs:devices/ncs:device-group/ncs:ned-id/ncs:rpc" {
    container rpc-routing-bgp-established {
      tailf:ncs-device-type "netconf";
      tailf:display-when "/ncs:devices/ncs:device[ncs:name=current()/../../../ncs:member]/ncs:module[ncs:name='Cisco-IOS-XR-snmp-test-trap-act']";
      tailf:action routing-bgp-established {
        tailf:actionpoint ncsproxy {
          tailf:internal;
        }
        description
          "Generate BGP4-MIB::bglEstablishedNotification";
      }
    }
  }
  augment "/ncs:devices/ncs:device/ncs:rpc" {
    container rpc-platform-hfr-plane-state {
      tailf:ncs-device-type "netconf";
      tailf:display-when "not(../../ncs:module) or ../../ncs:module[ncs:name='Cisco-IOS-XR-snmp-test-trap-act']";
      tailf:action platform-hfr-plane-state {
        tailf:actionpoint ncsproxy {
          tailf:internal;
        }
        description
          "Generate CISCO-FABRIC-HFR-MIB::cfhPlaneStateNotification";
        input {
          leaf plane-id {
            type uint32;
            description
              "plane identifier for which to generate the trap";
          }
        }
      }
    }
  }
  augment "/ncs:devices/ncs:device-group/ncs:ned-id/ncs:rpc" {
    container rpc-platform-hfr-plane-state {
      tailf:ncs-device-type "netconf";
      tailf:display-when "/ncs:devices/ncs:device[ncs:name=current()/../../../ncs:member]/ncs:module[ncs:name='Cisco-IOS-XR-snmp-test-trap-act']";
      tailf:action platform-hfr-plane-state {
        tailf:actionpoint ncsproxy {
          tailf:internal;
        }
        description
          "Generate CISCO-FABRIC-HFR-MIB::cfhPlaneStateNotification";
        input {
          leaf plane-id {
            type uint32;
            description
              "plane identifier for which to generate the trap";
          }
        }
      }
    }
  }
  augment "/ncs:devices/ncs:device/ncs:rpc" {
    container rpc-platform-hfr-bundle-state {
      tailf:ncs-device-type "netconf";
      tailf:display-when "not(../../ncs:module) or ../../ncs:module[ncs:name='Cisco-IOS-XR-snmp-test-trap-act']";
      tailf:action platform-hfr-bundle-state {
        tailf:actionpoint ncsproxy {
          tailf:internal;
        }
        description
          "Generate CISCO-FABRIC-HFR-MIB::cfhBundleStateNotification";
        input {
          leaf bundle-name {
            type string;
            description
              "bundle name for which to generate the trap";
          }
        }
      }
    }
  }
  augment "/ncs:devices/ncs:device-group/ncs:ned-id/ncs:rpc" {
    container rpc-platform-hfr-bundle-state {
      tailf:ncs-device-type "netconf";
      tailf:display-when "/ncs:devices/ncs:device[ncs:name=current()/../../../ncs:member]/ncs:module[ncs:name='Cisco-IOS-XR-snmp-test-trap-act']";
      tailf:action platform-hfr-bundle-state {
        tailf:actionpoint ncsproxy {
          tailf:internal;
        }
        description
          "Generate CISCO-FABRIC-HFR-MIB::cfhBundleStateNotification";
        input {
          leaf bundle-name {
            type string;
            description
              "bundle name for which to generate the trap";
          }
        }
      }
    }
  }
  augment "/ncs:devices/ncs:device/ncs:rpc" {
    container rpc-platform-hfr-bundle-downed-link {
      tailf:ncs-device-type "netconf";
      tailf:display-when "not(../../ncs:module) or ../../ncs:module[ncs:name='Cisco-IOS-XR-snmp-test-trap-act']";
      tailf:action platform-hfr-bundle-downed-link {
        tailf:actionpoint ncsproxy {
          tailf:internal;
        }
        description
          "Generate CISCO-FABRIC-HFR-MIB::cfhBundleDownedLinkNotification";
        input {
          leaf bundle-name {
            type string;
            description
              "bundle name for which to generate the trap";
          }
        }
      }
    }
  }
  augment "/ncs:devices/ncs:device-group/ncs:ned-id/ncs:rpc" {
    container rpc-platform-hfr-bundle-downed-link {
      tailf:ncs-device-type "netconf";
      tailf:display-when "/ncs:devices/ncs:device[ncs:name=current()/../../../ncs:member]/ncs:module[ncs:name='Cisco-IOS-XR-snmp-test-trap-act']";
      tailf:action platform-hfr-bundle-downed-link {
        tailf:actionpoint ncsproxy {
          tailf:internal;
        }
        description
          "Generate CISCO-FABRIC-HFR-MIB::cfhBundleDownedLinkNotification";
        input {
          leaf bundle-name {
            type string;
            description
              "bundle name for which to generate the trap";
          }
        }
      }
    }
  }
  augment "/ncs:devices/ncs:device/ncs:rpc" {
    container rpc-entity-fru-fan-tray-removed {
      tailf:ncs-device-type "netconf";
      tailf:display-when "not(../../ncs:module) or ../../ncs:module[ncs:name='Cisco-IOS-XR-snmp-test-trap-act']";
      tailf:action entity-fru-fan-tray-removed {
        tailf:actionpoint ncsproxy {
          tailf:internal;
        }
        description
          "Generate CISCO-ENTITY-FRU-CONTROL-MIB::cefcFRURemoved";
        input {
          leaf entindex {
            type uint32 {
              range "1..2147483647";
            }
            description
              "entity Physical Index for which to generate trap";
          }
        }
      }
    }
  }
  augment "/ncs:devices/ncs:device-group/ncs:ned-id/ncs:rpc" {
    container rpc-entity-fru-fan-tray-removed {
      tailf:ncs-device-type "netconf";
      tailf:display-when "/ncs:devices/ncs:device[ncs:name=current()/../../../ncs:member]/ncs:module[ncs:name='Cisco-IOS-XR-snmp-test-trap-act']";
      tailf:action entity-fru-fan-tray-removed {
        tailf:actionpoint ncsproxy {
          tailf:internal;
        }
        description
          "Generate CISCO-ENTITY-FRU-CONTROL-MIB::cefcFRURemoved";
        input {
          leaf entindex {
            type uint32 {
              range "1..2147483647";
            }
            description
              "entity Physical Index for which to generate trap";
          }
        }
      }
    }
  }
  augment "/ncs:devices/ncs:device/ncs:rpc" {
    container rpc-entity-fru-fan-tray-inserted {
      tailf:ncs-device-type "netconf";
      tailf:display-when "not(../../ncs:module) or ../../ncs:module[ncs:name='Cisco-IOS-XR-snmp-test-trap-act']";
      tailf:action entity-fru-fan-tray-inserted {
        tailf:actionpoint ncsproxy {
          tailf:internal;
        }
        description
          "Generate CISCO-ENTITY-FRU-CONTROL-MIB::cefcFRUInserted";
        input {
          leaf entindex {
            type uint32 {
              range "1..2147483647";
            }
            description
              "entity Physical Index for which to generate trap";
          }
        }
      }
    }
  }
  augment "/ncs:devices/ncs:device-group/ncs:ned-id/ncs:rpc" {
    container rpc-entity-fru-fan-tray-inserted {
      tailf:ncs-device-type "netconf";
      tailf:display-when "/ncs:devices/ncs:device[ncs:name=current()/../../../ncs:member]/ncs:module[ncs:name='Cisco-IOS-XR-snmp-test-trap-act']";
      tailf:action entity-fru-fan-tray-inserted {
        tailf:actionpoint ncsproxy {
          tailf:internal;
        }
        description
          "Generate CISCO-ENTITY-FRU-CONTROL-MIB::cefcFRUInserted";
        input {
          leaf entindex {
            type uint32 {
              range "1..2147483647";
            }
            description
              "entity Physical Index for which to generate trap";
          }
        }
      }
    }
  }
  augment "/ncs:devices/ncs:device/ncs:rpc" {
    container rpc-entity-fru-fan-tray-oper-status-up {
      tailf:ncs-device-type "netconf";
      tailf:display-when "not(../../ncs:module) or ../../ncs:module[ncs:name='Cisco-IOS-XR-snmp-test-trap-act']";
      tailf:action entity-fru-fan-tray-oper-status-up {
        tailf:actionpoint ncsproxy {
          tailf:internal;
        }
        description
          "Generate CISCO-ENTITY-FRU-CONTROL-MIB::cefcFanTrayStatusChange";
        input {
          leaf entindex {
            type uint32 {
              range "1..2147483647";
            }
            description
              "entity Physical Index for which to generate trap";
          }
        }
      }
    }
  }
  augment "/ncs:devices/ncs:device-group/ncs:ned-id/ncs:rpc" {
    container rpc-entity-fru-fan-tray-oper-status-up {
      tailf:ncs-device-type "netconf";
      tailf:display-when "/ncs:devices/ncs:device[ncs:name=current()/../../../ncs:member]/ncs:module[ncs:name='Cisco-IOS-XR-snmp-test-trap-act']";
      tailf:action entity-fru-fan-tray-oper-status-up {
        tailf:actionpoint ncsproxy {
          tailf:internal;
        }
        description
          "Generate CISCO-ENTITY-FRU-CONTROL-MIB::cefcFanTrayStatusChange";
        input {
          leaf entindex {
            type uint32 {
              range "1..2147483647";
            }
            description
              "entity Physical Index for which to generate trap";
          }
        }
      }
    }
  }
  augment "/ncs:devices/ncs:device/ncs:rpc" {
    container rpc-entity-fru-module-status-change-down {
      tailf:ncs-device-type "netconf";
      tailf:display-when "not(../../ncs:module) or ../../ncs:module[ncs:name='Cisco-IOS-XR-snmp-test-trap-act']";
      tailf:action entity-fru-module-status-change-down {
        tailf:actionpoint ncsproxy {
          tailf:internal;
        }
        description
          "fu trap module status changed as failed";
        input {
          leaf entindex {
            type uint32 {
              range "1..2147483647";
            }
            description
              "entity Physical Index for which to generate trap";
          }
        }
      }
    }
  }
  augment "/ncs:devices/ncs:device-group/ncs:ned-id/ncs:rpc" {
    container rpc-entity-fru-module-status-change-down {
      tailf:ncs-device-type "netconf";
      tailf:display-when "/ncs:devices/ncs:device[ncs:name=current()/../../../ncs:member]/ncs:module[ncs:name='Cisco-IOS-XR-snmp-test-trap-act']";
      tailf:action entity-fru-module-status-change-down {
        tailf:actionpoint ncsproxy {
          tailf:internal;
        }
        description
          "fu trap module status changed as failed";
        input {
          leaf entindex {
            type uint32 {
              range "1..2147483647";
            }
            description
              "entity Physical Index for which to generate trap";
          }
        }
      }
    }
  }
  augment "/ncs:devices/ncs:device/ncs:rpc" {
    container rpc-entity-fru-module-status-change-up {
      tailf:ncs-device-type "netconf";
      tailf:display-when "not(../../ncs:module) or ../../ncs:module[ncs:name='Cisco-IOS-XR-snmp-test-trap-act']";
      tailf:action entity-fru-module-status-change-up {
        tailf:actionpoint ncsproxy {
          tailf:internal;
        }
        description
          "fu trap module status changed as ok";
        input {
          leaf entindex {
            type uint32 {
              range "1..2147483647";
            }
            description
              "entity Physical Index for which to generate trap";
          }
        }
      }
    }
  }
  augment "/ncs:devices/ncs:device-group/ncs:ned-id/ncs:rpc" {
    container rpc-entity-fru-module-status-change-up {
      tailf:ncs-device-type "netconf";
      tailf:display-when "/ncs:devices/ncs:device[ncs:name=current()/../../../ncs:member]/ncs:module[ncs:name='Cisco-IOS-XR-snmp-test-trap-act']";
      tailf:action entity-fru-module-status-change-up {
        tailf:actionpoint ncsproxy {
          tailf:internal;
        }
        description
          "fu trap module status changed as ok";
        input {
          leaf entindex {
            type uint32 {
              range "1..2147483647";
            }
            description
              "entity Physical Index for which to generate trap";
          }
        }
      }
    }
  }
  augment "/ncs:devices/ncs:device/ncs:rpc" {
    container rpc-entity-fru-power-status-change-failed {
      tailf:ncs-device-type "netconf";
      tailf:display-when "not(../../ncs:module) or ../../ncs:module[ncs:name='Cisco-IOS-XR-snmp-test-trap-act']";
      tailf:action entity-fru-power-status-change-failed {
        tailf:actionpoint ncsproxy {
          tailf:internal;
        }
        description
          "oper status changed to failed";
        input {
          leaf entindex {
            type uint32 {
              range "1..2147483647";
            }
            description
              "entity Physical Index for which to generate trap";
          }
        }
      }
    }
  }
  augment "/ncs:devices/ncs:device-group/ncs:ned-id/ncs:rpc" {
    container rpc-entity-fru-power-status-change-failed {
      tailf:ncs-device-type "netconf";
      tailf:display-when "/ncs:devices/ncs:device[ncs:name=current()/../../../ncs:member]/ncs:module[ncs:name='Cisco-IOS-XR-snmp-test-trap-act']";
      tailf:action entity-fru-power-status-change-failed {
        tailf:actionpoint ncsproxy {
          tailf:internal;
        }
        description
          "oper status changed to failed";
        input {
          leaf entindex {
            type uint32 {
              range "1..2147483647";
            }
            description
              "entity Physical Index for which to generate trap";
          }
        }
      }
    }
  }
  augment "/ncs:devices/ncs:device/ncs:rpc" {
    container rpc-entity-sensor-threshold-notification {
      tailf:ncs-device-type "netconf";
      tailf:display-when "not(../../ncs:module) or ../../ncs:module[ncs:name='Cisco-IOS-XR-snmp-test-trap-act']";
      tailf:action entity-sensor-threshold-notification {
        tailf:actionpoint ncsproxy {
          tailf:internal;
        }
        description
          "Generate CISCO-ENTITY-SENSOR-MIB::entSensorThresholdNotification";
        input {
          leaf entindex {
            type uint32 {
              range "1..2147483647";
            }
            description
              "entity Physical Index for which to generate trap";
          }
        }
      }
    }
  }
  augment "/ncs:devices/ncs:device-group/ncs:ned-id/ncs:rpc" {
    container rpc-entity-sensor-threshold-notification {
      tailf:ncs-device-type "netconf";
      tailf:display-when "/ncs:devices/ncs:device[ncs:name=current()/../../../ncs:member]/ncs:module[ncs:name='Cisco-IOS-XR-snmp-test-trap-act']";
      tailf:action entity-sensor-threshold-notification {
        tailf:actionpoint ncsproxy {
          tailf:internal;
        }
        description
          "Generate CISCO-ENTITY-SENSOR-MIB::entSensorThresholdNotification";
        input {
          leaf entindex {
            type uint32 {
              range "1..2147483647";
            }
            description
              "entity Physical Index for which to generate trap";
          }
        }
      }
    }
  }
  augment "/ncs:devices/ncs:device/ncs:rpc" {
    container rpc-infra-config-event {
      tailf:ncs-device-type "netconf";
      tailf:display-when "not(../../ncs:module) or ../../ncs:module[ncs:name='Cisco-IOS-XR-snmp-test-trap-act']";
      tailf:action infra-config-event {
        tailf:actionpoint ncsproxy {
          tailf:internal;
        }
        description
          "Generate CISCO-CONFIG-MAN-MIB::ciscoConfigManEvent";
      }
    }
  }
  augment "/ncs:devices/ncs:device-group/ncs:ned-id/ncs:rpc" {
    container rpc-infra-config-event {
      tailf:ncs-device-type "netconf";
      tailf:display-when "/ncs:devices/ncs:device[ncs:name=current()/../../../ncs:member]/ncs:module[ncs:name='Cisco-IOS-XR-snmp-test-trap-act']";
      tailf:action infra-config-event {
        tailf:actionpoint ncsproxy {
          tailf:internal;
        }
        description
          "Generate CISCO-CONFIG-MAN-MIB::ciscoConfigManEvent";
      }
    }
  }
  augment "/ncs:devices/ncs:device/ncs:rpc" {
    container rpc-infra-bridge-topology-change {
      tailf:ncs-device-type "netconf";
      tailf:display-when "not(../../ncs:module) or ../../ncs:module[ncs:name='Cisco-IOS-XR-snmp-test-trap-act']";
      tailf:action infra-bridge-topology-change {
        tailf:actionpoint ncsproxy {
          tailf:internal;
        }
        description
          "Generate BRIDGE-MIB::topologyChange";
      }
    }
  }
  augment "/ncs:devices/ncs:device-group/ncs:ned-id/ncs:rpc" {
    container rpc-infra-bridge-topology-change {
      tailf:ncs-device-type "netconf";
      tailf:display-when "/ncs:devices/ncs:device[ncs:name=current()/../../../ncs:member]/ncs:module[ncs:name='Cisco-IOS-XR-snmp-test-trap-act']";
      tailf:action infra-bridge-topology-change {
        tailf:actionpoint ncsproxy {
          tailf:internal;
        }
        description
          "Generate BRIDGE-MIB::topologyChange";
      }
    }
  }
  augment "/ncs:devices/ncs:device/ncs:rpc" {
    container rpc-infra-bridge-new-root {
      tailf:ncs-device-type "netconf";
      tailf:display-when "not(../../ncs:module) or ../../ncs:module[ncs:name='Cisco-IOS-XR-snmp-test-trap-act']";
      tailf:action infra-bridge-new-root {
        tailf:actionpoint ncsproxy {
          tailf:internal;
        }
        description
          "Generate BRIDGE-MIB::newRoot";
      }
    }
  }
  augment "/ncs:devices/ncs:device-group/ncs:ned-id/ncs:rpc" {
    container rpc-infra-bridge-new-root {
      tailf:ncs-device-type "netconf";
      tailf:display-when "/ncs:devices/ncs:device[ncs:name=current()/../../../ncs:member]/ncs:module[ncs:name='Cisco-IOS-XR-snmp-test-trap-act']";
      tailf:action infra-bridge-new-root {
        tailf:actionpoint ncsproxy {
          tailf:internal;
        }
        description
          "Generate BRIDGE-MIB::newRoot";
      }
    }
  }
  augment "/ncs:devices/ncs:device/ncs:rpc" {
    container rpc-infra-redundancy-switch {
      tailf:ncs-device-type "netconf";
      tailf:display-when "not(../../ncs:module) or ../../ncs:module[ncs:name='Cisco-IOS-XR-snmp-test-trap-act']";
      tailf:action infra-redundancy-switch {
        tailf:actionpoint ncsproxy {
          tailf:internal;
        }
        description
          "Generate CISCO-RF-MIB::ciscoRFSwactNotif";
      }
    }
  }
  augment "/ncs:devices/ncs:device-group/ncs:ned-id/ncs:rpc" {
    container rpc-infra-redundancy-switch {
      tailf:ncs-device-type "netconf";
      tailf:display-when "/ncs:devices/ncs:device[ncs:name=current()/../../../ncs:member]/ncs:module[ncs:name='Cisco-IOS-XR-snmp-test-trap-act']";
      tailf:action infra-redundancy-switch {
        tailf:actionpoint ncsproxy {
          tailf:internal;
        }
        description
          "Generate CISCO-RF-MIB::ciscoRFSwactNotif";
      }
    }
  }
  augment "/ncs:devices/ncs:device/ncs:rpc" {
    container rpc-infra-redundancy-progression {
      tailf:ncs-device-type "netconf";
      tailf:display-when "not(../../ncs:module) or ../../ncs:module[ncs:name='Cisco-IOS-XR-snmp-test-trap-act']";
      tailf:action infra-redundancy-progression {
        tailf:actionpoint ncsproxy {
          tailf:internal;
        }
        description
          "Generate CISCO-RF-MIB::ciscoRFProgressionNotif";
      }
    }
  }
  augment "/ncs:devices/ncs:device-group/ncs:ned-id/ncs:rpc" {
    container rpc-infra-redundancy-progression {
      tailf:ncs-device-type "netconf";
      tailf:display-when "/ncs:devices/ncs:device[ncs:name=current()/../../../ncs:member]/ncs:module[ncs:name='Cisco-IOS-XR-snmp-test-trap-act']";
      tailf:action infra-redundancy-progression {
        tailf:actionpoint ncsproxy {
          tailf:internal;
        }
        description
          "Generate CISCO-RF-MIB::ciscoRFProgressionNotif";
      }
    }
  }
  augment "/ncs:devices/ncs:device/ncs:rpc" {
    container rpc-infra-flash-device-removed {
      tailf:ncs-device-type "netconf";
      tailf:display-when "not(../../ncs:module) or ../../ncs:module[ncs:name='Cisco-IOS-XR-snmp-test-trap-act']";
      tailf:action infra-flash-device-removed {
        tailf:actionpoint ncsproxy {
          tailf:internal;
        }
        description
          "Generate CISCO-FLASH-MIB::ciscoFlashDeviceRemovedNotif";
      }
    }
  }
  augment "/ncs:devices/ncs:device-group/ncs:ned-id/ncs:rpc" {
    container rpc-infra-flash-device-removed {
      tailf:ncs-device-type "netconf";
      tailf:display-when "/ncs:devices/ncs:device[ncs:name=current()/../../../ncs:member]/ncs:module[ncs:name='Cisco-IOS-XR-snmp-test-trap-act']";
      tailf:action infra-flash-device-removed {
        tailf:actionpoint ncsproxy {
          tailf:internal;
        }
        description
          "Generate CISCO-FLASH-MIB::ciscoFlashDeviceRemovedNotif";
      }
    }
  }
  augment "/ncs:devices/ncs:device/ncs:rpc" {
    container rpc-infra-flash-device-inserted {
      tailf:ncs-device-type "netconf";
      tailf:display-when "not(../../ncs:module) or ../../ncs:module[ncs:name='Cisco-IOS-XR-snmp-test-trap-act']";
      tailf:action infra-flash-device-inserted {
        tailf:actionpoint ncsproxy {
          tailf:internal;
        }
        description
          "Generate CISCO-FLASH-MIB::ciscoFlashDeviceInsertedNotif";
      }
    }
  }
  augment "/ncs:devices/ncs:device-group/ncs:ned-id/ncs:rpc" {
    container rpc-infra-flash-device-inserted {
      tailf:ncs-device-type "netconf";
      tailf:display-when "/ncs:devices/ncs:device[ncs:name=current()/../../../ncs:member]/ncs:module[ncs:name='Cisco-IOS-XR-snmp-test-trap-act']";
      tailf:action infra-flash-device-inserted {
        tailf:actionpoint ncsproxy {
          tailf:internal;
        }
        description
          "Generate CISCO-FLASH-MIB::ciscoFlashDeviceInsertedNotif";
      }
    }
  }
  augment "/ncs:devices/ncs:device/ncs:rpc" {
    container rpc-infra-syslog-message-generated {
      tailf:ncs-device-type "netconf";
      tailf:display-when "not(../../ncs:module) or ../../ncs:module[ncs:name='Cisco-IOS-XR-snmp-test-trap-act']";
      tailf:action infra-syslog-message-generated {
        tailf:actionpoint ncsproxy {
          tailf:internal;
        }
        description
          "Generate CISCO-SYSLOG-MIB::clogMessageGenerated";
      }
    }
  }
  augment "/ncs:devices/ncs:device-group/ncs:ned-id/ncs:rpc" {
    container rpc-infra-syslog-message-generated {
      tailf:ncs-device-type "netconf";
      tailf:display-when "/ncs:devices/ncs:device[ncs:name=current()/../../../ncs:member]/ncs:module[ncs:name='Cisco-IOS-XR-snmp-test-trap-act']";
      tailf:action infra-syslog-message-generated {
        tailf:actionpoint ncsproxy {
          tailf:internal;
        }
        description
          "Generate CISCO-SYSLOG-MIB::clogMessageGenerated";
      }
    }
  }
  augment "/ncs:devices/ncs:device/ncs:rpc" {
    container rpc-sonet-path-status {
      tailf:ncs-device-type "netconf";
      tailf:display-when "not(../../ncs:module) or ../../ncs:module[ncs:name='Cisco-IOS-XR-snmp-test-trap-act']";
      tailf:action sonet-path-status {
        tailf:actionpoint ncsproxy {
          tailf:internal;
        }
        description
          "Generate CISCO-SONET-MIB::ciscoSonetPathStatusChange";
        input {
          leaf ifindex {
            type uint32 {
              range "1..2147483647";
            }
            description
              "interface index for which to generate ciscoSonetPathStatusChange trap";
          }
        }
      }
    }
  }
  augment "/ncs:devices/ncs:device-group/ncs:ned-id/ncs:rpc" {
    container rpc-sonet-path-status {
      tailf:ncs-device-type "netconf";
      tailf:display-when "/ncs:devices/ncs:device[ncs:name=current()/../../../ncs:member]/ncs:module[ncs:name='Cisco-IOS-XR-snmp-test-trap-act']";
      tailf:action sonet-path-status {
        tailf:actionpoint ncsproxy {
          tailf:internal;
        }
        description
          "Generate CISCO-SONET-MIB::ciscoSonetPathStatusChange";
        input {
          leaf ifindex {
            type uint32 {
              range "1..2147483647";
            }
            description
              "interface index for which to generate ciscoSonetPathStatusChange trap";
          }
        }
      }
    }
  }
  augment "/ncs:devices/ncs:device/ncs:rpc" {
    container rpc-sonet-line-status {
      tailf:ncs-device-type "netconf";
      tailf:display-when "not(../../ncs:module) or ../../ncs:module[ncs:name='Cisco-IOS-XR-snmp-test-trap-act']";
      tailf:action sonet-line-status {
        tailf:actionpoint ncsproxy {
          tailf:internal;
        }
        description
          "Generate CISCO-SONET-MIB::ciscoSonetLineStatusChange";
        input {
          leaf ifindex {
            type uint32 {
              range "1..2147483647";
            }
            description
              "interface index for which to generate ciscoSonetLineStatusChange trap";
          }
        }
      }
    }
  }
  augment "/ncs:devices/ncs:device-group/ncs:ned-id/ncs:rpc" {
    container rpc-sonet-line-status {
      tailf:ncs-device-type "netconf";
      tailf:display-when "/ncs:devices/ncs:device[ncs:name=current()/../../../ncs:member]/ncs:module[ncs:name='Cisco-IOS-XR-snmp-test-trap-act']";
      tailf:action sonet-line-status {
        tailf:actionpoint ncsproxy {
          tailf:internal;
        }
        description
          "Generate CISCO-SONET-MIB::ciscoSonetLineStatusChange";
        input {
          leaf ifindex {
            type uint32 {
              range "1..2147483647";
            }
            description
              "interface index for which to generate ciscoSonetLineStatusChange trap";
          }
        }
      }
    }
  }
  augment "/ncs:devices/ncs:device/ncs:rpc" {
    container rpc-sonet-section-status {
      tailf:ncs-device-type "netconf";
      tailf:display-when "not(../../ncs:module) or ../../ncs:module[ncs:name='Cisco-IOS-XR-snmp-test-trap-act']";
      tailf:action sonet-section-status {
        tailf:actionpoint ncsproxy {
          tailf:internal;
        }
        description
          "Generate CISCO-SONET-MIB::ciscoSonetSectionStatusChange";
        input {
          leaf ifindex {
            type uint32 {
              range "1..2147483647";
            }
            description
              "interface index for which to generate ciscoSonetSectionStatusChange trap";
          }
        }
      }
    }
  }
  augment "/ncs:devices/ncs:device-group/ncs:ned-id/ncs:rpc" {
    container rpc-sonet-section-status {
      tailf:ncs-device-type "netconf";
      tailf:display-when "/ncs:devices/ncs:device[ncs:name=current()/../../../ncs:member]/ncs:module[ncs:name='Cisco-IOS-XR-snmp-test-trap-act']";
      tailf:action sonet-section-status {
        tailf:actionpoint ncsproxy {
          tailf:internal;
        }
        description
          "Generate CISCO-SONET-MIB::ciscoSonetSectionStatusChange";
        input {
          leaf ifindex {
            type uint32 {
              range "1..2147483647";
            }
            description
              "interface index for which to generate ciscoSonetSectionStatusChange trap";
          }
        }
      }
    }
  }
  augment "/ncs:devices/ncs:device/ncs:rpc" {
    container rpc-interface-link-down {
      tailf:ncs-device-type "netconf";
      tailf:display-when "not(../../ncs:module) or ../../ncs:module[ncs:name='Cisco-IOS-XR-snmp-test-trap-act']";
      tailf:action interface-link-down {
        tailf:actionpoint ncsproxy {
          tailf:internal;
        }
        description
          "Generate IF-MIB::linkDown";
        input {
          leaf ifindex {
            type uint32 {
              range "1..2147483647";
            }
            description
              "interface index for which to generate LinkDown trap";
          }
        }
      }
    }
  }
  augment "/ncs:devices/ncs:device-group/ncs:ned-id/ncs:rpc" {
    container rpc-interface-link-down {
      tailf:ncs-device-type "netconf";
      tailf:display-when "/ncs:devices/ncs:device[ncs:name=current()/../../../ncs:member]/ncs:module[ncs:name='Cisco-IOS-XR-snmp-test-trap-act']";
      tailf:action interface-link-down {
        tailf:actionpoint ncsproxy {
          tailf:internal;
        }
        description
          "Generate IF-MIB::linkDown";
        input {
          leaf ifindex {
            type uint32 {
              range "1..2147483647";
            }
            description
              "interface index for which to generate LinkDown trap";
          }
        }
      }
    }
  }
  augment "/ncs:devices/ncs:device/ncs:rpc" {
    container rpc-interface-link-up {
      tailf:ncs-device-type "netconf";
      tailf:display-when "not(../../ncs:module) or ../../ncs:module[ncs:name='Cisco-IOS-XR-snmp-test-trap-act']";
      tailf:action interface-link-up {
        tailf:actionpoint ncsproxy {
          tailf:internal;
        }
        description
          "Generate IF-MIB::linkUp";
        input {
          leaf ifindex {
            type uint32 {
              range "1..2147483647";
            }
            description
              "interface index for which to generate LinkUp trap";
          }
        }
      }
    }
  }
  augment "/ncs:devices/ncs:device-group/ncs:ned-id/ncs:rpc" {
    container rpc-interface-link-up {
      tailf:ncs-device-type "netconf";
      tailf:display-when "/ncs:devices/ncs:device[ncs:name=current()/../../../ncs:member]/ncs:module[ncs:name='Cisco-IOS-XR-snmp-test-trap-act']";
      tailf:action interface-link-up {
        tailf:actionpoint ncsproxy {
          tailf:internal;
        }
        description
          "Generate IF-MIB::linkUp";
        input {
          leaf ifindex {
            type uint32 {
              range "1..2147483647";
            }
            description
              "interface index for which to generate LinkUp trap";
          }
        }
      }
    }
  }
  augment "/ncs:devices/ncs:device/ncs:rpc" {
    container rpc-snmp-warm-start {
      tailf:ncs-device-type "netconf";
      tailf:display-when "not(../../ncs:module) or ../../ncs:module[ncs:name='Cisco-IOS-XR-snmp-test-trap-act']";
      tailf:action snmp-warm-start {
        tailf:actionpoint ncsproxy {
          tailf:internal;
        }
        description
          "Generate SNMPv2-MIB::warmStart";
      }
    }
  }
  augment "/ncs:devices/ncs:device-group/ncs:ned-id/ncs:rpc" {
    container rpc-snmp-warm-start {
      tailf:ncs-device-type "netconf";
      tailf:display-when "/ncs:devices/ncs:device[ncs:name=current()/../../../ncs:member]/ncs:module[ncs:name='Cisco-IOS-XR-snmp-test-trap-act']";
      tailf:action snmp-warm-start {
        tailf:actionpoint ncsproxy {
          tailf:internal;
        }
        description
          "Generate SNMPv2-MIB::warmStart";
      }
    }
  }
  augment "/ncs:devices/ncs:device/ncs:rpc" {
    container rpc-snmp-cold-start {
      tailf:ncs-device-type "netconf";
      tailf:display-when "not(../../ncs:module) or ../../ncs:module[ncs:name='Cisco-IOS-XR-snmp-test-trap-act']";
      tailf:action snmp-cold-start {
        tailf:actionpoint ncsproxy {
          tailf:internal;
        }
        description
          "Generate SNMPv2-MIB::coldStart";
      }
    }
  }
  augment "/ncs:devices/ncs:device-group/ncs:ned-id/ncs:rpc" {
    container rpc-snmp-cold-start {
      tailf:ncs-device-type "netconf";
      tailf:display-when "/ncs:devices/ncs:device[ncs:name=current()/../../../ncs:member]/ncs:module[ncs:name='Cisco-IOS-XR-snmp-test-trap-act']";
      tailf:action snmp-cold-start {
        tailf:actionpoint ncsproxy {
          tailf:internal;
        }
        description
          "Generate SNMPv2-MIB::coldStart";
      }
    }
  }
}

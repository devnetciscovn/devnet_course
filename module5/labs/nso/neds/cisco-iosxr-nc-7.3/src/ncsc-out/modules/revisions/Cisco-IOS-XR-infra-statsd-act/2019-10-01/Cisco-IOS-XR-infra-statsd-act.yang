module Cisco-IOS-XR-infra-statsd-act {
  // Generated by yanger -t ncs
  tailf:mount-id "cisco-iosxr-nc-7.3:cisco-iosxr-nc-7.3";
  tailf:ncs-device-type "netconf";

  namespace "http://cisco.com/ns/yang/Cisco-IOS-XR-infra-statsd-act";
  prefix statsd-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2019 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2018-01-10 {
    description
      "IOS XR 6.4.1 revision.";
  }

  augment "/ncs:devices/ncs:device/ncs:rpc" {
    container rpc-clear-counters-interface {
      tailf:ncs-device-type "netconf";
      tailf:display-when "not(../../ncs:module) or ../../ncs:module[ncs:name='Cisco-IOS-XR-infra-statsd-act']";
      tailf:action clear-counters-interface {
        tailf:actionpoint ncsproxy {
          tailf:internal;
        }
        description
          "Clear counters for interface.
          ";
        input {
          leaf interface-name {
            type csc:ncs_rpc_notif_Interface-name;
            mandatory true;
            description
              "Interface name";
          }
        }
        csc:xr-task "interface";
        csc:cli-command "clear counters interface <interface-name>";
      }
    }
  }
  augment "/ncs:devices/ncs:device-group/ncs:ned-id/ncs:rpc" {
    container rpc-clear-counters-interface {
      tailf:ncs-device-type "netconf";
      tailf:display-when "/ncs:devices/ncs:device[ncs:name=current()/../../../ncs:member]/ncs:module[ncs:name='Cisco-IOS-XR-infra-statsd-act']";
      tailf:action clear-counters-interface {
        tailf:actionpoint ncsproxy {
          tailf:internal;
        }
        description
          "Clear counters for interface.
          ";
        input {
          leaf interface-name {
            type csc:ncs_rpc_notif_Interface-name;
            mandatory true;
            description
              "Interface name";
          }
        }
        csc:xr-task "interface";
        csc:cli-command "clear counters interface <interface-name>";
      }
    }
  }
  augment "/ncs:devices/ncs:device/ncs:rpc" {
    container rpc-clear-counters-all {
      tailf:ncs-device-type "netconf";
      tailf:display-when "not(../../ncs:module) or ../../ncs:module[ncs:name='Cisco-IOS-XR-infra-statsd-act']";
      tailf:action clear-counters-all {
        tailf:actionpoint ncsproxy {
          tailf:internal;
        }
        description
          "Clear counters on all interfaces.
          ";
        csc:xr-task "interface";
        csc:cli-command "clear counters all";
      }
    }
  }
  augment "/ncs:devices/ncs:device-group/ncs:ned-id/ncs:rpc" {
    container rpc-clear-counters-all {
      tailf:ncs-device-type "netconf";
      tailf:display-when "/ncs:devices/ncs:device[ncs:name=current()/../../../ncs:member]/ncs:module[ncs:name='Cisco-IOS-XR-infra-statsd-act']";
      tailf:action clear-counters-all {
        tailf:actionpoint ncsproxy {
          tailf:internal;
        }
        description
          "Clear counters on all interfaces.
          ";
        csc:xr-task "interface";
        csc:cli-command "clear counters all";
      }
    }
  }
  augment "/ncs:devices/ncs:device/ncs:rpc" {
    container rpc-clear-counters-controller {
      tailf:ncs-device-type "netconf";
      tailf:display-when "not(../../ncs:module) or ../../ncs:module[ncs:name='Cisco-IOS-XR-infra-statsd-act']";
      tailf:action clear-counters-controller {
        tailf:actionpoint ncsproxy {
          tailf:internal;
        }
        description
          "Controller name.
          ";
        input {
          leaf controller-name {
            type csc:ncs_rpc_notif_Interface-name;
            mandatory true;
            description
              "Controller name";
          }
        }
        csc:xr-task "interface";
        csc:cli-command "clear counters <controller-name>";
      }
    }
  }
  augment "/ncs:devices/ncs:device-group/ncs:ned-id/ncs:rpc" {
    container rpc-clear-counters-controller {
      tailf:ncs-device-type "netconf";
      tailf:display-when "/ncs:devices/ncs:device[ncs:name=current()/../../../ncs:member]/ncs:module[ncs:name='Cisco-IOS-XR-infra-statsd-act']";
      tailf:action clear-counters-controller {
        tailf:actionpoint ncsproxy {
          tailf:internal;
        }
        description
          "Controller name.
          ";
        input {
          leaf controller-name {
            type csc:ncs_rpc_notif_Interface-name;
            mandatory true;
            description
              "Controller name";
          }
        }
        csc:xr-task "interface";
        csc:cli-command "clear counters <controller-name>";
      }
    }
  }
}

module Cisco-IOS-XR-sysadmin-ethsw-esdma-serdes {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-serdes";
  prefix esdma_serdes;

  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch serdes' commands.

     Copyright (c) 2011-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2016-07-06 {
    description
      "Initial revision with content extracted from esdma_cli.yang.";
  }

  grouping ncs_template_switch-serdes-group {
    container serdes {
      container serdes-statistics {
        list location {
          // NCS patched for predictable order
          ordered-by user;
          key "rack card switch-id";
          leaf rack {
            type esdma_types:ncs_template_esdma-rack-num-enum;
          }
          leaf card {
            type esdma_types:ncs_template_esdma-cpu;
            description
              "Card to list the switch Serdes information for";
          }
          leaf switch-id {
            type esdma_types:ncs_template_esdma-switch-type-enum;
            description
              "Switch type";
          }
          list port-iter {
            // NCS patched for predictable order
            ordered-by user;
            key "port";
            leaf port {
              type esdma_types:ncs_template_esdma-switch-port-type;
              description
                "Switch port";
            }
            list serdes-entry {
              // NCS patched for predictable order
              ordered-by user;
              key "id";
              leaf id {
                type string;
              }
              leaf base-reg {
                type string;
              }
              leaf desc {
                type string;
              }
              leaf lane-0 {
                type string;
              }
              leaf lane-1 {
                type string;
              }
              leaf lane-2 {
                type string;
              }
              leaf lane-3 {
                type string;
              }
            }
          }
        }
      }
    }
  }

  grouping ncs_rpc_notif_switch-serdes-group {
    container serdes {
      container serdes-statistics {
        list location {
          key "rack card switch-id";
          leaf rack {
            type esdma_types:ncs_rpc_notif_esdma-rack-num-enum;
          }
          leaf card {
            type esdma_types:ncs_rpc_notif_esdma-cpu;
            description
              "Card to list the switch Serdes information for";
          }
          leaf switch-id {
            type esdma_types:ncs_rpc_notif_esdma-switch-type-enum;
            description
              "Switch type";
          }
          list port-iter {
            key "port";
            leaf port {
              type esdma_types:ncs_rpc_notif_esdma-switch-port-type;
              description
                "Switch port";
            }
            list serdes-entry {
              key "id";
              leaf id {
                type uint32;
              }
              leaf base-reg {
                type string;
              }
              leaf desc {
                type string;
              }
              leaf lane-0 {
                type string;
              }
              leaf lane-1 {
                type string;
              }
              leaf lane-2 {
                type string;
              }
              leaf lane-3 {
                type string;
              }
            }
          }
        }
      }
    }
  }

  grouping live_ncs_switch-serdes-group {
    container serdes {
      container serdes-statistics {
        list location {
          key "rack card switch-id";
          leaf rack {
            type esdma_types:live_ncs_esdma-rack-num-enum;
          }
          leaf card {
            type esdma_types:live_ncs_esdma-cpu;
            description
              "Card to list the switch Serdes information for";
          }
          leaf switch-id {
            type esdma_types:live_ncs_esdma-switch-type-enum;
            description
              "Switch type";
          }
          list port-iter {
            key "port";
            leaf port {
              type esdma_types:live_ncs_esdma-switch-port-type;
              description
                "Switch port";
            }
            list serdes-entry {
              key "id";
              leaf id {
                type uint32;
              }
              leaf base-reg {
                type string;
              }
              leaf desc {
                type string;
              }
              leaf lane-0 {
                type string;
              }
              leaf lane-1 {
                type string;
              }
              leaf lane-2 {
                type string;
              }
              leaf lane-3 {
                type string;
              }
            }
          }
        }
      }
    }
  }

  grouping switch-serdes-group {
    container serdes {
      container serdes-statistics {
        list location {
          key "rack card switch-id";
          leaf rack {
            type esdma_types:esdma-rack-num-enum;
          }
          leaf card {
            type esdma_types:esdma-cpu;
            description
              "Card to list the switch Serdes information for";
          }
          leaf switch-id {
            type esdma_types:esdma-switch-type-enum;
            description
              "Switch type";
          }
          list port-iter {
            key "port";
            leaf port {
              type esdma_types:esdma-switch-port-type;
              description
                "Switch port";
            }
            list serdes-entry {
              key "id";
              leaf id {
                type uint32;
              }
              leaf base-reg {
                type string;
              }
              leaf desc {
                type string;
              }
              leaf lane-0 {
                type string;
              }
              leaf lane-1 {
                type string;
              }
              leaf lane-2 {
                type string;
              }
              leaf lane-3 {
                type string;
              }
            }
          }
        }
      }
    }
  }
}

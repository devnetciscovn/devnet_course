module Cisco-IOS-XR-kim-tpa-cfg {
  // Generated by yanger -t ncs
  tailf:mount-id "cisco-iosxr-nc-7.3:cisco-iosxr-nc-7.3";
  tailf:ncs-device-type "netconf";

  namespace "http://cisco.com/ns/yang/Cisco-IOS-XR-kim-tpa-cfg";
  prefix kim-tpa-cfg;

  import Cisco-IOS-XR-types {
    prefix xr;
  }
  import cisco-semver {
    prefix semver;
  }
  import ietf-inet-types {
    prefix inet;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR kim-tpa package configuration.

     This module contains definitions
     for the following management objects:
       tpa: tpa configuration commands

     Copyright (c) 2013-2019 by Cisco Systems, Inc.
     All rights reserved.";

  revision 2019-12-17 {
    description
      "Option to disable stats synchronization added.";
    semver:module-version "1.1.0";
  }
  revision 2019-04-05 {
    description
      "Establish semantic version baseline.";
    semver:module-version "1.0.0";
  }
  revision 2018-07-27 {
    description
      "Added support for protection configuration";
  }
  revision 2017-09-07 {
    description
      "Fixed type translation error.";
  }
  revision 2015-11-09 {
    description
      "IOS XR 6.0 revision.";
  }

  typedef ncs_template_Ip-protocol {
    type string;
    description
      "Ip protocol";
  }

  typedef ncs_rpc_notif_Ip-protocol {
    type enumeration {
      enum "tcp" {
        value 6;
        description
          "Transmission Control Protocol, RFC 793";
      }
      enum "udp" {
        value 17;
        description
          "User Datagram Protocol, RFC 768";
      }
    }
    description
      "Ip protocol";
  }

  typedef live_ncs_Ip-protocol {
    type enumeration {
      enum "tcp" {
        value 6;
        description
          "Transmission Control Protocol, RFC 793";
      }
      enum "udp" {
        value 17;
        description
          "User Datagram Protocol, RFC 768";
      }
    }
    description
      "Ip protocol";
  }

  typedef Ip-protocol {
    type enumeration {
      enum "tcp" {
        value 6;
        description
          "Transmission Control Protocol, RFC 793";
      }
      enum "udp" {
        value 17;
        description
          "User Datagram Protocol, RFC 768";
      }
    }
    description
      "Ip protocol";
  }

  grouping ncs_template_UPDATE-SOURCE {
    description
      "Common node of ipv4, ipv6";
    container update-source {
      description
        "Interface used for Source Address";
      leaf interface-name {
        type xr:ncs_template_Interface-name;
        // NCS drop must statement
        description
          "Interface name for source address";
      }
      leaf active-management {
        type empty;
        // NCS drop must statement
        description
          "Use the management port on the Active RP";
      }
    }
  }

  grouping ncs_template_PROTECTION {
    description
      "Common node of ipv4, ipv6";
    container allow-entries {
      description
        "Traffic protection configuration";
      list allow-entry {
        // NCS patched for predictable order
        ordered-by user;
        key "protocol local-port";
        description
          "Allow traffic matching a filter";
        leaf protocol {
          type ncs_template_Ip-protocol;
          description
            "L4 protocol";
        }
        leaf local-port {
          type xr:ncs_template_Cisco-ios-xr-port-number;
          description
            "Local port";
        }
      }
      list allow-entry-local-address {
        // NCS patched for predictable order
        ordered-by user;
        key "local-address protocol local-port";
        description
          "Allow traffic matching a filter";
        leaf local-address {
          type string;
          description
            "local prefix/length";
        }
        leaf protocol {
          type ncs_template_Ip-protocol;
          description
            "L4 protocol";
        }
        leaf local-port {
          type xr:ncs_template_Cisco-ios-xr-port-number;
          description
            "Local port";
        }
      }
      list allow-entry-remote-address {
        // NCS patched for predictable order
        ordered-by user;
        key "remote-address protocol local-port";
        description
          "Allow traffic matching a filter";
        leaf remote-address {
          type string;
          description
            "remote prefix/length";
        }
        leaf protocol {
          type ncs_template_Ip-protocol;
          description
            "L4 protocol";
        }
        leaf local-port {
          type xr:ncs_template_Cisco-ios-xr-port-number;
          description
            "Local port";
        }
      }
      list allow-entry-local-address-remote-address {
        // NCS patched for predictable order
        ordered-by user;
        key "local-address remote-address protocol local-port";
        description
          "Allow traffic matching a filter";
        leaf local-address {
          type string;
          description
            "local prefix/length";
        }
        leaf remote-address {
          type string;
          description
            "remote prefix/length";
        }
        leaf protocol {
          type ncs_template_Ip-protocol;
          description
            "L4 protocol";
        }
        leaf local-port {
          type xr:ncs_template_Cisco-ios-xr-port-number;
          description
            "Local port";
        }
      }
      list allow-entry-interface-name {
        // NCS patched for predictable order
        ordered-by user;
        key "interface-name protocol local-port";
        description
          "Allow traffic matching a filter";
        leaf interface-name {
          type xr:ncs_template_Interface-name;
          description
            "Interface name";
        }
        leaf protocol {
          type ncs_template_Ip-protocol;
          description
            "L4 protocol";
        }
        leaf local-port {
          type xr:ncs_template_Cisco-ios-xr-port-number;
          description
            "Local port";
        }
      }
      list allow-entry-local-address-interface-name {
        // NCS patched for predictable order
        ordered-by user;
        key "local-address interface-name protocol local-port";
        description
          "Allow traffic matching a filter";
        leaf local-address {
          type string;
          description
            "local prefix/length";
        }
        leaf interface-name {
          type xr:ncs_template_Interface-name;
          description
            "Interface name";
        }
        leaf protocol {
          type ncs_template_Ip-protocol;
          description
            "L4 protocol";
        }
        leaf local-port {
          type xr:ncs_template_Cisco-ios-xr-port-number;
          description
            "Local port";
        }
      }
      list allow-entry-remote-address-interface-name {
        // NCS patched for predictable order
        ordered-by user;
        key "remote-address interface-name protocol local-port";
        description
          "Allow traffic matching a filter";
        leaf remote-address {
          type string;
          description
            "remote prefix/length";
        }
        leaf interface-name {
          type xr:ncs_template_Interface-name;
          description
            "Interface name";
        }
        leaf protocol {
          type ncs_template_Ip-protocol;
          description
            "L4 protocol";
        }
        leaf local-port {
          type xr:ncs_template_Cisco-ios-xr-port-number;
          description
            "Local port";
        }
      }
      list allow-entry-local-address-remote-address-interface-name {
        // NCS patched for predictable order
        ordered-by user;
        key "local-address remote-address interface-name protocol local-port";
        description
          "Allow traffic matching a filter";
        leaf local-address {
          type string;
          description
            "local prefix/length";
        }
        leaf remote-address {
          type string;
          description
            "remote prefix/length";
        }
        leaf interface-name {
          type xr:ncs_template_Interface-name;
          description
            "Interface name";
        }
        leaf protocol {
          type ncs_template_Ip-protocol;
          description
            "L4 protocol";
        }
        leaf local-port {
          type xr:ncs_template_Cisco-ios-xr-port-number;
          description
            "Local port";
        }
      }
    }
  }

  grouping ncs_template_DEFAULT-ROUTE {
    description
      "Common node of ipv4, ipv6";
    leaf default-route {
      type string;
      description
        "Default interface used for routing";
    }
  }

  grouping ncs_template_EGRESS-UPDATE-SOURCE {
    description
      "Common node of ipv4, ipv6";
    container interface-names {
      description
        "Interface used for source address for egress
         interface";
      list interface-name {
        // NCS patched for predictable order
        ordered-by user;
        key "interface-name";
        description
          "Egress interface name";
        leaf egress-interface-source {
          type xr:ncs_template_Interface-name;
          description
            "Interface name for source address";
        }
        leaf interface-name {
          type xr:ncs_template_Cisco-ios-xr-string;
          description
            "Interface";
        }
      }
    }
  }

  grouping ncs_rpc_notif_UPDATE-SOURCE {
    description
      "Common node of ipv4, ipv6";
    container update-source {
      description
        "Interface used for Source Address";
      leaf interface-name {
        type xr:ncs_rpc_notif_Interface-name;
        must 'not(../active-management)' {
          tailf:xpath-root 3;
        }
        description
          "Interface name for source address";
      }
      leaf active-management {
        type empty;
        must 'not(../interface-name)' {
          tailf:xpath-root 3;
        }
        description
          "Use the management port on the Active RP";
      }
    }
  }

  grouping ncs_rpc_notif_PROTECTION {
    description
      "Common node of ipv4, ipv6";
    container allow-entries {
      description
        "Traffic protection configuration";
      list allow-entry {
        key "protocol local-port";
        description
          "Allow traffic matching a filter";
        leaf protocol {
          type ncs_rpc_notif_Ip-protocol;
          description
            "L4 protocol";
        }
        leaf local-port {
          type xr:ncs_rpc_notif_Cisco-ios-xr-port-number;
          description
            "Local port";
        }
      }
      list allow-entry-local-address {
        key "local-address protocol local-port";
        description
          "Allow traffic matching a filter";
        leaf local-address {
          type inet:ip-prefix;
          description
            "local prefix/length";
        }
        leaf protocol {
          type ncs_rpc_notif_Ip-protocol;
          description
            "L4 protocol";
        }
        leaf local-port {
          type xr:ncs_rpc_notif_Cisco-ios-xr-port-number;
          description
            "Local port";
        }
      }
      list allow-entry-remote-address {
        key "remote-address protocol local-port";
        description
          "Allow traffic matching a filter";
        leaf remote-address {
          type inet:ip-prefix;
          description
            "remote prefix/length";
        }
        leaf protocol {
          type ncs_rpc_notif_Ip-protocol;
          description
            "L4 protocol";
        }
        leaf local-port {
          type xr:ncs_rpc_notif_Cisco-ios-xr-port-number;
          description
            "Local port";
        }
      }
      list allow-entry-local-address-remote-address {
        key "local-address remote-address protocol local-port";
        description
          "Allow traffic matching a filter";
        leaf local-address {
          type inet:ip-prefix;
          description
            "local prefix/length";
        }
        leaf remote-address {
          type inet:ip-prefix;
          description
            "remote prefix/length";
        }
        leaf protocol {
          type ncs_rpc_notif_Ip-protocol;
          description
            "L4 protocol";
        }
        leaf local-port {
          type xr:ncs_rpc_notif_Cisco-ios-xr-port-number;
          description
            "Local port";
        }
      }
      list allow-entry-interface-name {
        key "interface-name protocol local-port";
        description
          "Allow traffic matching a filter";
        leaf interface-name {
          type xr:ncs_rpc_notif_Interface-name;
          description
            "Interface name";
        }
        leaf protocol {
          type ncs_rpc_notif_Ip-protocol;
          description
            "L4 protocol";
        }
        leaf local-port {
          type xr:ncs_rpc_notif_Cisco-ios-xr-port-number;
          description
            "Local port";
        }
      }
      list allow-entry-local-address-interface-name {
        key "local-address interface-name protocol local-port";
        description
          "Allow traffic matching a filter";
        leaf local-address {
          type inet:ip-prefix;
          description
            "local prefix/length";
        }
        leaf interface-name {
          type xr:ncs_rpc_notif_Interface-name;
          description
            "Interface name";
        }
        leaf protocol {
          type ncs_rpc_notif_Ip-protocol;
          description
            "L4 protocol";
        }
        leaf local-port {
          type xr:ncs_rpc_notif_Cisco-ios-xr-port-number;
          description
            "Local port";
        }
      }
      list allow-entry-remote-address-interface-name {
        key "remote-address interface-name protocol local-port";
        description
          "Allow traffic matching a filter";
        leaf remote-address {
          type inet:ip-prefix;
          description
            "remote prefix/length";
        }
        leaf interface-name {
          type xr:ncs_rpc_notif_Interface-name;
          description
            "Interface name";
        }
        leaf protocol {
          type ncs_rpc_notif_Ip-protocol;
          description
            "L4 protocol";
        }
        leaf local-port {
          type xr:ncs_rpc_notif_Cisco-ios-xr-port-number;
          description
            "Local port";
        }
      }
      list allow-entry-local-address-remote-address-interface-name {
        key "local-address remote-address interface-name protocol local-port";
        description
          "Allow traffic matching a filter";
        leaf local-address {
          type inet:ip-prefix;
          description
            "local prefix/length";
        }
        leaf remote-address {
          type inet:ip-prefix;
          description
            "remote prefix/length";
        }
        leaf interface-name {
          type xr:ncs_rpc_notif_Interface-name;
          description
            "Interface name";
        }
        leaf protocol {
          type ncs_rpc_notif_Ip-protocol;
          description
            "L4 protocol";
        }
        leaf local-port {
          type xr:ncs_rpc_notif_Cisco-ios-xr-port-number;
          description
            "Local port";
        }
      }
    }
  }

  grouping ncs_rpc_notif_DEFAULT-ROUTE {
    description
      "Common node of ipv4, ipv6";
    leaf default-route {
      type string;
      description
        "Default interface used for routing";
    }
  }

  grouping ncs_rpc_notif_EGRESS-UPDATE-SOURCE {
    description
      "Common node of ipv4, ipv6";
    container interface-names {
      description
        "Interface used for source address for egress
         interface";
      list interface-name {
        key "interface-name";
        description
          "Egress interface name";
        leaf egress-interface-source {
          type xr:ncs_rpc_notif_Interface-name;
          description
            "Interface name for source address";
        }
        leaf interface-name {
          type xr:ncs_rpc_notif_Cisco-ios-xr-string;
          description
            "Interface";
        }
      }
    }
  }

  grouping live_ncs_UPDATE-SOURCE {
    description
      "Common node of ipv4, ipv6";
    container update-source {
      description
        "Interface used for Source Address";
      leaf interface-name {
        type xr:live_ncs_Interface-name;
        // NCS drop must statement
        description
          "Interface name for source address";
      }
      leaf active-management {
        type empty;
        // NCS drop must statement
        description
          "Use the management port on the Active RP";
      }
    }
  }

  grouping live_ncs_PROTECTION {
    description
      "Common node of ipv4, ipv6";
    container allow-entries {
      description
        "Traffic protection configuration";
      list allow-entry {
        key "protocol local-port";
        description
          "Allow traffic matching a filter";
        leaf protocol {
          type live_ncs_Ip-protocol;
          description
            "L4 protocol";
        }
        leaf local-port {
          type xr:live_ncs_Cisco-ios-xr-port-number;
          description
            "Local port";
        }
      }
      list allow-entry-local-address {
        key "local-address protocol local-port";
        description
          "Allow traffic matching a filter";
        leaf local-address {
          type inet:ip-prefix;
          description
            "local prefix/length";
        }
        leaf protocol {
          type live_ncs_Ip-protocol;
          description
            "L4 protocol";
        }
        leaf local-port {
          type xr:live_ncs_Cisco-ios-xr-port-number;
          description
            "Local port";
        }
      }
      list allow-entry-remote-address {
        key "remote-address protocol local-port";
        description
          "Allow traffic matching a filter";
        leaf remote-address {
          type inet:ip-prefix;
          description
            "remote prefix/length";
        }
        leaf protocol {
          type live_ncs_Ip-protocol;
          description
            "L4 protocol";
        }
        leaf local-port {
          type xr:live_ncs_Cisco-ios-xr-port-number;
          description
            "Local port";
        }
      }
      list allow-entry-local-address-remote-address {
        key "local-address remote-address protocol local-port";
        description
          "Allow traffic matching a filter";
        leaf local-address {
          type inet:ip-prefix;
          description
            "local prefix/length";
        }
        leaf remote-address {
          type inet:ip-prefix;
          description
            "remote prefix/length";
        }
        leaf protocol {
          type live_ncs_Ip-protocol;
          description
            "L4 protocol";
        }
        leaf local-port {
          type xr:live_ncs_Cisco-ios-xr-port-number;
          description
            "Local port";
        }
      }
      list allow-entry-interface-name {
        key "interface-name protocol local-port";
        description
          "Allow traffic matching a filter";
        leaf interface-name {
          type xr:live_ncs_Interface-name;
          description
            "Interface name";
        }
        leaf protocol {
          type live_ncs_Ip-protocol;
          description
            "L4 protocol";
        }
        leaf local-port {
          type xr:live_ncs_Cisco-ios-xr-port-number;
          description
            "Local port";
        }
      }
      list allow-entry-local-address-interface-name {
        key "local-address interface-name protocol local-port";
        description
          "Allow traffic matching a filter";
        leaf local-address {
          type inet:ip-prefix;
          description
            "local prefix/length";
        }
        leaf interface-name {
          type xr:live_ncs_Interface-name;
          description
            "Interface name";
        }
        leaf protocol {
          type live_ncs_Ip-protocol;
          description
            "L4 protocol";
        }
        leaf local-port {
          type xr:live_ncs_Cisco-ios-xr-port-number;
          description
            "Local port";
        }
      }
      list allow-entry-remote-address-interface-name {
        key "remote-address interface-name protocol local-port";
        description
          "Allow traffic matching a filter";
        leaf remote-address {
          type inet:ip-prefix;
          description
            "remote prefix/length";
        }
        leaf interface-name {
          type xr:live_ncs_Interface-name;
          description
            "Interface name";
        }
        leaf protocol {
          type live_ncs_Ip-protocol;
          description
            "L4 protocol";
        }
        leaf local-port {
          type xr:live_ncs_Cisco-ios-xr-port-number;
          description
            "Local port";
        }
      }
      list allow-entry-local-address-remote-address-interface-name {
        key "local-address remote-address interface-name protocol local-port";
        description
          "Allow traffic matching a filter";
        leaf local-address {
          type inet:ip-prefix;
          description
            "local prefix/length";
        }
        leaf remote-address {
          type inet:ip-prefix;
          description
            "remote prefix/length";
        }
        leaf interface-name {
          type xr:live_ncs_Interface-name;
          description
            "Interface name";
        }
        leaf protocol {
          type live_ncs_Ip-protocol;
          description
            "L4 protocol";
        }
        leaf local-port {
          type xr:live_ncs_Cisco-ios-xr-port-number;
          description
            "Local port";
        }
      }
    }
  }

  grouping live_ncs_DEFAULT-ROUTE {
    description
      "Common node of ipv4, ipv6";
    leaf default-route {
      type string;
      description
        "Default interface used for routing";
    }
  }

  grouping live_ncs_EGRESS-UPDATE-SOURCE {
    description
      "Common node of ipv4, ipv6";
    container interface-names {
      description
        "Interface used for source address for egress
         interface";
      list interface-name {
        key "interface-name";
        description
          "Egress interface name";
        leaf egress-interface-source {
          type xr:live_ncs_Interface-name;
          description
            "Interface name for source address";
        }
        leaf interface-name {
          type xr:live_ncs_Cisco-ios-xr-string;
          description
            "Interface";
        }
      }
    }
  }

  grouping UPDATE-SOURCE {
    description
      "Common node of ipv4, ipv6";
    container update-source {
      description
        "Interface used for Source Address";
      leaf interface-name {
        type xr:Interface-name;
        must 'not(../active-management)' {
          tailf:xpath-root 3;
        }
        description
          "Interface name for source address";
      }
      leaf active-management {
        type empty;
        must 'not(../interface-name)' {
          tailf:xpath-root 3;
        }
        description
          "Use the management port on the Active RP";
      }
    }
  }

  grouping PROTECTION {
    description
      "Common node of ipv4, ipv6";
    container allow-entries {
      description
        "Traffic protection configuration";
      list allow-entry {
        key "protocol local-port";
        description
          "Allow traffic matching a filter";
        leaf protocol {
          type Ip-protocol;
          description
            "L4 protocol";
        }
        leaf local-port {
          type xr:Cisco-ios-xr-port-number;
          description
            "Local port";
        }
      }
      list allow-entry-local-address {
        key "local-address protocol local-port";
        description
          "Allow traffic matching a filter";
        leaf local-address {
          type inet:ip-prefix;
          description
            "local prefix/length";
        }
        leaf protocol {
          type Ip-protocol;
          description
            "L4 protocol";
        }
        leaf local-port {
          type xr:Cisco-ios-xr-port-number;
          description
            "Local port";
        }
      }
      list allow-entry-remote-address {
        key "remote-address protocol local-port";
        description
          "Allow traffic matching a filter";
        leaf remote-address {
          type inet:ip-prefix;
          description
            "remote prefix/length";
        }
        leaf protocol {
          type Ip-protocol;
          description
            "L4 protocol";
        }
        leaf local-port {
          type xr:Cisco-ios-xr-port-number;
          description
            "Local port";
        }
      }
      list allow-entry-local-address-remote-address {
        key "local-address remote-address protocol local-port";
        description
          "Allow traffic matching a filter";
        leaf local-address {
          type inet:ip-prefix;
          description
            "local prefix/length";
        }
        leaf remote-address {
          type inet:ip-prefix;
          description
            "remote prefix/length";
        }
        leaf protocol {
          type Ip-protocol;
          description
            "L4 protocol";
        }
        leaf local-port {
          type xr:Cisco-ios-xr-port-number;
          description
            "Local port";
        }
      }
      list allow-entry-interface-name {
        key "interface-name protocol local-port";
        description
          "Allow traffic matching a filter";
        leaf interface-name {
          type xr:Interface-name;
          description
            "Interface name";
        }
        leaf protocol {
          type Ip-protocol;
          description
            "L4 protocol";
        }
        leaf local-port {
          type xr:Cisco-ios-xr-port-number;
          description
            "Local port";
        }
      }
      list allow-entry-local-address-interface-name {
        key "local-address interface-name protocol local-port";
        description
          "Allow traffic matching a filter";
        leaf local-address {
          type inet:ip-prefix;
          description
            "local prefix/length";
        }
        leaf interface-name {
          type xr:Interface-name;
          description
            "Interface name";
        }
        leaf protocol {
          type Ip-protocol;
          description
            "L4 protocol";
        }
        leaf local-port {
          type xr:Cisco-ios-xr-port-number;
          description
            "Local port";
        }
      }
      list allow-entry-remote-address-interface-name {
        key "remote-address interface-name protocol local-port";
        description
          "Allow traffic matching a filter";
        leaf remote-address {
          type inet:ip-prefix;
          description
            "remote prefix/length";
        }
        leaf interface-name {
          type xr:Interface-name;
          description
            "Interface name";
        }
        leaf protocol {
          type Ip-protocol;
          description
            "L4 protocol";
        }
        leaf local-port {
          type xr:Cisco-ios-xr-port-number;
          description
            "Local port";
        }
      }
      list allow-entry-local-address-remote-address-interface-name {
        key "local-address remote-address interface-name protocol local-port";
        description
          "Allow traffic matching a filter";
        leaf local-address {
          type inet:ip-prefix;
          description
            "local prefix/length";
        }
        leaf remote-address {
          type inet:ip-prefix;
          description
            "remote prefix/length";
        }
        leaf interface-name {
          type xr:Interface-name;
          description
            "Interface name";
        }
        leaf protocol {
          type Ip-protocol;
          description
            "L4 protocol";
        }
        leaf local-port {
          type xr:Cisco-ios-xr-port-number;
          description
            "Local port";
        }
      }
    }
  }

  grouping DEFAULT-ROUTE {
    description
      "Common node of ipv4, ipv6";
    leaf default-route {
      type string;
      description
        "Default interface used for routing";
    }
  }

  grouping EGRESS-UPDATE-SOURCE {
    description
      "Common node of ipv4, ipv6";
    container interface-names {
      description
        "Interface used for source address for egress
         interface";
      list interface-name {
        key "interface-name";
        description
          "Egress interface name";
        leaf egress-interface-source {
          type xr:Interface-name;
          description
            "Interface name for source address";
        }
        leaf interface-name {
          type xr:Cisco-ios-xr-string;
          description
            "Interface";
        }
      }
    }
  }

  augment "/ncs:devices/ncs:device/ncs:config" {
    container tpa {
      tailf:ncs-device-type "netconf";
      tailf:display-when "not(../../ncs:module) or ../../ncs:module[ncs:name='Cisco-IOS-XR-kim-tpa-cfg']";
      description
        "tpa configuration commands";
      container vrf-names {
        description
          "VRF container";
        list vrf-name {
          key "vrf-name";
          description
            "VRF name";
          container east-west-names {
            description
              "EastWest container";
            list east-west-name {
              key "east-west-name";
              description
                "East West interface";
              leaf east-west-name {
                type xr:Cisco-ios-xr-string;
                description
                  "Interface";
              }
              leaf vrf {
                type string;
                description
                  "VRF name";
              }
              leaf interface {
                type string;
                description
                  "Interface";
              }
            }
          }
          container address-family {
            description
              "Address family";
            container ipv6 {
              description
                "IPv6 configuration";
              uses DEFAULT-ROUTE;
              uses EGRESS-UPDATE-SOURCE;
              uses PROTECTION;
              uses UPDATE-SOURCE;
            }
            container ipv4 {
              description
                "IPv4 configuration";
              uses DEFAULT-ROUTE;
              uses EGRESS-UPDATE-SOURCE;
              uses PROTECTION;
              uses UPDATE-SOURCE;
            }
          }
          leaf disable {
            type empty;
            description
              "Disable routes and interfaces";
          }
          leaf vrf-name {
            type xr:Cisco-ios-xr-string {
              length "1..32";
            }
            description
              "VRF name";
          }
        }
      }
      container logging {
        description
          "Third party app logging";
        container kim {
          description
            "KIM logging";
          leaf rotation-max {
            type uint32;
            description
              "How many log rotation files to keep";
          }
          leaf file-size-max-kb {
            type uint32;
            units "kilobyte";
            description
              "Size in Kilobytes of the log file";
          }
        }
      }
      container statistics {
        description
          "Statistics";
        leaf disable {
          type empty;
          description
            "set this item to disable stats collection";
        }
        leaf max-intf-events {
          type uint32;
          description
            "How many interface events to record";
        }
        leaf max-lpts-events {
          type uint32;
          description
            "How many LPTS events to record";
        }
        leaf statistics-update-frequency {
          type uint32;
          units "second";
          description
            "Statistics update frequency into Linux";
        }
      }
    }
  }
  augment "/ncs:devices/ncs:device/ncs:live-status" {
    container tpa {
      tailf:ncs-device-type "netconf";
      tailf:display-when "not(../../ncs:module) or ../../ncs:module[ncs:name='Cisco-IOS-XR-kim-tpa-cfg'] or (../../ncs:live-status-protocol[not(ncs:capability)]) or (../../ncs:live-status-protocol/ncs:capability/ncs:module[.='Cisco-IOS-XR-kim-tpa-cfg'])";
      description
        "tpa configuration commands";
      container vrf-names {
        description
          "VRF container";
        list vrf-name {
          key "vrf-name";
          description
            "VRF name";
          container east-west-names {
            description
              "EastWest container";
            list east-west-name {
              key "east-west-name";
              description
                "East West interface";
              leaf east-west-name {
                type xr:live_ncs_Cisco-ios-xr-string;
                description
                  "Interface";
              }
              leaf vrf {
                type string;
                description
                  "VRF name";
              }
              leaf interface {
                type string;
                description
                  "Interface";
              }
            }
          }
          container address-family {
            description
              "Address family";
            container ipv6 {
              description
                "IPv6 configuration";
              uses live_ncs_DEFAULT-ROUTE;
              uses live_ncs_EGRESS-UPDATE-SOURCE;
              uses live_ncs_PROTECTION;
              uses live_ncs_UPDATE-SOURCE;
            }
            container ipv4 {
              description
                "IPv4 configuration";
              uses live_ncs_DEFAULT-ROUTE;
              uses live_ncs_EGRESS-UPDATE-SOURCE;
              uses live_ncs_PROTECTION;
              uses live_ncs_UPDATE-SOURCE;
            }
          }
          leaf disable {
            type empty;
            description
              "Disable routes and interfaces";
          }
          leaf vrf-name {
            type xr:live_ncs_Cisco-ios-xr-string;
            description
              "VRF name";
          }
        }
      }
      container logging {
        description
          "Third party app logging";
        container kim {
          description
            "KIM logging";
          leaf rotation-max {
            type uint32;
            description
              "How many log rotation files to keep";
          }
          leaf file-size-max-kb {
            type uint32;
            units "kilobyte";
            description
              "Size in Kilobytes of the log file";
          }
        }
      }
      container statistics {
        description
          "Statistics";
        leaf disable {
          type empty;
          description
            "set this item to disable stats collection";
        }
        leaf max-intf-events {
          type uint32;
          description
            "How many interface events to record";
        }
        leaf max-lpts-events {
          type uint32;
          description
            "How many LPTS events to record";
        }
        leaf statistics-update-frequency {
          type uint32;
          units "second";
          description
            "Statistics update frequency into Linux";
        }
      }
    }
  }
  augment "/ncs:devices/ncs:template/ncs:ned-id/ncs:config" {
    container tpa {
      description
        "tpa configuration commands";
      container vrf-names {
        description
          "VRF container";
        list vrf-name {
          // NCS patched for predictable order
          ordered-by user;
          key "vrf-name";
          description
            "VRF name";
          container east-west-names {
            description
              "EastWest container";
            list east-west-name {
              // NCS patched for predictable order
              ordered-by user;
              key "east-west-name";
              description
                "East West interface";
              leaf east-west-name {
                type xr:ncs_template_Cisco-ios-xr-string;
                description
                  "Interface";
              }
              leaf vrf {
                type string;
                description
                  "VRF name";
              }
              leaf interface {
                type string;
                description
                  "Interface";
              }
            }
          }
          container address-family {
            description
              "Address family";
            container ipv6 {
              description
                "IPv6 configuration";
              uses ncs_template_DEFAULT-ROUTE;
              uses ncs_template_EGRESS-UPDATE-SOURCE;
              uses ncs_template_PROTECTION;
              uses ncs_template_UPDATE-SOURCE;
            }
            container ipv4 {
              description
                "IPv4 configuration";
              uses ncs_template_DEFAULT-ROUTE;
              uses ncs_template_EGRESS-UPDATE-SOURCE;
              uses ncs_template_PROTECTION;
              uses ncs_template_UPDATE-SOURCE;
            }
          }
          leaf disable {
            type empty;
            description
              "Disable routes and interfaces";
          }
          leaf vrf-name {
            type xr:ncs_template_Cisco-ios-xr-string;
            description
              "VRF name";
          }
        }
      }
      container logging {
        description
          "Third party app logging";
        container kim {
          description
            "KIM logging";
          leaf rotation-max {
            type string;
            description
              "How many log rotation files to keep";
          }
          leaf file-size-max-kb {
            type string;
            units "kilobyte";
            description
              "Size in Kilobytes of the log file";
          }
        }
      }
      container statistics {
        description
          "Statistics";
        leaf disable {
          type empty;
          description
            "set this item to disable stats collection";
        }
        leaf max-intf-events {
          type string;
          description
            "How many interface events to record";
        }
        leaf max-lpts-events {
          type string;
          description
            "How many LPTS events to record";
        }
        leaf statistics-update-frequency {
          type string;
          units "second";
          description
            "Statistics update frequency into Linux";
        }
      }
    }
  }
}

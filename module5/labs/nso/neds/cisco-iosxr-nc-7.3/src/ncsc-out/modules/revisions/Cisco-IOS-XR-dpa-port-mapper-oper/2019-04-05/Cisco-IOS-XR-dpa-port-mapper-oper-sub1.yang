submodule Cisco-IOS-XR-dpa-port-mapper-oper-sub1 {
  // Generated by yanger -t ncs
  tailf:mount-id "cisco-iosxr-nc-7.3:cisco-iosxr-nc-7.3";

  belongs-to Cisco-IOS-XR-dpa-port-mapper-oper {
    prefix Cisco-IOS-XR-dpa-port-mapper-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR dpa-port-mapper package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_OOR-INTERFACE-DETAIL {
    description
      "OOR specific details for the interface";
    leaf interface-name {
      type string;
      description
        "Name of the interface";
    }
    leaf interface-status {
      type string;
      description
        "The current state of the interface";
    }
    leaf time-stamp {
      type string;
      description
        "Timestamp";
    }
    leaf npu-id {
      type string;
      description
        "Npuid of the interface";
    }
    leaf hardware-resource {
      type string;
      description
        "Type of harware resoruce";
    }
  }

  grouping ncs_template_OOR-INTERFACE-INFO {
    description
      "OOR specific details for the bundle interface";
    list interface {
      // NCS patched for predictable order
      ordered-by user;
      description
        "Interface details";
      uses ncs_template_OOR-INTERFACE-DETAIL;
    }
  }

  grouping ncs_template_OOR-SUMMARY {
    description
      "Lists interfaces in each of the three states";
    leaf red {
      type string;
      description
        "interfaces in red state";
    }
    leaf green {
      type string;
      description
        "interfaces in green state";
    }
    leaf yel-low {
      type string;
      description
        "interfaces in yellow state";
    }
  }

  grouping ncs_rpc_notif_OOR-INTERFACE-DETAIL {
    description
      "OOR specific details for the interface";
    leaf interface-name {
      type string;
      description
        "Name of the interface";
    }
    leaf interface-status {
      type string;
      description
        "The current state of the interface";
    }
    leaf time-stamp {
      type string;
      description
        "Timestamp";
    }
    leaf npu-id {
      type string;
      description
        "Npuid of the interface";
    }
    leaf hardware-resource {
      type string;
      description
        "Type of harware resoruce";
    }
  }

  grouping ncs_rpc_notif_OOR-INTERFACE-INFO {
    description
      "OOR specific details for the bundle interface";
    list interface {
      description
        "Interface details";
      uses ncs_rpc_notif_OOR-INTERFACE-DETAIL;
    }
  }

  grouping ncs_rpc_notif_OOR-SUMMARY {
    description
      "Lists interfaces in each of the three states";
    leaf red {
      type uint32;
      description
        "interfaces in red state";
    }
    leaf green {
      type uint32;
      description
        "interfaces in green state";
    }
    leaf yel-low {
      type uint32;
      description
        "interfaces in yellow state";
    }
  }

  grouping live_ncs_OOR-INTERFACE-DETAIL {
    description
      "OOR specific details for the interface";
    leaf interface-name {
      type string;
      description
        "Name of the interface";
    }
    leaf interface-status {
      type string;
      description
        "The current state of the interface";
    }
    leaf time-stamp {
      type string;
      description
        "Timestamp";
    }
    leaf npu-id {
      type string;
      description
        "Npuid of the interface";
    }
    leaf hardware-resource {
      type string;
      description
        "Type of harware resoruce";
    }
  }

  grouping live_ncs_OOR-INTERFACE-INFO {
    description
      "OOR specific details for the bundle interface";
    list interface {
      description
        "Interface details";
      uses live_ncs_OOR-INTERFACE-DETAIL;
    }
  }

  grouping live_ncs_OOR-SUMMARY {
    description
      "Lists interfaces in each of the three states";
    leaf red {
      type uint32;
      description
        "interfaces in red state";
    }
    leaf green {
      type uint32;
      description
        "interfaces in green state";
    }
    leaf yel-low {
      type uint32;
      description
        "interfaces in yellow state";
    }
  }

  grouping OOR-INTERFACE-DETAIL {
    description
      "OOR specific details for the interface";
    leaf interface-name {
      type string;
      description
        "Name of the interface";
    }
    leaf interface-status {
      type string;
      description
        "The current state of the interface";
    }
    leaf time-stamp {
      type string;
      description
        "Timestamp";
    }
    leaf npu-id {
      type string;
      description
        "Npuid of the interface";
    }
    leaf hardware-resource {
      type string;
      description
        "Type of harware resoruce";
    }
  }

  grouping OOR-INTERFACE-INFO {
    description
      "OOR specific details for the bundle interface";
    list interface {
      description
        "Interface details";
      uses OOR-INTERFACE-DETAIL;
    }
  }

  grouping OOR-SUMMARY {
    description
      "Lists interfaces in each of the three states";
    leaf red {
      type uint32;
      description
        "interfaces in red state";
    }
    leaf green {
      type uint32;
      description
        "interfaces in green state";
    }
    leaf yel-low {
      type uint32;
      description
        "interfaces in yellow state";
    }
  }
}

module Cisco-IOS-XR-ip-iarm-v4-oper {
  // Generated by yanger -t ncs
  tailf:mount-id "cisco-iosxr-nc-7.3:cisco-iosxr-nc-7.3";
  tailf:ncs-device-type "netconf";

  namespace "http://cisco.com/ns/yang/Cisco-IOS-XR-ip-iarm-v4-oper";
  prefix ip-iarm-v4-oper;

  import ietf-inet-types {
    prefix inet;
  }
  import Cisco-IOS-XR-types {
    prefix xr;
  }
  import cisco-semver {
    prefix semver;
  }
  include Cisco-IOS-XR-ip-iarm-v4-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-iarm-v4 package operational data.

     This module contains definitions
     for the following management objects:
       ipv4arm: IPv4 Address Repository Manager (IPv4 ARM)
         operational data

     Copyright (c) 2013-2019 by Cisco Systems, Inc.
     All rights reserved.";

  revision 2019-04-05 {
    description
      "Establish semantic version baseline.";
    semver:module-version "1.0.0";
  }
  revision 2019-01-22 {
    description
      "Fixing yang usability issues.";
  }
  revision 2017-05-01 {
    description
      "Fixing backward compatibility error in module.";
  }
  revision 2016-12-19 {
    description
      "IOS XR 6.2.1 revision.";
  }
  revision 2015-11-09 {
    description
      "IOS XR 6.0 revision.";
  }

  typedef ncs_template_Ipv4arm-prefix-length {
    type string;
    description
      "Ipv4arm prefix length";
  }

  typedef ncs_rpc_notif_Ipv4arm-prefix-length {
    type uint32 {
      range "0..32";
    }
    description
      "Ipv4arm prefix length";
  }

  typedef live_ncs_Ipv4arm-prefix-length {
    type uint32 {
      range "0..32";
    }
    description
      "Ipv4arm prefix length";
  }

  typedef Ipv4arm-prefix-length {
    type uint32 {
      range "0..32";
    }
    description
      "Ipv4arm prefix length";
  }

  augment "/ncs:devices/ncs:device/ncs:config" {
    // NCS drop config false container ipv4arm
  }
  augment "/ncs:devices/ncs:device/ncs:live-status" {
    container ipv4arm {
      tailf:ncs-device-type "netconf";
      tailf:display-when "not(../../ncs:module) or ../../ncs:module[ncs:name='Cisco-IOS-XR-ip-iarm-v4-oper'] or (../../ncs:live-status-protocol[not(ncs:capability)]) or (../../ncs:live-status-protocol/ncs:capability/ncs:module[.='Cisco-IOS-XR-ip-iarm-v4-oper'])";
      description
        "IPv4 Address Repository Manager (IPv4 ARM)
         operational data";
      container addresses {
        description
          "IPv4 ARM address database information";
        container vrfs {
          description
            "IPv4 ARM address database information per VRF";
          list vrf {
            key "vrf-name";
            description
              "IPv4 ARM address database information in a VRF";
            container networks {
              description
                "IPv4 ARM address database information by
                 network";
              list network {
                description
                  "An IPv4 Address in IPv4 ARM";
                leaf address {
                  type inet:ipv4-address-no-zone;
                  description
                    "An IPv4 Address in this Network.";
                }
                leaf prefix-length {
                  type live_ncs_Ipv4arm-prefix-length;
                  description
                    "Ipv4 ARM prefix length for this address in
                     the Network.";
                }
                leaf interface {
                  type xr:live_ncs_Interface-name;
                  description
                    "Ingress/Egress interface handle for this
                     address in the Network.";
                }
                uses live_ncs_IP-ARM-EDM-DB-NET-BAG-TYPE;
              }
            }
            container interfaces {
              description
                "IPv4 ARM address database information by
                 interface";
              list interface {
                key "interface";
                description
                  "An IPv4 address in IPv4 ARM";
                leaf interface {
                  type xr:live_ncs_Interface-name;
                  description
                    "Interface";
                }
                uses live_ncs_IP-ARM-EDM-DB-IF-BAG-TYPE;
              }
            }
            leaf vrf-name {
              type xr:live_ncs_Cisco-ios-xr-string;
              description
                "VRF name";
            }
          }
        }
      }
      container summary {
        description
          "IPv4 ARM summary information";
        uses live_ncs_IP-ARM-EDM-SUMMARY-BAG-TYPE;
      }
      container vrf-summaries {
        description
          "IPv4 ARM VRFs summary information";
        list vrf-summary {
          key "vrf-name";
          description
            "IPv4 ARM VRF summary information";
          leaf vrf-name {
            type xr:live_ncs_Cisco-ios-xr-string;
            description
              "VRF name";
          }
          uses live_ncs_IP-ARM-EDM-DB-VRF-BAG-TYPE;
        }
      }
      container router-id {
        description
          "IPv4 ARM Router ID information";
        uses live_ncs_IP-ARM-EDM-DB-RTRID-BAG-TYPE;
      }
      leaf multicast-host-interface {
        type xr:live_ncs_Interface-name;
        description
          "Interface Handle of Default Multicast Host";
      }
    }
  }
  augment "/ncs:devices/ncs:template/ncs:ned-id/ncs:config" {
    // NCS drop config false container ipv4arm
  }
}

module Cisco-IOS-XR-ncs1k-macsec-ea-oper {
  // Generated by yanger -t ncs
  tailf:mount-id "cisco-iosxr-nc-7.3:cisco-iosxr-nc-7.3";
  tailf:ncs-device-type "netconf";

  namespace "http://cisco.com/ns/yang/Cisco-IOS-XR-ncs1k-macsec-ea-oper";
  prefix ncs1k-macsec-ea-oper;

  import Cisco-IOS-XR-types {
    prefix xr;
  }
  import cisco-semver {
    prefix semver;
  }
  include Cisco-IOS-XR-ncs1k-macsec-ea-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1k-macsec-ea package operational data.

     This module contains definitions
     for the following management objects:
       ncs1k-macsec-oper: Macsec data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'ncs1k-macsec-oper'
  }
  augment "/ncs:devices/ncs:device/ncs:live-status" {
    container ncs1k-macsec-oper {
      tailf:ncs-device-type "netconf";
      tailf:display-when "not(../../ncs:module) or ../../ncs:module[ncs:name='Cisco-IOS-XR-ncs1k-macsec-ea-oper'] or (../../ncs:live-status-protocol[not(ncs:capability)]) or (../../ncs:live-status-protocol/ncs:capability/ncs:module[.='Cisco-IOS-XR-ncs1k-macsec-ea-oper'])";
      description
        "Macsec data";
      container ncs1k-macsec-ctrlr-names {
        description
          "All Macsec operational data";
        list ncs1k-macsec-ctrlr-name {
          key "name";
          description
            "Interface name";
          container ncs1k-status-info {
            description
              "controller data";
            uses live_ncs_NCS1K-MACSEC-IF-STATUS;
          }
          leaf name {
            type xr:live_ncs_Interface-name;
            description
              "Port name";
          }
        }
      }
    }
  }
  augment "/ncs:devices/ncs:template/ncs:ned-id/ncs:config" {
    // NCS drop config false container 'ncs1k-macsec-oper'
  }
}

submodule Cisco-IOS-XR-ipv4-bgp-oc-oper-sub1 {
  // Generated by yanger -t ncs
  tailf:mount-id "cisco-iosxr-nc-7.3:cisco-iosxr-nc-7.3";

  belongs-to Cisco-IOS-XR-ipv4-bgp-oc-oper {
    prefix Cisco-IOS-XR-ipv4-bgp-oc-oper;
  }

  import ietf-inet-types {
    prefix inet;
  }
  import ietf-yang-types {
    prefix yang;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv4-bgp-oc package operational data.

     Copyright (c) 2013-2020 by Cisco Systems, Inc.
     All rights reserved.";

  revision 2020-01-28 {
    description
      "Removing unsupported InvalidReason";
    semver:module-version "3.0.0";
  }
  revision 2019-08-31 {
    description
      "Fixing revision error in module.";
    semver:module-version "2.0.0";
  }
  revision 2019-04-05 {
    description
      "Fixing backward compatibility error in module";
    semver:module-version "1.0.0";
  }
  revision 2019-04-05 {
    description
      "Establish semantic version baseline.";
  }
  revision 2017-09-07 {
    description
      "Fixed type translation error.";
  }
  revision 2017-05-01 {
    description
      "Fixing backward compatibility error in module.";
  }
  revision 2015-11-09 {
    description
      "IOS XR 6.0 revision.";
  }

  typedef ncs_template_Bgp-oc-origin-attr {
    type string;
    description
      "Origin Type";
  }

  typedef ncs_template_Ipv6-address {
    type string;
    description
      "IPV6 Address type";
  }

  typedef ncs_template_Bgp-oc-afi {
    type string;
    description
      "BGP Address family";
  }

  typedef ncs_rpc_notif_Bgp-oc-origin-attr {
    type enumeration {
      enum "igp" {
        value 0;
        description
          "IGP";
      }
      enum "egp" {
        value 1;
        description
          "EGP";
      }
      enum "incomplete" {
        value 2;
        description
          "Incomplete";
      }
    }
    description
      "Origin Type";
  }

  typedef ncs_rpc_notif_Ipv6-address {
    type inet:ipv6-address;
    description
      "IPV6 Address type";
  }

  typedef ncs_rpc_notif_Bgp-oc-afi {
    type enumeration {
      enum "ipv4" {
        value 0;
        description
          "IPv4 unicast";
      }
      enum "ipv6" {
        value 5;
        description
          "IPv6 unicast";
      }
    }
    description
      "BGP Address family";
  }

  typedef live_ncs_Bgp-oc-origin-attr {
    type enumeration {
      enum "igp" {
        value 0;
        description
          "IGP";
      }
      enum "egp" {
        value 1;
        description
          "EGP";
      }
      enum "incomplete" {
        value 2;
        description
          "Incomplete";
      }
    }
    description
      "Origin Type";
  }

  typedef live_ncs_Ipv6-address {
    type inet:ipv6-address;
    description
      "IPV6 Address type";
  }

  typedef live_ncs_Bgp-oc-afi {
    type enumeration {
      enum "ipv4" {
        value 0;
        description
          "IPv4 unicast";
      }
      enum "ipv6" {
        value 5;
        description
          "IPv6 unicast";
      }
    }
    description
      "BGP Address family";
  }

  typedef Bgp-oc-origin-attr {
    type enumeration {
      enum "igp" {
        value 0;
        description
          "IGP";
      }
      enum "egp" {
        value 1;
        description
          "EGP";
      }
      enum "incomplete" {
        value 2;
        description
          "Incomplete";
      }
    }
    description
      "Origin Type";
  }

  typedef Ipv6-address {
    type inet:ipv6-address;
    description
      "IPV6 Address type";
  }

  typedef Bgp-oc-afi {
    type enumeration {
      enum "ipv4" {
        value 0;
        description
          "IPv4 unicast";
      }
      enum "ipv6" {
        value 5;
        description
          "IPv6 unicast";
      }
    }
    description
      "BGP Address family";
  }

  grouping ncs_template_BGP-OC-RIB-COMMON-BAG {
    description
      "OpenConfig BGP_RIB common attributes";
    leaf num-routes {
      type string;
      description
        "NumRoutes";
    }
  }

  grouping ncs_template_BGP-OC-DATE-AND-TIME {
    description
      "BGP OC DATE AND TIME";
    leaf time-value {
      type string;
      description
        "TimeValue";
    }
  }

  grouping ncs_template_BGP-OC-UNKNOWN-ATTR-TYPE {
    description
      "BGP OC UNKNOWN ATTR TYPE";
    leaf attribute-type {
      type string;
      description
        "BGP attribute type that is unknown  or not
         understood";
    }
    leaf attribute-length {
      type string;
      description
        "BGP attribute length that is unknown  or not
         understood";
    }
    leaf attribute-value {
      type string;
      description
        "BGP attribute value that is unknown  or not
         understood";
    }
  }

  grouping ncs_template_BGP-OC-EXT-ATTR {
    description
      "BGP OC EXT ATTR";
    leaf originator-id {
      type string;
      description
        "BGP Originator ID";
    }
    leaf aigp {
      type string;
      description
        "Accumulated Interior Gateway Protocol (AIGP)
         metric value";
    }
    leaf path-id {
      type string;
      description
        "BGP Path Identifier";
    }
    leaf-list cluster {
      // NCS patched for predictable order
      ordered-by user;
      type string;
      description
        "List of cluster IDs";
    }
    list ext-community {
      // NCS patched for predictable order
      ordered-by user;
      description
        "Array of extended communities";
      uses ncs_template_BGP-OC-STRING-TYPE;
    }
    list unknown-attributes {
      // NCS patched for predictable order
      ordered-by user;
      description
        "List of BGP attributes that are unknown";
      uses ncs_template_BGP-OC-UNKNOWN-ATTR-TYPE;
    }
  }

  grouping ncs_template_BGP-OC-STRING-TYPE {
    description
      "Names of bgp oc objects";
    leaf objects {
      type string;
      description
        "BGP OC objects";
    }
  }

  grouping ncs_template_BGP-OC-AGGREGATOR-TYPE {
    description
      "BGP OC AGGREGATOR TYPE";
    leaf as {
      type string;
      description
        "AS number";
    }
    leaf as4 {
      type string;
      description
        "AS4 number";
    }
    leaf address {
      type string;
      description
        "IPv4 address";
    }
  }

  grouping ncs_template_BGP-OC-ROUTE-ATTR {
    description
      "BGP OC ROUTE ATTR";
    container next-hop {
      description
        "NextHopAddress";
      uses ncs_template_BGP-OC-ADDRTYPE;
    }
    container aggregrator-attributes {
      description
        "AggregatorList";
      uses ncs_template_BGP-OC-AGGREGATOR-TYPE;
    }
    leaf origin-type {
      type ncs_template_Bgp-oc-origin-attr;
      description
        "Origin Attribute Type";
    }
    leaf as-path {
      type string;
      description
        "AS Path";
    }
    leaf as4-path {
      type string;
      description
        "AS4 Path";
    }
    leaf med {
      type string;
      description
        "Med";
    }
    leaf local-pref {
      type string;
      description
        "LocalPref";
    }
    leaf atomic-aggr {
      type string;
      description
        "AtomicAggr";
    }
    list community {
      // NCS patched for predictable order
      ordered-by user;
      description
        "CommunityArray";
      uses ncs_template_BGP-OC-STRING-TYPE;
    }
  }

  grouping ncs_template_BGP-OC-ADDRTYPE {
    description
      "BGP OC ADDRTYPE";
    leaf afi {
      type ncs_template_Bgp-oc-afi;
      description
        "AFI";
    }
    leaf ipv4-address {
      // NCS drop when statement
      type string;
      description
        "IPv4 Addr";
    }
    leaf ipv6-address {
      // NCS drop when statement
      type ncs_template_Ipv6-address;
      description
        "IPv6 Addr";
    }
  }

  grouping ncs_template_BGP-OC-PREFIXTYPE {
    description
      "BGP OC PREFIXTYPE";
    container prefix {
      description
        "IPv4 or IPv6 network address prefix";
      uses ncs_template_BGP-OC-ADDRTYPE;
    }
    leaf prefix-length {
      type string;
      description
        "Length of the subnet prefix";
    }
  }

  grouping ncs_template_BGP-OC-ROUTE-BAG {
    description
      "OpenConfig BGP_RIB Route";
    container prefix-name {
      description
        "Prefix";
      uses ncs_template_BGP-OC-PREFIXTYPE;
    }
    container route-attr-list {
      description
        "RouteAttributesList";
      uses ncs_template_BGP-OC-ROUTE-ATTR;
    }
    container ext-attributes-list {
      description
        "ExtAttributesList";
      uses ncs_template_BGP-OC-EXT-ATTR;
    }
    container last-modified-date {
      description
        "LastModifiedDate";
      uses ncs_template_BGP-OC-DATE-AND-TIME;
    }
    container last-update-recieved {
      description
        "LastUpdateRecieved";
      uses ncs_template_BGP-OC-DATE-AND-TIME;
    }
    leaf valid-route {
      type string;
      description
        "ValidRoute";
    }
    leaf best-path {
      type string;
      description
        "BestPath";
    }
  }

  grouping ncs_rpc_notif_BGP-OC-RIB-COMMON-BAG {
    description
      "OpenConfig BGP_RIB common attributes";
    leaf num-routes {
      type uint64;
      description
        "NumRoutes";
    }
  }

  grouping ncs_rpc_notif_BGP-OC-DATE-AND-TIME {
    description
      "BGP OC DATE AND TIME";
    leaf time-value {
      type string;
      description
        "TimeValue";
    }
  }

  grouping ncs_rpc_notif_BGP-OC-UNKNOWN-ATTR-TYPE {
    description
      "BGP OC UNKNOWN ATTR TYPE";
    leaf attribute-type {
      type uint16;
      description
        "BGP attribute type that is unknown  or not
         understood";
    }
    leaf attribute-length {
      type uint16;
      description
        "BGP attribute length that is unknown  or not
         understood";
    }
    leaf attribute-value {
      type yang:hex-string;
      description
        "BGP attribute value that is unknown  or not
         understood";
    }
  }

  grouping ncs_rpc_notif_BGP-OC-EXT-ATTR {
    description
      "BGP OC EXT ATTR";
    leaf originator-id {
      type inet:ipv4-address;
      description
        "BGP Originator ID";
    }
    leaf aigp {
      type uint64;
      description
        "Accumulated Interior Gateway Protocol (AIGP)
         metric value";
    }
    leaf path-id {
      type uint32;
      description
        "BGP Path Identifier";
    }
    leaf-list cluster {
      type inet:ipv4-address;
      description
        "List of cluster IDs";
    }
    list ext-community {
      description
        "Array of extended communities";
      uses ncs_rpc_notif_BGP-OC-STRING-TYPE;
    }
    list unknown-attributes {
      description
        "List of BGP attributes that are unknown";
      uses ncs_rpc_notif_BGP-OC-UNKNOWN-ATTR-TYPE;
    }
  }

  grouping ncs_rpc_notif_BGP-OC-STRING-TYPE {
    description
      "Names of bgp oc objects";
    leaf objects {
      type string;
      description
        "BGP OC objects";
    }
  }

  grouping ncs_rpc_notif_BGP-OC-AGGREGATOR-TYPE {
    description
      "BGP OC AGGREGATOR TYPE";
    leaf as {
      type uint32;
      description
        "AS number";
    }
    leaf as4 {
      type uint32;
      description
        "AS4 number";
    }
    leaf address {
      type inet:ipv4-address;
      description
        "IPv4 address";
    }
  }

  grouping ncs_rpc_notif_BGP-OC-ROUTE-ATTR {
    description
      "BGP OC ROUTE ATTR";
    container next-hop {
      description
        "NextHopAddress";
      uses ncs_rpc_notif_BGP-OC-ADDRTYPE;
    }
    container aggregrator-attributes {
      description
        "AggregatorList";
      uses ncs_rpc_notif_BGP-OC-AGGREGATOR-TYPE;
    }
    leaf origin-type {
      type ncs_rpc_notif_Bgp-oc-origin-attr;
      description
        "Origin Attribute Type";
    }
    leaf as-path {
      type string;
      description
        "AS Path";
    }
    leaf as4-path {
      type string;
      description
        "AS4 Path";
    }
    leaf med {
      type uint32;
      description
        "Med";
    }
    leaf local-pref {
      type uint32;
      description
        "LocalPref";
    }
    leaf atomic-aggr {
      type boolean;
      description
        "AtomicAggr";
    }
    list community {
      description
        "CommunityArray";
      uses ncs_rpc_notif_BGP-OC-STRING-TYPE;
    }
  }

  grouping ncs_rpc_notif_BGP-OC-ADDRTYPE {
    description
      "BGP OC ADDRTYPE";
    leaf afi {
      type ncs_rpc_notif_Bgp-oc-afi;
      description
        "AFI";
    }
    leaf ipv4-address {
      when "../afi = 'ipv4'" {
        tailf:xpath-root 3;
        description
          "../AFI = 'IPv4'";
      }
      type inet:ipv4-address;
      description
        "IPv4 Addr";
    }
    leaf ipv6-address {
      when "../afi = 'ipv6'" {
        tailf:xpath-root 3;
        description
          "../AFI = 'IPv6'";
      }
      type ncs_rpc_notif_Ipv6-address;
      description
        "IPv6 Addr";
    }
  }

  grouping ncs_rpc_notif_BGP-OC-PREFIXTYPE {
    description
      "BGP OC PREFIXTYPE";
    container prefix {
      description
        "IPv4 or IPv6 network address prefix";
      uses ncs_rpc_notif_BGP-OC-ADDRTYPE;
    }
    leaf prefix-length {
      type uint8;
      description
        "Length of the subnet prefix";
    }
  }

  grouping ncs_rpc_notif_BGP-OC-ROUTE-BAG {
    description
      "OpenConfig BGP_RIB Route";
    container prefix-name {
      description
        "Prefix";
      uses ncs_rpc_notif_BGP-OC-PREFIXTYPE;
    }
    container route-attr-list {
      description
        "RouteAttributesList";
      uses ncs_rpc_notif_BGP-OC-ROUTE-ATTR;
    }
    container ext-attributes-list {
      description
        "ExtAttributesList";
      uses ncs_rpc_notif_BGP-OC-EXT-ATTR;
    }
    container last-modified-date {
      description
        "LastModifiedDate";
      uses ncs_rpc_notif_BGP-OC-DATE-AND-TIME;
    }
    container last-update-recieved {
      description
        "LastUpdateRecieved";
      uses ncs_rpc_notif_BGP-OC-DATE-AND-TIME;
    }
    leaf valid-route {
      type boolean;
      description
        "ValidRoute";
    }
    leaf best-path {
      type boolean;
      description
        "BestPath";
    }
  }

  grouping live_ncs_BGP-OC-RIB-COMMON-BAG {
    description
      "OpenConfig BGP_RIB common attributes";
    leaf num-routes {
      type uint64;
      description
        "NumRoutes";
    }
  }

  grouping live_ncs_BGP-OC-DATE-AND-TIME {
    description
      "BGP OC DATE AND TIME";
    leaf time-value {
      type string;
      description
        "TimeValue";
    }
  }

  grouping live_ncs_BGP-OC-UNKNOWN-ATTR-TYPE {
    description
      "BGP OC UNKNOWN ATTR TYPE";
    leaf attribute-type {
      type uint16;
      description
        "BGP attribute type that is unknown  or not
         understood";
    }
    leaf attribute-length {
      type uint16;
      description
        "BGP attribute length that is unknown  or not
         understood";
    }
    leaf attribute-value {
      type yang:hex-string;
      description
        "BGP attribute value that is unknown  or not
         understood";
    }
  }

  grouping live_ncs_BGP-OC-EXT-ATTR {
    description
      "BGP OC EXT ATTR";
    leaf originator-id {
      type inet:ipv4-address;
      description
        "BGP Originator ID";
    }
    leaf aigp {
      type uint64;
      description
        "Accumulated Interior Gateway Protocol (AIGP)
         metric value";
    }
    leaf path-id {
      type uint32;
      description
        "BGP Path Identifier";
    }
    leaf-list cluster {
      type inet:ipv4-address;
      description
        "List of cluster IDs";
    }
    list ext-community {
      description
        "Array of extended communities";
      uses live_ncs_BGP-OC-STRING-TYPE;
    }
    list unknown-attributes {
      description
        "List of BGP attributes that are unknown";
      uses live_ncs_BGP-OC-UNKNOWN-ATTR-TYPE;
    }
  }

  grouping live_ncs_BGP-OC-STRING-TYPE {
    description
      "Names of bgp oc objects";
    leaf objects {
      type string;
      description
        "BGP OC objects";
    }
  }

  grouping live_ncs_BGP-OC-AGGREGATOR-TYPE {
    description
      "BGP OC AGGREGATOR TYPE";
    leaf as {
      type uint32;
      description
        "AS number";
    }
    leaf as4 {
      type uint32;
      description
        "AS4 number";
    }
    leaf address {
      type inet:ipv4-address;
      description
        "IPv4 address";
    }
  }

  grouping live_ncs_BGP-OC-ROUTE-ATTR {
    description
      "BGP OC ROUTE ATTR";
    container next-hop {
      description
        "NextHopAddress";
      uses live_ncs_BGP-OC-ADDRTYPE;
    }
    container aggregrator-attributes {
      description
        "AggregatorList";
      uses live_ncs_BGP-OC-AGGREGATOR-TYPE;
    }
    leaf origin-type {
      type live_ncs_Bgp-oc-origin-attr;
      description
        "Origin Attribute Type";
    }
    leaf as-path {
      type string;
      description
        "AS Path";
    }
    leaf as4-path {
      type string;
      description
        "AS4 Path";
    }
    leaf med {
      type uint32;
      description
        "Med";
    }
    leaf local-pref {
      type uint32;
      description
        "LocalPref";
    }
    leaf atomic-aggr {
      type boolean;
      description
        "AtomicAggr";
    }
    list community {
      description
        "CommunityArray";
      uses live_ncs_BGP-OC-STRING-TYPE;
    }
  }

  grouping live_ncs_BGP-OC-ADDRTYPE {
    description
      "BGP OC ADDRTYPE";
    leaf afi {
      type live_ncs_Bgp-oc-afi;
      description
        "AFI";
    }
    leaf ipv4-address {
      // NCS drop when statement
      type inet:ipv4-address;
      description
        "IPv4 Addr";
    }
    leaf ipv6-address {
      // NCS drop when statement
      type live_ncs_Ipv6-address;
      description
        "IPv6 Addr";
    }
  }

  grouping live_ncs_BGP-OC-PREFIXTYPE {
    description
      "BGP OC PREFIXTYPE";
    container prefix {
      description
        "IPv4 or IPv6 network address prefix";
      uses live_ncs_BGP-OC-ADDRTYPE;
    }
    leaf prefix-length {
      type uint8;
      description
        "Length of the subnet prefix";
    }
  }

  grouping live_ncs_BGP-OC-ROUTE-BAG {
    description
      "OpenConfig BGP_RIB Route";
    container prefix-name {
      description
        "Prefix";
      uses live_ncs_BGP-OC-PREFIXTYPE;
    }
    container route-attr-list {
      description
        "RouteAttributesList";
      uses live_ncs_BGP-OC-ROUTE-ATTR;
    }
    container ext-attributes-list {
      description
        "ExtAttributesList";
      uses live_ncs_BGP-OC-EXT-ATTR;
    }
    container last-modified-date {
      description
        "LastModifiedDate";
      uses live_ncs_BGP-OC-DATE-AND-TIME;
    }
    container last-update-recieved {
      description
        "LastUpdateRecieved";
      uses live_ncs_BGP-OC-DATE-AND-TIME;
    }
    leaf valid-route {
      type boolean;
      description
        "ValidRoute";
    }
    leaf best-path {
      type boolean;
      description
        "BestPath";
    }
  }

  grouping BGP-OC-RIB-COMMON-BAG {
    description
      "OpenConfig BGP_RIB common attributes";
    leaf num-routes {
      type uint64;
      description
        "NumRoutes";
    }
  }

  grouping BGP-OC-DATE-AND-TIME {
    description
      "BGP OC DATE AND TIME";
    leaf time-value {
      type string;
      description
        "TimeValue";
    }
  }

  grouping BGP-OC-UNKNOWN-ATTR-TYPE {
    description
      "BGP OC UNKNOWN ATTR TYPE";
    leaf attribute-type {
      type uint16;
      description
        "BGP attribute type that is unknown  or not
         understood";
    }
    leaf attribute-length {
      type uint16;
      description
        "BGP attribute length that is unknown  or not
         understood";
    }
    leaf attribute-value {
      type yang:hex-string;
      description
        "BGP attribute value that is unknown  or not
         understood";
    }
  }

  grouping BGP-OC-EXT-ATTR {
    description
      "BGP OC EXT ATTR";
    leaf originator-id {
      type inet:ipv4-address;
      description
        "BGP Originator ID";
    }
    leaf aigp {
      type uint64;
      description
        "Accumulated Interior Gateway Protocol (AIGP)
         metric value";
    }
    leaf path-id {
      type uint32;
      description
        "BGP Path Identifier";
    }
    leaf-list cluster {
      type inet:ipv4-address;
      description
        "List of cluster IDs";
    }
    list ext-community {
      description
        "Array of extended communities";
      uses BGP-OC-STRING-TYPE;
    }
    list unknown-attributes {
      description
        "List of BGP attributes that are unknown";
      uses BGP-OC-UNKNOWN-ATTR-TYPE;
    }
  }

  grouping BGP-OC-STRING-TYPE {
    description
      "Names of bgp oc objects";
    leaf objects {
      type string;
      description
        "BGP OC objects";
    }
  }

  grouping BGP-OC-AGGREGATOR-TYPE {
    description
      "BGP OC AGGREGATOR TYPE";
    leaf as {
      type uint32;
      description
        "AS number";
    }
    leaf as4 {
      type uint32;
      description
        "AS4 number";
    }
    leaf address {
      type inet:ipv4-address;
      description
        "IPv4 address";
    }
  }

  grouping BGP-OC-ROUTE-ATTR {
    description
      "BGP OC ROUTE ATTR";
    container next-hop {
      description
        "NextHopAddress";
      uses BGP-OC-ADDRTYPE;
    }
    container aggregrator-attributes {
      description
        "AggregatorList";
      uses BGP-OC-AGGREGATOR-TYPE;
    }
    leaf origin-type {
      type Bgp-oc-origin-attr;
      description
        "Origin Attribute Type";
    }
    leaf as-path {
      type string;
      description
        "AS Path";
    }
    leaf as4-path {
      type string;
      description
        "AS4 Path";
    }
    leaf med {
      type uint32;
      description
        "Med";
    }
    leaf local-pref {
      type uint32;
      description
        "LocalPref";
    }
    leaf atomic-aggr {
      type boolean;
      description
        "AtomicAggr";
    }
    list community {
      description
        "CommunityArray";
      uses BGP-OC-STRING-TYPE;
    }
  }

  grouping BGP-OC-ADDRTYPE {
    description
      "BGP OC ADDRTYPE";
    leaf afi {
      type Bgp-oc-afi;
      description
        "AFI";
    }
    leaf ipv4-address {
      when "../afi = 'ipv4'" {
        tailf:xpath-root 3;
        description
          "../AFI = 'IPv4'";
      }
      type inet:ipv4-address;
      description
        "IPv4 Addr";
    }
    leaf ipv6-address {
      when "../afi = 'ipv6'" {
        tailf:xpath-root 3;
        description
          "../AFI = 'IPv6'";
      }
      type Ipv6-address;
      description
        "IPv6 Addr";
    }
  }

  grouping BGP-OC-PREFIXTYPE {
    description
      "BGP OC PREFIXTYPE";
    container prefix {
      description
        "IPv4 or IPv6 network address prefix";
      uses BGP-OC-ADDRTYPE;
    }
    leaf prefix-length {
      type uint8;
      description
        "Length of the subnet prefix";
    }
  }

  grouping BGP-OC-ROUTE-BAG {
    description
      "OpenConfig BGP_RIB Route";
    container prefix-name {
      description
        "Prefix";
      uses BGP-OC-PREFIXTYPE;
    }
    container route-attr-list {
      description
        "RouteAttributesList";
      uses BGP-OC-ROUTE-ATTR;
    }
    container ext-attributes-list {
      description
        "ExtAttributesList";
      uses BGP-OC-EXT-ATTR;
    }
    container last-modified-date {
      description
        "LastModifiedDate";
      uses BGP-OC-DATE-AND-TIME;
    }
    container last-update-recieved {
      description
        "LastUpdateRecieved";
      uses BGP-OC-DATE-AND-TIME;
    }
    leaf valid-route {
      type boolean;
      description
        "ValidRoute";
    }
    leaf best-path {
      type boolean;
      description
        "BestPath";
    }
  }
}

module Cisco-IOS-XR-ipv4-igmp-dyn-tmpl-cfg {
  // Generated by yanger -t ncs
  tailf:mount-id "cisco-iosxr-nc-7.3:cisco-iosxr-nc-7.3";
  tailf:ncs-device-type "netconf";

  namespace "http://cisco.com/ns/yang/Cisco-IOS-XR-ipv4-igmp-dyn-tmpl-cfg";
  prefix ipv4-igmp-dyn-tmpl-cfg;

  import Cisco-IOS-XR-types {
    prefix xr;
  }
  import cisco-semver {
    prefix semver;
  }
  import Cisco-IOS-XR-subscriber-infra-tmplmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-igmp-dyn-tmpl package configuration.

     This YANG module augments the
       Cisco-IOS-XR-subscriber-infra-tmplmgr-cfg
     module with configuration data.

     Copyright (c) 2013-2021 by Cisco Systems, Inc.
     All rights reserved.";

  revision 2021-03-22 {
    description
      "Added new threashold leaf";
    semver:module-version "1.0.0";
  }
  revision 2019-04-05 {
    description
      "Establish semantic version baseline.";
    semver:module-version "1.0.0";
  }
  revision 2015-11-09 {
    description
      "IOS XR 6.0 revision.";
  }

  typedef ncs_template_Dyn-tmpl-multicast-mode {
    type string;
    description
      "Dyn tmpl multicast mode";
  }

  typedef ncs_rpc_notif_Dyn-tmpl-multicast-mode {
    type enumeration {
      enum "qos-correlation" {
        value 1;
        description
          "QOS Correlation";
      }
      enum "passive" {
        value 2;
        description
          "Passive";
      }
    }
    description
      "Dyn tmpl multicast mode";
  }

  typedef live_ncs_Dyn-tmpl-multicast-mode {
    type enumeration {
      enum "qos-correlation" {
        value 1;
        description
          "QOS Correlation";
      }
      enum "passive" {
        value 2;
        description
          "Passive";
      }
    }
    description
      "Dyn tmpl multicast mode";
  }

  typedef Dyn-tmpl-multicast-mode {
    type enumeration {
      enum "qos-correlation" {
        value 1;
        description
          "QOS Correlation";
      }
      enum "passive" {
        value 2;
        description
          "Passive";
      }
    }
    description
      "Dyn tmpl multicast mode";
  }

  grouping ncs_template_IGMP {
    description
      "Common node of ppp, ip-subscriber";
    container igmp {
      description
        "IGMPconfiguration";
      container default-vrf {
        description
          "Default VRF";
        container explicit-tracking {
          presence "Indicates a explicit-tracking node is configured.";
          description
            "IGMPv3 explicit host tracking";
          leaf enable {
            type string;
            // NCS drop mandatory statement
            description
              "Enable or disable, when value is TRUE or
               FALSE respectively";
          }
          leaf access-list-name {
            type xr:ncs_template_Cisco-ios-xr-string;
            description
              "Access list specifying tracking group range";
          }
        }
        leaf max-groups {
          type string;
          // NCS drop default statement
          description
            "IGMP Max Groups";
        }
        leaf access-group {
          type xr:ncs_template_Cisco-ios-xr-string;
          description
            "Access list specifying access-list group range";
        }
        leaf version {
          type string;
          // NCS drop default statement
          description
            "IGMP Version";
        }
        leaf query-interval {
          type string;
          units "second";
          // NCS drop default statement
          description
            "Query interval in seconds";
        }
        leaf query-max-response-time {
          type string;
          units "second";
          // NCS drop default statement
          description
            "Query response value in seconds";
        }
        leaf multicast-mode {
          type ncs_template_Dyn-tmpl-multicast-mode;
          description
            "Configure Multicast mode variable";
        }
      }
    }
  }

  grouping ncs_rpc_notif_IGMP {
    description
      "Common node of ppp, ip-subscriber";
    container igmp {
      description
        "IGMPconfiguration";
      container default-vrf {
        description
          "Default VRF";
        container explicit-tracking {
          presence "Indicates a explicit-tracking node is configured.";
          description
            "IGMPv3 explicit host tracking";
          leaf enable {
            type boolean;
            mandatory true;
            description
              "Enable or disable, when value is TRUE or
               FALSE respectively";
          }
          leaf access-list-name {
            type xr:ncs_rpc_notif_Cisco-ios-xr-string;
            description
              "Access list specifying tracking group range";
          }
        }
        leaf max-groups {
          type uint32 {
            range "1..40000";
          }
          default "25000";
          description
            "IGMP Max Groups";
        }
        leaf access-group {
          type xr:ncs_rpc_notif_Cisco-ios-xr-string;
          description
            "Access list specifying access-list group range";
        }
        leaf version {
          type uint32 {
            range "1..3";
          }
          default "3";
          description
            "IGMP Version";
        }
        leaf query-interval {
          type uint32 {
            range "1..3600";
          }
          units "second";
          default "60";
          description
            "Query interval in seconds";
        }
        leaf query-max-response-time {
          type uint32 {
            range "1..25";
          }
          units "second";
          default "10";
          description
            "Query response value in seconds";
        }
        leaf multicast-mode {
          type ncs_rpc_notif_Dyn-tmpl-multicast-mode;
          description
            "Configure Multicast mode variable";
        }
      }
    }
  }

  grouping live_ncs_IGMP {
    description
      "Common node of ppp, ip-subscriber";
    container igmp {
      description
        "IGMPconfiguration";
      container default-vrf {
        description
          "Default VRF";
        container explicit-tracking {
          presence "Indicates a explicit-tracking node is configured.";
          description
            "IGMPv3 explicit host tracking";
          leaf enable {
            type boolean;
            // NCS drop mandatory statement
            description
              "Enable or disable, when value is TRUE or
               FALSE respectively";
          }
          leaf access-list-name {
            type xr:live_ncs_Cisco-ios-xr-string;
            description
              "Access list specifying tracking group range";
          }
        }
        leaf max-groups {
          type uint32 {
            range "1..40000";
          }
          // NCS drop default statement
          description
            "IGMP Max Groups";
        }
        leaf access-group {
          type xr:live_ncs_Cisco-ios-xr-string;
          description
            "Access list specifying access-list group range";
        }
        leaf version {
          type uint32 {
            range "1..3";
          }
          // NCS drop default statement
          description
            "IGMP Version";
        }
        leaf query-interval {
          type uint32 {
            range "1..3600";
          }
          units "second";
          // NCS drop default statement
          description
            "Query interval in seconds";
        }
        leaf query-max-response-time {
          type uint32 {
            range "1..25";
          }
          units "second";
          // NCS drop default statement
          description
            "Query response value in seconds";
        }
        leaf multicast-mode {
          type live_ncs_Dyn-tmpl-multicast-mode;
          description
            "Configure Multicast mode variable";
        }
      }
    }
  }

  grouping IGMP {
    description
      "Common node of ppp, ip-subscriber";
    container igmp {
      description
        "IGMPconfiguration";
      container default-vrf {
        description
          "Default VRF";
        container explicit-tracking {
          presence "Indicates a explicit-tracking node is configured.";
          description
            "IGMPv3 explicit host tracking";
          leaf enable {
            type boolean;
            mandatory true;
            description
              "Enable or disable, when value is TRUE or
               FALSE respectively";
          }
          leaf access-list-name {
            type xr:Cisco-ios-xr-string {
              length "1..64";
            }
            description
              "Access list specifying tracking group range";
          }
        }
        leaf max-groups {
          type uint32 {
            range "1..40000";
          }
          default "25000";
          description
            "IGMP Max Groups";
        }
        leaf access-group {
          type xr:Cisco-ios-xr-string {
            length "1..64";
          }
          description
            "Access list specifying access-list group range";
        }
        leaf version {
          type uint32 {
            range "1..3";
          }
          default "3";
          description
            "IGMP Version";
        }
        leaf query-interval {
          type uint32 {
            range "1..3600";
          }
          units "second";
          default "60";
          description
            "Query interval in seconds";
        }
        leaf query-max-response-time {
          type uint32 {
            range "1..25";
          }
          units "second";
          default "10";
          description
            "Query response value in seconds";
        }
        leaf multicast-mode {
          type Dyn-tmpl-multicast-mode;
          description
            "Configure Multicast mode variable";
        }
      }
    }
  }

  augment "/ncs:devices/ncs:template/ncs:ned-id/ncs:config/a1:dynamic-template/a1:ip-subscribers/a1:ip-subscriber" {
    description
      "This augment extends the configuration data of
       'Cisco-IOS-XR-subscriber-infra-tmplmgr-cfg'";
    uses ncs_template_IGMP;
  }
  augment "/ncs:devices/ncs:device/ncs:live-status/a1:dynamic-template/a1:ip-subscribers/a1:ip-subscriber" {
    description
      "This augment extends the configuration data of
       'Cisco-IOS-XR-subscriber-infra-tmplmgr-cfg'";
    uses live_ncs_IGMP {
      refine igmp {
        tailf:ncs-device-type "netconf";
        tailf:display-when "not(../../../../../ncs:module) or ../../../../../ncs:module[ncs:name='Cisco-IOS-XR-ipv4-igmp-dyn-tmpl-cfg'] or (../../../../../ncs:live-status-protocol[not(ncs:capability)]) or (../../../../../ncs:live-status-protocol/ncs:capability/ncs:module[.='Cisco-IOS-XR-ipv4-igmp-dyn-tmpl-cfg'])";
      }
    }
  }
  augment "/ncs:devices/ncs:device/ncs:config/a1:dynamic-template/a1:ip-subscribers/a1:ip-subscriber" {
    description
      "This augment extends the configuration data of
       'Cisco-IOS-XR-subscriber-infra-tmplmgr-cfg'";
    uses IGMP {
      refine igmp {
        tailf:ncs-device-type "netconf";
        tailf:display-when "not(../../../../../ncs:module) or ../../../../../ncs:module[ncs:name='Cisco-IOS-XR-ipv4-igmp-dyn-tmpl-cfg']";
      }
    }
  }
  augment "/ncs:devices/ncs:template/ncs:ned-id/ncs:config/a1:dynamic-template/a1:ppps/a1:ppp" {
    description
      "This augment extends the configuration data of
       'Cisco-IOS-XR-subscriber-infra-tmplmgr-cfg'";
    uses ncs_template_IGMP;
  }
  augment "/ncs:devices/ncs:device/ncs:live-status/a1:dynamic-template/a1:ppps/a1:ppp" {
    description
      "This augment extends the configuration data of
       'Cisco-IOS-XR-subscriber-infra-tmplmgr-cfg'";
    uses live_ncs_IGMP {
      refine igmp {
        tailf:ncs-device-type "netconf";
        tailf:display-when "not(../../../../../ncs:module) or ../../../../../ncs:module[ncs:name='Cisco-IOS-XR-ipv4-igmp-dyn-tmpl-cfg'] or (../../../../../ncs:live-status-protocol[not(ncs:capability)]) or (../../../../../ncs:live-status-protocol/ncs:capability/ncs:module[.='Cisco-IOS-XR-ipv4-igmp-dyn-tmpl-cfg'])";
      }
    }
  }
  augment "/ncs:devices/ncs:device/ncs:config/a1:dynamic-template/a1:ppps/a1:ppp" {
    description
      "This augment extends the configuration data of
       'Cisco-IOS-XR-subscriber-infra-tmplmgr-cfg'";
    uses IGMP {
      refine igmp {
        tailf:ncs-device-type "netconf";
        tailf:display-when "not(../../../../../ncs:module) or ../../../../../ncs:module[ncs:name='Cisco-IOS-XR-ipv4-igmp-dyn-tmpl-cfg']";
      }
    }
  }
}

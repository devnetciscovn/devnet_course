module Cisco-IOS-XR-infra-script-mgmt-cfg {
  // Generated by yanger -t ncs
  tailf:mount-id "cisco-iosxr-nc-7.3:cisco-iosxr-nc-7.3";
  tailf:ncs-device-type "netconf";

  namespace "http://cisco.com/ns/yang/Cisco-IOS-XR-infra-script-mgmt-cfg";
  prefix infra-script-mgmt-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-script-mgmt package configuration.

     This module contains definitions
     for the following management objects:
       scripts: Script-mgmt configuration data

     Copyright (c) 2013-2021 by Cisco Systems, Inc.
     All rights reserved.";

  revision 2021-12-07 {
    description
      "checksum type change to Enum";
    semver:module-version "1.0.0";
  }
  revision 2019-04-05 {
    description
      "Establish semantic version baseline.";
  }
  revision 2015-11-09 {
    description
      "IOS XR 6.0 revision.";
  }

  typedef ncs_template_Config-checksum {
    type string;
    description
      "Config checksum";
  }

  typedef ncs_rpc_notif_Config-checksum {
    type enumeration {
      enum "sha256" {
        value 1;
        description
          "SHA256";
      }
    }
    description
      "Config checksum";
  }

  typedef live_ncs_Config-checksum {
    type enumeration {
      enum "sha256" {
        value 1;
        description
          "SHA256";
      }
    }
    description
      "Config checksum";
  }

  typedef Config-checksum {
    type enumeration {
      enum "sha256" {
        value 1;
        description
          "SHA256";
      }
    }
    description
      "Config checksum";
  }

  grouping ncs_template_SCRIPT-TABLE {
    description
      "Common node of exec-script, process-script";
    container scripts {
      description
        "Name of script";
      list script {
        // NCS patched for predictable order
        ordered-by user;
        key "script-name";
        description
          "Config Script activation item";
        container checksum {
          presence "Indicates a checksum node is configured.";
          description
            "Checksum of script";
          leaf checksum-type {
            type ncs_template_Config-checksum;
            // NCS drop mandatory statement
            description
              "Checksum type";
          }
          leaf checksum {
            type string;
            // NCS drop mandatory statement
            description
              "Checksum value";
          }
        }
        leaf script-name {
          type xr:ncs_template_Cisco-ios-xr-string;
          description
            "Script name";
        }
      }
    }
  }

  grouping ncs_rpc_notif_SCRIPT-TABLE {
    description
      "Common node of exec-script, process-script";
    container scripts {
      description
        "Name of script";
      list script {
        key "script-name";
        description
          "Config Script activation item";
        container checksum {
          presence "Indicates a checksum node is configured.";
          description
            "Checksum of script";
          leaf checksum-type {
            type ncs_rpc_notif_Config-checksum;
            mandatory true;
            description
              "Checksum type";
          }
          leaf checksum {
            type string {
              length "64";
            }
            mandatory true;
            description
              "Checksum value";
          }
        }
        leaf script-name {
          type xr:ncs_rpc_notif_Cisco-ios-xr-string;
          description
            "Script name";
        }
      }
    }
  }

  grouping live_ncs_SCRIPT-TABLE {
    description
      "Common node of exec-script, process-script";
    container scripts {
      description
        "Name of script";
      list script {
        key "script-name";
        description
          "Config Script activation item";
        container checksum {
          presence "Indicates a checksum node is configured.";
          description
            "Checksum of script";
          leaf checksum-type {
            type live_ncs_Config-checksum;
            // NCS drop mandatory statement
            description
              "Checksum type";
          }
          leaf checksum {
            type string {
              length "64";
            }
            // NCS drop mandatory statement
            description
              "Checksum value";
          }
        }
        leaf script-name {
          type xr:live_ncs_Cisco-ios-xr-string;
          description
            "Script name";
        }
      }
    }
  }

  grouping SCRIPT-TABLE {
    description
      "Common node of exec-script, process-script";
    container scripts {
      description
        "Name of script";
      list script {
        key "script-name";
        description
          "Config Script activation item";
        container checksum {
          presence "Indicates a checksum node is configured.";
          description
            "Checksum of script";
          leaf checksum-type {
            type Config-checksum;
            mandatory true;
            description
              "Checksum type";
          }
          leaf checksum {
            type string {
              length "64";
            }
            mandatory true;
            description
              "Checksum value";
          }
        }
        leaf script-name {
          type xr:Cisco-ios-xr-string;
          description
            "Script name";
        }
      }
    }
  }

  augment "/ncs:devices/ncs:device/ncs:config" {
    container scripts {
      tailf:ncs-device-type "netconf";
      tailf:display-when "not(../../ncs:module) or ../../ncs:module[ncs:name='Cisco-IOS-XR-infra-script-mgmt-cfg']";
      description
        "Script-mgmt configuration data";
      container exec-script {
        description
          "Exec script";
        uses SCRIPT-TABLE;
      }
      container process-script {
        description
          "Process script";
        uses SCRIPT-TABLE;
      }
    }
  }
  augment "/ncs:devices/ncs:device/ncs:live-status" {
    container scripts {
      tailf:ncs-device-type "netconf";
      tailf:display-when "not(../../ncs:module) or ../../ncs:module[ncs:name='Cisco-IOS-XR-infra-script-mgmt-cfg'] or (../../ncs:live-status-protocol[not(ncs:capability)]) or (../../ncs:live-status-protocol/ncs:capability/ncs:module[.='Cisco-IOS-XR-infra-script-mgmt-cfg'])";
      description
        "Script-mgmt configuration data";
      container exec-script {
        description
          "Exec script";
        uses live_ncs_SCRIPT-TABLE;
      }
      container process-script {
        description
          "Process script";
        uses live_ncs_SCRIPT-TABLE;
      }
    }
  }
  augment "/ncs:devices/ncs:template/ncs:ned-id/ncs:config" {
    container scripts {
      description
        "Script-mgmt configuration data";
      container exec-script {
        description
          "Exec script";
        uses ncs_template_SCRIPT-TABLE;
      }
      container process-script {
        description
          "Process script";
        uses ncs_template_SCRIPT-TABLE;
      }
    }
  }
}

module Cisco-IOS-XR-cmproxy-oper {
  // Generated by yanger -t ncs
  tailf:mount-id "cisco-iosxr-nc-7.3:cisco-iosxr-nc-7.3";
  tailf:ncs-device-type "netconf";

  namespace "http://cisco.com/ns/yang/Cisco-IOS-XR-cmproxy-oper";
  prefix cmproxy-oper;

  import Cisco-IOS-XR-types {
    prefix xr;
  }
  import cisco-semver {
    prefix semver;
  }
  include Cisco-IOS-XR-cmproxy-oper-sub1 {
    revision-date 2020-03-25;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cmproxy package operational data.

     This module contains definitions
     for the following management objects:
       sdr-inventory-vm: Platform VM information

     Copyright (c) 2013-2020 by Cisco Systems, Inc.
     All rights reserved.";

  revision 2020-03-25 {
    description
      "Moved few of the bag fields to private";
    semver:module-version "2.0.0";
  }
  revision 2019-04-05 {
    description
      "Establish semantic version baseline.";
    semver:module-version "1.0.1";
  }
  revision 2018-03-04 {
    description
      "Added good description for bag fields";
  }
  revision 2015-11-09 {
    description
      "IOS XR 6.0 revision.";
  }

  augment "/ncs:devices/ncs:device/ncs:config" {
    // NCS drop config false container 'sdr-inventory-vm'
  }
  augment "/ncs:devices/ncs:device/ncs:live-status" {
    container sdr-inventory-vm {
      tailf:ncs-device-type "netconf";
      tailf:display-when "not(../../ncs:module) or ../../ncs:module[ncs:name='Cisco-IOS-XR-cmproxy-oper'] or (../../ncs:live-status-protocol[not(ncs:capability)]) or (../../ncs:live-status-protocol/ncs:capability/ncs:module[.='Cisco-IOS-XR-cmproxy-oper'])";
      description
        "Platform VM information";
      container nodes {
        description
          "Node directory";
        list node {
          key "name";
          description
            "Node name";
          container node-entries {
            description
              "VM Information";
            list node-entry {
              key "name";
              description
                "VM information for a node";
              leaf name {
                type xr:live_ncs_Cisco-ios-xr-string;
                description
                  "Node name";
              }
              uses live_ncs_CMP-INV-ST;
            }
          }
          leaf name {
            type xr:live_ncs_Cisco-ios-xr-string;
            description
              "Node name";
          }
        }
      }
    }
  }
  augment "/ncs:devices/ncs:template/ncs:ned-id/ncs:config" {
    // NCS drop config false container 'sdr-inventory-vm'
  }
}

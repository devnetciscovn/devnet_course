submodule Cisco-IOS-XR-ncs1k-mxp-headless-oper-sub1 {
  // Generated by yanger -t ncs
  tailf:mount-id "cisco-iosxr-nc-7.3:cisco-iosxr-nc-7.3";

  belongs-to Cisco-IOS-XR-ncs1k-mxp-headless-oper {
    prefix Cisco-IOS-XR-ncs1k-mxp-headless-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1k-mxp-headless package operational data.

     Copyright (c) 2013-2019 by Cisco Systems, Inc.
     All rights reserved.";

  revision 2019-04-05 {
    description
      "Establish semantic version baseline.";
    semver:module-version "1.0.0";
  }
  revision 2017-03-30 {
    description
      "PRBS stats added";
  }
  revision 2015-11-09 {
    description
      "IOS XR 6.0 revision.";
  }

  typedef ncs_template_Mxp-otn-prbs-status {
    type string;
    description
      "Mxp otn prbs status";
  }

  typedef ncs_rpc_notif_Mxp-otn-prbs-status {
    type enumeration {
      enum "locked" {
        value 0;
        description
          "Locked";
      }
      enum "not-locked" {
        value 1;
        description
          "Not Locked";
      }
      enum "not-applicable" {
        value 2;
        description
          "Not Applicable";
      }
      enum "locked-with-errors" {
        value 3;
        description
          "Locked With Errors";
      }
    }
    description
      "Mxp otn prbs status";
  }

  typedef live_ncs_Mxp-otn-prbs-status {
    type enumeration {
      enum "locked" {
        value 0;
        description
          "Locked";
      }
      enum "not-locked" {
        value 1;
        description
          "Not Locked";
      }
      enum "not-applicable" {
        value 2;
        description
          "Not Applicable";
      }
      enum "locked-with-errors" {
        value 3;
        description
          "Locked With Errors";
      }
    }
    description
      "Mxp otn prbs status";
  }

  typedef Mxp-otn-prbs-status {
    type enumeration {
      enum "locked" {
        value 0;
        description
          "Locked";
      }
      enum "not-locked" {
        value 1;
        description
          "Not Locked";
      }
      enum "not-applicable" {
        value 2;
        description
          "Not Applicable";
      }
      enum "locked-with-errors" {
        value 3;
        description
          "Locked With Errors";
      }
    }
    description
      "Mxp otn prbs status";
  }

  grouping ncs_template_MXP-ETHER-PRIM-INFO {
    description
      "Ether statistics";
    leaf rx-pkts-over-sized {
      type string;
      description
        "RxPktsOverSized";
    }
    leaf rx-pkts-bad-fcs {
      type string;
      description
        "RxPktsBadFcs";
    }
    leaf rx-error-jabbers {
      type string;
      description
        "RxErrorJabbers";
    }
    leaf rx-pkts-multicast {
      type string;
      description
        "RxPktsMulticast";
    }
    leaf rx-pkts-broadcast {
      type string;
      description
        "RxPktsBroadcast";
    }
    leaf rx-pkts-under-sized {
      type string;
      description
        "RxPktsUnderSized";
    }
    leaf rx-packets {
      type string;
      description
        "RxPackets";
    }
    leaf rx-total-bytes {
      type string;
      description
        "RxTotalBytes";
    }
    leaf rx-bytes-good {
      type string;
      description
        "RxBytesGood";
    }
    leaf rx-pkts-good {
      type string;
      description
        "RxPktsGood";
    }
    leaf tx-bytes-good {
      type string;
      description
        "TxBytesGood";
    }
    leaf tx-pkts-good {
      type string;
      description
        "TxPktsGood";
    }
    leaf rx-recv-fragments {
      type string;
      description
        "RxRecvFragments";
    }
    leaf rx-pkts64-bytes {
      type string;
      description
        "RxPkts64Bytes";
    }
    leaf rx-pkts65-to127-bytes {
      type string;
      description
        "RxPkts65To127Bytes";
    }
    leaf rx-pkts128to255-bytes {
      type string;
      description
        "RxPkts128to255Bytes";
    }
    leaf rx-pkts256-to511-bytes {
      type string;
      description
        "RxPkts256To511Bytes";
    }
    leaf rx-pkts512-to1023-bytes {
      type string;
      description
        "RxPkts512To1023Bytes";
    }
    leaf rx-pkts1024-to1518-bytes {
      type string;
      description
        "RxPkts1024To1518Bytes";
    }
    leaf rx-pkts-unicast {
      type string;
      description
        "RxPktsUnicast";
    }
    leaf tx-packets {
      type string;
      description
        "TxPackets";
    }
    leaf tx-total-bytes {
      type string;
      description
        "TxTotalBytes";
    }
    leaf tx-pkts-under-sized {
      type string;
      description
        "TxPktsUnderSized";
    }
    leaf tx-pkts-over-sized {
      type string;
      description
        "TxPktsOverSized";
    }
    leaf tx-fragments {
      type string;
      description
        "TxFragments";
    }
    leaf tx-jabber {
      type string;
      description
        "TxJabber";
    }
    leaf tx-bad-fcs {
      type string;
      description
        "TxBadFCS";
    }
    leaf rx-pkt-drop {
      type string;
      description
        "RxPktDrop";
    }
    leaf rx-pause {
      type string;
      description
        "RxPause";
    }
    leaf tx-pause {
      type string;
      description
        "TxPause";
    }
    leaf rx-lldp-pkt {
      type string;
      description
        "RxLldpPkt";
    }
    leaf rx8021q-pkt {
      type string;
      description
        "Rx8021QPkt";
    }
  }

  grouping ncs_template_MXP-HEADLESS-ETHER-PRIM-INFO {
    description
      "Ether Headless Statistics";
    container ether-statistics {
      description
        "Ether Statistics";
      uses ncs_template_MXP-ETHER-PRIM-INFO;
    }
    leaf started-stateful {
      type string;
      description
        "Started Stateful";
    }
    leaf headless-start-time {
      type string;
      description
        "Headless Start Time";
    }
    leaf headless-end-time {
      type string;
      description
        "Headless End Time";
    }
  }

  grouping ncs_template_MXP-OTN-PRBS-INFO {
    description
      "PRBS Statistics";
    leaf ebc {
      type string;
      description
        "EBC";
    }
    leaf sync-status {
      type ncs_template_Mxp-otn-prbs-status;
      description
        "SyncStatus";
    }
  }

  grouping ncs_template_MXP-OTN-CNT-INFO {
    description
      "OTN statistics";
    leaf sm-bip {
      type string;
      description
        "SmBip";
    }
    leaf sm-bei {
      type string;
      description
        "SmBei";
    }
    leaf fec-ec {
      type string;
      description
        "FecEc";
    }
    leaf fec-uc {
      type string;
      description
        "FecUc";
    }
  }

  grouping ncs_template_MXP-HEADLESS-OTN-CNT-INFO {
    description
      "OTN Headless Statistics";
    container otn-statistics {
      description
        "OTN statistics";
      uses ncs_template_MXP-OTN-CNT-INFO;
    }
    container prbs-statistics {
      description
        "PRBS Statistics";
      uses ncs_template_MXP-OTN-PRBS-INFO;
    }
    leaf started-stateful {
      type string;
      description
        "Started Stateful";
    }
    leaf headless-start-time {
      type string;
      description
        "Headless Start Time";
    }
    leaf headless-end-time {
      type string;
      description
        "Headless End Time";
    }
  }

  grouping ncs_rpc_notif_MXP-ETHER-PRIM-INFO {
    description
      "Ether statistics";
    leaf rx-pkts-over-sized {
      type uint64;
      description
        "RxPktsOverSized";
    }
    leaf rx-pkts-bad-fcs {
      type uint64;
      description
        "RxPktsBadFcs";
    }
    leaf rx-error-jabbers {
      type uint64;
      description
        "RxErrorJabbers";
    }
    leaf rx-pkts-multicast {
      type uint64;
      description
        "RxPktsMulticast";
    }
    leaf rx-pkts-broadcast {
      type uint64;
      description
        "RxPktsBroadcast";
    }
    leaf rx-pkts-under-sized {
      type uint64;
      description
        "RxPktsUnderSized";
    }
    leaf rx-packets {
      type uint64;
      description
        "RxPackets";
    }
    leaf rx-total-bytes {
      type uint64;
      description
        "RxTotalBytes";
    }
    leaf rx-bytes-good {
      type uint64;
      description
        "RxBytesGood";
    }
    leaf rx-pkts-good {
      type uint64;
      description
        "RxPktsGood";
    }
    leaf tx-bytes-good {
      type uint64;
      description
        "TxBytesGood";
    }
    leaf tx-pkts-good {
      type uint64;
      description
        "TxPktsGood";
    }
    leaf rx-recv-fragments {
      type uint64;
      description
        "RxRecvFragments";
    }
    leaf rx-pkts64-bytes {
      type uint64;
      description
        "RxPkts64Bytes";
    }
    leaf rx-pkts65-to127-bytes {
      type uint64;
      description
        "RxPkts65To127Bytes";
    }
    leaf rx-pkts128to255-bytes {
      type uint64;
      description
        "RxPkts128to255Bytes";
    }
    leaf rx-pkts256-to511-bytes {
      type uint64;
      description
        "RxPkts256To511Bytes";
    }
    leaf rx-pkts512-to1023-bytes {
      type uint64;
      description
        "RxPkts512To1023Bytes";
    }
    leaf rx-pkts1024-to1518-bytes {
      type uint64;
      description
        "RxPkts1024To1518Bytes";
    }
    leaf rx-pkts-unicast {
      type uint64;
      description
        "RxPktsUnicast";
    }
    leaf tx-packets {
      type uint64;
      description
        "TxPackets";
    }
    leaf tx-total-bytes {
      type uint64;
      description
        "TxTotalBytes";
    }
    leaf tx-pkts-under-sized {
      type uint64;
      description
        "TxPktsUnderSized";
    }
    leaf tx-pkts-over-sized {
      type uint64;
      description
        "TxPktsOverSized";
    }
    leaf tx-fragments {
      type uint64;
      description
        "TxFragments";
    }
    leaf tx-jabber {
      type uint64;
      description
        "TxJabber";
    }
    leaf tx-bad-fcs {
      type uint64;
      description
        "TxBadFCS";
    }
    leaf rx-pkt-drop {
      type uint64;
      description
        "RxPktDrop";
    }
    leaf rx-pause {
      type uint64;
      description
        "RxPause";
    }
    leaf tx-pause {
      type uint64;
      description
        "TxPause";
    }
    leaf rx-lldp-pkt {
      type uint64;
      description
        "RxLldpPkt";
    }
    leaf rx8021q-pkt {
      type uint64;
      description
        "Rx8021QPkt";
    }
  }

  grouping ncs_rpc_notif_MXP-HEADLESS-ETHER-PRIM-INFO {
    description
      "Ether Headless Statistics";
    container ether-statistics {
      description
        "Ether Statistics";
      uses ncs_rpc_notif_MXP-ETHER-PRIM-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping ncs_rpc_notif_MXP-OTN-PRBS-INFO {
    description
      "PRBS Statistics";
    leaf ebc {
      type uint64;
      description
        "EBC";
    }
    leaf sync-status {
      type ncs_rpc_notif_Mxp-otn-prbs-status;
      description
        "SyncStatus";
    }
  }

  grouping ncs_rpc_notif_MXP-OTN-CNT-INFO {
    description
      "OTN statistics";
    leaf sm-bip {
      type uint64;
      description
        "SmBip";
    }
    leaf sm-bei {
      type uint64;
      description
        "SmBei";
    }
    leaf fec-ec {
      type uint64;
      description
        "FecEc";
    }
    leaf fec-uc {
      type uint64;
      description
        "FecUc";
    }
  }

  grouping ncs_rpc_notif_MXP-HEADLESS-OTN-CNT-INFO {
    description
      "OTN Headless Statistics";
    container otn-statistics {
      description
        "OTN statistics";
      uses ncs_rpc_notif_MXP-OTN-CNT-INFO;
    }
    container prbs-statistics {
      description
        "PRBS Statistics";
      uses ncs_rpc_notif_MXP-OTN-PRBS-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping live_ncs_MXP-ETHER-PRIM-INFO {
    description
      "Ether statistics";
    leaf rx-pkts-over-sized {
      type uint64;
      description
        "RxPktsOverSized";
    }
    leaf rx-pkts-bad-fcs {
      type uint64;
      description
        "RxPktsBadFcs";
    }
    leaf rx-error-jabbers {
      type uint64;
      description
        "RxErrorJabbers";
    }
    leaf rx-pkts-multicast {
      type uint64;
      description
        "RxPktsMulticast";
    }
    leaf rx-pkts-broadcast {
      type uint64;
      description
        "RxPktsBroadcast";
    }
    leaf rx-pkts-under-sized {
      type uint64;
      description
        "RxPktsUnderSized";
    }
    leaf rx-packets {
      type uint64;
      description
        "RxPackets";
    }
    leaf rx-total-bytes {
      type uint64;
      description
        "RxTotalBytes";
    }
    leaf rx-bytes-good {
      type uint64;
      description
        "RxBytesGood";
    }
    leaf rx-pkts-good {
      type uint64;
      description
        "RxPktsGood";
    }
    leaf tx-bytes-good {
      type uint64;
      description
        "TxBytesGood";
    }
    leaf tx-pkts-good {
      type uint64;
      description
        "TxPktsGood";
    }
    leaf rx-recv-fragments {
      type uint64;
      description
        "RxRecvFragments";
    }
    leaf rx-pkts64-bytes {
      type uint64;
      description
        "RxPkts64Bytes";
    }
    leaf rx-pkts65-to127-bytes {
      type uint64;
      description
        "RxPkts65To127Bytes";
    }
    leaf rx-pkts128to255-bytes {
      type uint64;
      description
        "RxPkts128to255Bytes";
    }
    leaf rx-pkts256-to511-bytes {
      type uint64;
      description
        "RxPkts256To511Bytes";
    }
    leaf rx-pkts512-to1023-bytes {
      type uint64;
      description
        "RxPkts512To1023Bytes";
    }
    leaf rx-pkts1024-to1518-bytes {
      type uint64;
      description
        "RxPkts1024To1518Bytes";
    }
    leaf rx-pkts-unicast {
      type uint64;
      description
        "RxPktsUnicast";
    }
    leaf tx-packets {
      type uint64;
      description
        "TxPackets";
    }
    leaf tx-total-bytes {
      type uint64;
      description
        "TxTotalBytes";
    }
    leaf tx-pkts-under-sized {
      type uint64;
      description
        "TxPktsUnderSized";
    }
    leaf tx-pkts-over-sized {
      type uint64;
      description
        "TxPktsOverSized";
    }
    leaf tx-fragments {
      type uint64;
      description
        "TxFragments";
    }
    leaf tx-jabber {
      type uint64;
      description
        "TxJabber";
    }
    leaf tx-bad-fcs {
      type uint64;
      description
        "TxBadFCS";
    }
    leaf rx-pkt-drop {
      type uint64;
      description
        "RxPktDrop";
    }
    leaf rx-pause {
      type uint64;
      description
        "RxPause";
    }
    leaf tx-pause {
      type uint64;
      description
        "TxPause";
    }
    leaf rx-lldp-pkt {
      type uint64;
      description
        "RxLldpPkt";
    }
    leaf rx8021q-pkt {
      type uint64;
      description
        "Rx8021QPkt";
    }
  }

  grouping live_ncs_MXP-HEADLESS-ETHER-PRIM-INFO {
    description
      "Ether Headless Statistics";
    container ether-statistics {
      description
        "Ether Statistics";
      uses live_ncs_MXP-ETHER-PRIM-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping live_ncs_MXP-OTN-PRBS-INFO {
    description
      "PRBS Statistics";
    leaf ebc {
      type uint64;
      description
        "EBC";
    }
    leaf sync-status {
      type live_ncs_Mxp-otn-prbs-status;
      description
        "SyncStatus";
    }
  }

  grouping live_ncs_MXP-OTN-CNT-INFO {
    description
      "OTN statistics";
    leaf sm-bip {
      type uint64;
      description
        "SmBip";
    }
    leaf sm-bei {
      type uint64;
      description
        "SmBei";
    }
    leaf fec-ec {
      type uint64;
      description
        "FecEc";
    }
    leaf fec-uc {
      type uint64;
      description
        "FecUc";
    }
  }

  grouping live_ncs_MXP-HEADLESS-OTN-CNT-INFO {
    description
      "OTN Headless Statistics";
    container otn-statistics {
      description
        "OTN statistics";
      uses live_ncs_MXP-OTN-CNT-INFO;
    }
    container prbs-statistics {
      description
        "PRBS Statistics";
      uses live_ncs_MXP-OTN-PRBS-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping MXP-ETHER-PRIM-INFO {
    description
      "Ether statistics";
    leaf rx-pkts-over-sized {
      type uint64;
      description
        "RxPktsOverSized";
    }
    leaf rx-pkts-bad-fcs {
      type uint64;
      description
        "RxPktsBadFcs";
    }
    leaf rx-error-jabbers {
      type uint64;
      description
        "RxErrorJabbers";
    }
    leaf rx-pkts-multicast {
      type uint64;
      description
        "RxPktsMulticast";
    }
    leaf rx-pkts-broadcast {
      type uint64;
      description
        "RxPktsBroadcast";
    }
    leaf rx-pkts-under-sized {
      type uint64;
      description
        "RxPktsUnderSized";
    }
    leaf rx-packets {
      type uint64;
      description
        "RxPackets";
    }
    leaf rx-total-bytes {
      type uint64;
      description
        "RxTotalBytes";
    }
    leaf rx-bytes-good {
      type uint64;
      description
        "RxBytesGood";
    }
    leaf rx-pkts-good {
      type uint64;
      description
        "RxPktsGood";
    }
    leaf tx-bytes-good {
      type uint64;
      description
        "TxBytesGood";
    }
    leaf tx-pkts-good {
      type uint64;
      description
        "TxPktsGood";
    }
    leaf rx-recv-fragments {
      type uint64;
      description
        "RxRecvFragments";
    }
    leaf rx-pkts64-bytes {
      type uint64;
      description
        "RxPkts64Bytes";
    }
    leaf rx-pkts65-to127-bytes {
      type uint64;
      description
        "RxPkts65To127Bytes";
    }
    leaf rx-pkts128to255-bytes {
      type uint64;
      description
        "RxPkts128to255Bytes";
    }
    leaf rx-pkts256-to511-bytes {
      type uint64;
      description
        "RxPkts256To511Bytes";
    }
    leaf rx-pkts512-to1023-bytes {
      type uint64;
      description
        "RxPkts512To1023Bytes";
    }
    leaf rx-pkts1024-to1518-bytes {
      type uint64;
      description
        "RxPkts1024To1518Bytes";
    }
    leaf rx-pkts-unicast {
      type uint64;
      description
        "RxPktsUnicast";
    }
    leaf tx-packets {
      type uint64;
      description
        "TxPackets";
    }
    leaf tx-total-bytes {
      type uint64;
      description
        "TxTotalBytes";
    }
    leaf tx-pkts-under-sized {
      type uint64;
      description
        "TxPktsUnderSized";
    }
    leaf tx-pkts-over-sized {
      type uint64;
      description
        "TxPktsOverSized";
    }
    leaf tx-fragments {
      type uint64;
      description
        "TxFragments";
    }
    leaf tx-jabber {
      type uint64;
      description
        "TxJabber";
    }
    leaf tx-bad-fcs {
      type uint64;
      description
        "TxBadFCS";
    }
    leaf rx-pkt-drop {
      type uint64;
      description
        "RxPktDrop";
    }
    leaf rx-pause {
      type uint64;
      description
        "RxPause";
    }
    leaf tx-pause {
      type uint64;
      description
        "TxPause";
    }
    leaf rx-lldp-pkt {
      type uint64;
      description
        "RxLldpPkt";
    }
    leaf rx8021q-pkt {
      type uint64;
      description
        "Rx8021QPkt";
    }
  }

  grouping MXP-HEADLESS-ETHER-PRIM-INFO {
    description
      "Ether Headless Statistics";
    container ether-statistics {
      description
        "Ether Statistics";
      uses MXP-ETHER-PRIM-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }

  grouping MXP-OTN-PRBS-INFO {
    description
      "PRBS Statistics";
    leaf ebc {
      type uint64;
      description
        "EBC";
    }
    leaf sync-status {
      type Mxp-otn-prbs-status;
      description
        "SyncStatus";
    }
  }

  grouping MXP-OTN-CNT-INFO {
    description
      "OTN statistics";
    leaf sm-bip {
      type uint64;
      description
        "SmBip";
    }
    leaf sm-bei {
      type uint64;
      description
        "SmBei";
    }
    leaf fec-ec {
      type uint64;
      description
        "FecEc";
    }
    leaf fec-uc {
      type uint64;
      description
        "FecUc";
    }
  }

  grouping MXP-HEADLESS-OTN-CNT-INFO {
    description
      "OTN Headless Statistics";
    container otn-statistics {
      description
        "OTN statistics";
      uses MXP-OTN-CNT-INFO;
    }
    container prbs-statistics {
      description
        "PRBS Statistics";
      uses MXP-OTN-PRBS-INFO;
    }
    leaf started-stateful {
      type boolean;
      description
        "Started Stateful";
    }
    leaf headless-start-time {
      type string {
        length "0..64";
      }
      description
        "Headless Start Time";
    }
    leaf headless-end-time {
      type string {
        length "0..64";
      }
      description
        "Headless End Time";
    }
  }
}

module Cisco-IOS-XR-ppp-ma-syslog-cfg {
  // Generated by yanger -t ncs
  tailf:mount-id "cisco-iosxr-nc-7.3:cisco-iosxr-nc-7.3";
  tailf:ncs-device-type "netconf";

  namespace "http://cisco.com/ns/yang/Cisco-IOS-XR-ppp-ma-syslog-cfg";
  prefix ppp-ma-syslog-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ppp-ma-syslog package configuration.

     This module contains definitions
     for the following management objects:
       ppp: PPP configuration

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    container ppp {
      tailf:ncs-device-type "netconf";
      tailf:display-when "not(../../ncs:module) or ../../ncs:module[ncs:name='Cisco-IOS-XR-ppp-ma-syslog-cfg']";
      description
        "PPP configuration";
      container syslog {
        description
          "syslog option for session status";
        leaf enable-session-status {
          type empty;
          description
            "Enable syslog for ppp session status";
        }
      }
    }
  }
  augment "/ncs:devices/ncs:device/ncs:live-status" {
    container ppp {
      tailf:ncs-device-type "netconf";
      tailf:display-when "not(../../ncs:module) or ../../ncs:module[ncs:name='Cisco-IOS-XR-ppp-ma-syslog-cfg'] or (../../ncs:live-status-protocol[not(ncs:capability)]) or (../../ncs:live-status-protocol/ncs:capability/ncs:module[.='Cisco-IOS-XR-ppp-ma-syslog-cfg'])";
      description
        "PPP configuration";
      container syslog {
        description
          "syslog option for session status";
        leaf enable-session-status {
          type empty;
          description
            "Enable syslog for ppp session status";
        }
      }
    }
  }
  augment "/ncs:devices/ncs:template/ncs:ned-id/ncs:config" {
    container ppp {
      description
        "PPP configuration";
      container syslog {
        description
          "syslog option for session status";
        leaf enable-session-status {
          type empty;
          description
            "Enable syslog for ppp session status";
        }
      }
    }
  }
}

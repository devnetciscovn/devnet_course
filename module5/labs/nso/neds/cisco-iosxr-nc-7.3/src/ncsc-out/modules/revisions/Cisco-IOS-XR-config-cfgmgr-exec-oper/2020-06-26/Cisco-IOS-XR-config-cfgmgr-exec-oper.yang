module Cisco-IOS-XR-config-cfgmgr-exec-oper {
  // Generated by yanger -t ncs
  tailf:mount-id "cisco-iosxr-nc-7.3:cisco-iosxr-nc-7.3";
  tailf:ncs-device-type "netconf";

  namespace "http://cisco.com/ns/yang/Cisco-IOS-XR-config-cfgmgr-exec-oper";
  prefix config-cfgmgr-exec-oper;

  import Cisco-IOS-XR-types {
    prefix xr;
  }
  import cisco-semver {
    prefix semver;
  }
  include Cisco-IOS-XR-config-cfgmgr-exec-oper-sub1 {
    revision-date 2020-06-26;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-cfgmgr-exec package operational data.

     This module contains definitions
     for the following management objects:
       config-manager: Show Configuration <*> Global path information

     Copyright (c) 2013-2020 by Cisco Systems, Inc.
     All rights reserved.";

  revision 2020-06-26 {
    description
      "Updated schema to restrict user-access based on taskgroup.";
    semver:module-version "1.0.1";
  }
  revision 2019-04-05 {
    description
      "Establish semantic version baseline.";
    semver:module-version "1.0.1";
  }
  revision 2017-09-07 {
    description
      "Fixed type translation error.";
  }
  revision 2015-11-09 {
    description
      "IOS XR 6.0 revision.";
  }

  augment "/ncs:devices/ncs:device/ncs:config" {
    // NCS drop config false container 'config-manager'
  }
  augment "/ncs:devices/ncs:device/ncs:live-status" {
    container config-manager {
      tailf:ncs-device-type "netconf";
      tailf:display-when "not(../../ncs:module) or ../../ncs:module[ncs:name='Cisco-IOS-XR-config-cfgmgr-exec-oper'] or (../../ncs:live-status-protocol[not(ncs:capability)]) or (../../ncs:live-status-protocol/ncs:capability/ncs:module[.='Cisco-IOS-XR-config-cfgmgr-exec-oper'])";
      description
        "Show Configuration <*> Global path information";
      container global {
        description
          "Show Configuration <*> Global path information";
        container config-commit {
          description
            "Show Configuration Commit <*> Global path
             information";
          container commits {
            description
              "Show Configuration Commit List Detail";
            list commit {
              key "commit";
              description
                "Commit information for a specific commit
                 entry";
              leaf commit {
                type xr:live_ncs_Cisco-ios-xr-string;
                description
                  "Each Session Details";
              }
              uses live_ncs_CFGCOMMITLIST-D-ENTRY;
            }
          }
        }
        container history-tables {
          description
            "Show Configuration History <*> Global path
             information";
          list history-table {
            key "history-type";
            description
              "List of possible type of History";
            leaf history-type {
              type xr:live_ncs_Cisco-ios-xr-string;
              description
                "Type of History";
            }
            list history {
              key "history";
              description
                "History summary information for a specific
                 type of history";
              leaf history {
                type xr:live_ncs_Cisco-ios-xr-string;
                description
                  "History Record";
              }
              uses live_ncs_CONFIGURATIONHISTORY-ENTRY;
            }
          }
        }
        container config-session {
          description
            "Show Configuration Session <*> Global path
             information";
          container sessions {
            description
              "Show Configuration Session Detail";
            list session {
              key "session";
              description
                "Session information for a specific session
                 entry";
              leaf session {
                type xr:live_ncs_Cisco-ios-xr-string;
                description
                  "Each Session Details";
              }
              uses live_ncs_CFGSESSION-D-ENTRY;
            }
          }
        }
      }
    }
  }
  augment "/ncs:devices/ncs:template/ncs:ned-id/ncs:config" {
    // NCS drop config false container 'config-manager'
  }
}

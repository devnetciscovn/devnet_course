submodule Cisco-IOS-XR-crypto-macsec-mka-oper-sub1 {
  // Generated by yanger -t ncs
  tailf:mount-id "cisco-iosxr-nc-7.3:cisco-iosxr-nc-7.3";

  belongs-to Cisco-IOS-XR-crypto-macsec-mka-oper {
    prefix Cisco-IOS-XR-crypto-macsec-mka-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR crypto-macsec-mka package operational data.

     Copyright (c) 2013-2021 by Cisco Systems, Inc.
     All rights reserved.";

  revision 2021-04-28 {
    description
      "Modified to display port power status
       2021-04-15
         Modified to display session stats";
    semver:module-version "1.2.0";
  }
  revision 2019-05-27 {
    description
      "MKA ISSU";
    semver:module-version "1.1.0";
  }
  revision 2019-04-05 {
    description
      "MKA ISSU";
    semver:module-version "1.1.0";
  }
  revision 2015-11-09 {
    description
      "IOS XR 6.0 revision.";
  }

  typedef ncs_template_Mka-authentication-mode {
    type string;
    description
      "Mka authentication mode";
  }

  typedef ncs_template_Macsec-service-port {
    type string;
    description
      "Macsec service port";
  }

  typedef ncs_template_Macsec-cipher-suite {
    type string;
    description
      "Macsec cipher suite";
  }

  typedef ncs_rpc_notif_Mka-authentication-mode {
    type enumeration {
      enum "auth-mode-invalid" {
        value 0;
        description
          "Invalid authentication mode";
      }
      enum "auth-mode-psk" {
        value 1;
        description
          "Preshared Key";
      }
      enum "auth-mode-eap" {
        value 2;
        description
          "EAP";
      }
    }
    description
      "Mka authentication mode";
  }

  typedef ncs_rpc_notif_Macsec-service-port {
    type enumeration {
      enum "macsec-service-port-none" {
        value 0;
        description
          "Macsec Service not enabled";
      }
      enum "macsec-service-port-encryption" {
        value 1;
        description
          "Macsec Service Encryption Port";
      }
      enum "macsec-service-port-decryption" {
        value 2;
        description
          "Macsec Service Decryption Port";
      }
    }
    description
      "Macsec service port";
  }

  typedef ncs_rpc_notif_Macsec-cipher-suite {
    type enumeration {
      enum "cipher-suite-none" {
        value 0;
        description
          "Invalid MACsec cipher";
      }
      enum "cipher-suite-gcm-aes-128" {
        value 1;
        description
          "128 bit GCM_AES MACsec cipher suite";
      }
      enum "cipher-suite-gcm-aes-256" {
        value 2;
        description
          "256 bit GCM_AES MACsec cipher suite";
      }
      enum "cipher-suite-gcm-aes-128-xpn" {
        value 3;
        description
          "128 bit GCM_AES MACsec XPN cipher suite";
      }
      enum "cipher-suite-gcm-aes-256-xpn" {
        value 4;
        description
          "256 bit GCM_AES MACsec XPN cipher suite";
      }
    }
    description
      "Macsec cipher suite";
  }

  typedef live_ncs_Mka-authentication-mode {
    type enumeration {
      enum "auth-mode-invalid" {
        value 0;
        description
          "Invalid authentication mode";
      }
      enum "auth-mode-psk" {
        value 1;
        description
          "Preshared Key";
      }
      enum "auth-mode-eap" {
        value 2;
        description
          "EAP";
      }
    }
    description
      "Mka authentication mode";
  }

  typedef live_ncs_Macsec-service-port {
    type enumeration {
      enum "macsec-service-port-none" {
        value 0;
        description
          "Macsec Service not enabled";
      }
      enum "macsec-service-port-encryption" {
        value 1;
        description
          "Macsec Service Encryption Port";
      }
      enum "macsec-service-port-decryption" {
        value 2;
        description
          "Macsec Service Decryption Port";
      }
    }
    description
      "Macsec service port";
  }

  typedef live_ncs_Macsec-cipher-suite {
    type enumeration {
      enum "cipher-suite-none" {
        value 0;
        description
          "Invalid MACsec cipher";
      }
      enum "cipher-suite-gcm-aes-128" {
        value 1;
        description
          "128 bit GCM_AES MACsec cipher suite";
      }
      enum "cipher-suite-gcm-aes-256" {
        value 2;
        description
          "256 bit GCM_AES MACsec cipher suite";
      }
      enum "cipher-suite-gcm-aes-128-xpn" {
        value 3;
        description
          "128 bit GCM_AES MACsec XPN cipher suite";
      }
      enum "cipher-suite-gcm-aes-256-xpn" {
        value 4;
        description
          "256 bit GCM_AES MACsec XPN cipher suite";
      }
    }
    description
      "Macsec cipher suite";
  }

  typedef Mka-authentication-mode {
    type enumeration {
      enum "auth-mode-invalid" {
        value 0;
        description
          "Invalid authentication mode";
      }
      enum "auth-mode-psk" {
        value 1;
        description
          "Preshared Key";
      }
      enum "auth-mode-eap" {
        value 2;
        description
          "EAP";
      }
    }
    description
      "Mka authentication mode";
  }

  typedef Macsec-service-port {
    type enumeration {
      enum "macsec-service-port-none" {
        value 0;
        description
          "Macsec Service not enabled";
      }
      enum "macsec-service-port-encryption" {
        value 1;
        description
          "Macsec Service Encryption Port";
      }
      enum "macsec-service-port-decryption" {
        value 2;
        description
          "Macsec Service Decryption Port";
      }
    }
    description
      "Macsec service port";
  }

  typedef Macsec-cipher-suite {
    type enumeration {
      enum "cipher-suite-none" {
        value 0;
        description
          "Invalid MACsec cipher";
      }
      enum "cipher-suite-gcm-aes-128" {
        value 1;
        description
          "128 bit GCM_AES MACsec cipher suite";
      }
      enum "cipher-suite-gcm-aes-256" {
        value 2;
        description
          "256 bit GCM_AES MACsec cipher suite";
      }
      enum "cipher-suite-gcm-aes-128-xpn" {
        value 3;
        description
          "128 bit GCM_AES MACsec XPN cipher suite";
      }
      enum "cipher-suite-gcm-aes-256-xpn" {
        value 4;
        description
          "256 bit GCM_AES MACsec XPN cipher suite";
      }
    }
    description
      "Macsec cipher suite";
  }

  grouping ncs_template_MKA-INTERFACE-SUMMARY {
    description
      "MKA INTERFACE SUMMARY";
    leaf interface-name {
      type string;
      description
        "macsec configured interface";
    }
    leaf short-name {
      type string;
      description
        "Short Name String";
    }
    leaf key-chain {
      type string;
      description
        "Name  of the Key chain";
    }
    leaf policy {
      type string;
      description
        "Policy name";
    }
    leaf macsec-svc-port {
      type string;
      description
        "Is macsec-service port or not";
    }
    leaf macsec-svc-port-type {
      type ncs_template_Macsec-service-port;
      description
        "Macsec-service Encryption / Decryption port";
    }
    leaf svcport-short-name {
      type string;
      description
        "Macsec Service paired port Short Name String";
    }
    leaf mka-mode {
      type ncs_template_Mka-authentication-mode;
      description
        "MKA authentication mode";
    }
    leaf fallback-keychain {
      type string;
      description
        "fallback Keychain name";
    }
    leaf macsec-shutdown {
      type string;
      description
        "MacsecShutdown";
    }
    leaf macsec-power-status {
      type string;
      description
        "MACsec Power Status";
    }
  }

  grouping ncs_template_MKA-INTERFACE-INFO {
    description
      "MKA INTERFACE INFO";
    container interface-summary {
      description
        "MKA Interface Summary";
      uses ncs_template_MKA-INTERFACE-SUMMARY;
    }
  }

  grouping ncs_template_MKPDU-CA-RX-FAIL {
    description
      "MKPDU CA RX FAIL";
    leaf rx-icv-validation-fail {
      type string;
      description
        "Rx ICV validation fail";
    }
    leaf rx-bad-peer-mn {
      type string;
      description
        "Rx Bad Peer MN";
    }
    leaf rx-non-recent-peerlist-mn {
      type string;
      description
        "Rx non-recent peerlist MN";
    }
    leaf rx-sak-use-kn-mismatch {
      type string;
      description
        "Rx SAK USE KN mismatch";
    }
    leaf rx-sak-use-rx-not-set {
      type string;
      description
        "Rx SAK USE rx not set";
    }
    leaf rx-sak-use-key-mi-mismatch {
      type string;
      description
        "Rx SAK USE Key MI mismatch";
    }
    leaf rx-sak-use-an-not-in-use {
      type string;
      description
        "Rx SAK USE AN not in use";
    }
    leaf rx-sak-use-ks-rx-tx-not-set {
      type string;
      description
        "Rx SAK USE KS RX/TX not set";
    }
  }

  grouping ncs_template_MKPDU-CA-RX {
    description
      "MKPDU CA RX";
    leaf mkpdu-received {
      type string;
      description
        "MKPDU Received";
    }
    leaf dist-sak {
      type string;
      description
        "Distributed SAK";
    }
    leaf dist-cak {
      type string;
      description
        "Distributed CAK";
    }
  }

  grouping ncs_template_MKPDU-CA-TX {
    description
      "MKPDU CA TX";
    leaf mkpdu-transmitted {
      type string;
      description
        "MKPDU Transmitted";
    }
    leaf dist-sak {
      type string;
      description
        "Distributed SAK";
    }
    leaf dist-cak {
      type string;
      description
        "Distributed CAK";
    }
  }

  grouping ncs_template_MKA-MKPDU-CA-STATS {
    description
      "MKA MKPDU CA STATS";
    container ca-tx {
      description
        "MKPDU CA tx stats";
      uses ncs_template_MKPDU-CA-TX;
    }
    container ca-rx {
      description
        "MKPDU CA rx stats";
      uses ncs_template_MKPDU-CA-RX;
    }
    container ca-rx-fail {
      description
        "CA Rx Fail";
      uses ncs_template_MKPDU-CA-RX-FAIL;
    }
  }

  grouping ncs_template_MKA-KEY-DERIVATION-STATS {
    description
      "MKA KEY DERIVATION STATS";
    leaf sak-generated {
      type string;
      description
        "SAK Generated";
    }
    leaf sak-rekeyed {
      type string;
      description
        "SAK Rekeyed";
    }
    leaf sak-received {
      type string;
      description
        "SAK Received";
    }
    leaf sak-resp-rvcd {
      type string;
      description
        "SAK Respone Received";
    }
    leaf pairwise-cak-derived {
      type string;
      description
        "Pairwise CAK derived";
    }
    leaf pairwise-cak-rekey {
      type string;
      description
        "Pairwise CAK rekey";
    }
  }

  grouping ncs_template_MKA-INTF-CA-STATS {
    description
      "MKA INTF CA STATS";
    container key-derivation-stats {
      description
        "MKA Key derivation stats";
      uses ncs_template_MKA-KEY-DERIVATION-STATS;
    }
    container mkpdu-stats {
      description
        "MKA MKPDU CA stats";
      uses ncs_template_MKA-MKPDU-CA-STATS;
    }
    leaf ckn {
      type string;
      description
        "CKN";
    }
    leaf ca-type {
      type string;
      description
        "CA type";
    }
  }

  grouping ncs_template_MKA-MACSEC-FAILURE {
    description
      "MKA MACSEC FAILURE";
    leaf rx-sc-creation {
      type string;
      description
        "Rx SC creation failure";
    }
    leaf tx-sc-creation {
      type string;
      description
        "Tx SC creation failure";
    }
    leaf rx-sa-install {
      type string;
      description
        "Rx SA install failure";
    }
    leaf tx-sa-install {
      type string;
      description
        "Tx SA install failure";
    }
  }

  grouping ncs_template_MKA-SAK-FAILURE {
    description
      "MKA SAK FAILURE";
    leaf sak-gen {
      type string;
      description
        "SAK gen failure";
    }
    leaf hash-key-gen {
      type string;
      description
        "Hash key gen failure";
    }
    leaf sak-encr-wrap {
      type string;
      description
        "SAK Encryption/Wrap Failure";
    }
    leaf sak-decr-unwrap {
      type string;
      description
        "SAK Decryption/Unwrap Failure";
    }
  }

  grouping ncs_template_MKA-IDB-FAILURE-STATS {
    description
      "MKA IDB FAILURE STATS";
    container sak-failure {
      description
        "MKA IDB SAK Failure";
      uses ncs_template_MKA-SAK-FAILURE;
    }
    container macsec-failure {
      description
        "MKA IDB MACsec Failure";
      uses ncs_template_MKA-MACSEC-FAILURE;
    }
  }

  grouping ncs_template_MKPDU-OPER-STATS {
    description
      "MKPDU OPER STATS";
    leaf tx-success {
      type string;
      description
        "MKPDU Tx Success";
    }
    leaf rx-success {
      type string;
      description
        "MKPDU Rx Success";
    }
    leaf tx-force-suspended {
      type string;
      description
        "MKPDU Tx force suspended";
    }
    leaf rx-force-suspended {
      type string;
      description
        "MKPDU Rx force suspended";
    }
    leaf no-tx-on-intf-down {
      type string;
      description
        "No Tx on intf down";
    }
    leaf no-rx-on-intf-down {
      type string;
      description
        "No Rx on intf down";
    }
    leaf tx-fail {
      type string;
      description
        "Tx Fail";
    }
    leaf tx-pkt-build-fail {
      type string;
      description
        "Tx Pkt Build Fail";
    }
    leaf rx-ca-not-found {
      type string;
      description
        "Rx CA not found";
    }
    leaf rx-error {
      type string;
      description
        "Rx Error";
    }
    leaf rx-invalid-length {
      type string;
      description
        "Rx Invalid length";
    }
    leaf rx-invalid-ckn {
      type string;
      description
        "Rx invalid ckn";
    }
    leaf rx-icv-validation-fail {
      type string;
      description
        "Rx ICV validation fail";
    }
    leaf rx-bad-peer-mn {
      type string;
      description
        "Rx Bad Peer MN";
    }
    leaf rx-non-recent-peerlist-mn {
      type string;
      description
        "Rx non-recent peerlist MN";
    }
    leaf rx-sak-use-kn-mismatch {
      type string;
      description
        "Rx SAK USE KN mismatch";
    }
    leaf rx-sak-use-rx-not-set {
      type string;
      description
        "Rx SAK USE rx not set";
    }
    leaf rx-sak-use-key-mi-mismatch {
      type string;
      description
        "Rx SAK USE Key MI mismatch";
    }
    leaf rx-sak-use-an-not-in-use {
      type string;
      description
        "Rx SAK USE AN not in use";
    }
    leaf rx-sak-use-ks-rx-tx-not-set {
      type string;
      description
        "Rx SAK USE KS RX/TX not set";
    }
    leaf rx-pkt-sak-use-ethertype-mismatch {
      type string;
      description
        "RX Packet ethertype mismatch";
    }
    leaf rx-pkt-source-mac-null {
      type string;
      description
        "Rx Packet Source mac null";
    }
    leaf rx-pkt-dest-mac-null {
      type string;
      description
        "Rx Packet dest mac null";
    }
    leaf rx-pkt-pyld-null {
      type string;
      description
        "Rx Packet Payload Null";
    }
  }

  grouping ncs_template_MKA-INTF-IDB-STATS {
    description
      "MKA INTF IDB STATS";
    container mkpdu-stats {
      description
        "MKPDU Stats";
      uses ncs_template_MKPDU-OPER-STATS;
    }
    container failure-stats {
      description
        "MKA IDB Failure Stats";
      uses ncs_template_MKA-IDB-FAILURE-STATS;
    }
  }

  grouping ncs_template_LAST-SAK-DATA {
    description
      "LAST SAK DATA";
    leaf an {
      type string;
      description
        "AN";
    }
    leaf sa-install-time {
      type string;
      description
        "SA Install Time";
    }
  }

  grouping ncs_template_MKA-INTF-SESSION-STATS {
    description
      "MKA INTF SESSION STATS";
    container sak-data {
      description
        "Latest SAK Data";
      uses ncs_template_LAST-SAK-DATA;
    }
    leaf link-secure-up-time {
      type string;
      description
        "Link Secure Uptime";
    }
    leaf session-up-time {
      type string;
      description
        "Session Uptime";
    }
    leaf sak-rekey-count-ha {
      type string;
      description
        "Number of SAK Rekeys (since link secured)";
    }
    leaf sak-rekey-count {
      type string;
      description
        "Number of SAK Rekeys";
    }
  }

  grouping ncs_template_MKA-INTF-STATISTICS {
    description
      "MKA INTF STATISTICS";
    container session-stats {
      description
        "Session Stats for interface";
      uses ncs_template_MKA-INTF-SESSION-STATS;
    }
    container idb-stats {
      description
        "IDB stats for interface";
      uses ncs_template_MKA-INTF-IDB-STATS;
    }
    leaf interface-name {
      type string;
      description
        "Interface Name";
    }
    list ca-stat {
      // NCS patched for predictable order
      ordered-by user;
      description
        "List of CA stats";
      uses ncs_template_MKA-INTF-CA-STATS;
    }
  }

  grouping ncs_template_SUSPEND-PEER-DATA {
    description
      "SUSPEND PEER DATA";
    leaf rx-sci {
      type string;
      description
        "RX SCI";
    }
    leaf rx-ssci {
      type string;
      description
        "RX SSCI";
    }
  }

  grouping ncs_template_PEER-DATA {
    description
      "PEER DATA";
    leaf mi {
      type string;
      description
        "Member ID";
    }
    leaf sci {
      type string;
      description
        "Rx SCI";
    }
    leaf mn {
      type string;
      description
        "Message Number";
    }
    leaf priority {
      type string;
      description
        "KS Priority";
    }
    leaf ssci {
      type string;
      description
        "Peer SSCI";
    }
  }

  grouping ncs_template_CA-DATA {
    description
      "CA DATA";
    container peers-status {
      description
        "Peers Status";
      uses ncs_template_PEERS-STATUS-DATA;
    }
    leaf is-key-server {
      type string;
      description
        "Is Key Server";
    }
    leaf status {
      type string;
      description
        "Session Status [Secured/Not Secured]";
    }
    leaf num-live-peers {
      type string;
      description
        "Number of Live Peers";
    }
    leaf first-ca {
      type string;
      description
        "Is First CA";
    }
    leaf peer-sci {
      type string;
      description
        "Peer SCI(MAC)";
    }
    leaf num-live-peers-responded {
      type string;
      description
        "Number of Live Peers responded";
    }
    leaf ckn {
      type string;
      description
        "CKN";
    }
    leaf my-mi {
      type string;
      description
        "Member Identifier";
    }
    leaf my-mn {
      type string;
      description
        "Message Number";
    }
    leaf authenticator {
      type string;
      description
        "authenticator";
    }
    leaf num-suspend-request {
      type string;
      description
        "Number of Suspend Request";
    }
    leaf status-description {
      type string;
      description
        "Status Description";
    }
    leaf authentication-mode {
      type string;
      description
        "CA Authentication Mode
         :PRIMARY-PSK/FALLBACK-PSK/EAP";
    }
    leaf key-chain {
      type string;
      description
        "Key Chain name";
    }
    list live-peer {
      // NCS patched for predictable order
      ordered-by user;
      description
        "Live Peer List";
      uses ncs_template_PEER-DATA;
    }
    list potential-peer {
      // NCS patched for predictable order
      ordered-by user;
      description
        "Potential Peer List";
      uses ncs_template_PEER-DATA;
    }
    list dormant-peer {
      // NCS patched for predictable order
      ordered-by user;
      description
        "Dormant Peer List";
      uses ncs_template_PEER-DATA;
    }
    list suspend-peer {
      // NCS patched for predictable order
      ordered-by user;
      description
        "Suspend Peer List";
      uses ncs_template_SUSPEND-PEER-DATA;
    }
  }

  grouping ncs_template_PEER-STATUS-DATA-INTERNAL {
    description
      "PEER STATUS DATA INTERNAL";
    leaf mi {
      type string;
      description
        "Member ID";
    }
    leaf icv-status {
      type string;
      description
        "ICV Status";
    }
    leaf icv-check-timestamp {
      type string;
      description
        "ICV Check Timestamp";
    }
  }

  grouping ncs_template_PEER-STATUS-DATA {
    description
      "PEER STATUS DATA";
    container peer-data {
      description
        "Peer Status Data";
      uses ncs_template_PEER-STATUS-DATA-INTERNAL;
    }
    leaf sci {
      type string;
      description
        "Rx SCI";
    }
  }

  grouping ncs_template_PEERS-STATUS-DATA {
    description
      "PEERS STATUS DATA";
    leaf tx-mkpdu-timestamp {
      type string;
      description
        "Tx MKPDU Timestamp";
    }
    leaf peer-count {
      type string;
      description
        "Peer Count";
    }
    list peer {
      // NCS patched for predictable order
      ordered-by user;
      description
        "Peer List";
      uses ncs_template_PEER-STATUS-DATA;
    }
  }

  grouping ncs_template_FALLBACK-KEEPALIVE-DATA {
    description
      "FALLBACK KEEPALIVE DATA";
    container peers-status {
      description
        "Peers Status";
      uses ncs_template_PEERS-STATUS-DATA;
    }
    leaf ckn {
      type string;
      description
        "CKN";
    }
    leaf mi {
      type string;
      description
        "Member Identifier";
    }
    leaf mn {
      type string;
      description
        "Message Number";
    }
  }

  grouping ncs_template_VP-DATA {
    description
      "VP DATA";
    leaf my-sci {
      type string;
      description
        "Local SCI(MAC)";
    }
    leaf virtual-port-id {
      type string;
      description
        "Virtual Port ID";
    }
    leaf latest-rx {
      type string;
      description
        "Latest Rx status";
    }
    leaf latest-tx {
      type string;
      description
        "Latest Tx status";
    }
    leaf latest-an {
      type string;
      description
        "Latest SAK AN";
    }
    leaf latest-ki {
      type string;
      description
        "Latest SAK KI";
    }
    leaf latest-kn {
      type string;
      description
        "Latest SAK KN";
    }
    leaf old-rx {
      type string;
      description
        "Old Rx status";
    }
    leaf old-tx {
      type string;
      description
        "Old Tx status";
    }
    leaf old-an {
      type string;
      description
        "Old SAK AN";
    }
    leaf old-ki {
      type string;
      description
        "Old SAK KI";
    }
    leaf old-kn {
      type string;
      description
        "Old SAK KN";
    }
    leaf wait-time {
      type string;
      description
        "SAK Transmit Wait Time";
    }
    leaf retire-time {
      type string;
      description
        "SAK Retire time";
    }
    leaf macsec-cipher-suite {
      type ncs_template_Macsec-cipher-suite;
      description
        "SAK Cipher Suite";
    }
    leaf ssci {
      type string;
      description
        "SSCI of the Local TxSC";
    }
    leaf time-to-sak-rekey {
      type string;
      description
        "Next SAK Rekey time in Sec";
    }
    leaf time-to-exit-suspension {
      type string;
      description
        "Time to exit suspension";
    }
    list fallback-keepalive {
      // NCS patched for predictable order
      ordered-by user;
      description
        "Fallback Keepalive";
      uses ncs_template_FALLBACK-KEEPALIVE-DATA;
    }
  }

  grouping ncs_template_MKA-VLAN-TAG {
    description
      "MKA VLAN TAG";
    leaf ether-type {
      type string;
      description
        "EtherType";
    }
    leaf priority {
      type string;
      description
        "Priority";
    }
    leaf cfi {
      type string;
      description
        "Cannonical Format Identifier";
    }
    leaf vlan-id {
      type string;
      description
        "Vlan Id";
    }
  }

  grouping ncs_template_MKA-SESSION-SUMMARY {
    description
      "MKA SESSION SUMMARY";
    container outer-tag {
      description
        "VLAN Outer TAG";
      uses ncs_template_MKA-VLAN-TAG;
    }
    container inner-tag {
      description
        "VLAN Inner TAG";
      uses ncs_template_MKA-VLAN-TAG;
    }
    leaf interface-name {
      type string;
      description
        "macsec configured interface";
    }
    leaf inherited-policy {
      type string;
      description
        "Is Inherited Policy";
    }
    leaf policy {
      type string;
      description
        "Policy Name";
    }
    leaf priority {
      type string;
      description
        "Key Server Priority";
    }
    leaf my-mac {
      type string;
      description
        "My MAC";
    }
    leaf delay-protection {
      type string;
      description
        "Delay Protect";
    }
    leaf replay-protect {
      type string;
      description
        "Replay Protect";
    }
    leaf window-size {
      type string;
      description
        "Replay Window Size";
    }
    leaf include-icv-indicator {
      type string;
      description
        "IncludeICVIndicator";
    }
    leaf confidentiality-offset {
      type string;
      description
        "Confidentiality Offset";
    }
    leaf algo-agility {
      type string;
      description
        "Alogorithm Agility";
    }
    leaf capability {
      type string;
      description
        "MACSec Capability";
    }
    leaf mka-cipher-suite {
      type string;
      description
        "MKA Cipher Suite";
    }
    leaf configured-mac-sec-cipher-suite {
      type string;
      description
        "configured cipher suite";
    }
    leaf mac-sec-desired {
      type string;
      description
        "MACSec Desired";
    }
  }

  grouping ncs_template_MKA-SESSION {
    description
      "MKA SESSION";
    container session-summary {
      description
        "Session summary";
      uses ncs_template_MKA-SESSION-SUMMARY;
    }
    container vp {
      description
        "Virtual Pointer Info";
      uses ncs_template_VP-DATA;
    }
    list ca {
      // NCS patched for predictable order
      ordered-by user;
      description
        "CA List for a Session";
      uses ncs_template_CA-DATA;
    }
  }

  grouping ncs_rpc_notif_MKA-INTERFACE-SUMMARY {
    description
      "MKA INTERFACE SUMMARY";
    leaf interface-name {
      type string;
      description
        "macsec configured interface";
    }
    leaf short-name {
      type string;
      description
        "Short Name String";
    }
    leaf key-chain {
      type string;
      description
        "Name  of the Key chain";
    }
    leaf policy {
      type string;
      description
        "Policy name";
    }
    leaf macsec-svc-port {
      type boolean;
      description
        "Is macsec-service port or not";
    }
    leaf macsec-svc-port-type {
      type ncs_rpc_notif_Macsec-service-port;
      description
        "Macsec-service Encryption / Decryption port";
    }
    leaf svcport-short-name {
      type string;
      description
        "Macsec Service paired port Short Name String";
    }
    leaf mka-mode {
      type ncs_rpc_notif_Mka-authentication-mode;
      description
        "MKA authentication mode";
    }
    leaf fallback-keychain {
      type string;
      description
        "fallback Keychain name";
    }
    leaf macsec-shutdown {
      type boolean;
      description
        "MacsecShutdown";
    }
    leaf macsec-power-status {
      type string;
      description
        "MACsec Power Status";
    }
  }

  grouping ncs_rpc_notif_MKA-INTERFACE-INFO {
    description
      "MKA INTERFACE INFO";
    container interface-summary {
      description
        "MKA Interface Summary";
      uses ncs_rpc_notif_MKA-INTERFACE-SUMMARY;
    }
  }

  grouping ncs_rpc_notif_MKPDU-CA-RX-FAIL {
    description
      "MKPDU CA RX FAIL";
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
  }

  grouping ncs_rpc_notif_MKPDU-CA-RX {
    description
      "MKPDU CA RX";
    leaf mkpdu-received {
      type uint32;
      description
        "MKPDU Received";
    }
    leaf dist-sak {
      type uint32;
      description
        "Distributed SAK";
    }
    leaf dist-cak {
      type uint32;
      description
        "Distributed CAK";
    }
  }

  grouping ncs_rpc_notif_MKPDU-CA-TX {
    description
      "MKPDU CA TX";
    leaf mkpdu-transmitted {
      type uint32;
      description
        "MKPDU Transmitted";
    }
    leaf dist-sak {
      type uint32;
      description
        "Distributed SAK";
    }
    leaf dist-cak {
      type uint32;
      description
        "Distributed CAK";
    }
  }

  grouping ncs_rpc_notif_MKA-MKPDU-CA-STATS {
    description
      "MKA MKPDU CA STATS";
    container ca-tx {
      description
        "MKPDU CA tx stats";
      uses ncs_rpc_notif_MKPDU-CA-TX;
    }
    container ca-rx {
      description
        "MKPDU CA rx stats";
      uses ncs_rpc_notif_MKPDU-CA-RX;
    }
    container ca-rx-fail {
      description
        "CA Rx Fail";
      uses ncs_rpc_notif_MKPDU-CA-RX-FAIL;
    }
  }

  grouping ncs_rpc_notif_MKA-KEY-DERIVATION-STATS {
    description
      "MKA KEY DERIVATION STATS";
    leaf sak-generated {
      type uint32;
      description
        "SAK Generated";
    }
    leaf sak-rekeyed {
      type uint32;
      description
        "SAK Rekeyed";
    }
    leaf sak-received {
      type uint32;
      description
        "SAK Received";
    }
    leaf sak-resp-rvcd {
      type uint32;
      description
        "SAK Respone Received";
    }
    leaf pairwise-cak-derived {
      type uint32;
      description
        "Pairwise CAK derived";
    }
    leaf pairwise-cak-rekey {
      type uint32;
      description
        "Pairwise CAK rekey";
    }
  }

  grouping ncs_rpc_notif_MKA-INTF-CA-STATS {
    description
      "MKA INTF CA STATS";
    container key-derivation-stats {
      description
        "MKA Key derivation stats";
      uses ncs_rpc_notif_MKA-KEY-DERIVATION-STATS;
    }
    container mkpdu-stats {
      description
        "MKA MKPDU CA stats";
      uses ncs_rpc_notif_MKA-MKPDU-CA-STATS;
    }
    leaf ckn {
      type string;
      description
        "CKN";
    }
    leaf ca-type {
      type string;
      description
        "CA type";
    }
  }

  grouping ncs_rpc_notif_MKA-MACSEC-FAILURE {
    description
      "MKA MACSEC FAILURE";
    leaf rx-sc-creation {
      type uint32;
      description
        "Rx SC creation failure";
    }
    leaf tx-sc-creation {
      type uint32;
      description
        "Tx SC creation failure";
    }
    leaf rx-sa-install {
      type uint32;
      description
        "Rx SA install failure";
    }
    leaf tx-sa-install {
      type uint32;
      description
        "Tx SA install failure";
    }
  }

  grouping ncs_rpc_notif_MKA-SAK-FAILURE {
    description
      "MKA SAK FAILURE";
    leaf sak-gen {
      type uint32;
      description
        "SAK gen failure";
    }
    leaf hash-key-gen {
      type uint32;
      description
        "Hash key gen failure";
    }
    leaf sak-encr-wrap {
      type uint32;
      description
        "SAK Encryption/Wrap Failure";
    }
    leaf sak-decr-unwrap {
      type uint32;
      description
        "SAK Decryption/Unwrap Failure";
    }
  }

  grouping ncs_rpc_notif_MKA-IDB-FAILURE-STATS {
    description
      "MKA IDB FAILURE STATS";
    container sak-failure {
      description
        "MKA IDB SAK Failure";
      uses ncs_rpc_notif_MKA-SAK-FAILURE;
    }
    container macsec-failure {
      description
        "MKA IDB MACsec Failure";
      uses ncs_rpc_notif_MKA-MACSEC-FAILURE;
    }
  }

  grouping ncs_rpc_notif_MKPDU-OPER-STATS {
    description
      "MKPDU OPER STATS";
    leaf tx-success {
      type uint32;
      description
        "MKPDU Tx Success";
    }
    leaf rx-success {
      type uint32;
      description
        "MKPDU Rx Success";
    }
    leaf tx-force-suspended {
      type uint32;
      description
        "MKPDU Tx force suspended";
    }
    leaf rx-force-suspended {
      type uint32;
      description
        "MKPDU Rx force suspended";
    }
    leaf no-tx-on-intf-down {
      type uint32;
      description
        "No Tx on intf down";
    }
    leaf no-rx-on-intf-down {
      type uint32;
      description
        "No Rx on intf down";
    }
    leaf tx-fail {
      type uint32;
      description
        "Tx Fail";
    }
    leaf tx-pkt-build-fail {
      type uint32;
      description
        "Tx Pkt Build Fail";
    }
    leaf rx-ca-not-found {
      type uint32;
      description
        "Rx CA not found";
    }
    leaf rx-error {
      type uint32;
      description
        "Rx Error";
    }
    leaf rx-invalid-length {
      type uint32;
      description
        "Rx Invalid length";
    }
    leaf rx-invalid-ckn {
      type uint32;
      description
        "Rx invalid ckn";
    }
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
    leaf rx-pkt-sak-use-ethertype-mismatch {
      type uint32;
      description
        "RX Packet ethertype mismatch";
    }
    leaf rx-pkt-source-mac-null {
      type uint32;
      description
        "Rx Packet Source mac null";
    }
    leaf rx-pkt-dest-mac-null {
      type uint32;
      description
        "Rx Packet dest mac null";
    }
    leaf rx-pkt-pyld-null {
      type uint32;
      description
        "Rx Packet Payload Null";
    }
  }

  grouping ncs_rpc_notif_MKA-INTF-IDB-STATS {
    description
      "MKA INTF IDB STATS";
    container mkpdu-stats {
      description
        "MKPDU Stats";
      uses ncs_rpc_notif_MKPDU-OPER-STATS;
    }
    container failure-stats {
      description
        "MKA IDB Failure Stats";
      uses ncs_rpc_notif_MKA-IDB-FAILURE-STATS;
    }
  }

  grouping ncs_rpc_notif_LAST-SAK-DATA {
    description
      "LAST SAK DATA";
    leaf an {
      type string;
      description
        "AN";
    }
    leaf sa-install-time {
      type string;
      description
        "SA Install Time";
    }
  }

  grouping ncs_rpc_notif_MKA-INTF-SESSION-STATS {
    description
      "MKA INTF SESSION STATS";
    container sak-data {
      description
        "Latest SAK Data";
      uses ncs_rpc_notif_LAST-SAK-DATA;
    }
    leaf link-secure-up-time {
      type string;
      description
        "Link Secure Uptime";
    }
    leaf session-up-time {
      type string;
      description
        "Session Uptime";
    }
    leaf sak-rekey-count-ha {
      type uint32;
      description
        "Number of SAK Rekeys (since link secured)";
    }
    leaf sak-rekey-count {
      type uint32;
      description
        "Number of SAK Rekeys";
    }
  }

  grouping ncs_rpc_notif_MKA-INTF-STATISTICS {
    description
      "MKA INTF STATISTICS";
    container session-stats {
      description
        "Session Stats for interface";
      uses ncs_rpc_notif_MKA-INTF-SESSION-STATS;
    }
    container idb-stats {
      description
        "IDB stats for interface";
      uses ncs_rpc_notif_MKA-INTF-IDB-STATS;
    }
    leaf interface-name {
      type string;
      description
        "Interface Name";
    }
    list ca-stat {
      description
        "List of CA stats";
      uses ncs_rpc_notif_MKA-INTF-CA-STATS;
    }
  }

  grouping ncs_rpc_notif_SUSPEND-PEER-DATA {
    description
      "SUSPEND PEER DATA";
    leaf rx-sci {
      type uint64;
      description
        "RX SCI";
    }
    leaf rx-ssci {
      type uint32;
      description
        "RX SSCI";
    }
  }

  grouping ncs_rpc_notif_PEER-DATA {
    description
      "PEER DATA";
    leaf mi {
      type string;
      description
        "Member ID";
    }
    leaf sci {
      type string;
      description
        "Rx SCI";
    }
    leaf mn {
      type uint32;
      description
        "Message Number";
    }
    leaf priority {
      type uint32;
      description
        "KS Priority";
    }
    leaf ssci {
      type uint32;
      description
        "Peer SSCI";
    }
  }

  grouping ncs_rpc_notif_CA-DATA {
    description
      "CA DATA";
    container peers-status {
      description
        "Peers Status";
      uses ncs_rpc_notif_PEERS-STATUS-DATA;
    }
    leaf is-key-server {
      type boolean;
      description
        "Is Key Server";
    }
    leaf status {
      type string;
      description
        "Session Status [Secured/Not Secured]";
    }
    leaf num-live-peers {
      type uint32;
      description
        "Number of Live Peers";
    }
    leaf first-ca {
      type boolean;
      description
        "Is First CA";
    }
    leaf peer-sci {
      type string;
      description
        "Peer SCI(MAC)";
    }
    leaf num-live-peers-responded {
      type uint32;
      description
        "Number of Live Peers responded";
    }
    leaf ckn {
      type string;
      description
        "CKN";
    }
    leaf my-mi {
      type string;
      description
        "Member Identifier";
    }
    leaf my-mn {
      type uint32;
      description
        "Message Number";
    }
    leaf authenticator {
      type boolean;
      description
        "authenticator";
    }
    leaf num-suspend-request {
      type uint32;
      description
        "Number of Suspend Request";
    }
    leaf status-description {
      type string;
      description
        "Status Description";
    }
    leaf authentication-mode {
      type string;
      description
        "CA Authentication Mode
         :PRIMARY-PSK/FALLBACK-PSK/EAP";
    }
    leaf key-chain {
      type string;
      description
        "Key Chain name";
    }
    list live-peer {
      description
        "Live Peer List";
      uses ncs_rpc_notif_PEER-DATA;
    }
    list potential-peer {
      description
        "Potential Peer List";
      uses ncs_rpc_notif_PEER-DATA;
    }
    list dormant-peer {
      description
        "Dormant Peer List";
      uses ncs_rpc_notif_PEER-DATA;
    }
    list suspend-peer {
      description
        "Suspend Peer List";
      uses ncs_rpc_notif_SUSPEND-PEER-DATA;
    }
  }

  grouping ncs_rpc_notif_PEER-STATUS-DATA-INTERNAL {
    description
      "PEER STATUS DATA INTERNAL";
    leaf mi {
      type string {
        length "0..25";
      }
      description
        "Member ID";
    }
    leaf icv-status {
      type string {
        length "0..10";
      }
      description
        "ICV Status";
    }
    leaf icv-check-timestamp {
      type string {
        length "0..128";
      }
      description
        "ICV Check Timestamp";
    }
  }

  grouping ncs_rpc_notif_PEER-STATUS-DATA {
    description
      "PEER STATUS DATA";
    container peer-data {
      description
        "Peer Status Data";
      uses ncs_rpc_notif_PEER-STATUS-DATA-INTERNAL;
    }
    leaf sci {
      type string {
        length "0..17";
      }
      description
        "Rx SCI";
    }
  }

  grouping ncs_rpc_notif_PEERS-STATUS-DATA {
    description
      "PEERS STATUS DATA";
    leaf tx-mkpdu-timestamp {
      type string {
        length "0..128";
      }
      description
        "Tx MKPDU Timestamp";
    }
    leaf peer-count {
      type uint32;
      description
        "Peer Count";
    }
    list peer {
      description
        "Peer List";
      uses ncs_rpc_notif_PEER-STATUS-DATA;
    }
  }

  grouping ncs_rpc_notif_FALLBACK-KEEPALIVE-DATA {
    description
      "FALLBACK KEEPALIVE DATA";
    container peers-status {
      description
        "Peers Status";
      uses ncs_rpc_notif_PEERS-STATUS-DATA;
    }
    leaf ckn {
      type string {
        length "0..65";
      }
      description
        "CKN";
    }
    leaf mi {
      type string {
        length "0..25";
      }
      description
        "Member Identifier";
    }
    leaf mn {
      type uint32;
      description
        "Message Number";
    }
  }

  grouping ncs_rpc_notif_VP-DATA {
    description
      "VP DATA";
    leaf my-sci {
      type string;
      description
        "Local SCI(MAC)";
    }
    leaf virtual-port-id {
      type uint32;
      description
        "Virtual Port ID";
    }
    leaf latest-rx {
      type boolean;
      description
        "Latest Rx status";
    }
    leaf latest-tx {
      type boolean;
      description
        "Latest Tx status";
    }
    leaf latest-an {
      type uint32;
      description
        "Latest SAK AN";
    }
    leaf latest-ki {
      type string;
      description
        "Latest SAK KI";
    }
    leaf latest-kn {
      type uint32;
      description
        "Latest SAK KN";
    }
    leaf old-rx {
      type boolean;
      description
        "Old Rx status";
    }
    leaf old-tx {
      type boolean;
      description
        "Old Tx status";
    }
    leaf old-an {
      type uint32;
      description
        "Old SAK AN";
    }
    leaf old-ki {
      type string;
      description
        "Old SAK KI";
    }
    leaf old-kn {
      type uint32;
      description
        "Old SAK KN";
    }
    leaf wait-time {
      type uint32;
      description
        "SAK Transmit Wait Time";
    }
    leaf retire-time {
      type uint32;
      description
        "SAK Retire time";
    }
    leaf macsec-cipher-suite {
      type ncs_rpc_notif_Macsec-cipher-suite;
      description
        "SAK Cipher Suite";
    }
    leaf ssci {
      type uint32;
      description
        "SSCI of the Local TxSC";
    }
    leaf time-to-sak-rekey {
      type string;
      description
        "Next SAK Rekey time in Sec";
    }
    leaf time-to-exit-suspension {
      type string;
      description
        "Time to exit suspension";
    }
    list fallback-keepalive {
      description
        "Fallback Keepalive";
      uses ncs_rpc_notif_FALLBACK-KEEPALIVE-DATA;
    }
  }

  grouping ncs_rpc_notif_MKA-VLAN-TAG {
    description
      "MKA VLAN TAG";
    leaf ether-type {
      type uint16;
      description
        "EtherType";
    }
    leaf priority {
      type uint8;
      description
        "Priority";
    }
    leaf cfi {
      type uint8;
      description
        "Cannonical Format Identifier";
    }
    leaf vlan-id {
      type uint16;
      description
        "Vlan Id";
    }
  }

  grouping ncs_rpc_notif_MKA-SESSION-SUMMARY {
    description
      "MKA SESSION SUMMARY";
    container outer-tag {
      description
        "VLAN Outer TAG";
      uses ncs_rpc_notif_MKA-VLAN-TAG;
    }
    container inner-tag {
      description
        "VLAN Inner TAG";
      uses ncs_rpc_notif_MKA-VLAN-TAG;
    }
    leaf interface-name {
      type string;
      description
        "macsec configured interface";
    }
    leaf inherited-policy {
      type boolean;
      description
        "Is Inherited Policy";
    }
    leaf policy {
      type string;
      description
        "Policy Name";
    }
    leaf priority {
      type uint32;
      description
        "Key Server Priority";
    }
    leaf my-mac {
      type string;
      description
        "My MAC";
    }
    leaf delay-protection {
      type boolean;
      description
        "Delay Protect";
    }
    leaf replay-protect {
      type boolean;
      description
        "Replay Protect";
    }
    leaf window-size {
      type uint32;
      description
        "Replay Window Size";
    }
    leaf include-icv-indicator {
      type boolean;
      description
        "IncludeICVIndicator";
    }
    leaf confidentiality-offset {
      type uint32;
      description
        "Confidentiality Offset";
    }
    leaf algo-agility {
      type uint32;
      description
        "Alogorithm Agility";
    }
    leaf capability {
      type uint32;
      description
        "MACSec Capability";
    }
    leaf mka-cipher-suite {
      type string;
      description
        "MKA Cipher Suite";
    }
    leaf configured-mac-sec-cipher-suite {
      type string;
      description
        "configured cipher suite";
    }
    leaf mac-sec-desired {
      type boolean;
      description
        "MACSec Desired";
    }
  }

  grouping ncs_rpc_notif_MKA-SESSION {
    description
      "MKA SESSION";
    container session-summary {
      description
        "Session summary";
      uses ncs_rpc_notif_MKA-SESSION-SUMMARY;
    }
    container vp {
      description
        "Virtual Pointer Info";
      uses ncs_rpc_notif_VP-DATA;
    }
    list ca {
      description
        "CA List for a Session";
      uses ncs_rpc_notif_CA-DATA;
    }
  }

  grouping live_ncs_MKA-INTERFACE-SUMMARY {
    description
      "MKA INTERFACE SUMMARY";
    leaf interface-name {
      type string;
      description
        "macsec configured interface";
    }
    leaf short-name {
      type string;
      description
        "Short Name String";
    }
    leaf key-chain {
      type string;
      description
        "Name  of the Key chain";
    }
    leaf policy {
      type string;
      description
        "Policy name";
    }
    leaf macsec-svc-port {
      type boolean;
      description
        "Is macsec-service port or not";
    }
    leaf macsec-svc-port-type {
      type live_ncs_Macsec-service-port;
      description
        "Macsec-service Encryption / Decryption port";
    }
    leaf svcport-short-name {
      type string;
      description
        "Macsec Service paired port Short Name String";
    }
    leaf mka-mode {
      type live_ncs_Mka-authentication-mode;
      description
        "MKA authentication mode";
    }
    leaf fallback-keychain {
      type string;
      description
        "fallback Keychain name";
    }
    leaf macsec-shutdown {
      type boolean;
      description
        "MacsecShutdown";
    }
    leaf macsec-power-status {
      type string;
      description
        "MACsec Power Status";
    }
  }

  grouping live_ncs_MKA-INTERFACE-INFO {
    description
      "MKA INTERFACE INFO";
    container interface-summary {
      description
        "MKA Interface Summary";
      uses live_ncs_MKA-INTERFACE-SUMMARY;
    }
  }

  grouping live_ncs_MKPDU-CA-RX-FAIL {
    description
      "MKPDU CA RX FAIL";
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
  }

  grouping live_ncs_MKPDU-CA-RX {
    description
      "MKPDU CA RX";
    leaf mkpdu-received {
      type uint32;
      description
        "MKPDU Received";
    }
    leaf dist-sak {
      type uint32;
      description
        "Distributed SAK";
    }
    leaf dist-cak {
      type uint32;
      description
        "Distributed CAK";
    }
  }

  grouping live_ncs_MKPDU-CA-TX {
    description
      "MKPDU CA TX";
    leaf mkpdu-transmitted {
      type uint32;
      description
        "MKPDU Transmitted";
    }
    leaf dist-sak {
      type uint32;
      description
        "Distributed SAK";
    }
    leaf dist-cak {
      type uint32;
      description
        "Distributed CAK";
    }
  }

  grouping live_ncs_MKA-MKPDU-CA-STATS {
    description
      "MKA MKPDU CA STATS";
    container ca-tx {
      description
        "MKPDU CA tx stats";
      uses live_ncs_MKPDU-CA-TX;
    }
    container ca-rx {
      description
        "MKPDU CA rx stats";
      uses live_ncs_MKPDU-CA-RX;
    }
    container ca-rx-fail {
      description
        "CA Rx Fail";
      uses live_ncs_MKPDU-CA-RX-FAIL;
    }
  }

  grouping live_ncs_MKA-KEY-DERIVATION-STATS {
    description
      "MKA KEY DERIVATION STATS";
    leaf sak-generated {
      type uint32;
      description
        "SAK Generated";
    }
    leaf sak-rekeyed {
      type uint32;
      description
        "SAK Rekeyed";
    }
    leaf sak-received {
      type uint32;
      description
        "SAK Received";
    }
    leaf sak-resp-rvcd {
      type uint32;
      description
        "SAK Respone Received";
    }
    leaf pairwise-cak-derived {
      type uint32;
      description
        "Pairwise CAK derived";
    }
    leaf pairwise-cak-rekey {
      type uint32;
      description
        "Pairwise CAK rekey";
    }
  }

  grouping live_ncs_MKA-INTF-CA-STATS {
    description
      "MKA INTF CA STATS";
    container key-derivation-stats {
      description
        "MKA Key derivation stats";
      uses live_ncs_MKA-KEY-DERIVATION-STATS;
    }
    container mkpdu-stats {
      description
        "MKA MKPDU CA stats";
      uses live_ncs_MKA-MKPDU-CA-STATS;
    }
    leaf ckn {
      type string;
      description
        "CKN";
    }
    leaf ca-type {
      type string;
      description
        "CA type";
    }
  }

  grouping live_ncs_MKA-MACSEC-FAILURE {
    description
      "MKA MACSEC FAILURE";
    leaf rx-sc-creation {
      type uint32;
      description
        "Rx SC creation failure";
    }
    leaf tx-sc-creation {
      type uint32;
      description
        "Tx SC creation failure";
    }
    leaf rx-sa-install {
      type uint32;
      description
        "Rx SA install failure";
    }
    leaf tx-sa-install {
      type uint32;
      description
        "Tx SA install failure";
    }
  }

  grouping live_ncs_MKA-SAK-FAILURE {
    description
      "MKA SAK FAILURE";
    leaf sak-gen {
      type uint32;
      description
        "SAK gen failure";
    }
    leaf hash-key-gen {
      type uint32;
      description
        "Hash key gen failure";
    }
    leaf sak-encr-wrap {
      type uint32;
      description
        "SAK Encryption/Wrap Failure";
    }
    leaf sak-decr-unwrap {
      type uint32;
      description
        "SAK Decryption/Unwrap Failure";
    }
  }

  grouping live_ncs_MKA-IDB-FAILURE-STATS {
    description
      "MKA IDB FAILURE STATS";
    container sak-failure {
      description
        "MKA IDB SAK Failure";
      uses live_ncs_MKA-SAK-FAILURE;
    }
    container macsec-failure {
      description
        "MKA IDB MACsec Failure";
      uses live_ncs_MKA-MACSEC-FAILURE;
    }
  }

  grouping live_ncs_MKPDU-OPER-STATS {
    description
      "MKPDU OPER STATS";
    leaf tx-success {
      type uint32;
      description
        "MKPDU Tx Success";
    }
    leaf rx-success {
      type uint32;
      description
        "MKPDU Rx Success";
    }
    leaf tx-force-suspended {
      type uint32;
      description
        "MKPDU Tx force suspended";
    }
    leaf rx-force-suspended {
      type uint32;
      description
        "MKPDU Rx force suspended";
    }
    leaf no-tx-on-intf-down {
      type uint32;
      description
        "No Tx on intf down";
    }
    leaf no-rx-on-intf-down {
      type uint32;
      description
        "No Rx on intf down";
    }
    leaf tx-fail {
      type uint32;
      description
        "Tx Fail";
    }
    leaf tx-pkt-build-fail {
      type uint32;
      description
        "Tx Pkt Build Fail";
    }
    leaf rx-ca-not-found {
      type uint32;
      description
        "Rx CA not found";
    }
    leaf rx-error {
      type uint32;
      description
        "Rx Error";
    }
    leaf rx-invalid-length {
      type uint32;
      description
        "Rx Invalid length";
    }
    leaf rx-invalid-ckn {
      type uint32;
      description
        "Rx invalid ckn";
    }
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
    leaf rx-pkt-sak-use-ethertype-mismatch {
      type uint32;
      description
        "RX Packet ethertype mismatch";
    }
    leaf rx-pkt-source-mac-null {
      type uint32;
      description
        "Rx Packet Source mac null";
    }
    leaf rx-pkt-dest-mac-null {
      type uint32;
      description
        "Rx Packet dest mac null";
    }
    leaf rx-pkt-pyld-null {
      type uint32;
      description
        "Rx Packet Payload Null";
    }
  }

  grouping live_ncs_MKA-INTF-IDB-STATS {
    description
      "MKA INTF IDB STATS";
    container mkpdu-stats {
      description
        "MKPDU Stats";
      uses live_ncs_MKPDU-OPER-STATS;
    }
    container failure-stats {
      description
        "MKA IDB Failure Stats";
      uses live_ncs_MKA-IDB-FAILURE-STATS;
    }
  }

  grouping live_ncs_LAST-SAK-DATA {
    description
      "LAST SAK DATA";
    leaf an {
      type string;
      description
        "AN";
    }
    leaf sa-install-time {
      type string;
      description
        "SA Install Time";
    }
  }

  grouping live_ncs_MKA-INTF-SESSION-STATS {
    description
      "MKA INTF SESSION STATS";
    container sak-data {
      description
        "Latest SAK Data";
      uses live_ncs_LAST-SAK-DATA;
    }
    leaf link-secure-up-time {
      type string;
      description
        "Link Secure Uptime";
    }
    leaf session-up-time {
      type string;
      description
        "Session Uptime";
    }
    leaf sak-rekey-count-ha {
      type uint32;
      description
        "Number of SAK Rekeys (since link secured)";
    }
    leaf sak-rekey-count {
      type uint32;
      description
        "Number of SAK Rekeys";
    }
  }

  grouping live_ncs_MKA-INTF-STATISTICS {
    description
      "MKA INTF STATISTICS";
    container session-stats {
      description
        "Session Stats for interface";
      uses live_ncs_MKA-INTF-SESSION-STATS;
    }
    container idb-stats {
      description
        "IDB stats for interface";
      uses live_ncs_MKA-INTF-IDB-STATS;
    }
    leaf interface-name {
      type string;
      description
        "Interface Name";
    }
    list ca-stat {
      description
        "List of CA stats";
      uses live_ncs_MKA-INTF-CA-STATS;
    }
  }

  grouping live_ncs_SUSPEND-PEER-DATA {
    description
      "SUSPEND PEER DATA";
    leaf rx-sci {
      type uint64;
      description
        "RX SCI";
    }
    leaf rx-ssci {
      type uint32;
      description
        "RX SSCI";
    }
  }

  grouping live_ncs_PEER-DATA {
    description
      "PEER DATA";
    leaf mi {
      type string;
      description
        "Member ID";
    }
    leaf sci {
      type string;
      description
        "Rx SCI";
    }
    leaf mn {
      type uint32;
      description
        "Message Number";
    }
    leaf priority {
      type uint32;
      description
        "KS Priority";
    }
    leaf ssci {
      type uint32;
      description
        "Peer SSCI";
    }
  }

  grouping live_ncs_CA-DATA {
    description
      "CA DATA";
    container peers-status {
      description
        "Peers Status";
      uses live_ncs_PEERS-STATUS-DATA;
    }
    leaf is-key-server {
      type boolean;
      description
        "Is Key Server";
    }
    leaf status {
      type string;
      description
        "Session Status [Secured/Not Secured]";
    }
    leaf num-live-peers {
      type uint32;
      description
        "Number of Live Peers";
    }
    leaf first-ca {
      type boolean;
      description
        "Is First CA";
    }
    leaf peer-sci {
      type string;
      description
        "Peer SCI(MAC)";
    }
    leaf num-live-peers-responded {
      type uint32;
      description
        "Number of Live Peers responded";
    }
    leaf ckn {
      type string;
      description
        "CKN";
    }
    leaf my-mi {
      type string;
      description
        "Member Identifier";
    }
    leaf my-mn {
      type uint32;
      description
        "Message Number";
    }
    leaf authenticator {
      type boolean;
      description
        "authenticator";
    }
    leaf num-suspend-request {
      type uint32;
      description
        "Number of Suspend Request";
    }
    leaf status-description {
      type string;
      description
        "Status Description";
    }
    leaf authentication-mode {
      type string;
      description
        "CA Authentication Mode
         :PRIMARY-PSK/FALLBACK-PSK/EAP";
    }
    leaf key-chain {
      type string;
      description
        "Key Chain name";
    }
    list live-peer {
      description
        "Live Peer List";
      uses live_ncs_PEER-DATA;
    }
    list potential-peer {
      description
        "Potential Peer List";
      uses live_ncs_PEER-DATA;
    }
    list dormant-peer {
      description
        "Dormant Peer List";
      uses live_ncs_PEER-DATA;
    }
    list suspend-peer {
      description
        "Suspend Peer List";
      uses live_ncs_SUSPEND-PEER-DATA;
    }
  }

  grouping live_ncs_PEER-STATUS-DATA-INTERNAL {
    description
      "PEER STATUS DATA INTERNAL";
    leaf mi {
      type string {
        length "0..25";
      }
      description
        "Member ID";
    }
    leaf icv-status {
      type string {
        length "0..10";
      }
      description
        "ICV Status";
    }
    leaf icv-check-timestamp {
      type string {
        length "0..128";
      }
      description
        "ICV Check Timestamp";
    }
  }

  grouping live_ncs_PEER-STATUS-DATA {
    description
      "PEER STATUS DATA";
    container peer-data {
      description
        "Peer Status Data";
      uses live_ncs_PEER-STATUS-DATA-INTERNAL;
    }
    leaf sci {
      type string {
        length "0..17";
      }
      description
        "Rx SCI";
    }
  }

  grouping live_ncs_PEERS-STATUS-DATA {
    description
      "PEERS STATUS DATA";
    leaf tx-mkpdu-timestamp {
      type string {
        length "0..128";
      }
      description
        "Tx MKPDU Timestamp";
    }
    leaf peer-count {
      type uint32;
      description
        "Peer Count";
    }
    list peer {
      description
        "Peer List";
      uses live_ncs_PEER-STATUS-DATA;
    }
  }

  grouping live_ncs_FALLBACK-KEEPALIVE-DATA {
    description
      "FALLBACK KEEPALIVE DATA";
    container peers-status {
      description
        "Peers Status";
      uses live_ncs_PEERS-STATUS-DATA;
    }
    leaf ckn {
      type string {
        length "0..65";
      }
      description
        "CKN";
    }
    leaf mi {
      type string {
        length "0..25";
      }
      description
        "Member Identifier";
    }
    leaf mn {
      type uint32;
      description
        "Message Number";
    }
  }

  grouping live_ncs_VP-DATA {
    description
      "VP DATA";
    leaf my-sci {
      type string;
      description
        "Local SCI(MAC)";
    }
    leaf virtual-port-id {
      type uint32;
      description
        "Virtual Port ID";
    }
    leaf latest-rx {
      type boolean;
      description
        "Latest Rx status";
    }
    leaf latest-tx {
      type boolean;
      description
        "Latest Tx status";
    }
    leaf latest-an {
      type uint32;
      description
        "Latest SAK AN";
    }
    leaf latest-ki {
      type string;
      description
        "Latest SAK KI";
    }
    leaf latest-kn {
      type uint32;
      description
        "Latest SAK KN";
    }
    leaf old-rx {
      type boolean;
      description
        "Old Rx status";
    }
    leaf old-tx {
      type boolean;
      description
        "Old Tx status";
    }
    leaf old-an {
      type uint32;
      description
        "Old SAK AN";
    }
    leaf old-ki {
      type string;
      description
        "Old SAK KI";
    }
    leaf old-kn {
      type uint32;
      description
        "Old SAK KN";
    }
    leaf wait-time {
      type uint32;
      description
        "SAK Transmit Wait Time";
    }
    leaf retire-time {
      type uint32;
      description
        "SAK Retire time";
    }
    leaf macsec-cipher-suite {
      type live_ncs_Macsec-cipher-suite;
      description
        "SAK Cipher Suite";
    }
    leaf ssci {
      type uint32;
      description
        "SSCI of the Local TxSC";
    }
    leaf time-to-sak-rekey {
      type string;
      description
        "Next SAK Rekey time in Sec";
    }
    leaf time-to-exit-suspension {
      type string;
      description
        "Time to exit suspension";
    }
    list fallback-keepalive {
      description
        "Fallback Keepalive";
      uses live_ncs_FALLBACK-KEEPALIVE-DATA;
    }
  }

  grouping live_ncs_MKA-VLAN-TAG {
    description
      "MKA VLAN TAG";
    leaf ether-type {
      type uint16;
      description
        "EtherType";
    }
    leaf priority {
      type uint8;
      description
        "Priority";
    }
    leaf cfi {
      type uint8;
      description
        "Cannonical Format Identifier";
    }
    leaf vlan-id {
      type uint16;
      description
        "Vlan Id";
    }
  }

  grouping live_ncs_MKA-SESSION-SUMMARY {
    description
      "MKA SESSION SUMMARY";
    container outer-tag {
      description
        "VLAN Outer TAG";
      uses live_ncs_MKA-VLAN-TAG;
    }
    container inner-tag {
      description
        "VLAN Inner TAG";
      uses live_ncs_MKA-VLAN-TAG;
    }
    leaf interface-name {
      type string;
      description
        "macsec configured interface";
    }
    leaf inherited-policy {
      type boolean;
      description
        "Is Inherited Policy";
    }
    leaf policy {
      type string;
      description
        "Policy Name";
    }
    leaf priority {
      type uint32;
      description
        "Key Server Priority";
    }
    leaf my-mac {
      type string;
      description
        "My MAC";
    }
    leaf delay-protection {
      type boolean;
      description
        "Delay Protect";
    }
    leaf replay-protect {
      type boolean;
      description
        "Replay Protect";
    }
    leaf window-size {
      type uint32;
      description
        "Replay Window Size";
    }
    leaf include-icv-indicator {
      type boolean;
      description
        "IncludeICVIndicator";
    }
    leaf confidentiality-offset {
      type uint32;
      description
        "Confidentiality Offset";
    }
    leaf algo-agility {
      type uint32;
      description
        "Alogorithm Agility";
    }
    leaf capability {
      type uint32;
      description
        "MACSec Capability";
    }
    leaf mka-cipher-suite {
      type string;
      description
        "MKA Cipher Suite";
    }
    leaf configured-mac-sec-cipher-suite {
      type string;
      description
        "configured cipher suite";
    }
    leaf mac-sec-desired {
      type boolean;
      description
        "MACSec Desired";
    }
  }

  grouping live_ncs_MKA-SESSION {
    description
      "MKA SESSION";
    container session-summary {
      description
        "Session summary";
      uses live_ncs_MKA-SESSION-SUMMARY;
    }
    container vp {
      description
        "Virtual Pointer Info";
      uses live_ncs_VP-DATA;
    }
    list ca {
      description
        "CA List for a Session";
      uses live_ncs_CA-DATA;
    }
  }

  grouping MKA-INTERFACE-SUMMARY {
    description
      "MKA INTERFACE SUMMARY";
    leaf interface-name {
      type string;
      description
        "macsec configured interface";
    }
    leaf short-name {
      type string;
      description
        "Short Name String";
    }
    leaf key-chain {
      type string;
      description
        "Name  of the Key chain";
    }
    leaf policy {
      type string;
      description
        "Policy name";
    }
    leaf macsec-svc-port {
      type boolean;
      description
        "Is macsec-service port or not";
    }
    leaf macsec-svc-port-type {
      type Macsec-service-port;
      description
        "Macsec-service Encryption / Decryption port";
    }
    leaf svcport-short-name {
      type string;
      description
        "Macsec Service paired port Short Name String";
    }
    leaf mka-mode {
      type Mka-authentication-mode;
      description
        "MKA authentication mode";
    }
    leaf fallback-keychain {
      type string;
      description
        "fallback Keychain name";
    }
    leaf macsec-shutdown {
      type boolean;
      description
        "MacsecShutdown";
    }
    leaf macsec-power-status {
      type string;
      description
        "MACsec Power Status";
    }
  }

  grouping MKA-INTERFACE-INFO {
    description
      "MKA INTERFACE INFO";
    container interface-summary {
      description
        "MKA Interface Summary";
      uses MKA-INTERFACE-SUMMARY;
    }
  }

  grouping MKPDU-CA-RX-FAIL {
    description
      "MKPDU CA RX FAIL";
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
  }

  grouping MKPDU-CA-RX {
    description
      "MKPDU CA RX";
    leaf mkpdu-received {
      type uint32;
      description
        "MKPDU Received";
    }
    leaf dist-sak {
      type uint32;
      description
        "Distributed SAK";
    }
    leaf dist-cak {
      type uint32;
      description
        "Distributed CAK";
    }
  }

  grouping MKPDU-CA-TX {
    description
      "MKPDU CA TX";
    leaf mkpdu-transmitted {
      type uint32;
      description
        "MKPDU Transmitted";
    }
    leaf dist-sak {
      type uint32;
      description
        "Distributed SAK";
    }
    leaf dist-cak {
      type uint32;
      description
        "Distributed CAK";
    }
  }

  grouping MKA-MKPDU-CA-STATS {
    description
      "MKA MKPDU CA STATS";
    container ca-tx {
      description
        "MKPDU CA tx stats";
      uses MKPDU-CA-TX;
    }
    container ca-rx {
      description
        "MKPDU CA rx stats";
      uses MKPDU-CA-RX;
    }
    container ca-rx-fail {
      description
        "CA Rx Fail";
      uses MKPDU-CA-RX-FAIL;
    }
  }

  grouping MKA-KEY-DERIVATION-STATS {
    description
      "MKA KEY DERIVATION STATS";
    leaf sak-generated {
      type uint32;
      description
        "SAK Generated";
    }
    leaf sak-rekeyed {
      type uint32;
      description
        "SAK Rekeyed";
    }
    leaf sak-received {
      type uint32;
      description
        "SAK Received";
    }
    leaf sak-resp-rvcd {
      type uint32;
      description
        "SAK Respone Received";
    }
    leaf pairwise-cak-derived {
      type uint32;
      description
        "Pairwise CAK derived";
    }
    leaf pairwise-cak-rekey {
      type uint32;
      description
        "Pairwise CAK rekey";
    }
  }

  grouping MKA-INTF-CA-STATS {
    description
      "MKA INTF CA STATS";
    container key-derivation-stats {
      description
        "MKA Key derivation stats";
      uses MKA-KEY-DERIVATION-STATS;
    }
    container mkpdu-stats {
      description
        "MKA MKPDU CA stats";
      uses MKA-MKPDU-CA-STATS;
    }
    leaf ckn {
      type string;
      description
        "CKN";
    }
    leaf ca-type {
      type string;
      description
        "CA type";
    }
  }

  grouping MKA-MACSEC-FAILURE {
    description
      "MKA MACSEC FAILURE";
    leaf rx-sc-creation {
      type uint32;
      description
        "Rx SC creation failure";
    }
    leaf tx-sc-creation {
      type uint32;
      description
        "Tx SC creation failure";
    }
    leaf rx-sa-install {
      type uint32;
      description
        "Rx SA install failure";
    }
    leaf tx-sa-install {
      type uint32;
      description
        "Tx SA install failure";
    }
  }

  grouping MKA-SAK-FAILURE {
    description
      "MKA SAK FAILURE";
    leaf sak-gen {
      type uint32;
      description
        "SAK gen failure";
    }
    leaf hash-key-gen {
      type uint32;
      description
        "Hash key gen failure";
    }
    leaf sak-encr-wrap {
      type uint32;
      description
        "SAK Encryption/Wrap Failure";
    }
    leaf sak-decr-unwrap {
      type uint32;
      description
        "SAK Decryption/Unwrap Failure";
    }
  }

  grouping MKA-IDB-FAILURE-STATS {
    description
      "MKA IDB FAILURE STATS";
    container sak-failure {
      description
        "MKA IDB SAK Failure";
      uses MKA-SAK-FAILURE;
    }
    container macsec-failure {
      description
        "MKA IDB MACsec Failure";
      uses MKA-MACSEC-FAILURE;
    }
  }

  grouping MKPDU-OPER-STATS {
    description
      "MKPDU OPER STATS";
    leaf tx-success {
      type uint32;
      description
        "MKPDU Tx Success";
    }
    leaf rx-success {
      type uint32;
      description
        "MKPDU Rx Success";
    }
    leaf tx-force-suspended {
      type uint32;
      description
        "MKPDU Tx force suspended";
    }
    leaf rx-force-suspended {
      type uint32;
      description
        "MKPDU Rx force suspended";
    }
    leaf no-tx-on-intf-down {
      type uint32;
      description
        "No Tx on intf down";
    }
    leaf no-rx-on-intf-down {
      type uint32;
      description
        "No Rx on intf down";
    }
    leaf tx-fail {
      type uint32;
      description
        "Tx Fail";
    }
    leaf tx-pkt-build-fail {
      type uint32;
      description
        "Tx Pkt Build Fail";
    }
    leaf rx-ca-not-found {
      type uint32;
      description
        "Rx CA not found";
    }
    leaf rx-error {
      type uint32;
      description
        "Rx Error";
    }
    leaf rx-invalid-length {
      type uint32;
      description
        "Rx Invalid length";
    }
    leaf rx-invalid-ckn {
      type uint32;
      description
        "Rx invalid ckn";
    }
    leaf rx-icv-validation-fail {
      type uint32;
      description
        "Rx ICV validation fail";
    }
    leaf rx-bad-peer-mn {
      type uint32;
      description
        "Rx Bad Peer MN";
    }
    leaf rx-non-recent-peerlist-mn {
      type uint32;
      description
        "Rx non-recent peerlist MN";
    }
    leaf rx-sak-use-kn-mismatch {
      type uint32;
      description
        "Rx SAK USE KN mismatch";
    }
    leaf rx-sak-use-rx-not-set {
      type uint32;
      description
        "Rx SAK USE rx not set";
    }
    leaf rx-sak-use-key-mi-mismatch {
      type uint32;
      description
        "Rx SAK USE Key MI mismatch";
    }
    leaf rx-sak-use-an-not-in-use {
      type uint32;
      description
        "Rx SAK USE AN not in use";
    }
    leaf rx-sak-use-ks-rx-tx-not-set {
      type uint32;
      description
        "Rx SAK USE KS RX/TX not set";
    }
    leaf rx-pkt-sak-use-ethertype-mismatch {
      type uint32;
      description
        "RX Packet ethertype mismatch";
    }
    leaf rx-pkt-source-mac-null {
      type uint32;
      description
        "Rx Packet Source mac null";
    }
    leaf rx-pkt-dest-mac-null {
      type uint32;
      description
        "Rx Packet dest mac null";
    }
    leaf rx-pkt-pyld-null {
      type uint32;
      description
        "Rx Packet Payload Null";
    }
  }

  grouping MKA-INTF-IDB-STATS {
    description
      "MKA INTF IDB STATS";
    container mkpdu-stats {
      description
        "MKPDU Stats";
      uses MKPDU-OPER-STATS;
    }
    container failure-stats {
      description
        "MKA IDB Failure Stats";
      uses MKA-IDB-FAILURE-STATS;
    }
  }

  grouping LAST-SAK-DATA {
    description
      "LAST SAK DATA";
    leaf an {
      type string;
      description
        "AN";
    }
    leaf sa-install-time {
      type string;
      description
        "SA Install Time";
    }
  }

  grouping MKA-INTF-SESSION-STATS {
    description
      "MKA INTF SESSION STATS";
    container sak-data {
      description
        "Latest SAK Data";
      uses LAST-SAK-DATA;
    }
    leaf link-secure-up-time {
      type string;
      description
        "Link Secure Uptime";
    }
    leaf session-up-time {
      type string;
      description
        "Session Uptime";
    }
    leaf sak-rekey-count-ha {
      type uint32;
      description
        "Number of SAK Rekeys (since link secured)";
    }
    leaf sak-rekey-count {
      type uint32;
      description
        "Number of SAK Rekeys";
    }
  }

  grouping MKA-INTF-STATISTICS {
    description
      "MKA INTF STATISTICS";
    container session-stats {
      description
        "Session Stats for interface";
      uses MKA-INTF-SESSION-STATS;
    }
    container idb-stats {
      description
        "IDB stats for interface";
      uses MKA-INTF-IDB-STATS;
    }
    leaf interface-name {
      type string;
      description
        "Interface Name";
    }
    list ca-stat {
      description
        "List of CA stats";
      uses MKA-INTF-CA-STATS;
    }
  }

  grouping SUSPEND-PEER-DATA {
    description
      "SUSPEND PEER DATA";
    leaf rx-sci {
      type uint64;
      description
        "RX SCI";
    }
    leaf rx-ssci {
      type uint32;
      description
        "RX SSCI";
    }
  }

  grouping PEER-DATA {
    description
      "PEER DATA";
    leaf mi {
      type string;
      description
        "Member ID";
    }
    leaf sci {
      type string;
      description
        "Rx SCI";
    }
    leaf mn {
      type uint32;
      description
        "Message Number";
    }
    leaf priority {
      type uint32;
      description
        "KS Priority";
    }
    leaf ssci {
      type uint32;
      description
        "Peer SSCI";
    }
  }

  grouping CA-DATA {
    description
      "CA DATA";
    container peers-status {
      description
        "Peers Status";
      uses PEERS-STATUS-DATA;
    }
    leaf is-key-server {
      type boolean;
      description
        "Is Key Server";
    }
    leaf status {
      type string;
      description
        "Session Status [Secured/Not Secured]";
    }
    leaf num-live-peers {
      type uint32;
      description
        "Number of Live Peers";
    }
    leaf first-ca {
      type boolean;
      description
        "Is First CA";
    }
    leaf peer-sci {
      type string;
      description
        "Peer SCI(MAC)";
    }
    leaf num-live-peers-responded {
      type uint32;
      description
        "Number of Live Peers responded";
    }
    leaf ckn {
      type string;
      description
        "CKN";
    }
    leaf my-mi {
      type string;
      description
        "Member Identifier";
    }
    leaf my-mn {
      type uint32;
      description
        "Message Number";
    }
    leaf authenticator {
      type boolean;
      description
        "authenticator";
    }
    leaf num-suspend-request {
      type uint32;
      description
        "Number of Suspend Request";
    }
    leaf status-description {
      type string;
      description
        "Status Description";
    }
    leaf authentication-mode {
      type string;
      description
        "CA Authentication Mode
         :PRIMARY-PSK/FALLBACK-PSK/EAP";
    }
    leaf key-chain {
      type string;
      description
        "Key Chain name";
    }
    list live-peer {
      description
        "Live Peer List";
      uses PEER-DATA;
    }
    list potential-peer {
      description
        "Potential Peer List";
      uses PEER-DATA;
    }
    list dormant-peer {
      description
        "Dormant Peer List";
      uses PEER-DATA;
    }
    list suspend-peer {
      description
        "Suspend Peer List";
      uses SUSPEND-PEER-DATA;
    }
  }

  grouping PEER-STATUS-DATA-INTERNAL {
    description
      "PEER STATUS DATA INTERNAL";
    leaf mi {
      type string {
        length "0..25";
      }
      description
        "Member ID";
    }
    leaf icv-status {
      type string {
        length "0..10";
      }
      description
        "ICV Status";
    }
    leaf icv-check-timestamp {
      type string {
        length "0..128";
      }
      description
        "ICV Check Timestamp";
    }
  }

  grouping PEER-STATUS-DATA {
    description
      "PEER STATUS DATA";
    container peer-data {
      description
        "Peer Status Data";
      uses PEER-STATUS-DATA-INTERNAL;
    }
    leaf sci {
      type string {
        length "0..17";
      }
      description
        "Rx SCI";
    }
  }

  grouping PEERS-STATUS-DATA {
    description
      "PEERS STATUS DATA";
    leaf tx-mkpdu-timestamp {
      type string {
        length "0..128";
      }
      description
        "Tx MKPDU Timestamp";
    }
    leaf peer-count {
      type uint32;
      description
        "Peer Count";
    }
    list peer {
      description
        "Peer List";
      uses PEER-STATUS-DATA;
    }
  }

  grouping FALLBACK-KEEPALIVE-DATA {
    description
      "FALLBACK KEEPALIVE DATA";
    container peers-status {
      description
        "Peers Status";
      uses PEERS-STATUS-DATA;
    }
    leaf ckn {
      type string {
        length "0..65";
      }
      description
        "CKN";
    }
    leaf mi {
      type string {
        length "0..25";
      }
      description
        "Member Identifier";
    }
    leaf mn {
      type uint32;
      description
        "Message Number";
    }
  }

  grouping VP-DATA {
    description
      "VP DATA";
    leaf my-sci {
      type string;
      description
        "Local SCI(MAC)";
    }
    leaf virtual-port-id {
      type uint32;
      description
        "Virtual Port ID";
    }
    leaf latest-rx {
      type boolean;
      description
        "Latest Rx status";
    }
    leaf latest-tx {
      type boolean;
      description
        "Latest Tx status";
    }
    leaf latest-an {
      type uint32;
      description
        "Latest SAK AN";
    }
    leaf latest-ki {
      type string;
      description
        "Latest SAK KI";
    }
    leaf latest-kn {
      type uint32;
      description
        "Latest SAK KN";
    }
    leaf old-rx {
      type boolean;
      description
        "Old Rx status";
    }
    leaf old-tx {
      type boolean;
      description
        "Old Tx status";
    }
    leaf old-an {
      type uint32;
      description
        "Old SAK AN";
    }
    leaf old-ki {
      type string;
      description
        "Old SAK KI";
    }
    leaf old-kn {
      type uint32;
      description
        "Old SAK KN";
    }
    leaf wait-time {
      type uint32;
      description
        "SAK Transmit Wait Time";
    }
    leaf retire-time {
      type uint32;
      description
        "SAK Retire time";
    }
    leaf macsec-cipher-suite {
      type Macsec-cipher-suite;
      description
        "SAK Cipher Suite";
    }
    leaf ssci {
      type uint32;
      description
        "SSCI of the Local TxSC";
    }
    leaf time-to-sak-rekey {
      type string;
      description
        "Next SAK Rekey time in Sec";
    }
    leaf time-to-exit-suspension {
      type string;
      description
        "Time to exit suspension";
    }
    list fallback-keepalive {
      description
        "Fallback Keepalive";
      uses FALLBACK-KEEPALIVE-DATA;
    }
  }

  grouping MKA-VLAN-TAG {
    description
      "MKA VLAN TAG";
    leaf ether-type {
      type uint16;
      description
        "EtherType";
    }
    leaf priority {
      type uint8;
      description
        "Priority";
    }
    leaf cfi {
      type uint8;
      description
        "Cannonical Format Identifier";
    }
    leaf vlan-id {
      type uint16;
      description
        "Vlan Id";
    }
  }

  grouping MKA-SESSION-SUMMARY {
    description
      "MKA SESSION SUMMARY";
    container outer-tag {
      description
        "VLAN Outer TAG";
      uses MKA-VLAN-TAG;
    }
    container inner-tag {
      description
        "VLAN Inner TAG";
      uses MKA-VLAN-TAG;
    }
    leaf interface-name {
      type string;
      description
        "macsec configured interface";
    }
    leaf inherited-policy {
      type boolean;
      description
        "Is Inherited Policy";
    }
    leaf policy {
      type string;
      description
        "Policy Name";
    }
    leaf priority {
      type uint32;
      description
        "Key Server Priority";
    }
    leaf my-mac {
      type string;
      description
        "My MAC";
    }
    leaf delay-protection {
      type boolean;
      description
        "Delay Protect";
    }
    leaf replay-protect {
      type boolean;
      description
        "Replay Protect";
    }
    leaf window-size {
      type uint32;
      description
        "Replay Window Size";
    }
    leaf include-icv-indicator {
      type boolean;
      description
        "IncludeICVIndicator";
    }
    leaf confidentiality-offset {
      type uint32;
      description
        "Confidentiality Offset";
    }
    leaf algo-agility {
      type uint32;
      description
        "Alogorithm Agility";
    }
    leaf capability {
      type uint32;
      description
        "MACSec Capability";
    }
    leaf mka-cipher-suite {
      type string;
      description
        "MKA Cipher Suite";
    }
    leaf configured-mac-sec-cipher-suite {
      type string;
      description
        "configured cipher suite";
    }
    leaf mac-sec-desired {
      type boolean;
      description
        "MACSec Desired";
    }
  }

  grouping MKA-SESSION {
    description
      "MKA SESSION";
    container session-summary {
      description
        "Session summary";
      uses MKA-SESSION-SUMMARY;
    }
    container vp {
      description
        "Virtual Pointer Info";
      uses VP-DATA;
    }
    list ca {
      description
        "CA List for a Session";
      uses CA-DATA;
    }
  }
}

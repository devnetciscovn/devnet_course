module Cisco-IOS-XR-sysadmin-ext-alarm {
  // Generated by yanger -t ncs
  tailf:mount-id "cisco-iosxr-nc-7.3:cisco-iosxr-nc-7.3";
  tailf:ncs-device-type "netconf";

  namespace "http://www.cisco.com/ns/yang/Cisco-IOS-XR-sysadmin-ext-alarm";
  prefix ext-alarm;

  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the external alarms config
     functionality in the sysadmin plane.

     Copyright(c) 2020 by Cisco Systems, Inc.
     All rights reserved.

     Copyright (c) 2012-2020 by Cisco Systems, Inc.
     All rights reserved.";

  revision 2020-07-31 {
    description
      "Initial revision.";
    semver:module-version "1.0.0";
  }

  augment "/ncs:devices/ncs:device/ncs:config" {
    container alarm-contact-config {
      tailf:ncs-device-type "netconf";
      tailf:display-when "not(../../ncs:module) or ../../ncs:module[ncs:name='Cisco-IOS-XR-sysadmin-ext-alarm']";
      list alarm-contact {
        key "num";
        leaf num {
          type uint32 {
            range "0..3";
          }
          must 'true() = (../desc)' {
            tailf:xpath-root 3;
            error-message
              "User cannot configure pin alone,
               Usage: <pin number> desc <> severity <>";
          }
          description
            "Alarm pin number [0-3]";
        }
        leaf desc {
          type string {
            length "1..80";
          }
          must 'true() = (../severity)' {
            tailf:xpath-root 3;
            error-message
              "User must configure both desc and severity,
               Usage: desc <> severity <>";
          }
          // NCS dropped explicit config true
          description
            "Description of the alarm";
        }
        leaf severity {
          type enumeration {
            enum "minor" {
              value 3;
            }
            enum "major" {
              value 4;
            }
            enum "critical" {
              value 5;
            }
          }
          must 'true() = (../desc)' {
            tailf:xpath-root 3;
            error-message
              "User must configure both desc and severity,
               Usage: severity <> desc <>";
          }
          // NCS dropped explicit config true
          description
            "Severity of the alarm";
        }
      }
    }
  }
  augment "/ncs:devices/ncs:device/ncs:live-status" {
    container alarm-contact-config {
      tailf:ncs-device-type "netconf";
      tailf:display-when "not(../../ncs:module) or ../../ncs:module[ncs:name='Cisco-IOS-XR-sysadmin-ext-alarm'] or (../../ncs:live-status-protocol[not(ncs:capability)]) or (../../ncs:live-status-protocol/ncs:capability/ncs:module[.='Cisco-IOS-XR-sysadmin-ext-alarm'])";
      list alarm-contact {
        key "num";
        leaf num {
          type uint32 {
            range "0..3";
          }
          // NCS drop must statement
          description
            "Alarm pin number [0-3]";
        }
        leaf desc {
          type string {
            length "1..80";
          }
          // NCS drop must statement
          description
            "Description of the alarm";
        }
        leaf severity {
          type enumeration {
            enum "minor" {
              value 3;
            }
            enum "major" {
              value 4;
            }
            enum "critical" {
              value 5;
            }
          }
          // NCS drop must statement
          description
            "Severity of the alarm";
        }
      }
    }
  }
  augment "/ncs:devices/ncs:template/ncs:ned-id/ncs:config" {
    container alarm-contact-config {
      list alarm-contact {
        // NCS patched for predictable order
        ordered-by user;
        key "num";
        leaf num {
          type string;
          // NCS drop must statement
          description
            "Alarm pin number [0-3]";
        }
        leaf desc {
          type string;
          // NCS drop must statement
          // NCS dropped explicit config true
          description
            "Description of the alarm";
        }
        leaf severity {
          type string;
          // NCS drop must statement
          // NCS dropped explicit config true
          description
            "Severity of the alarm";
        }
      }
    }
  }
}

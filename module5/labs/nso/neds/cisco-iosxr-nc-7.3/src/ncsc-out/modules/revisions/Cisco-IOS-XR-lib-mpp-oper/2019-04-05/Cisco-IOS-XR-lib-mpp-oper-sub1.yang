submodule Cisco-IOS-XR-lib-mpp-oper-sub1 {
  // Generated by yanger -t ncs
  tailf:mount-id "cisco-iosxr-nc-7.3:cisco-iosxr-nc-7.3";

  belongs-to Cisco-IOS-XR-lib-mpp-oper {
    prefix Cisco-IOS-XR-lib-mpp-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR lib-mpp package operational data.

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-01-07 {
    description
      "IOS XR 5.3.1 revision.";
  }

  typedef ncs_template_Mpp-in6-addr {
    type string;
    description
      "Mpp in6 addr";
  }

  typedef ncs_template_Mpp-in-addr {
    type string;
    description
      "Mpp in addr";
  }

  typedef ncs_template_Mpp-af-id {
    type string;
    description
      "MPP address family types";
  }

  typedef ncs_template_Mpp-allow {
    type string;
    description
      "MPP protocol types";
  }

  typedef ncs_rpc_notif_Mpp-in6-addr {
    type inet:ipv6-address;
    description
      "Mpp in6 addr";
  }

  typedef ncs_rpc_notif_Mpp-in-addr {
    type inet:ipv4-address;
    description
      "Mpp in addr";
  }

  typedef ncs_rpc_notif_Mpp-af-id {
    type identityref {
      base Mpp-af-id-base;
    }
    description
      "MPP address family types";
  }

  typedef ncs_rpc_notif_Mpp-allow {
    type enumeration {
      enum "ssh" {
        description
          "SSH protocol";
      }
      enum "telnet" {
        description
          "TELNET protocol";
      }
      enum "snmp" {
        description
          "SNMP protocol";
      }
      enum "tftp" {
        description
          "TFTP protocol";
      }
      enum "http" {
        description
          "HTTP protocol";
      }
      enum "xr-xml" {
        description
          "XML";
      }
      enum "netconf" {
        description
          "NETCONF protocol";
      }
      enum "all" {
        description
          "All";
      }
    }
    description
      "MPP protocol types";
  }

  typedef live_ncs_Mpp-in6-addr {
    type inet:ipv6-address;
    description
      "Mpp in6 addr";
  }

  typedef live_ncs_Mpp-in-addr {
    type inet:ipv4-address;
    description
      "Mpp in addr";
  }

  typedef live_ncs_Mpp-af-id {
    type identityref {
      base Mpp-af-id-base;
    }
    description
      "MPP address family types";
  }

  typedef live_ncs_Mpp-allow {
    type enumeration {
      enum "ssh" {
        description
          "SSH protocol";
      }
      enum "telnet" {
        description
          "TELNET protocol";
      }
      enum "snmp" {
        description
          "SNMP protocol";
      }
      enum "tftp" {
        description
          "TFTP protocol";
      }
      enum "http" {
        description
          "HTTP protocol";
      }
      enum "xr-xml" {
        description
          "XML";
      }
      enum "netconf" {
        description
          "NETCONF protocol";
      }
      enum "all" {
        description
          "All";
      }
    }
    description
      "MPP protocol types";
  }

  typedef Mpp-in6-addr {
    type inet:ipv6-address;
    description
      "Mpp in6 addr";
  }

  typedef Mpp-in-addr {
    type inet:ipv4-address;
    description
      "Mpp in addr";
  }

  typedef Mpp-af-id {
    type identityref {
      base Mpp-af-id-base;
    }
    description
      "MPP address family types";
  }

  typedef Mpp-allow {
    type enumeration {
      enum "ssh" {
        description
          "SSH protocol";
      }
      enum "telnet" {
        description
          "TELNET protocol";
      }
      enum "snmp" {
        description
          "SNMP protocol";
      }
      enum "tftp" {
        description
          "TFTP protocol";
      }
      enum "http" {
        description
          "HTTP protocol";
      }
      enum "xr-xml" {
        description
          "XML";
      }
      enum "netconf" {
        description
          "NETCONF protocol";
      }
      enum "all" {
        description
          "All";
      }
    }
    description
      "MPP protocol types";
  }

  grouping ncs_template_IP-ADDR-T-UNION {
    description
      "IP ADDR T UNION";
    leaf af-name {
      type ncs_template_Mpp-af-id;
      description
        "AFName";
    }
    leaf ipv4-address {
      // NCS drop when statement
      type ncs_template_Mpp-in-addr;
      description
        "IPv4 address";
    }
    leaf ipv6-address {
      // NCS drop when statement
      type ncs_template_Mpp-in6-addr;
      description
        "IPv6 address";
    }
  }

  grouping ncs_template_MPP-INFO {
    description
      "MPP Information";
    leaf allow {
      type ncs_template_Mpp-allow;
      description
        "MPP allow";
    }
    leaf is-all-peers-allowed {
      type string;
      description
        "If TRUE, all peers are allowed";
    }
    list peer-address {
      // NCS patched for predictable order
      ordered-by user;
      description
        "List of peer addresses";
      uses ncs_template_IP-ADDR-T-UNION;
    }
  }

  grouping ncs_template_MPP-PROTO {
    description
      "MPP Interface protocols";
    list protocol {
      // NCS patched for predictable order
      ordered-by user;
      description
        "MPP Interface protocols";
      uses ncs_template_MPP-INFO;
    }
  }

  grouping ncs_template_VRF-INFO {
    description
      "Outband VRF name";
    leaf vrf-name {
      type string;
      description
        "Outband VRF name";
    }
  }

  grouping ncs_rpc_notif_IP-ADDR-T-UNION {
    description
      "IP ADDR T UNION";
    leaf af-name {
      type ncs_rpc_notif_Mpp-af-id;
      description
        "AFName";
    }
    leaf ipv4-address {
      when "../af-name = 'ipv4'" {
        tailf:xpath-root 3;
        description
          "../AFName = 'IPv4'";
      }
      type ncs_rpc_notif_Mpp-in-addr;
      description
        "IPv4 address";
    }
    leaf ipv6-address {
      when "../af-name = 'ipv6'" {
        tailf:xpath-root 3;
        description
          "../AFName = 'IPv6'";
      }
      type ncs_rpc_notif_Mpp-in6-addr;
      description
        "IPv6 address";
    }
  }

  grouping ncs_rpc_notif_MPP-INFO {
    description
      "MPP Information";
    leaf allow {
      type ncs_rpc_notif_Mpp-allow;
      description
        "MPP allow";
    }
    leaf is-all-peers-allowed {
      type boolean;
      description
        "If TRUE, all peers are allowed";
    }
    list peer-address {
      description
        "List of peer addresses";
      uses ncs_rpc_notif_IP-ADDR-T-UNION;
    }
  }

  grouping ncs_rpc_notif_MPP-PROTO {
    description
      "MPP Interface protocols";
    list protocol {
      description
        "MPP Interface protocols";
      uses ncs_rpc_notif_MPP-INFO;
    }
  }

  grouping ncs_rpc_notif_VRF-INFO {
    description
      "Outband VRF name";
    leaf vrf-name {
      type string;
      description
        "Outband VRF name";
    }
  }

  grouping live_ncs_IP-ADDR-T-UNION {
    description
      "IP ADDR T UNION";
    leaf af-name {
      type live_ncs_Mpp-af-id;
      description
        "AFName";
    }
    leaf ipv4-address {
      // NCS drop when statement
      type live_ncs_Mpp-in-addr;
      description
        "IPv4 address";
    }
    leaf ipv6-address {
      // NCS drop when statement
      type live_ncs_Mpp-in6-addr;
      description
        "IPv6 address";
    }
  }

  grouping live_ncs_MPP-INFO {
    description
      "MPP Information";
    leaf allow {
      type live_ncs_Mpp-allow;
      description
        "MPP allow";
    }
    leaf is-all-peers-allowed {
      type boolean;
      description
        "If TRUE, all peers are allowed";
    }
    list peer-address {
      description
        "List of peer addresses";
      uses live_ncs_IP-ADDR-T-UNION;
    }
  }

  grouping live_ncs_MPP-PROTO {
    description
      "MPP Interface protocols";
    list protocol {
      description
        "MPP Interface protocols";
      uses live_ncs_MPP-INFO;
    }
  }

  grouping live_ncs_VRF-INFO {
    description
      "Outband VRF name";
    leaf vrf-name {
      type string;
      description
        "Outband VRF name";
    }
  }

  grouping IP-ADDR-T-UNION {
    description
      "IP ADDR T UNION";
    leaf af-name {
      type Mpp-af-id;
      description
        "AFName";
    }
    leaf ipv4-address {
      when "../af-name = 'ipv4'" {
        tailf:xpath-root 3;
        description
          "../AFName = 'IPv4'";
      }
      type Mpp-in-addr;
      description
        "IPv4 address";
    }
    leaf ipv6-address {
      when "../af-name = 'ipv6'" {
        tailf:xpath-root 3;
        description
          "../AFName = 'IPv6'";
      }
      type Mpp-in6-addr;
      description
        "IPv6 address";
    }
  }

  grouping MPP-INFO {
    description
      "MPP Information";
    leaf allow {
      type Mpp-allow;
      description
        "MPP allow";
    }
    leaf is-all-peers-allowed {
      type boolean;
      description
        "If TRUE, all peers are allowed";
    }
    list peer-address {
      description
        "List of peer addresses";
      uses IP-ADDR-T-UNION;
    }
  }

  grouping MPP-PROTO {
    description
      "MPP Interface protocols";
    list protocol {
      description
        "MPP Interface protocols";
      uses MPP-INFO;
    }
  }

  grouping VRF-INFO {
    description
      "Outband VRF name";
    leaf vrf-name {
      type string;
      description
        "Outband VRF name";
    }
  }

  identity ipv6 {
    base Mpp-af-id-base;
    description
      "IPv6 address family";
  }

  identity ipv4 {
    base Mpp-af-id-base;
    description
      "IPv4 address family";
  }

  identity Mpp-af-id-base {
    description
      "Base identity for Mpp-af-id";
  }
}

module Cisco-IOS-XR-sysadmin-ethsw-esdma-admin-exec {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-admin-exec";
  prefix esdma_admin_exec;

  import tailf-common {
    prefix tailf;
  }
  import Cisco-IOS-XR-sysadmin-ethsw-esdma-types {
    prefix esdma_types;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'controller switch port-state' command.

     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping ncs_template_switch-exec-admin {
    container port-state {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest";
        }
        leaf switch-id {
          type esdma_types:ncs_template_esdma-switch-type-enum;
          description
            "Switch type";
        }
        list port-iter {
          // NCS patched for predictable order
          ordered-by user;
          key "port";
          leaf port {
            type esdma_types:ncs_template_esdma-switch-port-type;
            description
              "Switch port";
          }
        }
      }
    }
  }

  grouping ncs_rpc_notif_switch-exec-admin {
    container port-state {
      list location {
        key "rack card switch-id";
        leaf rack {
          type esdma_types:ncs_rpc_notif_esdma-rack-num-enum;
        }
        leaf card {
          type esdma_types:ncs_rpc_notif_esdma-cpu;
          description
            "Card that owns a switch of interest";
        }
        leaf switch-id {
          type esdma_types:ncs_rpc_notif_esdma-switch-type-enum;
          description
            "Switch type";
        }
        list port-iter {
          key "port";
          leaf port {
            type esdma_types:ncs_rpc_notif_esdma-switch-port-type;
            description
              "Switch port";
          }
        }
      }
    }
  }

  grouping live_ncs_switch-exec-admin {
    container port-state {
      list location {
        key "rack card switch-id";
        leaf rack {
          type esdma_types:live_ncs_esdma-rack-num-enum;
        }
        leaf card {
          type esdma_types:live_ncs_esdma-cpu;
          description
            "Card that owns a switch of interest";
        }
        leaf switch-id {
          type esdma_types:live_ncs_esdma-switch-type-enum;
          description
            "Switch type";
        }
        list port-iter {
          key "port";
          leaf port {
            type esdma_types:live_ncs_esdma-switch-port-type;
            description
              "Switch port";
          }
        }
      }
    }
  }

  grouping switch-exec-admin {
    container port-state {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        list port-iter {
          key "port";
          leaf port {
            type esdma_types:esdma-switch-port-type;
            description
              "Switch port";
          }
        }
      }
    }
  }
}

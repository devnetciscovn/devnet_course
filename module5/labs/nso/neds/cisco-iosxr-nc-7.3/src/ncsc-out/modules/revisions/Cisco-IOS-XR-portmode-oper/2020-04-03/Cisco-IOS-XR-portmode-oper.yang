module Cisco-IOS-XR-portmode-oper {
  // Generated by yanger -t ncs
  tailf:mount-id "cisco-iosxr-nc-7.3:cisco-iosxr-nc-7.3";
  tailf:ncs-device-type "netconf";

  namespace "http://cisco.com/ns/yang/Cisco-IOS-XR-portmode-oper";
  prefix portmode-oper;

  import Cisco-IOS-XR-types {
    prefix xr;
  }
  import cisco-semver {
    prefix semver;
  }
  include Cisco-IOS-XR-portmode-oper-sub1 {
    revision-date 2020-04-03;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR portmode package operational data.

     This module contains definitions
     for the following management objects:
       port-mode: PortMode operational data

     Copyright (c) 2013-2020 by Cisco Systems, Inc.
     All rights reserved.";

  revision 2020-04-03 {
    description
      "Portmode Oper Yang and Oper Sub-Yang Model added.";
    semver:module-version "1.1.0";
  }
  revision 2019-07-05 {
    description
      "Portmode Oper Yang and Oper Sub-Yang Model added.";
    semver:module-version "1.0.0";
  }
  revision 2019-04-05 {
    description
      "Establish semantic version baseline.";
  }
  revision 2015-11-09 {
    description
      "IOS XR 6.0 revision.";
  }

  augment "/ncs:devices/ncs:device/ncs:config" {
    // NCS drop config false container 'port-mode'
  }
  augment "/ncs:devices/ncs:device/ncs:live-status" {
    container port-mode {
      tailf:ncs-device-type "netconf";
      tailf:display-when "not(../../ncs:module) or ../../ncs:module[ncs:name='Cisco-IOS-XR-portmode-oper'] or (../../ncs:live-status-protocol[not(ncs:capability)]) or (../../ncs:live-status-protocol/ncs:capability/ncs:module[.='Cisco-IOS-XR-portmode-oper'])";
      description
        "PortMode operational data";
      container controllers {
        description
          "All PortMode Port operational data";
        list controller {
          key "controller-name";
          description
            "PortMode Port operational data";
          container portmode-info {
            description
              "PortMode operational data";
            uses live_ncs_PORTMODE-DETAILS;
          }
          container portmode-info-all {
            description
              "PortMode operational data";
            uses live_ncs_PORTMODE-DETAILS-ALL;
          }
          container capability-info {
            description
              "PortMode operational data";
            uses live_ncs_PORTMODE-CAPABILITY-ALL;
          }
          leaf controller-name {
            type xr:live_ncs_Cisco-ios-xr-string;
            description
              "Port name";
          }
        }
      }
    }
  }
  augment "/ncs:devices/ncs:template/ncs:ned-id/ncs:config" {
    // NCS drop config false container 'port-mode'
  }
}

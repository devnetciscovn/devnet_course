module Cisco-IOS-XR-sysadmin-aaa-aaa-show {
  // Generated by yanger -t ncs
  tailf:mount-id "cisco-iosxr-nc-7.3:cisco-iosxr-nc-7.3";
  tailf:ncs-device-type "netconf";

  namespace "http://www.cisco.com/ns/yang/Cisco-IOS-XR-sysadmin-aaa-aaa-show";
  prefix aaa_show;

  import tailf-aaa {
    prefix aaa;
  }
  import cisco-semver {
    prefix semver;
  }
  import tailf-common {
    prefix tailf;
  }
  import tailf-ncs {
    prefix ncs;
  }

  organization
    "Cisco Systems Inc.";
  contact
    "clos-mgbl@cisco.com";
  description
    "This module defines yang model
     for logging user/date who accessed
     shell last time

     Copyright (c) 2012-2020 by Cisco Systems, Inc.
     All rights reserved.";

  revision 2019-04-15 {
    description
      "Establish semantic version baseline.";
    semver:module-version "1.0.0";
  }
  revision 2017-05-10 {
    description
      "Namespace changed from aaa_show to Cisco-IOS-XR-sysadmin-aaa-aaa-show";
  }
  revision 2011-06-20 {
    description
      "Initial revision";
  }

  augment "/ncs:devices/ncs:template/ncs:ned-id/ncs:config/aaa:aaa" {
    // NCS drop config false container 'privileged-access'
    // NCS drop config false container accounting
    // NCS drop config false container 'user-group'
  }
  augment "/ncs:devices/ncs:device/ncs:live-status/aaa:aaa" {
    container privileged-access {
      tailf:ncs-device-type "netconf";
      tailf:display-when "not(../../../ncs:module) or ../../../ncs:module[ncs:name='Cisco-IOS-XR-sysadmin-aaa-aaa-show'] or (../../../ncs:live-status-protocol[not(ncs:capability)]) or (../../../ncs:live-status-protocol/ncs:capability/ncs:module[.='Cisco-IOS-XR-sysadmin-aaa-aaa-show'])";
      leaf shell-access {
        type string;
        // NCS drop mandatory statement
      }
      leaf first-user {
        type string;
        // NCS drop mandatory statement
      }
      leaf first-user-change {
        type string;
        // NCS drop mandatory statement
      }
      leaf current-disaster-recovery-user {
        type string;
        // NCS drop mandatory statement
      }
    }
    container accounting {
      tailf:ncs-device-type "netconf";
      tailf:display-when "not(../../../ncs:module) or ../../../ncs:module[ncs:name='Cisco-IOS-XR-sysadmin-aaa-aaa-show'] or (../../../ncs:live-status-protocol[not(ncs:capability)]) or (../../../ncs:live-status-protocol/ncs:capability/ncs:module[.='Cisco-IOS-XR-sysadmin-aaa-aaa-show'])";
      leaf log-data {
        type string;
        // NCS drop mandatory statement
      }
    }
    container user-group {
      tailf:ncs-device-type "netconf";
      tailf:display-when "not(../../../ncs:module) or ../../../ncs:module[ncs:name='Cisco-IOS-XR-sysadmin-aaa-aaa-show'] or (../../../ncs:live-status-protocol[not(ncs:capability)]) or (../../../ncs:live-status-protocol/ncs:capability/ncs:module[.='Cisco-IOS-XR-sysadmin-aaa-aaa-show'])";
      leaf grp-data {
        type string;
        // NCS drop mandatory statement
      }
    }
  }
  augment "/ncs:devices/ncs:device/ncs:config/aaa:aaa" {
    // NCS drop config false container 'privileged-access'
    // NCS drop config false container accounting
    // NCS drop config false container 'user-group'
  }
}

module Cisco-IOS-XR-iedge4710-oper {
  // Generated by yanger -t ncs
  tailf:mount-id "cisco-iosxr-nc-7.3:cisco-iosxr-nc-7.3";
  tailf:ncs-device-type "netconf";

  namespace "http://cisco.com/ns/yang/Cisco-IOS-XR-iedge4710-oper";
  prefix iedge4710-oper;

  import ietf-inet-types {
    prefix inet;
  }
  import ietf-yang-types {
    prefix yang;
  }
  import Cisco-IOS-XR-types {
    prefix xr;
  }
  import cisco-semver {
    prefix semver;
  }
  include Cisco-IOS-XR-iedge4710-oper-sub2 {
    revision-date 2021-06-27;
  }
  include Cisco-IOS-XR-iedge4710-oper-sub1 {
    revision-date 2021-06-27;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR iedge4710 package operational data.

     This module contains definitions
     for the following management objects:
       subscriber: Subscriber operational data
       iedge-license-manager: Session License Manager Configuration
         data

     Copyright (c) 2013-2021 by Cisco Systems, Inc.
     All rights reserved.";

  revision 2021-06-27 {
    description
      "Updated iedge_coord_stop_storage_int_data.
       2020-12-24
         Updated acct stop internal stats.";
    semver:module-version "2.2.0";
  }
  revision 2020-11-17 {
    description
      "Updated acct stop internal stats.
       2020-10-09
       Added acct stop statistics.
       2020-08-24
       Added Feature ID to session export.";
    semver:module-version "2.1.0";
  }
  revision 2020-02-20 {
    description
      "Added FADB statistics.
       2020-01-04
       Added disconnect history support.";
    semver:module-version "2.0.0";
  }
  revision 2019-04-05 {
    description
      "Establish semantic version baseline.";
    semver:module-version "1.0.1";
  }
  revision 2018-09-20 {
    description
      "Fixed yang gaps.";
  }
  revision 2015-11-09 {
    description
      "IOS XR 6.0 revision.";
  }

  typedef ncs_template_Subscriber-author-state-filter-flag {
    type string;
    description
      "Subscriber author state filter flag";
  }

  typedef ncs_template_Subscriber-srg-oper-filter-flag {
    type string;
    description
      "Subscriber srg oper filter flag";
  }

  typedef ncs_template_Subscriber-address-family-filter-flag {
    type string;
    description
      "Subscriber address family filter flag";
  }

  typedef ncs_template_Subscriber-state-filter-flag {
    type string;
    description
      "Subscriber state filter flag";
  }

  typedef ncs_template_Subscriber-authen-state-filter-flag {
    type string;
    description
      "Subscriber authen state filter flag";
  }

  typedef ncs_rpc_notif_Subscriber-author-state-filter-flag {
    type enumeration {
      enum "un-authorized" {
        value 0;
        description
          "UnAuthorized";
      }
      enum "authorized" {
        value 1;
        description
          "Authorized";
      }
    }
    description
      "Subscriber author state filter flag";
  }

  typedef ncs_rpc_notif_Subscriber-srg-oper-filter-flag {
    type enumeration {
      enum "srg-none" {
        value 0;
        description
          "SRG Role None";
      }
      enum "srg-master" {
        value 16384;
        description
          "SRG Role Master";
      }
      enum "srg-slave" {
        value 65536;
        description
          "SRG Role Slave";
      }
      enum "srg-both" {
        value 81920;
        description
          "SRG Role Master Slave";
      }
    }
    description
      "Subscriber srg oper filter flag";
  }

  typedef ncs_rpc_notif_Subscriber-address-family-filter-flag {
    type enumeration {
      enum "ipv4-only" {
        value 0;
        description
          "IPv4 only";
      }
      enum "ipv6-only" {
        value 1;
        description
          "IPv6 only";
      }
      enum "ipv4-all" {
        value 2;
        description
          "IPv4 all";
      }
      enum "ipv6-all" {
        value 3;
        description
          "IPv6 all";
      }
      enum "dual-all" {
        value 4;
        description
          "Dual all";
      }
      enum "dual-part-up" {
        value 5;
        description
          "Dual part up";
      }
      enum "dual-up" {
        value 6;
        description
          "Dual up";
      }
      enum "lac" {
        value 7;
        description
          "LAC";
      }
    }
    description
      "Subscriber address family filter flag";
  }

  typedef ncs_rpc_notif_Subscriber-state-filter-flag {
    type enumeration {
      enum "initializing" {
        value 0;
        description
          "Initializing";
      }
      enum "connecting" {
        value 1;
        description
          "Connecting";
      }
      enum "connected" {
        value 2;
        description
          "Connected";
      }
      enum "activated" {
        value 3;
        description
          "Activated";
      }
      enum "idle" {
        value 4;
        description
          "Idle";
      }
      enum "disconnecting" {
        value 5;
        description
          "Disconnecting";
      }
      enum "end" {
        value 6;
        description
          "End";
      }
    }
    description
      "Subscriber state filter flag";
  }

  typedef ncs_rpc_notif_Subscriber-authen-state-filter-flag {
    type enumeration {
      enum "un-authenticated" {
        value 0;
        description
          "UnAuthenticated";
      }
      enum "authenticated" {
        value 1;
        description
          "Authenticated";
      }
    }
    description
      "Subscriber authen state filter flag";
  }

  typedef live_ncs_Subscriber-author-state-filter-flag {
    type enumeration {
      enum "un-authorized" {
        value 0;
        description
          "UnAuthorized";
      }
      enum "authorized" {
        value 1;
        description
          "Authorized";
      }
    }
    description
      "Subscriber author state filter flag";
  }

  typedef live_ncs_Subscriber-srg-oper-filter-flag {
    type enumeration {
      enum "srg-none" {
        value 0;
        description
          "SRG Role None";
      }
      enum "srg-master" {
        value 16384;
        description
          "SRG Role Master";
      }
      enum "srg-slave" {
        value 65536;
        description
          "SRG Role Slave";
      }
      enum "srg-both" {
        value 81920;
        description
          "SRG Role Master Slave";
      }
    }
    description
      "Subscriber srg oper filter flag";
  }

  typedef live_ncs_Subscriber-address-family-filter-flag {
    type enumeration {
      enum "ipv4-only" {
        value 0;
        description
          "IPv4 only";
      }
      enum "ipv6-only" {
        value 1;
        description
          "IPv6 only";
      }
      enum "ipv4-all" {
        value 2;
        description
          "IPv4 all";
      }
      enum "ipv6-all" {
        value 3;
        description
          "IPv6 all";
      }
      enum "dual-all" {
        value 4;
        description
          "Dual all";
      }
      enum "dual-part-up" {
        value 5;
        description
          "Dual part up";
      }
      enum "dual-up" {
        value 6;
        description
          "Dual up";
      }
      enum "lac" {
        value 7;
        description
          "LAC";
      }
    }
    description
      "Subscriber address family filter flag";
  }

  typedef live_ncs_Subscriber-state-filter-flag {
    type enumeration {
      enum "initializing" {
        value 0;
        description
          "Initializing";
      }
      enum "connecting" {
        value 1;
        description
          "Connecting";
      }
      enum "connected" {
        value 2;
        description
          "Connected";
      }
      enum "activated" {
        value 3;
        description
          "Activated";
      }
      enum "idle" {
        value 4;
        description
          "Idle";
      }
      enum "disconnecting" {
        value 5;
        description
          "Disconnecting";
      }
      enum "end" {
        value 6;
        description
          "End";
      }
    }
    description
      "Subscriber state filter flag";
  }

  typedef live_ncs_Subscriber-authen-state-filter-flag {
    type enumeration {
      enum "un-authenticated" {
        value 0;
        description
          "UnAuthenticated";
      }
      enum "authenticated" {
        value 1;
        description
          "Authenticated";
      }
    }
    description
      "Subscriber authen state filter flag";
  }

  typedef Subscriber-author-state-filter-flag {
    type enumeration {
      enum "un-authorized" {
        value 0;
        description
          "UnAuthorized";
      }
      enum "authorized" {
        value 1;
        description
          "Authorized";
      }
    }
    description
      "Subscriber author state filter flag";
  }

  typedef Subscriber-srg-oper-filter-flag {
    type enumeration {
      enum "srg-none" {
        value 0;
        description
          "SRG Role None";
      }
      enum "srg-master" {
        value 16384;
        description
          "SRG Role Master";
      }
      enum "srg-slave" {
        value 65536;
        description
          "SRG Role Slave";
      }
      enum "srg-both" {
        value 81920;
        description
          "SRG Role Master Slave";
      }
    }
    description
      "Subscriber srg oper filter flag";
  }

  typedef Subscriber-address-family-filter-flag {
    type enumeration {
      enum "ipv4-only" {
        value 0;
        description
          "IPv4 only";
      }
      enum "ipv6-only" {
        value 1;
        description
          "IPv6 only";
      }
      enum "ipv4-all" {
        value 2;
        description
          "IPv4 all";
      }
      enum "ipv6-all" {
        value 3;
        description
          "IPv6 all";
      }
      enum "dual-all" {
        value 4;
        description
          "Dual all";
      }
      enum "dual-part-up" {
        value 5;
        description
          "Dual part up";
      }
      enum "dual-up" {
        value 6;
        description
          "Dual up";
      }
      enum "lac" {
        value 7;
        description
          "LAC";
      }
    }
    description
      "Subscriber address family filter flag";
  }

  typedef Subscriber-state-filter-flag {
    type enumeration {
      enum "initializing" {
        value 0;
        description
          "Initializing";
      }
      enum "connecting" {
        value 1;
        description
          "Connecting";
      }
      enum "connected" {
        value 2;
        description
          "Connected";
      }
      enum "activated" {
        value 3;
        description
          "Activated";
      }
      enum "idle" {
        value 4;
        description
          "Idle";
      }
      enum "disconnecting" {
        value 5;
        description
          "Disconnecting";
      }
      enum "end" {
        value 6;
        description
          "End";
      }
    }
    description
      "Subscriber state filter flag";
  }

  typedef Subscriber-authen-state-filter-flag {
    type enumeration {
      enum "un-authenticated" {
        value 0;
        description
          "UnAuthenticated";
      }
      enum "authenticated" {
        value 1;
        description
          "Authenticated";
      }
    }
    description
      "Subscriber authen state filter flag";
  }

  augment "/ncs:devices/ncs:device/ncs:config" {
    // NCS drop config false container subscriber
    // NCS drop config false container 'iedge-license-manager'
  }
  augment "/ncs:devices/ncs:device/ncs:live-status" {
    container subscriber {
      tailf:ncs-device-type "netconf";
      tailf:display-when "not(../../ncs:module) or ../../ncs:module[ncs:name='Cisco-IOS-XR-iedge4710-oper'] or (../../ncs:live-status-protocol[not(ncs:capability)]) or (../../ncs:live-status-protocol/ncs:capability/ncs:module[.='Cisco-IOS-XR-iedge4710-oper'])";
      description
        "Subscriber operational data";
      container manager {
        description
          "Subscriber manager operational data";
        container nodes {
          description
            "Subscriber manager list of nodes";
          list node {
            key "node-name";
            description
              "Subscriber manager operational data for a
               particular node";
            container statistics {
              description
                "Subscriber manager statistics";
              container aaa {
                description
                  "AAA statistics";
                container aggregate-accounting {
                  description
                    "Aggregate accounting statistics";
                  uses live_ncs_IEDGE-STATS-COORD-ACCT-DATA;
                }
                container authentication {
                  description
                    "Authentication statistics";
                  uses live_ncs_IEDGE-STATS-COORD-AUTH-DATA;
                }
                container aggregate-mobility {
                  description
                    "Aggregate mobility statistics";
                  uses live_ncs_IEDGE-STATS-MOB-DATA;
                }
                container accounting-stop-storage {
                  description
                    "Accounting stop storage statistics";
                  container stop-details {
                    description
                      "Accounting stop detail statistics";
                    list stop-detail {
                      key "offset-idx";
                      description
                        "Accounting stop detail per record
                         statistics";
                      leaf offset-idx {
                        type xr:live_ncs_Hex-integer;
                        description
                          "Offset index";
                      }
                      uses live_ncs_IEDGE-COORD-STOP-STORAGE-DETAIL-DATA;
                    }
                  }
                  container stop-summaries {
                    description
                      "Accounting stop summary table statistics";
                    list stop-summary {
                      key "mlist";
                      description
                        "Accounting stop summary per method list
                         statistics";
                      leaf mlist {
                        type xr:live_ncs_Cisco-ios-xr-string;
                        description
                          "method list name";
                      }
                      uses live_ncs_IEDGE-COORD-STOP-STORAGE-SUM-DATA;
                    }
                  }
                  container stop-internal {
                    description
                      "Accounting stop internal statistics";
                    uses live_ncs_IEDGE-COORD-STOP-STORAGE-INT-DATA;
                  }
                  container stop-accounting {
                    description
                      "Accounting stop accounting statistics";
                    uses live_ncs_IEDGE-COORD-STOP-STORAGE-ACCT-STATS-DATA;
                  }
                }
                container aggregate-authentication {
                  description
                    "Aggregate authentication statistics";
                  uses live_ncs_IEDGE-STATS-COORD-AUTH-DATA;
                }
                container accounting-stats-all {
                  description
                    "Display all subscriber management
                     statistics";
                  uses live_ncs_IEDGE-STATS-COORD-ALL-DATA;
                }
                container change-of-authorization {
                  description
                    "Change of authorization (COA) statistics";
                  uses live_ncs_IEDGE-STATS-CH-DATA;
                }
                container authorization {
                  description
                    "Authorization statistics";
                  uses live_ncs_IEDGE-STATS-COORD-AUTH-DATA;
                }
                container aggregate-authorization {
                  description
                    "Aggregate authorization statistics";
                  uses live_ncs_IEDGE-STATS-COORD-AUTH-DATA;
                }
                container aggregate-accounting-stats-all {
                  description
                    "Display all subscriber management total
                     statistics";
                  uses live_ncs_IEDGE-STATS-COORD-ALL-DATA;
                }
                container accounting {
                  description
                    "Accounting statistics";
                  uses live_ncs_IEDGE-STATS-COORD-ACCT-DATA;
                }
                container mobility {
                  description
                    "Mobility statistics";
                  uses live_ncs_IEDGE-STATS-MOB-DATA;
                }
                container aggregate-change-of-authorization {
                  description
                    "Aggregate change of authorization (COA)
                     statistics";
                  uses live_ncs_IEDGE-STATS-CH-DATA;
                }
              }
              container aggregate-summary {
                description
                  "Aggregate summary of statistics";
                uses live_ncs_IEDGE-STATS-SUMMARY-DATA;
              }
              container disconn-unique {
                description
                  "Disconnect Unique Summary statistics";
                uses live_ncs_IEDGE-STATS-DISCONNECT-DATA;
              }
              container disconn-last {
                description
                  "Disconnect Last Detail";
                uses live_ncs_IEDGE-STATS-DISCONNECT-DATA;
              }
              container fadb {
                description
                  "FADB statistics";
                uses live_ncs_IEDGE-STATS-FADB-DATA;
              }
              container srg {
                description
                  "Geo Redundancy statistics";
                uses live_ncs_IEDGE-STATS-SRG-DATA;
              }
            }
            leaf node-name {
              type xr:live_ncs_Node-id;
              description
                "Node name";
            }
          }
        }
      }
      container session {
        description
          "Subscriber session operational data";
        container nodes {
          description
            "List of subscriber session supported nodes";
          list node {
            key "node-name";
            description
              "Subscriber session operational data for a
               particular node";
            container srg-roles {
              description
                "List of subscriber session supported srg
                 roles";
              list srg-role {
                key "srg";
                description
                  "Subscriber session operational data based on
                   srg role";
                container author-summaries {
                  description
                    "Summary information filtered by
                     authorization state";
                  list author-summary {
                    key "author-state";
                    description
                      "authorization summary";
                    leaf author-state {
                      type live_ncs_Subscriber-author-state-filter-flag;
                      description
                        "Authorization state";
                    }
                    uses live_ncs_SUBSCRIBER-SESSION-SUMMARY;
                  }
                }
                container username-summaries {
                  description
                    "Summary information filtered by username";
                  list username-summary {
                    key "username";
                    description
                      "Username summary";
                    leaf username {
                      type xr:live_ncs_Cisco-ios-xr-string;
                      description
                        "Subscriber username";
                    }
                    uses live_ncs_SUBSCRIBER-SESSION-SUMMARY;
                  }
                }
                container mac-summaries {
                  description
                    "Summary information filtered by MAC address";
                  list mac-summary {
                    key "mac-address";
                    description
                      "MAC address summary";
                    leaf mac-address {
                      type yang:mac-address;
                      description
                        "Subscriber MAC address";
                    }
                    uses live_ncs_SUBSCRIBER-SESSION-SUMMARY;
                  }
                }
                container interface-summaries {
                  description
                    "Summary information filtered by interface";
                  list interface-summary {
                    key "interface-name";
                    description
                      "Interface summary";
                    leaf interface-name {
                      type xr:live_ncs_Interface-name;
                      description
                        "Interface name";
                    }
                    uses live_ncs_SUBSCRIBER-SESSION-SUMMARY;
                  }
                }
                container state-summaries {
                  description
                    "Summary information filtered by session
                     state";
                  list state-summary {
                    key "state";
                    description
                      "State summary";
                    leaf state {
                      type live_ncs_Subscriber-state-filter-flag;
                      description
                        "Subscriber state";
                    }
                    uses live_ncs_SUBSCRIBER-SESSION-SUMMARY;
                  }
                }
                container authentication-summaries {
                  description
                    "Summary information filtered by
                     authentication state";
                  list authentication-summary {
                    key "authentication-state";
                    description
                      "authentication summary";
                    leaf authentication-state {
                      type live_ncs_Subscriber-authen-state-filter-flag;
                      description
                        "Authentication state";
                    }
                    uses live_ncs_SUBSCRIBER-SESSION-SUMMARY;
                  }
                }
                container subscriber-sessions {
                  description
                    "IP subscriber sessions";
                  list subscriber-session {
                    key "session-id";
                    description
                      "Subscriber session information";
                    leaf session-id {
                      type xr:live_ncs_Hex-integer;
                      description
                        "Session ID";
                    }
                    uses live_ncs_SUBSCRIBER-SESSION-DATA;
                  }
                }
                container ipv4-address-vrf-summaries {
                  description
                    "Summary information filtered by IPv4
                     address and VRF";
                  list ipv4-address-vrf-summary {
                    description
                      "IPv4 address and VRF summary";
                    leaf vrf-name {
                      type xr:live_ncs_Cisco-ios-xr-string;
                      description
                        "VRF name";
                    }
                    leaf address {
                      type inet:ipv4-address-no-zone;
                      description
                        "Subscriber IPv4 address";
                    }
                    uses live_ncs_SUBSCRIBER-SESSION-SUMMARY;
                  }
                }
                container srg-summary {
                  description
                    "Subscriber session summary information";
                  uses live_ncs_SUBSCRIBER-SESSION-SUMMARY;
                }
                container access-interface-summaries {
                  description
                    "Summary information filtered by access
                     interface";
                  list access-interface-summary {
                    key "interface-name";
                    description
                      "Access interface summary";
                    leaf interface-name {
                      type xr:live_ncs_Interface-name;
                      description
                        "Interface name";
                    }
                    uses live_ncs_SUBSCRIBER-SESSION-SUMMARY;
                  }
                }
                container address-family-summaries {
                  description
                    "Summary information filtered by address
                     family";
                  list address-family-summary {
                    key "address-family";
                    description
                      "Address family summary";
                    leaf address-family {
                      type live_ncs_Subscriber-address-family-filter-flag;
                      description
                        "Address family";
                    }
                    uses live_ncs_SUBSCRIBER-SESSION-SUMMARY;
                  }
                }
                container ipv4-address-summaries {
                  description
                    "Summary information filtered by subscriber
                     IPv4 address";
                  list ipv4-address-summary {
                    key "address";
                    description
                      "IPv4 address summary";
                    leaf address {
                      type inet:ipv4-address-no-zone;
                      description
                        "Subscriber IPv4 address";
                    }
                    uses live_ncs_SUBSCRIBER-SESSION-SUMMARY;
                  }
                }
                container vrf-summaries {
                  description
                    "Summary information filtered by VRF";
                  list vrf-summary {
                    key "vrf-name";
                    description
                      "VRF summary";
                    leaf vrf-name {
                      type xr:live_ncs_Cisco-ios-xr-string;
                      description
                        "VRF name";
                    }
                    uses live_ncs_SUBSCRIBER-SESSION-SUMMARY;
                  }
                }
                leaf srg {
                  type live_ncs_Subscriber-srg-oper-filter-flag;
                  description
                    "Subscriber srg role";
                }
              }
            }
            container author-summaries {
              description
                "Summary information filtered by authorization
                 state";
              list author-summary {
                key "author-state";
                description
                  "authorization summary";
                leaf author-state {
                  type live_ncs_Subscriber-author-state-filter-flag;
                  description
                    "Authorization state";
                }
                uses live_ncs_SUBSCRIBER-SESSION-SUMMARY;
              }
            }
            container summary {
              description
                "Subscriber session summary information";
              uses live_ncs_SUBSCRIBER-SESSION-SUMMARY;
            }
            container mac-summaries {
              description
                "Summary information filtered by MAC address";
              list mac-summary {
                key "mac-address";
                description
                  "MAC address summary";
                leaf mac-address {
                  type yang:mac-address;
                  description
                    "Subscriber MAC address";
                }
                uses live_ncs_SUBSCRIBER-SESSION-SUMMARY;
              }
            }
            container interface-summaries {
              description
                "Summary information filtered by interface";
              list interface-summary {
                key "interface-name";
                description
                  "Interface summary";
                leaf interface-name {
                  type xr:live_ncs_Interface-name;
                  description
                    "Interface name";
                }
                uses live_ncs_SUBSCRIBER-SESSION-SUMMARY;
              }
            }
            container authentication-summaries {
              description
                "Summary information filtered by
                 authentication state";
              list authentication-summary {
                key "authentication-state";
                description
                  "authentication summary";
                leaf authentication-state {
                  type live_ncs_Subscriber-authen-state-filter-flag;
                  description
                    "Authentication state";
                }
                uses live_ncs_SUBSCRIBER-SESSION-SUMMARY;
              }
            }
            container state-summaries {
              description
                "Summary information filtered by session state";
              list state-summary {
                key "state";
                description
                  "State summary";
                leaf state {
                  type live_ncs_Subscriber-state-filter-flag;
                  description
                    "Subscriber state";
                }
                uses live_ncs_SUBSCRIBER-SESSION-SUMMARY;
              }
            }
            container ipv4-address-vrf-summaries {
              description
                "Summary information filtered by IPv4 address
                 and VRF";
              list ipv4-address-vrf-summary {
                description
                  "IPv4 address and VRF summary";
                leaf vrf-name {
                  type xr:live_ncs_Cisco-ios-xr-string;
                  description
                    "VRF name";
                }
                leaf address {
                  type inet:ipv4-address-no-zone;
                  description
                    "Subscriber IPv4 address";
                }
                uses live_ncs_SUBSCRIBER-SESSION-SUMMARY;
              }
            }
            container address-family-summaries {
              description
                "Summary information filtered by address
                 family";
              list address-family-summary {
                key "address-family";
                description
                  "Address family summary";
                leaf address-family {
                  type live_ncs_Subscriber-address-family-filter-flag;
                  description
                    "Address family";
                }
                uses live_ncs_SUBSCRIBER-SESSION-SUMMARY;
              }
            }
            container username-summaries {
              description
                "Summary information filtered by username";
              list username-summary {
                key "username";
                description
                  "Username summary";
                leaf username {
                  type xr:live_ncs_Cisco-ios-xr-string;
                  description
                    "Subscriber username";
                }
                uses live_ncs_SUBSCRIBER-SESSION-SUMMARY;
              }
            }
            container access-interface-summaries {
              description
                "Summary information filtered by access
                 interface";
              list access-interface-summary {
                key "interface-name";
                description
                  "Access interface summary";
                leaf interface-name {
                  type xr:live_ncs_Interface-name;
                  description
                    "Interface name";
                }
                uses live_ncs_SUBSCRIBER-SESSION-SUMMARY;
              }
            }
            container ipv4-address-summaries {
              description
                "Summary information filtered by subscriber
                 IPv4 address";
              list ipv4-address-summary {
                key "address";
                description
                  "IPv4 address summary";
                leaf address {
                  type inet:ipv4-address-no-zone;
                  description
                    "Subscriber IPv4 address";
                }
                uses live_ncs_SUBSCRIBER-SESSION-SUMMARY;
              }
            }
            container vrf-summaries {
              description
                "Summary information filtered by VRF";
              list vrf-summary {
                key "vrf-name";
                description
                  "VRF summary";
                leaf vrf-name {
                  type xr:live_ncs_Cisco-ios-xr-string;
                  description
                    "VRF name";
                }
                uses live_ncs_SUBSCRIBER-SESSION-SUMMARY;
              }
            }
            container sessions {
              description
                "IP subscriber sessions";
              list session {
                key "session-id";
                description
                  "Subscriber session information";
                leaf session-id {
                  type xr:live_ncs_Hex-integer;
                  description
                    "Session ID";
                }
                uses live_ncs_SUBSCRIBER-SESSION-DATA;
              }
            }
            leaf node-name {
              type xr:live_ncs_Node-id;
              description
                "Node name";
            }
          }
        }
      }
    }
    container iedge-license-manager {
      tailf:ncs-device-type "netconf";
      tailf:display-when "not(../../ncs:module) or ../../ncs:module[ncs:name='Cisco-IOS-XR-iedge4710-oper'] or (../../ncs:live-status-protocol[not(ncs:capability)]) or (../../ncs:live-status-protocol/ncs:capability/ncs:module[.='Cisco-IOS-XR-iedge4710-oper'])";
      description
        "Session License Manager Configuration data";
      container nodes {
        description
          "Session License Manager operational data for a
           location";
        list node {
          key "nodeid";
          description
            "Location. For example, 0/1/CPU0";
          container iedge-license-manager-summary {
            description
              "Display Session License Manager summary data";
            uses live_ncs_ISLM-SUMMARY-DATA;
          }
          leaf nodeid {
            type xr:live_ncs_Node-id;
            description
              "The node id to filter on. For example,
               0/1/CPU0";
          }
        }
      }
    }
  }
  augment "/ncs:devices/ncs:template/ncs:ned-id/ncs:config" {
    // NCS drop config false container subscriber
    // NCS drop config false container 'iedge-license-manager'
  }
}

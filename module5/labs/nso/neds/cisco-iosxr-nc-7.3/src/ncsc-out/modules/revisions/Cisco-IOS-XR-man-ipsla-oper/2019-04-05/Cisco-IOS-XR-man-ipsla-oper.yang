module Cisco-IOS-XR-man-ipsla-oper {
  // Generated by yanger -t ncs
  tailf:mount-id "cisco-iosxr-nc-7.3:cisco-iosxr-nc-7.3";
  tailf:ncs-device-type "netconf";

  namespace "http://cisco.com/ns/yang/Cisco-IOS-XR-man-ipsla-oper";
  prefix man-ipsla-oper;

  import ietf-inet-types {
    prefix inet;
  }
  import Cisco-IOS-XR-types {
    prefix xr;
  }
  import cisco-semver {
    prefix semver;
  }
  include Cisco-IOS-XR-man-ipsla-oper-sub3 {
    revision-date 2019-04-05;
  }
  include Cisco-IOS-XR-man-ipsla-oper-sub2 {
    revision-date 2019-04-05;
  }
  include Cisco-IOS-XR-man-ipsla-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-ipsla package operational data.

     This module contains definitions
     for the following management objects:
       ipsla: IPSLA operational data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Ipsla-hour-index {
    type string;
    description
      "Ipsla hour index";
  }

  typedef ncs_template_Ipsla-operation-id {
    type string;
    description
      "Ipsla operation id";
  }

  typedef ncs_template_Ipsla-distribution-index {
    type string;
    description
      "Ipsla distribution index";
  }

  typedef ncs_template_Ipsla-bucket-index {
    type string;
    description
      "Ipsla bucket index";
  }

  typedef ncs_template_Ipsla-lsp-monitor-id {
    type string;
    description
      "Ipsla lsp monitor id";
  }

  typedef ncs_template_Ipsla-lpd-path-index {
    type string;
    description
      "Ipsla lpd path index";
  }

  typedef ncs_template_Ipsla-hop-index {
    type string;
    description
      "Ipsla hop index";
  }

  typedef ncs_template_Ipsla-life-index {
    type string;
    description
      "Ipsla life index";
  }

  typedef ncs_template_Ipsla-path-index {
    type string;
    description
      "Ipsla path index";
  }

  typedef ncs_template_Ipsla-sample-index {
    type string;
    description
      "Ipsla sample index";
  }

  typedef ncs_template_Ipsla-enhanced-interval {
    type string;
    description
      "Ipsla enhanced interval";
  }

  typedef ncs_rpc_notif_Ipsla-hour-index {
    type uint32;
    description
      "Ipsla hour index";
  }

  typedef ncs_rpc_notif_Ipsla-operation-id {
    type uint32;
    description
      "Ipsla operation id";
  }

  typedef ncs_rpc_notif_Ipsla-distribution-index {
    type uint32;
    description
      "Ipsla distribution index";
  }

  typedef ncs_rpc_notif_Ipsla-bucket-index {
    type uint32;
    description
      "Ipsla bucket index";
  }

  typedef ncs_rpc_notif_Ipsla-lsp-monitor-id {
    type uint32;
    description
      "Ipsla lsp monitor id";
  }

  typedef ncs_rpc_notif_Ipsla-lpd-path-index {
    type uint32;
    description
      "Ipsla lpd path index";
  }

  typedef ncs_rpc_notif_Ipsla-hop-index {
    type uint32;
    description
      "Ipsla hop index";
  }

  typedef ncs_rpc_notif_Ipsla-life-index {
    type uint32;
    description
      "Ipsla life index";
  }

  typedef ncs_rpc_notif_Ipsla-path-index {
    type uint32;
    description
      "Ipsla path index";
  }

  typedef ncs_rpc_notif_Ipsla-sample-index {
    type uint32;
    description
      "Ipsla sample index";
  }

  typedef ncs_rpc_notif_Ipsla-enhanced-interval {
    type uint32;
    description
      "Ipsla enhanced interval";
  }

  typedef live_ncs_Ipsla-hour-index {
    type uint32;
    description
      "Ipsla hour index";
  }

  typedef live_ncs_Ipsla-operation-id {
    type uint32;
    description
      "Ipsla operation id";
  }

  typedef live_ncs_Ipsla-distribution-index {
    type uint32;
    description
      "Ipsla distribution index";
  }

  typedef live_ncs_Ipsla-bucket-index {
    type uint32;
    description
      "Ipsla bucket index";
  }

  typedef live_ncs_Ipsla-lsp-monitor-id {
    type uint32;
    description
      "Ipsla lsp monitor id";
  }

  typedef live_ncs_Ipsla-lpd-path-index {
    type uint32;
    description
      "Ipsla lpd path index";
  }

  typedef live_ncs_Ipsla-hop-index {
    type uint32;
    description
      "Ipsla hop index";
  }

  typedef live_ncs_Ipsla-life-index {
    type uint32;
    description
      "Ipsla life index";
  }

  typedef live_ncs_Ipsla-path-index {
    type uint32;
    description
      "Ipsla path index";
  }

  typedef live_ncs_Ipsla-sample-index {
    type uint32;
    description
      "Ipsla sample index";
  }

  typedef live_ncs_Ipsla-enhanced-interval {
    type uint32;
    description
      "Ipsla enhanced interval";
  }

  typedef Ipsla-hour-index {
    type uint32;
    description
      "Ipsla hour index";
  }

  typedef Ipsla-operation-id {
    type uint32;
    description
      "Ipsla operation id";
  }

  typedef Ipsla-distribution-index {
    type uint32;
    description
      "Ipsla distribution index";
  }

  typedef Ipsla-bucket-index {
    type uint32;
    description
      "Ipsla bucket index";
  }

  typedef Ipsla-lsp-monitor-id {
    type uint32;
    description
      "Ipsla lsp monitor id";
  }

  typedef Ipsla-lpd-path-index {
    type uint32;
    description
      "Ipsla lpd path index";
  }

  typedef Ipsla-hop-index {
    type uint32;
    description
      "Ipsla hop index";
  }

  typedef Ipsla-life-index {
    type uint32;
    description
      "Ipsla life index";
  }

  typedef Ipsla-path-index {
    type uint32;
    description
      "Ipsla path index";
  }

  typedef Ipsla-sample-index {
    type uint32;
    description
      "Ipsla sample index";
  }

  typedef Ipsla-enhanced-interval {
    type uint32;
    description
      "Ipsla enhanced interval";
  }

  grouping ncs_template_DISTRIBUTION-INTERVAL-TABLE {
    description
      "Common node of target, hop";
    container distribution-intervals {
      description
        "Table of distribution intervals for a particular
         hop";
      list distribution-interval {
        // NCS patched for predictable order
        ordered-by user;
        key "distribution-index";
        description
          "1-hour aggregated statistics for a hop in a
           path-enabled operation";
        leaf distribution-index {
          type ncs_template_Ipsla-distribution-index;
          description
            "Distribution Interval";
        }
        uses ncs_template_IPSLA-GLOBAL-STATS-BAG;
      }
    }
  }

  grouping ncs_rpc_notif_DISTRIBUTION-INTERVAL-TABLE {
    description
      "Common node of target, hop";
    container distribution-intervals {
      description
        "Table of distribution intervals for a particular
         hop";
      list distribution-interval {
        key "distribution-index";
        description
          "1-hour aggregated statistics for a hop in a
           path-enabled operation";
        leaf distribution-index {
          type ncs_rpc_notif_Ipsla-distribution-index;
          description
            "Distribution Interval";
        }
        uses ncs_rpc_notif_IPSLA-GLOBAL-STATS-BAG;
      }
    }
  }

  grouping live_ncs_DISTRIBUTION-INTERVAL-TABLE {
    description
      "Common node of target, hop";
    container distribution-intervals {
      description
        "Table of distribution intervals for a particular
         hop";
      list distribution-interval {
        key "distribution-index";
        description
          "1-hour aggregated statistics for a hop in a
           path-enabled operation";
        leaf distribution-index {
          type live_ncs_Ipsla-distribution-index;
          description
            "Distribution Interval";
        }
        uses live_ncs_IPSLA-GLOBAL-STATS-BAG;
      }
    }
  }

  grouping DISTRIBUTION-INTERVAL-TABLE {
    description
      "Common node of target, hop";
    container distribution-intervals {
      description
        "Table of distribution intervals for a particular
         hop";
      list distribution-interval {
        key "distribution-index";
        description
          "1-hour aggregated statistics for a hop in a
           path-enabled operation";
        leaf distribution-index {
          type Ipsla-distribution-index;
          description
            "Distribution Interval";
        }
        uses IPSLA-GLOBAL-STATS-BAG;
      }
    }
  }

  augment "/ncs:devices/ncs:device/ncs:config" {
    // NCS drop config false container ipsla
  }
  augment "/ncs:devices/ncs:device/ncs:live-status" {
    container ipsla {
      tailf:ncs-device-type "netconf";
      tailf:display-when "not(../../ncs:module) or ../../ncs:module[ncs:name='Cisco-IOS-XR-man-ipsla-oper'] or (../../ncs:live-status-protocol[not(ncs:capability)]) or (../../ncs:live-status-protocol/ncs:capability/ncs:module[.='Cisco-IOS-XR-man-ipsla-oper'])";
      description
        "IPSLA operational data";
      container mpls-data {
        description
          "MPLS operational data";
        container lsp-monitors {
          description
            "List of MPLS LSP Monitor instances";
          list lsp-monitor {
            key "monitor-id";
            description
              "Operational data for MPLS LSP Monitor";
            container state {
              description
                "Operational state of MPLS LSP Monitor";
              uses live_ncs_IPSLA-MPLSLM-STATE-BAG;
            }
            container operations {
              description
                "List of operations in MPLS LSP Monitor";
              list operation {
                key "operation-id";
                description
                  "Operation created in MPLS LSP Monitor";
                container state {
                  description
                    "Operational state of the created operation";
                  uses live_ncs_IPSLA-MPLSLM-OP-STATE-BAG;
                }
                container lpd-paths {
                  description
                    "List of LPD paths in MPLS LPD group
                     operation";
                  list lpd-path {
                    key "path-index";
                    description
                      "Operational state of LPD path in MPLS LSP
                       Group operation";
                    leaf path-index {
                      type live_ncs_Ipsla-lpd-path-index;
                      description
                        "LPD path index";
                    }
                    uses live_ncs_IPSLA-MPLSLM-OP-PATH-STATE-BAG;
                  }
                }
                leaf operation-id {
                  type live_ncs_Ipsla-operation-id;
                  description
                    "Operation ID";
                }
              }
            }
            container scan-queues {
              description
                "List of Scan Queue entries in MPLS LSP
                 Monitor";
              list scan-queue {
                key "address";
                description
                  "Provider Edge(PE) addition or deletion
                   requests in Scan Queue";
                leaf address {
                  type inet:ipv4-address-no-zone;
                  description
                    "Nexthop Address";
                }
                uses live_ncs_IPSLA-MPLSLM-SCAN-QUEUE-BAG;
              }
            }
            leaf monitor-id {
              type live_ncs_Ipsla-lsp-monitor-id;
              description
                "Monitor ID";
            }
          }
        }
        container discovery {
          description
            "Provider Edge(PE) discovery operational data";
          container vpn {
            description
              "L3 VPN PE discovery operational data";
            container state {
              description
                "Operational state of PE discovery";
              uses live_ncs_IPSLA-DISCOVERY-STATE-BAG;
            }
            container nexthops {
              description
                "List of nexthop addresses for remote PE
                 routers";
              list nexthop {
                key "address";
                description
                  "Nexthop address for remote PE router";
                container vrfs {
                  description
                    "List of VRFs for the nexthop address";
                  list vrf {
                    key "vrf-name";
                    description
                      "VRF information of the nexthop address";
                    leaf vrf-name {
                      type xr:live_ncs_Cisco-ios-xr-string;
                      description
                        "VRF Name";
                    }
                    uses live_ncs_IPSLA-DISCOVERY-VRF-BAG;
                  }
                }
                container prefix {
                  description
                    "Prefix of the nexthop address";
                  uses live_ncs_IPSLA-DISCOVERY-PREFIX-BAG;
                }
                leaf address {
                  type inet:ipv4-address-no-zone;
                  description
                    "Nexthop Address";
                }
              }
            }
          }
        }
      }
      container responder {
        description
          "Data from responder probe handling";
        container ports {
          description
            "Statistics maintained by responder";
          list port {
            key "port";
            description
              "Port data";
            leaf port {
              type inet:port-number;
              description
                "Port";
            }
            uses live_ncs_IPSLA-RESP-PORT-INFO-BAG;
          }
        }
      }
      container operation-data {
        description
          "Operations data";
        container operations {
          description
            "Configured operations";
          list operation {
            key "operation-id";
            description
              "Operational data for an operation";
            container common {
              description
                "Common data for all operation types";
              container operational-state {
                description
                  "Operational state for an operation";
                uses live_ncs_IPSLA-OPER-STATE-BAG;
              }
            }
            container lpd {
              description
                "LPD operational data of MPLS LSP group
                 operation";
              container statistics {
                description
                  "Statistics collected for LPD group";
                container latest {
                  description
                    "LPD statistics collected during the last
                     sampling cycle";
                  container target {
                    description
                      "Latest statistics of LPD group";
                    uses live_ncs_IPSLA-LPD-STATS-BAG;
                  }
                }
                container aggregated {
                  description
                    "Statistics aggregated for LPD group
                     collected over time intervals";
                  container hours {
                    description
                      "Table of LPD statistics aggregated over
                       1-hour intervals";
                    list hour {
                      key "hour-index";
                      description
                        "LPD statistics aggregated for a 1-hour
                         interval";
                      leaf hour-index {
                        type live_ncs_Ipsla-hour-index;
                        description
                          "Hour Index";
                      }
                      uses live_ncs_IPSLA-LPD-STATS-BAG;
                    }
                  }
                }
              }
              container status {
                description
                  "Operational status of LPD group";
                container lpd-paths {
                  description
                    "Operational path state in LPD group";
                  list lpd-path {
                    key "path-index";
                    description
                      "Current operational path state in LPD
                       group";
                    leaf path-index {
                      type live_ncs_Ipsla-lpd-path-index;
                      description
                        "LPD path index";
                    }
                    uses live_ncs_IPSLA-LPD-PATH-STATE-BAG;
                  }
                }
                container state {
                  description
                    "Operational status of LPD group";
                  uses live_ncs_IPSLA-LPD-STATE-BAG;
                }
              }
            }
            container history {
              description
                "Historical data for an operation";
              container path {
                description
                  "Historical data with multiple hops along the
                   path";
                container lifes {
                  description
                    "Tables of lives for an operation";
                  list life {
                    key "life-index";
                    description
                      "History data for a particular life of the
                       operation";
                    container buckets {
                      description
                        "Table of history buckets (samples) for a
                         particular operation";
                      list bucket {
                        key "bucket-index";
                        description
                          "History bucket for an operation";
                        container samples {
                          description
                            "Table of samples for a particular cycle";
                          list sample {
                            key "sample-index";
                            description
                              "Data sample for particular cycle";
                            leaf sample-index {
                              type live_ncs_Ipsla-sample-index;
                              description
                                "Sample Index";
                            }
                            uses live_ncs_IPSLA-HISTORY-BAG;
                          }
                        }
                        leaf bucket-index {
                          type live_ncs_Ipsla-bucket-index;
                          description
                            "Bucket Index";
                        }
                      }
                    }
                    leaf life-index {
                      type live_ncs_Ipsla-life-index;
                      description
                        "Life Index";
                    }
                  }
                }
              }
              container target {
                description
                  "Historical data for the destination node";
                container lifes {
                  description
                    "Tables of lives for an operation";
                  list life {
                    key "life-index";
                    description
                      "Operational data for a particular life of
                       the operation";
                    container buckets {
                      description
                        "Table of history buckets (samples) for a
                         particular operation";
                      list bucket {
                        key "bucket-index";
                        description
                          "History bucket for an operation";
                        leaf bucket-index {
                          type live_ncs_Ipsla-bucket-index;
                          description
                            "Bucket Index";
                        }
                        uses live_ncs_IPSLA-HISTORY-BAG;
                      }
                    }
                    leaf life-index {
                      type live_ncs_Ipsla-life-index;
                      description
                        "Life Index";
                    }
                  }
                }
              }
            }
            container statistics {
              description
                "Statistics collected for an operation";
              container latest {
                description
                  "Statistics collected during the last
                   sampling cycle of the operation";
                container target {
                  description
                    "Latest statistics for the target node";
                  uses live_ncs_IPSLA-GLOBAL-STATS-BAG;
                }
                container hops {
                  description
                    "Latest statistics for hops in a
                     path-enabled operation";
                  list hop {
                    key "hop-index";
                    description
                      "Latest stats for a hop in a path-enabled
                       operation";
                    leaf hop-index {
                      type live_ncs_Ipsla-hop-index;
                      description
                        "Hop Index";
                    }
                    uses live_ncs_IPSLA-GLOBAL-STATS-BAG;
                  }
                }
                container lpd-paths {
                  description
                    "List of latest LPD paths";
                  list lpd-path {
                    key "path-index";
                    description
                      "Latest path statistics of MPLS LSP group
                       operation";
                    leaf path-index {
                      type live_ncs_Ipsla-lpd-path-index;
                      description
                        "LPD path index";
                    }
                    uses live_ncs_IPSLA-LPD-PATH-STATS-BAG;
                  }
                }
              }
              container aggregated {
                description
                  "Statistics aggregated for data collected
                   over time intervals";
                container enhanced-intervals {
                  description
                    "Table of statistics aggregated over
                     enhanced intervals";
                  list enhanced-interval {
                    key "enhanced-interval";
                    description
                      "Statistics aggregated over an interval
                       specified in seconds. Specified interval
                       must be a multiple of the operation
                       frequency";
                    container start-times {
                      description
                        "Table of start times for the intervals";
                      list start-time {
                        key "interval-start-time";
                        description
                          "Statistics aggregated over an enhanced
                           interval which starts at a specific time";
                        leaf interval-start-time {
                          type xr:live_ncs_Cisco-ios-xr-string;
                          description
                            "Interval Start Time";
                        }
                        uses live_ncs_IPSLA-GLOBAL-STATS-BAG;
                      }
                    }
                    leaf enhanced-interval {
                      type live_ncs_Ipsla-enhanced-interval;
                      units "second";
                      description
                        "Enhanced Interval in seconds";
                    }
                  }
                }
                container hours {
                  description
                    "Table of statistics aggregated over 1-hour
                     intervals";
                  list hour {
                    key "hour-index";
                    description
                      "Statistics aggregated for a 1-hour
                       interval";
                    container distributed {
                      description
                        "Statistics aggregated on distribution
                         value intervals for in 1-hour intervals";
                      container paths {
                        description
                          "Table of paths identified in the 1-hour
                           interval";
                        list path {
                          key "path-index";
                          description
                            "Paths identified in a 1-hour interval";
                          container hops {
                            description
                              "Table of hops for a particular path";
                            list hop {
                              key "hop-index";
                              description
                                "1-hour aggregated statistics for a
                                 hop in a path-enabled operation";
                              leaf hop-index {
                                type live_ncs_Ipsla-hop-index;
                                description
                                  "Hop Index";
                              }
                              uses live_ncs_DISTRIBUTION-INTERVAL-TABLE;
                            }
                          }
                          leaf path-index {
                            type live_ncs_Ipsla-path-index;
                            description
                              "Path Index";
                          }
                        }
                      }
                      container target {
                        description
                          "Distribution statistics for the target
                           node";
                        uses live_ncs_DISTRIBUTION-INTERVAL-TABLE;
                      }
                    }
                    container non-distributed {
                      description
                        "Statistics aggregated for the total range
                         of values in 1-hour intervals";
                      container target {
                        description
                          "Total 1-hour aggregated statistics for
                           the target node";
                        uses live_ncs_IPSLA-GLOBAL-STATS-BAG;
                      }
                      container paths {
                        description
                          "Table of paths identified in the 1-hour
                           interval";
                        list path {
                          key "path-index";
                          description
                            "Paths identified in a 1-hour interval";
                          container hops {
                            description
                              "Table of hops for a particular path";
                            list hop {
                              key "hop-index";
                              description
                                "Total 1-hour aggregated statistics
                                 for a hop in a path-enabled operation";
                              leaf hop-index {
                                type live_ncs_Ipsla-hop-index;
                                description
                                  "Hop Index";
                              }
                              uses live_ncs_IPSLA-GLOBAL-STATS-BAG;
                            }
                          }
                          leaf path-index {
                            type live_ncs_Ipsla-path-index;
                            description
                              "Path Index";
                          }
                        }
                      }
                      container lpd-paths {
                        description
                          "List of latest LPD paths";
                        list lpd-path {
                          key "path-index";
                          description
                            "Latest path statistics of MPLS LSP
                             group operation";
                          leaf path-index {
                            type live_ncs_Ipsla-lpd-path-index;
                            description
                              "LPD path index";
                          }
                          uses live_ncs_IPSLA-LPD-PATH-STATS-BAG;
                        }
                      }
                    }
                    leaf hour-index {
                      type live_ncs_Ipsla-hour-index;
                      description
                        "Hour Index";
                    }
                  }
                }
              }
            }
            leaf operation-id {
              type live_ncs_Ipsla-operation-id;
              description
                "Operation ID";
            }
          }
        }
      }
      container application-info {
        description
          "IPSLA application information";
        uses live_ncs_IPSLA-APPLICATION-BAG;
      }
    }
  }
  augment "/ncs:devices/ncs:template/ncs:ned-id/ncs:config" {
    // NCS drop config false container ipsla
  }
}

submodule Cisco-IOS-XR-evpn-oper-sub1 {
  // Generated by yanger -t ncs
  tailf:mount-id "cisco-iosxr-nc-7.3:cisco-iosxr-nc-7.3";

  belongs-to Cisco-IOS-XR-evpn-oper {
    prefix Cisco-IOS-XR-evpn-oper;
  }

  import ietf-inet-types {
    prefix inet;
  }
  import ietf-yang-types {
    prefix yang;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR evpn package operational data.

     Copyright (c) 2013-2021 by Cisco Systems, Inc.
     All rights reserved.";

  revision 2021-05-12 {
    description
      "Added Union Path list buffer";
    semver:module-version "4.1.0";
  }
  revision 2020-05-05 {
    description
      "changes related to treat SRv6 and SID as well-known when parsing XML for yang
       2020-04-02
       EVPN DF Election Synchronization with NTP related changes";
    semver:module-version "4.0.0";
  }
  revision 2019-12-20 {
    description
      "EVPN SRv6 related changes";
    semver:module-version "3.0.0";
  }
  revision 2019-04-05 {
    description
      "Establish semantic version baseline.";
    semver:module-version "2.0.0";
  }
  revision 2018-09-26 {
    description
      "Duplicate detection parameters config moved from l2vpn to l2rib.";
  }
  revision 2017-09-07 {
    description
      "Fixed type translation error.";
  }
  revision 2017-05-01 {
    description
      "Fixing backward compatibility error in module.";
  }
  revision 2015-11-09 {
    description
      "IOS XR 6.0 revision.";
  }

  typedef ncs_template_L2vpn-evpn-es-access-signal-mode {
    type string;
    description
      "L2vpn evpn es access signal mode";
  }

  typedef ncs_template_L2vpn-evpn-sc-mcast-mode {
    type string;
    description
      "EVPN Ethernet-Segment service multicast carving
       mode";
  }

  typedef ncs_template_L2vpn-evpn-sc-synchronization-mode {
    type string;
    description
      "EVPN Ethernet-Segment service carving
       synchronization mode";
  }

  typedef ncs_template_L2vpn-evpn-sc-mode {
    type string;
    description
      "EVPN Ethernet-Segment service carving mode";
  }

  typedef ncs_template_L2vpn-evpn-smac-src {
    type string;
    description
      "L2vpn evpn smac src";
  }

  typedef ncs_template_L2vpn-evpn-lb-mode {
    type string;
    description
      "L2VPN EVPN load balancing mode";
  }

  typedef ncs_template_L2vpn-evpn-mf-mode {
    type string;
    description
      "L2VPN EVPN MAC flushing mode";
  }

  typedef ncs_template_L2vpn-evpn-rt-origin {
    type string;
    description
      "L2vpn evpn rt origin";
  }

  typedef ncs_template_L2vpn-rg-role {
    type string;
    description
      "L2vpn rg role";
  }

  typedef ncs_template_L2vpn-evpn-es-state {
    type string;
    description
      "L2vpn evpn es state";
  }

  typedef ncs_template_L2vpn-evpn-esi {
    type string;
    description
      "EVPN ESI types";
  }

  typedef ncs_template_Evpn-bag-label-unresolved-reason {
    type string;
    description
      "EVPN label entry unresolved reasons";
  }

  typedef ncs_template_L2vpn-ad-rt-role {
    type string;
    description
      "L2vpn ad rt role";
  }

  typedef ncs_template_Evpn-bag-path-issues {
    type string;
    description
      "Evpn bag path issues";
  }

  typedef ncs_template_Evpn-bag-l2-attr-cw {
    type string;
    description
      "Evpn bag l2 attr cw";
  }

  typedef ncs_template_Evpn-bag-df-role {
    type string;
    description
      "Evpn bag df role";
  }

  typedef ncs_template_Evpn-pref-ecmp-nh-mode {
    type string;
    description
      "Evpn pref ecmp nh mode";
  }

  typedef ncs_template_L2vpn-ad-rt {
    type string;
    description
      "L2vpn ad rt";
  }

  typedef ncs_template_L2vpn-ad-rd {
    type string;
    description
      "L2vpn ad rd";
  }

  typedef ncs_template_L2vpn-evpn {
    type string;
    description
      "L2vpn evpn";
  }

  typedef ncs_template_Evpn-child {
    type string;
    description
      "Evpn child";
  }

  typedef ncs_template_Evpn-igmp-grp {
    type string;
    description
      "Evpn igmp grp";
  }

  typedef ncs_template_Evpn-igmp-version {
    type string;
    description
      "Evpn igmp version";
  }

  typedef ncs_template_L2vpn-bag-in6-addr {
    type string;
    description
      "L2vpn bag in6 addr";
  }

  typedef ncs_template_Evpn-igmp-source {
    type string;
    description
      "Evpn igmp source";
  }

  typedef ncs_template_Evpn-igmp-msg {
    type string;
    description
      "Evpn igmp msg";
  }

  typedef ncs_template_Evpn-client1 {
    type string;
    description
      "Evpn client1";
  }

  typedef ncs_template_Im-state-enum {
    type string;
    description
      "Im state enum";
  }

  typedef ncs_template_Evpn-grp {
    type string;
    description
      "EVPN Group State";
  }

  typedef ncs_rpc_notif_L2vpn-evpn-es-access-signal-mode {
    type enumeration {
      enum "unsupported" {
        description
          "Unsupported interface type";
      }
      enum "oos" {
        description
          "Out of Sync";
      }
      enum "down" {
        description
          "Down";
      }
    }
    description
      "L2vpn evpn es access signal mode";
  }

  typedef ncs_rpc_notif_L2vpn-evpn-sc-mcast-mode {
    type enumeration {
      enum "disabled" {
        description
          "multicast service carving is disabled";
      }
      enum "hrw-s-g" {
        description
          "Multicast HRW S,G";
      }
      enum "hrw-g" {
        description
          "Multicast HRW *,G";
      }
    }
    description
      "EVPN Ethernet-Segment service multicast carving
       mode";
  }

  typedef ncs_rpc_notif_L2vpn-evpn-sc-synchronization-mode {
    type enumeration {
      enum "none" {
        description
          "No service carving synchronization";
      }
      enum "ntp" {
        description
          "NTP SCT based service carving synchronization";
      }
      enum "handshake" {
        description
          "Handshake messaging based service carving
           synchronization";
      }
      enum "invalid" {
        description
          "Invalid or unknown service carving
           synchronization mode";
      }
    }
    description
      "EVPN Ethernet-Segment service carving
       synchronization mode";
  }

  typedef ncs_rpc_notif_L2vpn-evpn-sc-mode {
    type enumeration {
      enum "invalid" {
        description
          "Invalid service carving mode";
      }
      enum "auto" {
        description
          "Auto service carving mode";
      }
      enum "manual" {
        description
          "Manual service carving";
      }
      enum "manual-list" {
        description
          "Manual List service carving";
      }
      enum "hrw" {
        description
          "HRW service carving";
      }
      enum "pref" {
        description
          "Preferential service carving";
      }
    }
    description
      "EVPN Ethernet-Segment service carving mode";
  }

  typedef ncs_rpc_notif_L2vpn-evpn-smac-src {
    type enumeration {
      enum "invalid" {
        description
          "Incomplete Configuration";
      }
      enum "not-applicable" {
        description
          "Source MAC Not Applicable (EVPN)";
      }
      enum "local" {
        description
          "Local";
      }
      enum "pbb-bsa" {
        description
          "PBB BSA";
      }
      enum "esi" {
        description
          "From ESI";
      }
      enum "esi-invalid" {
        description
          "From ESI, Error";
      }
      enum "pbb-bsa-overrride" {
        description
          "PBB BSA, no ESI";
      }
    }
    description
      "L2vpn evpn smac src";
  }

  typedef ncs_rpc_notif_L2vpn-evpn-lb-mode {
    type enumeration {
      enum "invalid-load-balancing" {
        description
          "Invalid load balancing";
      }
      enum "single-homed" {
        description
          "Single-homed site or network";
      }
      enum "multi-homed-aa-per-flow" {
        description
          "Multi-homed access network active/active per
           flow";
      }
      enum "multi-homed-aa-per-service" {
        description
          "Multi-homed access network active/active per
           service";
      }
      enum "multi-homed-single-flow-active" {
        description
          "Multi-homed access network single-flow-active";
      }
      enum "multi-homed-port-active" {
        description
          "Multi-homed access network port-active";
      }
    }
    description
      "L2VPN EVPN load balancing mode";
  }

  typedef ncs_rpc_notif_L2vpn-evpn-mf-mode {
    type enumeration {
      enum "invalid" {
        description
          "Invalid MAC Flushing mode";
      }
      enum "tcn-stp" {
        description
          "TCN STP MAC Flushing mode";
      }
      enum "mvrp" {
        description
          "MVRP MAC Flushing mode";
      }
    }
    description
      "L2VPN EVPN MAC flushing mode";
  }

  typedef ncs_rpc_notif_L2vpn-evpn-rt-origin {
    type enumeration {
      enum "invalid" {
        description
          "Incomplete Configuration";
      }
      enum "extracted" {
        description
          "From ESI";
      }
      enum "configured" {
        description
          "Locally configured";
      }
    }
    description
      "L2vpn evpn rt origin";
  }

  typedef ncs_rpc_notif_L2vpn-rg-role {
    type enumeration {
      enum "l2vpn-rg-role-not-defined" {
        description
          "l2vpn rg role not defined";
      }
      enum "l2vpn-rg-role-active" {
        description
          "l2vpn rg role active";
      }
      enum "l2vpn-rg-role-standby" {
        description
          "l2vpn rg role standby";
      }
      enum "l2vpn-rg-role-max" {
        description
          "l2vpn rg role max";
      }
    }
    description
      "L2vpn rg role";
  }

  typedef ncs_rpc_notif_L2vpn-evpn-es-state {
    type enumeration {
      enum "not-ready" {
        description
          "Not Ready";
      }
      enum "peering" {
        description
          "Peering";
      }
      enum "up" {
        description
          "Up";
      }
      enum "down" {
        description
          "Down";
      }
      enum "standby" {
        description
          "Standby";
      }
    }
    description
      "L2vpn evpn es state";
  }

  typedef ncs_rpc_notif_L2vpn-evpn-esi {
    type enumeration {
      enum "esi-type0" {
        value 0;
        description
          "ESI type zero";
      }
      enum "esi-type1" {
        value 1;
        description
          "ESI type one";
      }
      enum "esi-type2" {
        value 2;
        description
          "ESI type two";
      }
      enum "esi-type3" {
        value 3;
        description
          "ESI type three";
      }
      enum "esi-type4" {
        value 4;
        description
          "ESI type four";
      }
      enum "esi-type5" {
        value 5;
        description
          "ESI type five";
      }
      enum "l2vpn-evpn-esi-type-legacy" {
        value 128;
        description
          "ESI type legacy";
      }
      enum "l2vpn-evpn-esi-type-override" {
        value 129;
        description
          "ESI type override (10-octet value)";
      }
      enum "esi-type-invalid" {
        value 255;
        description
          "ESI type invalid";
      }
    }
    description
      "EVPN ESI types";
  }

  typedef ncs_rpc_notif_Evpn-bag-label-unresolved-reason {
    type enumeration {
      enum "none" {
        description
          "No reasons";
      }
      enum "no-evi-paths" {
        description
          "No valid per-EVI EAD paths";
      }
      enum "no-es-ead" {
        description
          "No per-ES EAD";
      }
      enum "local-not-ready" {
        description
          "Local service not ready, or multiple matching
           remote EADs";
      }
    }
    description
      "EVPN label entry unresolved reasons";
  }

  typedef ncs_rpc_notif_L2vpn-ad-rt-role {
    type enumeration {
      enum "both" {
        value 0;
        description
          "Both";
      }
      enum "import" {
        value 1;
        description
          "Import";
      }
      enum "export" {
        value 2;
        description
          "Export";
      }
    }
    description
      "L2vpn ad rt role";
  }

  typedef ncs_rpc_notif_Evpn-bag-path-issues {
    type enumeration {
      enum "unknown" {
        description
          "Unknown Issue";
      }
      enum "invalid-transport-id" {
        description
          "Invalid Transport ID";
      }
      enum "sid-format-mismatch" {
        description
          "SIDs Do Not Match Local Format";
      }
      enum "control-word-mismatch" {
        description
          "Control Word Mismatch";
      }
      enum "mtu-mismatch" {
        description
          "MTU Mismatch";
      }
    }
    description
      "Evpn bag path issues";
  }

  typedef ncs_rpc_notif_Evpn-bag-l2-attr-cw {
    type enumeration {
      enum "unspecified" {
        description
          "Control Word Not Specified";
      }
      enum "disabled" {
        description
          "Control Word Disabled";
      }
      enum "enabled" {
        description
          "Control Word Enabled";
      }
    }
    description
      "Evpn bag l2 attr cw";
  }

  typedef ncs_rpc_notif_Evpn-bag-df-role {
    type enumeration {
      enum "invalid" {
        description
          "Designated Forwarder Role Not Specified";
      }
      enum "primary" {
        description
          "Designated Forwarder Role Primary";
      }
      enum "backup" {
        description
          "Designated Forwarder Role Backup";
      }
      enum "not-designated-forwarder" {
        description
          "No Designated Forwarder Role";
      }
    }
    description
      "Evpn bag df role";
  }

  typedef ncs_rpc_notif_Evpn-pref-ecmp-nh-mode {
    type enumeration {
      enum "invalid" {
        description
          "Invalid";
      }
      enum "pref-nh-lowest-ip" {
        description
          "Preferred ECMP Nexthop Lowest IP";
      }
      enum "pref-nh-highest-ip" {
        description
          "Preferred ECMP Nexthop Highest IP";
      }
      enum "pref-nh-modulo" {
        description
          "Preferred ECMP Nexthop Modulo";
      }
      enum "ecmp-disable" {
        description
          "ECMP Disable";
      }
    }
    description
      "Evpn pref ecmp nh mode";
  }

  typedef ncs_rpc_notif_L2vpn-ad-rt {
    type enumeration {
      enum "l2vpn-ad-rt-none" {
        value 0;
        description
          "Route target not set";
      }
      enum "l2vpn-ad-rt-as" {
        value 1;
        description
          "Route Target with 2 Byte AS number";
      }
      enum "l2vpn-ad-rt-4byte-as" {
        value 2;
        description
          "Route Target with 4 Byte AS number";
      }
      enum "l2vpn-ad-rt-v4-addr" {
        value 3;
        description
          "Route Target with IPv4 Address";
      }
      enum "es-import" {
        value 1538;
        description
          "Ethernet Segment Route Target from BGP";
      }
    }
    description
      "L2vpn ad rt";
  }

  typedef ncs_rpc_notif_L2vpn-ad-rd {
    type enumeration {
      enum "l2vpn-ad-rd-none" {
        value 0;
        description
          "Route Distinguisher not set";
      }
      enum "l2vpn-ad-rd-auto" {
        value 1;
        description
          "Route Distinguisher auto-generated";
      }
      enum "l2vpn-ad-rd-as" {
        value 2;
        description
          "Route Distinguisher with 2 Byte AS number";
      }
      enum "l2vpn-ad-rd-4byte-as" {
        value 3;
        description
          "Route Distinguisher with 4 Byte AS number";
      }
      enum "l2vpn-ad-rd-v4-addr" {
        value 4;
        description
          "Route Distinguisher with IPv4 Address";
      }
    }
    description
      "L2vpn ad rd";
  }

  typedef ncs_rpc_notif_L2vpn-evpn {
    type enumeration {
      enum "evpn-type-invalid" {
        description
          "Unspecify type for that EVI entry";
      }
      enum "evpn-type-evpn" {
        description
          "EVPN service type";
      }
      enum "evpn-type-pbb-evpn" {
        description
          "PBB EVPN service type";
      }
      enum "evpn-type-evpn-vpws-vlan-unaware" {
        description
          "EVPN VPWS vlan-unaware service type";
      }
      enum "evpn-type-evpn-vpws-vlan-aware" {
        description
          "EVPN VPWS vlan-aware service type";
      }
      enum "evpn-type-max" {
        description
          "Max EVPN type";
      }
    }
    description
      "L2vpn evpn";
  }

  typedef ncs_rpc_notif_Evpn-child {
    type enumeration {
      enum "l2-fwd" {
        description
          "L2 FWD";
      }
      enum "l3-sub-if" {
        description
          "L3 SUBIF";
      }
    }
    description
      "Evpn child";
  }

  typedef ncs_rpc_notif_Evpn-igmp-grp {
    type enumeration {
      enum "include" {
        description
          "Include";
      }
      enum "exclude" {
        description
          "Exclude";
      }
    }
    description
      "Evpn igmp grp";
  }

  typedef ncs_rpc_notif_Evpn-igmp-version {
    type enumeration {
      enum "v1" {
        description
          "Version 1";
      }
      enum "v2" {
        description
          "Version 2";
      }
      enum "v3" {
        description
          "Version 3";
      }
    }
    description
      "Evpn igmp version";
  }

  typedef ncs_rpc_notif_L2vpn-bag-in6-addr {
    type inet:ipv6-address;
    description
      "L2vpn bag in6 addr";
  }

  typedef ncs_rpc_notif_Evpn-igmp-source {
    type enumeration {
      enum "local" {
        description
          "Local";
      }
      enum "remote" {
        description
          "Remote";
      }
    }
    description
      "Evpn igmp source";
  }

  typedef ncs_rpc_notif_Evpn-igmp-msg {
    type enumeration {
      enum "join" {
        description
          "Join";
      }
      enum "leave" {
        description
          "Leave";
      }
    }
    description
      "Evpn igmp msg";
  }

  typedef ncs_rpc_notif_Evpn-client1 {
    type enumeration {
      enum "igmpsn" {
        description
          "IGMPSN";
      }
      enum "igmp" {
        description
          "IGMP";
      }
      enum "mrib" {
        description
          "MRIB";
      }
      enum "mld" {
        description
          "MLD";
      }
      enum "invalid" {
        description
          "Invalid";
      }
    }
    description
      "Evpn client1";
  }

  typedef ncs_rpc_notif_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef ncs_rpc_notif_Evpn-grp {
    type enumeration {
      enum "deisolating" {
        description
          "Deisolating";
      }
      enum "isolated" {
        description
          "Isolated";
      }
      enum "ready" {
        description
          "Ready";
      }
      enum "incomplete" {
        description
          "Incomplete";
      }
    }
    description
      "EVPN Group State";
  }

  typedef live_ncs_L2vpn-evpn-es-access-signal-mode {
    type enumeration {
      enum "unsupported" {
        description
          "Unsupported interface type";
      }
      enum "oos" {
        description
          "Out of Sync";
      }
      enum "down" {
        description
          "Down";
      }
    }
    description
      "L2vpn evpn es access signal mode";
  }

  typedef live_ncs_L2vpn-evpn-sc-mcast-mode {
    type enumeration {
      enum "disabled" {
        description
          "multicast service carving is disabled";
      }
      enum "hrw-s-g" {
        description
          "Multicast HRW S,G";
      }
      enum "hrw-g" {
        description
          "Multicast HRW *,G";
      }
    }
    description
      "EVPN Ethernet-Segment service multicast carving
       mode";
  }

  typedef live_ncs_L2vpn-evpn-sc-synchronization-mode {
    type enumeration {
      enum "none" {
        description
          "No service carving synchronization";
      }
      enum "ntp" {
        description
          "NTP SCT based service carving synchronization";
      }
      enum "handshake" {
        description
          "Handshake messaging based service carving
           synchronization";
      }
      enum "invalid" {
        description
          "Invalid or unknown service carving
           synchronization mode";
      }
    }
    description
      "EVPN Ethernet-Segment service carving
       synchronization mode";
  }

  typedef live_ncs_L2vpn-evpn-sc-mode {
    type enumeration {
      enum "invalid" {
        description
          "Invalid service carving mode";
      }
      enum "auto" {
        description
          "Auto service carving mode";
      }
      enum "manual" {
        description
          "Manual service carving";
      }
      enum "manual-list" {
        description
          "Manual List service carving";
      }
      enum "hrw" {
        description
          "HRW service carving";
      }
      enum "pref" {
        description
          "Preferential service carving";
      }
    }
    description
      "EVPN Ethernet-Segment service carving mode";
  }

  typedef live_ncs_L2vpn-evpn-smac-src {
    type enumeration {
      enum "invalid" {
        description
          "Incomplete Configuration";
      }
      enum "not-applicable" {
        description
          "Source MAC Not Applicable (EVPN)";
      }
      enum "local" {
        description
          "Local";
      }
      enum "pbb-bsa" {
        description
          "PBB BSA";
      }
      enum "esi" {
        description
          "From ESI";
      }
      enum "esi-invalid" {
        description
          "From ESI, Error";
      }
      enum "pbb-bsa-overrride" {
        description
          "PBB BSA, no ESI";
      }
    }
    description
      "L2vpn evpn smac src";
  }

  typedef live_ncs_L2vpn-evpn-lb-mode {
    type enumeration {
      enum "invalid-load-balancing" {
        description
          "Invalid load balancing";
      }
      enum "single-homed" {
        description
          "Single-homed site or network";
      }
      enum "multi-homed-aa-per-flow" {
        description
          "Multi-homed access network active/active per
           flow";
      }
      enum "multi-homed-aa-per-service" {
        description
          "Multi-homed access network active/active per
           service";
      }
      enum "multi-homed-single-flow-active" {
        description
          "Multi-homed access network single-flow-active";
      }
      enum "multi-homed-port-active" {
        description
          "Multi-homed access network port-active";
      }
    }
    description
      "L2VPN EVPN load balancing mode";
  }

  typedef live_ncs_L2vpn-evpn-mf-mode {
    type enumeration {
      enum "invalid" {
        description
          "Invalid MAC Flushing mode";
      }
      enum "tcn-stp" {
        description
          "TCN STP MAC Flushing mode";
      }
      enum "mvrp" {
        description
          "MVRP MAC Flushing mode";
      }
    }
    description
      "L2VPN EVPN MAC flushing mode";
  }

  typedef live_ncs_L2vpn-evpn-rt-origin {
    type enumeration {
      enum "invalid" {
        description
          "Incomplete Configuration";
      }
      enum "extracted" {
        description
          "From ESI";
      }
      enum "configured" {
        description
          "Locally configured";
      }
    }
    description
      "L2vpn evpn rt origin";
  }

  typedef live_ncs_L2vpn-rg-role {
    type enumeration {
      enum "l2vpn-rg-role-not-defined" {
        description
          "l2vpn rg role not defined";
      }
      enum "l2vpn-rg-role-active" {
        description
          "l2vpn rg role active";
      }
      enum "l2vpn-rg-role-standby" {
        description
          "l2vpn rg role standby";
      }
      enum "l2vpn-rg-role-max" {
        description
          "l2vpn rg role max";
      }
    }
    description
      "L2vpn rg role";
  }

  typedef live_ncs_L2vpn-evpn-es-state {
    type enumeration {
      enum "not-ready" {
        description
          "Not Ready";
      }
      enum "peering" {
        description
          "Peering";
      }
      enum "up" {
        description
          "Up";
      }
      enum "down" {
        description
          "Down";
      }
      enum "standby" {
        description
          "Standby";
      }
    }
    description
      "L2vpn evpn es state";
  }

  typedef live_ncs_L2vpn-evpn-esi {
    type enumeration {
      enum "esi-type0" {
        value 0;
        description
          "ESI type zero";
      }
      enum "esi-type1" {
        value 1;
        description
          "ESI type one";
      }
      enum "esi-type2" {
        value 2;
        description
          "ESI type two";
      }
      enum "esi-type3" {
        value 3;
        description
          "ESI type three";
      }
      enum "esi-type4" {
        value 4;
        description
          "ESI type four";
      }
      enum "esi-type5" {
        value 5;
        description
          "ESI type five";
      }
      enum "l2vpn-evpn-esi-type-legacy" {
        value 128;
        description
          "ESI type legacy";
      }
      enum "l2vpn-evpn-esi-type-override" {
        value 129;
        description
          "ESI type override (10-octet value)";
      }
      enum "esi-type-invalid" {
        value 255;
        description
          "ESI type invalid";
      }
    }
    description
      "EVPN ESI types";
  }

  typedef live_ncs_Evpn-bag-label-unresolved-reason {
    type enumeration {
      enum "none" {
        description
          "No reasons";
      }
      enum "no-evi-paths" {
        description
          "No valid per-EVI EAD paths";
      }
      enum "no-es-ead" {
        description
          "No per-ES EAD";
      }
      enum "local-not-ready" {
        description
          "Local service not ready, or multiple matching
           remote EADs";
      }
    }
    description
      "EVPN label entry unresolved reasons";
  }

  typedef live_ncs_L2vpn-ad-rt-role {
    type enumeration {
      enum "both" {
        value 0;
        description
          "Both";
      }
      enum "import" {
        value 1;
        description
          "Import";
      }
      enum "export" {
        value 2;
        description
          "Export";
      }
    }
    description
      "L2vpn ad rt role";
  }

  typedef live_ncs_Evpn-bag-path-issues {
    type enumeration {
      enum "unknown" {
        description
          "Unknown Issue";
      }
      enum "invalid-transport-id" {
        description
          "Invalid Transport ID";
      }
      enum "sid-format-mismatch" {
        description
          "SIDs Do Not Match Local Format";
      }
      enum "control-word-mismatch" {
        description
          "Control Word Mismatch";
      }
      enum "mtu-mismatch" {
        description
          "MTU Mismatch";
      }
    }
    description
      "Evpn bag path issues";
  }

  typedef live_ncs_Evpn-bag-l2-attr-cw {
    type enumeration {
      enum "unspecified" {
        description
          "Control Word Not Specified";
      }
      enum "disabled" {
        description
          "Control Word Disabled";
      }
      enum "enabled" {
        description
          "Control Word Enabled";
      }
    }
    description
      "Evpn bag l2 attr cw";
  }

  typedef live_ncs_Evpn-bag-df-role {
    type enumeration {
      enum "invalid" {
        description
          "Designated Forwarder Role Not Specified";
      }
      enum "primary" {
        description
          "Designated Forwarder Role Primary";
      }
      enum "backup" {
        description
          "Designated Forwarder Role Backup";
      }
      enum "not-designated-forwarder" {
        description
          "No Designated Forwarder Role";
      }
    }
    description
      "Evpn bag df role";
  }

  typedef live_ncs_Evpn-pref-ecmp-nh-mode {
    type enumeration {
      enum "invalid" {
        description
          "Invalid";
      }
      enum "pref-nh-lowest-ip" {
        description
          "Preferred ECMP Nexthop Lowest IP";
      }
      enum "pref-nh-highest-ip" {
        description
          "Preferred ECMP Nexthop Highest IP";
      }
      enum "pref-nh-modulo" {
        description
          "Preferred ECMP Nexthop Modulo";
      }
      enum "ecmp-disable" {
        description
          "ECMP Disable";
      }
    }
    description
      "Evpn pref ecmp nh mode";
  }

  typedef live_ncs_L2vpn-ad-rt {
    type enumeration {
      enum "l2vpn-ad-rt-none" {
        value 0;
        description
          "Route target not set";
      }
      enum "l2vpn-ad-rt-as" {
        value 1;
        description
          "Route Target with 2 Byte AS number";
      }
      enum "l2vpn-ad-rt-4byte-as" {
        value 2;
        description
          "Route Target with 4 Byte AS number";
      }
      enum "l2vpn-ad-rt-v4-addr" {
        value 3;
        description
          "Route Target with IPv4 Address";
      }
      enum "es-import" {
        value 1538;
        description
          "Ethernet Segment Route Target from BGP";
      }
    }
    description
      "L2vpn ad rt";
  }

  typedef live_ncs_L2vpn-ad-rd {
    type enumeration {
      enum "l2vpn-ad-rd-none" {
        value 0;
        description
          "Route Distinguisher not set";
      }
      enum "l2vpn-ad-rd-auto" {
        value 1;
        description
          "Route Distinguisher auto-generated";
      }
      enum "l2vpn-ad-rd-as" {
        value 2;
        description
          "Route Distinguisher with 2 Byte AS number";
      }
      enum "l2vpn-ad-rd-4byte-as" {
        value 3;
        description
          "Route Distinguisher with 4 Byte AS number";
      }
      enum "l2vpn-ad-rd-v4-addr" {
        value 4;
        description
          "Route Distinguisher with IPv4 Address";
      }
    }
    description
      "L2vpn ad rd";
  }

  typedef live_ncs_L2vpn-evpn {
    type enumeration {
      enum "evpn-type-invalid" {
        description
          "Unspecify type for that EVI entry";
      }
      enum "evpn-type-evpn" {
        description
          "EVPN service type";
      }
      enum "evpn-type-pbb-evpn" {
        description
          "PBB EVPN service type";
      }
      enum "evpn-type-evpn-vpws-vlan-unaware" {
        description
          "EVPN VPWS vlan-unaware service type";
      }
      enum "evpn-type-evpn-vpws-vlan-aware" {
        description
          "EVPN VPWS vlan-aware service type";
      }
      enum "evpn-type-max" {
        description
          "Max EVPN type";
      }
    }
    description
      "L2vpn evpn";
  }

  typedef live_ncs_Evpn-child {
    type enumeration {
      enum "l2-fwd" {
        description
          "L2 FWD";
      }
      enum "l3-sub-if" {
        description
          "L3 SUBIF";
      }
    }
    description
      "Evpn child";
  }

  typedef live_ncs_Evpn-igmp-grp {
    type enumeration {
      enum "include" {
        description
          "Include";
      }
      enum "exclude" {
        description
          "Exclude";
      }
    }
    description
      "Evpn igmp grp";
  }

  typedef live_ncs_Evpn-igmp-version {
    type enumeration {
      enum "v1" {
        description
          "Version 1";
      }
      enum "v2" {
        description
          "Version 2";
      }
      enum "v3" {
        description
          "Version 3";
      }
    }
    description
      "Evpn igmp version";
  }

  typedef live_ncs_L2vpn-bag-in6-addr {
    type inet:ipv6-address;
    description
      "L2vpn bag in6 addr";
  }

  typedef live_ncs_Evpn-igmp-source {
    type enumeration {
      enum "local" {
        description
          "Local";
      }
      enum "remote" {
        description
          "Remote";
      }
    }
    description
      "Evpn igmp source";
  }

  typedef live_ncs_Evpn-igmp-msg {
    type enumeration {
      enum "join" {
        description
          "Join";
      }
      enum "leave" {
        description
          "Leave";
      }
    }
    description
      "Evpn igmp msg";
  }

  typedef live_ncs_Evpn-client1 {
    type enumeration {
      enum "igmpsn" {
        description
          "IGMPSN";
      }
      enum "igmp" {
        description
          "IGMP";
      }
      enum "mrib" {
        description
          "MRIB";
      }
      enum "mld" {
        description
          "MLD";
      }
      enum "invalid" {
        description
          "Invalid";
      }
    }
    description
      "Evpn client1";
  }

  typedef live_ncs_Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef live_ncs_Evpn-grp {
    type enumeration {
      enum "deisolating" {
        description
          "Deisolating";
      }
      enum "isolated" {
        description
          "Isolated";
      }
      enum "ready" {
        description
          "Ready";
      }
      enum "incomplete" {
        description
          "Incomplete";
      }
    }
    description
      "EVPN Group State";
  }

  typedef L2vpn-evpn-es-access-signal-mode {
    type enumeration {
      enum "unsupported" {
        description
          "Unsupported interface type";
      }
      enum "oos" {
        description
          "Out of Sync";
      }
      enum "down" {
        description
          "Down";
      }
    }
    description
      "L2vpn evpn es access signal mode";
  }

  typedef L2vpn-evpn-sc-mcast-mode {
    type enumeration {
      enum "disabled" {
        description
          "multicast service carving is disabled";
      }
      enum "hrw-s-g" {
        description
          "Multicast HRW S,G";
      }
      enum "hrw-g" {
        description
          "Multicast HRW *,G";
      }
    }
    description
      "EVPN Ethernet-Segment service multicast carving
       mode";
  }

  typedef L2vpn-evpn-sc-synchronization-mode {
    type enumeration {
      enum "none" {
        description
          "No service carving synchronization";
      }
      enum "ntp" {
        description
          "NTP SCT based service carving synchronization";
      }
      enum "handshake" {
        description
          "Handshake messaging based service carving
           synchronization";
      }
      enum "invalid" {
        description
          "Invalid or unknown service carving
           synchronization mode";
      }
    }
    description
      "EVPN Ethernet-Segment service carving
       synchronization mode";
  }

  typedef L2vpn-evpn-sc-mode {
    type enumeration {
      enum "invalid" {
        description
          "Invalid service carving mode";
      }
      enum "auto" {
        description
          "Auto service carving mode";
      }
      enum "manual" {
        description
          "Manual service carving";
      }
      enum "manual-list" {
        description
          "Manual List service carving";
      }
      enum "hrw" {
        description
          "HRW service carving";
      }
      enum "pref" {
        description
          "Preferential service carving";
      }
    }
    description
      "EVPN Ethernet-Segment service carving mode";
  }

  typedef L2vpn-evpn-smac-src {
    type enumeration {
      enum "invalid" {
        description
          "Incomplete Configuration";
      }
      enum "not-applicable" {
        description
          "Source MAC Not Applicable (EVPN)";
      }
      enum "local" {
        description
          "Local";
      }
      enum "pbb-bsa" {
        description
          "PBB BSA";
      }
      enum "esi" {
        description
          "From ESI";
      }
      enum "esi-invalid" {
        description
          "From ESI, Error";
      }
      enum "pbb-bsa-overrride" {
        description
          "PBB BSA, no ESI";
      }
    }
    description
      "L2vpn evpn smac src";
  }

  typedef L2vpn-evpn-lb-mode {
    type enumeration {
      enum "invalid-load-balancing" {
        description
          "Invalid load balancing";
      }
      enum "single-homed" {
        description
          "Single-homed site or network";
      }
      enum "multi-homed-aa-per-flow" {
        description
          "Multi-homed access network active/active per
           flow";
      }
      enum "multi-homed-aa-per-service" {
        description
          "Multi-homed access network active/active per
           service";
      }
      enum "multi-homed-single-flow-active" {
        description
          "Multi-homed access network single-flow-active";
      }
      enum "multi-homed-port-active" {
        description
          "Multi-homed access network port-active";
      }
    }
    description
      "L2VPN EVPN load balancing mode";
  }

  typedef L2vpn-evpn-mf-mode {
    type enumeration {
      enum "invalid" {
        description
          "Invalid MAC Flushing mode";
      }
      enum "tcn-stp" {
        description
          "TCN STP MAC Flushing mode";
      }
      enum "mvrp" {
        description
          "MVRP MAC Flushing mode";
      }
    }
    description
      "L2VPN EVPN MAC flushing mode";
  }

  typedef L2vpn-evpn-rt-origin {
    type enumeration {
      enum "invalid" {
        description
          "Incomplete Configuration";
      }
      enum "extracted" {
        description
          "From ESI";
      }
      enum "configured" {
        description
          "Locally configured";
      }
    }
    description
      "L2vpn evpn rt origin";
  }

  typedef L2vpn-rg-role {
    type enumeration {
      enum "l2vpn-rg-role-not-defined" {
        description
          "l2vpn rg role not defined";
      }
      enum "l2vpn-rg-role-active" {
        description
          "l2vpn rg role active";
      }
      enum "l2vpn-rg-role-standby" {
        description
          "l2vpn rg role standby";
      }
      enum "l2vpn-rg-role-max" {
        description
          "l2vpn rg role max";
      }
    }
    description
      "L2vpn rg role";
  }

  typedef L2vpn-evpn-es-state {
    type enumeration {
      enum "not-ready" {
        description
          "Not Ready";
      }
      enum "peering" {
        description
          "Peering";
      }
      enum "up" {
        description
          "Up";
      }
      enum "down" {
        description
          "Down";
      }
      enum "standby" {
        description
          "Standby";
      }
    }
    description
      "L2vpn evpn es state";
  }

  typedef L2vpn-evpn-esi {
    type enumeration {
      enum "esi-type0" {
        value 0;
        description
          "ESI type zero";
      }
      enum "esi-type1" {
        value 1;
        description
          "ESI type one";
      }
      enum "esi-type2" {
        value 2;
        description
          "ESI type two";
      }
      enum "esi-type3" {
        value 3;
        description
          "ESI type three";
      }
      enum "esi-type4" {
        value 4;
        description
          "ESI type four";
      }
      enum "esi-type5" {
        value 5;
        description
          "ESI type five";
      }
      enum "l2vpn-evpn-esi-type-legacy" {
        value 128;
        description
          "ESI type legacy";
      }
      enum "l2vpn-evpn-esi-type-override" {
        value 129;
        description
          "ESI type override (10-octet value)";
      }
      enum "esi-type-invalid" {
        value 255;
        description
          "ESI type invalid";
      }
    }
    description
      "EVPN ESI types";
  }

  typedef Evpn-bag-label-unresolved-reason {
    type enumeration {
      enum "none" {
        description
          "No reasons";
      }
      enum "no-evi-paths" {
        description
          "No valid per-EVI EAD paths";
      }
      enum "no-es-ead" {
        description
          "No per-ES EAD";
      }
      enum "local-not-ready" {
        description
          "Local service not ready, or multiple matching
           remote EADs";
      }
    }
    description
      "EVPN label entry unresolved reasons";
  }

  typedef L2vpn-ad-rt-role {
    type enumeration {
      enum "both" {
        value 0;
        description
          "Both";
      }
      enum "import" {
        value 1;
        description
          "Import";
      }
      enum "export" {
        value 2;
        description
          "Export";
      }
    }
    description
      "L2vpn ad rt role";
  }

  typedef Evpn-bag-path-issues {
    type enumeration {
      enum "unknown" {
        description
          "Unknown Issue";
      }
      enum "invalid-transport-id" {
        description
          "Invalid Transport ID";
      }
      enum "sid-format-mismatch" {
        description
          "SIDs Do Not Match Local Format";
      }
      enum "control-word-mismatch" {
        description
          "Control Word Mismatch";
      }
      enum "mtu-mismatch" {
        description
          "MTU Mismatch";
      }
    }
    description
      "Evpn bag path issues";
  }

  typedef Evpn-bag-l2-attr-cw {
    type enumeration {
      enum "unspecified" {
        description
          "Control Word Not Specified";
      }
      enum "disabled" {
        description
          "Control Word Disabled";
      }
      enum "enabled" {
        description
          "Control Word Enabled";
      }
    }
    description
      "Evpn bag l2 attr cw";
  }

  typedef Evpn-bag-df-role {
    type enumeration {
      enum "invalid" {
        description
          "Designated Forwarder Role Not Specified";
      }
      enum "primary" {
        description
          "Designated Forwarder Role Primary";
      }
      enum "backup" {
        description
          "Designated Forwarder Role Backup";
      }
      enum "not-designated-forwarder" {
        description
          "No Designated Forwarder Role";
      }
    }
    description
      "Evpn bag df role";
  }

  typedef Evpn-pref-ecmp-nh-mode {
    type enumeration {
      enum "invalid" {
        description
          "Invalid";
      }
      enum "pref-nh-lowest-ip" {
        description
          "Preferred ECMP Nexthop Lowest IP";
      }
      enum "pref-nh-highest-ip" {
        description
          "Preferred ECMP Nexthop Highest IP";
      }
      enum "pref-nh-modulo" {
        description
          "Preferred ECMP Nexthop Modulo";
      }
      enum "ecmp-disable" {
        description
          "ECMP Disable";
      }
    }
    description
      "Evpn pref ecmp nh mode";
  }

  typedef L2vpn-ad-rt {
    type enumeration {
      enum "l2vpn-ad-rt-none" {
        value 0;
        description
          "Route target not set";
      }
      enum "l2vpn-ad-rt-as" {
        value 1;
        description
          "Route Target with 2 Byte AS number";
      }
      enum "l2vpn-ad-rt-4byte-as" {
        value 2;
        description
          "Route Target with 4 Byte AS number";
      }
      enum "l2vpn-ad-rt-v4-addr" {
        value 3;
        description
          "Route Target with IPv4 Address";
      }
      enum "es-import" {
        value 1538;
        description
          "Ethernet Segment Route Target from BGP";
      }
    }
    description
      "L2vpn ad rt";
  }

  typedef L2vpn-ad-rd {
    type enumeration {
      enum "l2vpn-ad-rd-none" {
        value 0;
        description
          "Route Distinguisher not set";
      }
      enum "l2vpn-ad-rd-auto" {
        value 1;
        description
          "Route Distinguisher auto-generated";
      }
      enum "l2vpn-ad-rd-as" {
        value 2;
        description
          "Route Distinguisher with 2 Byte AS number";
      }
      enum "l2vpn-ad-rd-4byte-as" {
        value 3;
        description
          "Route Distinguisher with 4 Byte AS number";
      }
      enum "l2vpn-ad-rd-v4-addr" {
        value 4;
        description
          "Route Distinguisher with IPv4 Address";
      }
    }
    description
      "L2vpn ad rd";
  }

  typedef L2vpn-evpn {
    type enumeration {
      enum "evpn-type-invalid" {
        description
          "Unspecify type for that EVI entry";
      }
      enum "evpn-type-evpn" {
        description
          "EVPN service type";
      }
      enum "evpn-type-pbb-evpn" {
        description
          "PBB EVPN service type";
      }
      enum "evpn-type-evpn-vpws-vlan-unaware" {
        description
          "EVPN VPWS vlan-unaware service type";
      }
      enum "evpn-type-evpn-vpws-vlan-aware" {
        description
          "EVPN VPWS vlan-aware service type";
      }
      enum "evpn-type-max" {
        description
          "Max EVPN type";
      }
    }
    description
      "L2vpn evpn";
  }

  typedef Evpn-child {
    type enumeration {
      enum "l2-fwd" {
        description
          "L2 FWD";
      }
      enum "l3-sub-if" {
        description
          "L3 SUBIF";
      }
    }
    description
      "Evpn child";
  }

  typedef Evpn-igmp-grp {
    type enumeration {
      enum "include" {
        description
          "Include";
      }
      enum "exclude" {
        description
          "Exclude";
      }
    }
    description
      "Evpn igmp grp";
  }

  typedef Evpn-igmp-version {
    type enumeration {
      enum "v1" {
        description
          "Version 1";
      }
      enum "v2" {
        description
          "Version 2";
      }
      enum "v3" {
        description
          "Version 3";
      }
    }
    description
      "Evpn igmp version";
  }

  typedef L2vpn-bag-in6-addr {
    type inet:ipv6-address;
    description
      "L2vpn bag in6 addr";
  }

  typedef Evpn-igmp-source {
    type enumeration {
      enum "local" {
        description
          "Local";
      }
      enum "remote" {
        description
          "Remote";
      }
    }
    description
      "Evpn igmp source";
  }

  typedef Evpn-igmp-msg {
    type enumeration {
      enum "join" {
        description
          "Join";
      }
      enum "leave" {
        description
          "Leave";
      }
    }
    description
      "Evpn igmp msg";
  }

  typedef Evpn-client1 {
    type enumeration {
      enum "igmpsn" {
        description
          "IGMPSN";
      }
      enum "igmp" {
        description
          "IGMP";
      }
      enum "mrib" {
        description
          "MRIB";
      }
      enum "mld" {
        description
          "MLD";
      }
      enum "invalid" {
        description
          "Invalid";
      }
    }
    description
      "Evpn client1";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Evpn-grp {
    type enumeration {
      enum "deisolating" {
        description
          "Deisolating";
      }
      enum "isolated" {
        description
          "Isolated";
      }
      enum "ready" {
        description
          "Ready";
      }
      enum "incomplete" {
        description
          "Incomplete";
      }
    }
    description
      "EVPN Group State";
  }

  grouping ncs_template_L2VPN-ATOM-ACID {
    description
      "L2VPN ATOM ACID";
    leaf source-ac-id {
      type string;
      description
        "Source AC ID";
    }
    leaf target-ac-id {
      type string;
      description
        "Target AC ID";
    }
    leaf vpn-id {
      type string;
      description
        "VPN ID";
    }
    leaf taii-global-id {
      type string;
      description
        "TAII Global ID";
    }
    leaf taii-ac-id {
      type string;
      description
        "TAII AC ID";
    }
    leaf taii-prefix {
      type string;
      description
        "TAII Prefix";
    }
  }

  grouping ncs_template_L2VPN-EVPN-EAD-SERVICE-INFO {
    description
      "L2VPN EVPN EAD Ethernet Tag";
    leaf vpn-id {
      type string;
      description
        "VPN ID";
    }
    leaf type {
      type ncs_template_L2vpn-evpn;
      description
        "Service Type";
    }
    leaf ethernet-tag {
      type string;
      description
        "Ethernet Tag";
    }
  }

  grouping ncs_template_L2VPN-BAG-TIMESPEC {
    description
      "L2VPN Timespec Data Structure";
    leaf tv-sec {
      type string;
      description
        "tv sec";
    }
    leaf tv-nsec {
      type string;
      description
        "tv nsec";
    }
  }

  grouping ncs_template_L2VPN-STAT-ITEM {
    description
      "L2VPN EVPN Ethernet Segment (ES) private stats
       item";
    container last-time {
      description
        "last time";
      uses ncs_template_L2VPN-BAG-TIMESPEC;
    }
    leaf count {
      type string;
      description
        "count";
    }
    leaf last-arg {
      type string;
      description
        "last arg";
    }
  }

  grouping ncs_template_L2VPN-EVPN-ES-NH-BUFFER {
    description
      "L2VPN EVPN Ethernet Segment (ES) nexthops
       information";
    leaf next-hop {
      type string;
      description
        "Next-hop IP address (v6 format)";
    }
    leaf df-dont-preempt {
      type string;
      description
        "DF Dont Preemption";
    }
    leaf df-type {
      type string;
      description
        "DF Election Mode Configured";
    }
    leaf df-pref {
      type string;
      description
        "DF Election Preference Set";
    }
    leaf df-ntp-enabled {
      type string;
      description
        "NTP based DF Election Synchronization";
    }
    leaf ntp-sct-microseconds {
      type string;
      units "microsecond";
      description
        "NTP based SCT: represented in microseconds
         relative to Unix epoch: 1st Jan 1970";
    }
  }

  grouping ncs_template_L2VPN-EVPN-ES {
    description
      "EVPN Ethernet Segment (ES) database information";
    container msti-flush-count {
      description
        "Statistics for Host-mobility driven flush
         operations";
      uses ncs_template_L2VPN-STAT-ITEM;
    }
    leaf esi-type {
      type ncs_template_L2vpn-evpn-esi;
      description
        "ESI Type";
    }
    leaf esi-system-identifier {
      type string;
      description
        "ESI System Identifier";
    }
    leaf esi-port-key {
      type string;
      description
        "ESI Port Key";
    }
    leaf esi-system-priority {
      type string;
      description
        "ESI System Priority";
    }
    leaf ethernet-segment-name {
      type string;
      description
        "Ethernet Segment Name";
    }
    leaf ethernet-segment-state {
      type ncs_template_L2vpn-evpn-es-state;
      description
        "State of the ethernet segment";
    }
    leaf in-staggered-bringup {
      type string;
      description
        "Is this ES in the staggered bring-up queue?";
    }
    leaf if-handle {
      type xr:ncs_template_Interface-name;
      description
        "Main port ifhandle";
    }
    leaf main-port-role {
      type ncs_template_L2vpn-rg-role;
      description
        "Main port redundancy group role";
    }
    leaf main-port-mac {
      type string;
      description
        "Main Port MAC Address";
    }
    leaf num-up-p-ws {
      type string;
      description
        "Number of PWs in Up state";
    }
    leaf route-target {
      type string;
      description
        "ES-Import Route Target";
    }
    leaf rt-origin {
      type ncs_template_L2vpn-evpn-rt-origin;
      description
        "Origin of operational ES-Import RT";
    }
    leaf es-bgp-gates {
      type string;
      description
        "ES BGP Gates";
    }
    leaf es-l2fib-gates {
      type string;
      description
        "ES L2FIB Gates";
    }
    leaf mac-flushing-mode-config {
      type ncs_template_L2vpn-evpn-mf-mode;
      description
        "Configured MAC Flushing mode";
    }
    leaf load-balance-mode-config {
      type ncs_template_L2vpn-evpn-lb-mode;
      description
        "Configured load balancing mode";
    }
    leaf load-balance-mode-is-default {
      type string;
      description
        "Load balancing mode is default";
    }
    leaf load-balance-mode-oper {
      type ncs_template_L2vpn-evpn-lb-mode;
      description
        "Operational load balancing mode";
    }
    leaf force-single-home {
      type string;
      description
        "Ethernet-Segment forced to single home";
    }
    leaf convergence-mac-mobility {
      type string;
      description
        "Fast convergence mode based on MAC-mobility.";
    }
    leaf convergence-reroute {
      type string;
      description
        "Fast convergence mode based on reroute to backup
         peer.";
    }
    leaf convergence-nh-tracking {
      type string;
      description
        "Fast DF-Election based on tracking peer BGP
         Nexthop reachability";
    }
    leaf source-mac-oper {
      type string;
      description
        "Operational Source MAC address";
    }
    leaf source-mac-origin {
      type ncs_template_L2vpn-evpn-smac-src;
      description
        "Origin of operational source MAC address";
    }
    leaf peering-timer {
      type string;
      units "second";
      description
        "Configured timer for triggering DF election
         (seconds)";
    }
    leaf peering-timer-left {
      type string;
      units "millisecond";
      description
        "Milliseconds left on DF election timer";
    }
    leaf recovery-timer {
      type string;
      units "second";
      description
        "Configured timer for (STP) recovery (seconds)";
    }
    leaf recovery-timer-left {
      type string;
      units "millisecond";
      description
        "Milliseconds left on (STP) recovery timer";
    }
    leaf carving-timer {
      type string;
      units "second";
      description
        "Configured timer for delaying DF election
         (seconds)";
    }
    leaf carving-timer-left {
      type string;
      units "millisecond";
      description
        "Milliseconds left on carving timer";
    }
    leaf hrw-reset-timer {
      type string;
      units "second";
      description
        "Configured timer for HRW reset (seconds)";
    }
    leaf hrw-reset-timer-left {
      type string;
      units "millisecond";
      description
        "Milliseconds left on HRW reset timer";
    }
    leaf service-carving-mode {
      type ncs_template_L2vpn-evpn-sc-mode;
      description
        "Service carving mode";
    }
    leaf service-carving-synchronization-mode {
      type ncs_template_L2vpn-evpn-sc-synchronization-mode;
      description
        "Service carving synchronization mode";
    }
    leaf service-carving-mcast-mode {
      type ncs_template_L2vpn-evpn-sc-mcast-mode;
      description
        "Service carving multicast mode";
    }
    leaf primary-services-input {
      type string;
      description
        "Input string of Primary services ESI/I-SIDs";
    }
    leaf secondary-services-input {
      type string;
      description
        "Input string of Secondary services ESI/I-SIDs";
    }
    leaf preferential-df-configured-weight {
      type string;
      description
        "Configured Weight for Preferential DF Election";
    }
    leaf preferential-df-operational-weight {
      type string;
      description
        "Operational Weight for Preferential DF Election";
    }
    leaf access-driven-df-election {
      type string;
      description
        "Access Driven DF Election is active";
    }
    leaf forwarder-ports {
      type string;
      description
        "Count of Forwarders (AC, AC PW, VFI PW)";
    }
    leaf permanent-forwarder-ports {
      type string;
      description
        "Count of Forwarders with permanent service";
    }
    leaf elected-forwarder-ports {
      type string;
      description
        "Count of Forwarders with elected service";
    }
    leaf not-elected-forwarder-ports {
      type string;
      description
        "Count of Forwarders with not elected service";
    }
    leaf not-config-forwarder-ports {
      type string;
      description
        "Count of forwarders with missing config detected";
    }
    leaf mp-protected {
      type string;
      description
        "MP is protected and not under EVPN control";
    }
    leaf nve-anycast-vtep {
      type string;
      description
        "Anycast VTEP mode on NVE main-interface";
    }
    leaf nve-ingress-replication {
      type string;
      description
        "Ingress-Replication is configured on NVE
         main-interface";
    }
    leaf msti-flush-debounce {
      type string;
      description
        "Value of scale-dependant debouncing";
    }
    leaf tracked-bgp-nexthop {
      type string;
      description
        "Reachability-tracked BGP Nexthop";
    }
    leaf local-split-horizon-group-label-valid {
      type string;
      description
        "Local split horizon group label is valid";
    }
    leaf local-split-horizon-group-label {
      type string;
      description
        "Local split horizon group label";
    }
    leaf access-signal-mode {
      type ncs_template_L2vpn-evpn-es-access-signal-mode;
      description
        "Operational access signal mode";
    }
    list ethernet-segment-identifier {
      // NCS patched for predictable order
      ordered-by user;
      description
        "Ethernet Segment id";
      leaf entry {
        type string;
        description
          "Ethernet Segment id";
      }
    }
    list primary-service {
      // NCS patched for predictable order
      ordered-by user;
      description
        "List of Primary services ESI/I-SIDs";
      leaf entry {
        type string;
        description
          "List of Primary services ESI/I-SIDs";
      }
    }
    list secondary-service {
      // NCS patched for predictable order
      ordered-by user;
      description
        "List of Secondary services ESI/I-SIDs";
      leaf entry {
        type string;
        description
          "List of Secondary services ESI/I-SIDs";
      }
    }
    list service-carving-i-sidelected-result {
      // NCS patched for predictable order
      ordered-by user;
      description
        "Elected ISID service carving results";
      leaf entry {
        type string;
        description
          "Elected ISID service carving results";
      }
    }
    list service-carving-isid-not-elected-result {
      // NCS patched for predictable order
      ordered-by user;
      description
        "Not elected ISID service carving results";
      leaf entry {
        type string;
        description
          "Not elected ISID service carving results";
      }
    }
    list service-carving-evi-elected-result {
      // NCS patched for predictable order
      ordered-by user;
      description
        "Elected EVI service carving results";
      leaf entry {
        type string;
        description
          "Elected EVI service carving results";
      }
    }
    list service-carving-evi-not-elected-result {
      // NCS patched for predictable order
      ordered-by user;
      description
        "Not elected EVI service carving results";
      leaf entry {
        type string;
        description
          "Not elected EVI service carving results";
      }
    }
    list service-carving-vni-elected-result {
      // NCS patched for predictable order
      ordered-by user;
      description
        "Elected VNI service carving results";
      leaf entry {
        type string;
        description
          "Elected VNI service carving results";
      }
    }
    list service-carving-vni-not-elected-result {
      // NCS patched for predictable order
      ordered-by user;
      description
        "Not elected VNI service carving results";
      leaf entry {
        type string;
        description
          "Not elected VNI service carving results";
      }
    }
    list next-hop {
      // NCS patched for predictable order
      ordered-by user;
      description
        "List of nexthop IPv6 addresses";
      uses ncs_template_L2VPN-EVPN-ES-NH-BUFFER;
    }
    list service-carving-evpn-vpws-primary-result {
      // NCS patched for predictable order
      ordered-by user;
      description
        "EVPN VPWS service carving primary results";
      uses ncs_template_L2VPN-EVPN-EAD-SERVICE-INFO;
    }
    list service-carving-evpn-vpws-backup-result {
      // NCS patched for predictable order
      ordered-by user;
      description
        "EVPN VPWS service carving backup results";
      uses ncs_template_L2VPN-EVPN-EAD-SERVICE-INFO;
    }
    list service-carving-evpn-vpws-ndf-result {
      // NCS patched for predictable order
      ordered-by user;
      description
        "EVPN VPWS service carving non-DF results";
      uses ncs_template_L2VPN-EVPN-EAD-SERVICE-INFO;
    }
    list remote-split-horizon-group-label {
      // NCS patched for predictable order
      ordered-by user;
      description
        "Remote split horizon group labels";
      uses ncs_template_L2VPN-EVPN-REMOTE-SHG-INFO;
    }
  }

  grouping ncs_template_EVPN-SRV6-LOCATOR-INFO {
    description
      "EVPN SRv6 Locator information";
    leaf locator-name {
      type string;
      description
        "SRv6 Locator name";
    }
    leaf locator-prefix {
      type string;
      description
        "SRv6 Locator prefix";
    }
    leaf locator-length {
      type string;
      description
        "SRv6 Locator length";
    }
    leaf oor-state {
      type string;
      description
        "Out of Resources state";
    }
    leaf in-use {
      type string;
      description
        "In use by services";
    }
    leaf service-count {
      type string;
      description
        "Number of services using this locator implicitly
         and explicitly";
    }
    leaf sid-count {
      type string;
      description
        "Number of SIDs allocated by services for this
         locator";
    }
    leaf is-default {
      type string;
      description
        "Configured default locator";
    }
    list evi {
      // NCS patched for predictable order
      ordered-by user;
      description
        "List of EVIs with this locator explicitly

         configured";
      leaf entry {
        type string;
        description
          "List of EVIs with this locator explicitly

           configured";
      }
    }
    list pw {
      // NCS patched for predictable order
      ordered-by user;
      description
        "List of VPWS services with this locator
         explicitly configured";
      uses ncs_template_EVPN-SRV6-VPWS-KEY;
    }
  }

  grouping ncs_template_EVPN-SRV6-VPWS-KEY {
    description
      "EVPN SRv6 VPWS service key";
    leaf evi {
      type string;
      description
        "EVI for the VPWS service";
    }
    leaf acid {
      type string;
      description
        "Attachment circuit ID for the VPWS service";
    }
  }

  grouping ncs_template_L2VPN-EVPN-SRV6 {
    description
      "EVPN SRv6 info object";
    leaf enabled {
      type string;
      description
        "SRv6 Enabled";
    }
    leaf configured-default-locator {
      type string;
      description
        "Configured default SRv6 locator";
    }
    list unknown-locator-evi {
      // NCS patched for predictable order
      ordered-by user;
      description
        "List of EVIs with unknown locator names

         configured";
      leaf entry {
        type string;
        description
          "List of EVIs with unknown locator names

           configured";
      }
    }
    list unknown-locator-vpws {
      // NCS patched for predictable order
      ordered-by user;
      description
        "List of VPWS services with unknown locator names
         configured";
      uses ncs_template_EVPN-SRV6-VPWS-KEY;
    }
    list locator {
      // NCS patched for predictable order
      ordered-by user;
      description
        "List of locators from L3RIB";
      uses ncs_template_EVPN-SRV6-LOCATOR-INFO;
    }
  }

  grouping ncs_template_L2VPN-EVPN-LABEL {
    description
      "EVPN Internal Label database information";
    container evpn-instance {
      description
        "EVPN Instance summary information";
      uses ncs_template_L2VPN-EVPN-EVI-SUMMARY;
    }
    leaf esi {
      type string;
      description
        "Ethernet Segment id";
    }
    leaf tag {
      type string;
      description
        "Label Tag";
    }
    leaf internal-label {
      type string;
      description
        "MPLS Internal Label";
    }
    leaf alternate-internal-label {
      type string;
      description
        "Alternate MPLS Internal Label";
    }
    leaf internal-id {
      type string;
      description
        "SRv6 Internal ID";
    }
    leaf resolved {
      type string;
      description
        "Internal Label has resolved per-ES EAD and
         per-EVI EAD or MAC routes";
    }
    leaf unresolved-reason {
      type ncs_template_Evpn-bag-label-unresolved-reason;
      description
        "Optional reason why the label entry has not been
         resolved";
    }
    leaf preferred-nh-mode {
      type ncs_template_Evpn-pref-ecmp-nh-mode;
      description
        "Preferred ECMP Nexthop Mode";
    }
    leaf redundancy-single-active {
      type string;
      description
        "Single-active redundancy configured at remote ES";
    }
    leaf redundancy-single-flow-active {
      type string;
      description
        "Single-flow-active redundancy at remote ES
         (MST-AG)";
    }
    list mac-path-buffer {
      // NCS patched for predictable order
      ordered-by user;
      description
        "MAC Path list buffer";
      uses ncs_template_L2VPN-LABEL-PATH-BUFFER;
    }
    list ead-path-buffer {
      // NCS patched for predictable order
      ordered-by user;
      description
        "EAD/ES Path list buffer";
      uses ncs_template_L2VPN-LABEL-PATH-BUFFER;
    }
    list evi-path-buffer {
      // NCS patched for predictable order
      ordered-by user;
      description
        "EAD/EVI Path list buffer";
      uses ncs_template_L2VPN-LABEL-PATH-BUFFER;
    }
    list union-path-buffer {
      // NCS patched for predictable order
      ordered-by user;
      description
        "Union Path list buffer";
      uses ncs_template_L2VPN-LABEL-PATH-BUFFER;
    }
    list summary-path-buffer {
      // NCS patched for predictable order
      ordered-by user;
      description
        "Summary Path list buffer";
      uses ncs_template_L2VPN-LABEL-PATH-BUFFER;
    }
    list alternate-summary-path-buffer {
      // NCS patched for predictable order
      ordered-by user;
      description
        "Alternate Summary Path list buffer";
      uses ncs_template_L2VPN-LABEL-PATH-BUFFER;
    }
  }

  grouping ncs_template_L2VPN-EVPN-TEP-INFO {
    description
      "L2VPN EVPN TEP INFO";
    leaf ethernet-vpn-id {
      type string;
      description
        "Ethernet VPN id";
    }
    leaf encapsulation {
      type string;
      description
        "EVPN Tunnel encapsulation";
    }
    leaf ip {
      type string;
      description
        "IP address (v6 format)";
    }
  }

  grouping ncs_template_L2VPN-EVPN-TEP {
    description
      "EVPN Tunnel Endpoint database information";
    container local-info {
      description
        "Local TEP Information";
      uses ncs_template_L2VPN-EVPN-TEP-INFO;
    }
    container remote-info {
      description
        "Remote TEP Information";
      uses ncs_template_L2VPN-EVPN-TEP-INFO;
    }
    leaf tunnel-endpoint-id {
      type string;
      description
        "Tunnel Endpoint id";
    }
    leaf type {
      type string;
      description
        "EVPN Tunnel Endpoint Type";
    }
    leaf use-count {
      type string;
      description
        "in-use counter";
    }
    leaf vrf-name {
      type string;
      description
        "VRF Name";
    }
    leaf vrf-table-id {
      type string;
      description
        "VRF Table Id in RIB";
    }
    leaf udp-port {
      type string;
      description
        "UDP port";
    }
  }

  grouping ncs_template_L2VPN-EVPN-TEP-NOTIFICATION-ENTRY {
    description
      "EVPN Tunnel Endpoint notification entry
       information";
    leaf entry-name {
      type string;
      description
        "Entry Name";
    }
  }

  grouping ncs_template_L2VPN-EVPN-MAC {
    description
      "L2VPN EVPN MAC database information";
    container evpn-instance {
      description
        "EVPN Instance summary information";
      uses ncs_template_L2VPN-EVPN-EVI-SUMMARY;
    }
    leaf ethernet-tag-xr {
      type string;
      description
        "Ethernet Tag";
    }
    leaf mac-address-xr {
      type string;
      description
        "MAC address";
    }
    leaf ip-address-xr {
      type string;
      description
        "IP address (v6 format)";
    }
    leaf local-label {
      type string;
      description
        "Associated local label";
    }
    leaf is-local-mac {
      type string;
      description
        "Indication of MAC being locally generated";
    }
    leaf is-proxy-entry {
      type string;
      description
        "Proxy entry";
    }
    leaf is-remote-mac {
      type string;
      description
        "Indication of MAC being remotely generated";
    }
    leaf soo-nexthop {
      type string;
      description
        "SOO nexthop (v6 format)";
    }
    leaf ipnh-address {
      type string;
      description
        "IP nexthop address (v6 format)";
    }
    leaf esi-port-key {
      type string;
      description
        "ESI port key";
    }
    leaf local-encap-type {
      type string;
      description
        "Encap type of local MAC";
    }
    leaf remote-encap-type {
      type string;
      description
        "Encap type of remote MAC";
    }
    leaf learned-bridge-port-name {
      type string;
      description
        "Port the MAC was learned on";
    }
    leaf local-seq-id {
      type string;
      description
        "local seq id";
    }
    leaf remote-seq-id {
      type string;
      description
        "remote seq id";
    }
    leaf local-l3-label {
      type string;
      description
        "local l3 label";
    }
    leaf router-mac-address {
      type string;
      description
        "Router MAC address";
    }
    leaf mac-flush-requested {
      type string;
      description
        "Number of flushes requested ";
    }
    leaf mac-flush-received {
      type string;
      description
        "Number of flushes received ";
    }
    leaf internal-label {
      type string;
      description
        "MPLS Internal Label";
    }
    leaf resolved {
      type string;
      description
        "Internal Label has resolved per-ES EAD and
         per-EVI EAD or MAC routes";
    }
    leaf local-is-static {
      type string;
      description
        "Indication if Local MAC is statically configured";
    }
    leaf remote-is-static {
      type string;
      description
        "Indication if Remote MAC is statically
         configured";
    }
    leaf local-etree-leaf {
      type string;
      description
        "Local E-Tree Leaf Indication";
    }
    leaf remote-etree-leaf {
      type string;
      description
        "Remote E-Tree Leaf Indication";
    }
    leaf remote-etree-rt-leaf {
      type string;
      description
        "Remote MAC matching E-Tree Route-Target Leaf";
    }
    leaf local-attachment-circuit-id {
      type string;
      description
        "Local Attachement Circuit ID used in
         ac-aware-vlan-bundling";
    }
    leaf remote-attachment-circuit-id {
      type string;
      description
        "Remote Attachement Circuit ID used in
         ac-aware-vlan-bundling";
    }
    list local-ethernet-segment-identifier {
      // NCS patched for predictable order
      ordered-by user;
      description
        "Local Ethernet Segment id";
      leaf entry {
        type string;
        description
          "Local Ethernet Segment id";
      }
    }
    list remote-ethernet-segment-identifier {
      // NCS patched for predictable order
      ordered-by user;
      description
        "Remote Ethernet Segment id";
      leaf entry {
        type string;
        description
          "Remote Ethernet Segment id";
      }
    }
    list path-buffer {
      // NCS patched for predictable order
      ordered-by user;
      description
        "Path List Buffer";
      uses ncs_template_L2VPN-LABEL-PATH-BUFFER;
    }
  }

  grouping ncs_template_L2VPN-EVPN-EVI-BGP-RT {
    description
      "EVPN Instance Route Target information";
    container evpn-instance {
      description
        "EVPN Instance summary information";
      uses ncs_template_L2VPN-EVPN-EVI-SUMMARY;
    }
    container route-target {
      description
        "Route Target";
      uses ncs_template_L2VPN-RT;
    }
    leaf route-target-role {
      type ncs_template_L2vpn-ad-rt-role;
      description
        "RT Role";
    }
    leaf route-target-stitching {
      type string;
      description
        "RT Stitching";
    }
  }

  grouping ncs_template_L2VPN-EVPN-IMCAST {
    description
      "L2VPN EVPN Inclusive Multicast database
       information";
    container evpn-instance {
      description
        "EVPN Instance summary information";
      uses ncs_template_L2VPN-EVPN-EVI-SUMMARY;
    }
    container sr-te-info {
      description
        "SR(v6)-TE Policy info from ODN";
      uses ncs_template_L2VPN-EVPN-SRTE-INFO;
    }
    leaf ethernet-tag-xr {
      type string;
      description
        "Ethernet Tag";
    }
    leaf originating-ip-xr {
      type string;
      description
        "Originating IP";
    }
    leaf tunnel-endpoint-id {
      type string;
      description
        "Tunnel Endpoint ID";
    }
    leaf pmsi-tunnel-type {
      type string;
      description
        "PMSI Tunnel Type";
    }
    leaf next-hop {
      type string;
      description
        "IP of nexthop";
    }
    leaf output-label {
      type string;
      description
        "Output label";
    }
    leaf is-local-entry {
      type string;
      description
        "Local entry";
    }
    leaf is-proxy-entry {
      type string;
      description
        "Proxy entry";
    }
    leaf etree-leaf {
      type string;
      description
        "E-Tree Leaf Indication";
    }
  }

  grouping ncs_template_L2VPN-EVPN-L2-ATTRS {
    description
      "L2VPN EVPN L2 ATTRS";
    leaf mtu {
      type string;
      description
        "Maximum Transmission Unit";
    }
    leaf designated-forwarder-role {
      type ncs_template_Evpn-bag-df-role;
      description
        "Designated Forwarder Role";
    }
    leaf control-word {
      type ncs_template_Evpn-bag-l2-attr-cw;
      description
        "Control Word";
    }
  }

  grouping ncs_template_L2VPN-EVPN-SRTE-INFO {
    description
      "L2VPN EVPN SRTE INFO";
    leaf sr-te-type {
      type string;
      description
        "Type of SR-TE Policy path from ODN";
    }
    leaf sr-te-interface-name {
      type xr:ncs_template_Interface-name;
      description
        "SR Traffic Engineering Interface Name";
    }
    leaf sr-te-bsid {
      type string;
      description
        "SR Traffic Engineering Binding-SID (Label)";
    }
    leaf srv6-te-bsid {
      type string;
      description
        "SRv6 Traffic Engineering Binding-SID";
    }
  }

  grouping ncs_template_L2VPN-LABEL-PATH-BUFFER {
    description
      "L2VPN LABEL PATH BUFFER";
    container sr-te-info {
      description
        "SR(v6)-TE Policy info from ODN";
      uses ncs_template_L2VPN-EVPN-SRTE-INFO;
    }
    container layer2-attributes {
      description
        "Layer 2 Attributes";
      uses ncs_template_L2VPN-EVPN-L2-ATTRS;
    }
    leaf tunnel-endpoint-id {
      type string;
      description
        "Tunnel Endpoint Identifier";
    }
    leaf next-hop {
      type string;
      description
        "Next-hop IP address (v6 format)";
    }
    leaf output-label {
      type string;
      description
        "Output Label";
    }
    leaf reroute-label {
      type string;
      description
        "Reroute Label";
    }
    list issue {
      // NCS patched for predictable order
      ordered-by user;
      description
        "Issues with this path item";
      leaf entry {
        type ncs_template_Evpn-bag-path-issues;
        description
          "Issues with this path item";
      }
    }
    list srv6-sid-info {
      // NCS patched for predictable order
      ordered-by user;
      description
        "Array of SRv6 SID information";
      uses ncs_template_L2VPN-EVPN-SRV6-SID-INFO;
    }
  }

  grouping ncs_template_L2VPN-EVPN-SRV6-SID-INFO {
    description
      "SRv6 SID information for EVPN services";
    leaf srv6-sid {
      type string;
      description
        "SRv6 SID";
    }
  }

  grouping ncs_template_L2VPN-EVPN-EAD {
    description
      "L2VPN EVPN EAD database information";
    container evpn-instance {
      description
        "EVPN Instance summary information";
      uses ncs_template_L2VPN-EVPN-EVI-SUMMARY;
    }
    container layer2-attributes {
      description
        "Layer 2 Attributes";
      uses ncs_template_L2VPN-EVPN-L2-ATTRS;
    }
    leaf ethernet-tag-xr {
      type string;
      description
        "Ethernet Tag";
    }
    leaf local-next-hop {
      type string;
      description
        "Local nexthop IP";
    }
    leaf local-label {
      type string;
      description
        "Associated local label";
    }
    leaf is-local-ead {
      type string;
      description
        "Indication of EthernetAutoDiscovery Route is
         local";
    }
    leaf redundancy-single-active {
      type string;
      description
        "Single-active redundancy configured at remote
         EAD";
    }
    leaf redundancy-single-flow-active {
      type string;
      description
        "Single-flow-active redundancy configured at
         remote EAD";
    }
    list ethernet-segment-identifier {
      // NCS patched for predictable order
      ordered-by user;
      description
        "Ethernet Segment id";
      leaf entry {
        type string;
        description
          "Ethernet Segment id";
      }
    }
    list local-sid-array {
      // NCS patched for predictable order
      ordered-by user;
      description
        "Associated local SIDs";
      uses ncs_template_L2VPN-EVPN-SRV6-SID-INFO;
    }
    list path-buffer {
      // NCS patched for predictable order
      ordered-by user;
      description
        "Path List Buffer";
      uses ncs_template_L2VPN-LABEL-PATH-BUFFER;
    }
  }

  grouping ncs_template_L2VPN-EVPN-NEIGHBOR {
    description
      "L2VPN EVPN Neighbor database information";
    container evpn-instance {
      description
        "EVPN Instance summary information";
      uses ncs_template_L2VPN-EVPN-EVI-SUMMARY;
    }
    leaf neighbor {
      type string;
      description
        "Neighbor IP";
    }
    list leaf-evis {
      // NCS patched for predictable order
      ordered-by user;
      description
        "Leaf EVIs";
      leaf entry {
        type string;
        description
          "Leaf EVIs";
      }
    }
  }

  grouping ncs_template_L2VPN-RT-ES-IMPORT {
    description
      "L2VPN RT ES IMPORT";
    leaf high-bytes {
      type string;
      description
        "Top 4 bytes of ES Import";
    }
    leaf low-bytes {
      type string;
      description
        "Low 2 bytes of ES Import";
    }
  }

  grouping ncs_template_L2VPN-RT-V4ADDR {
    description
      "L2VPN RT V4ADDR";
    leaf ipv4-address {
      type string;
      description
        "IPv4 Address";
    }
    leaf two-byte-index {
      type string;
      description
        "2 Byte Index";
    }
  }

  grouping ncs_template_L2VPN-RT-4BYTE-AS {
    description
      "L2VPN RT 4BYTE AS";
    leaf four-byte-as {
      type string;
      description
        "4 Byte AS Number";
    }
    leaf two-byte-index {
      type string;
      description
        "2 Byte Index";
    }
  }

  grouping ncs_template_L2VPN-RT-2BYTE-AS {
    description
      "L2VPN RT 2BYTE AS";
    leaf two-byte-as {
      type string;
      description
        "2 Byte AS Number";
    }
    leaf four-byte-index {
      type string;
      description
        "4 Byte Index";
    }
  }

  grouping ncs_template_L2VPN-RT {
    description
      "L2VPN RT";
    container two-byte-as {
      // NCS drop when statement
      description
        "two byte as";
      uses ncs_template_L2VPN-RT-2BYTE-AS;
    }
    container four-byte-as {
      // NCS drop when statement
      description
        "four byte as";
      uses ncs_template_L2VPN-RT-4BYTE-AS;
    }
    container v4-addr {
      // NCS drop when statement
      description
        "v4 addr";
      uses ncs_template_L2VPN-RT-V4ADDR;
    }
    container es-import {
      // NCS drop when statement
      description
        "es import";
      uses ncs_template_L2VPN-RT-ES-IMPORT;
    }
    leaf rt {
      type ncs_template_L2vpn-ad-rt;
      description
        "RT";
    }
  }

  grouping ncs_template_L2VPN-RD-V4ADDR {
    description
      "L2VPN RD V4ADDR";
    leaf ipv4-address {
      type string;
      description
        "IPv4 Address";
    }
    leaf two-byte-index {
      type string;
      description
        "2 Byte Index";
    }
  }

  grouping ncs_template_L2VPN-RD-4BYTE-AS {
    description
      "L2VPN RD 4BYTE AS";
    leaf four-byte-as {
      type string;
      description
        "4 Byte AS Number";
    }
    leaf two-byte-index {
      type string;
      description
        "2 Byte Index";
    }
  }

  grouping ncs_template_L2VPN-RD-2BYTE-AS {
    description
      "L2VPN RD 2BYTE AS";
    leaf two-byte-as {
      type string;
      description
        "2 Byte AS Number";
    }
    leaf four-byte-index {
      type string;
      description
        "4 Byte Index";
    }
  }

  grouping ncs_template_L2VPN-RD-AUTO {
    description
      "L2VPN RD AUTO";
    leaf router-id {
      type string;
      description
        "BGP Router ID";
    }
    leaf auto-index {
      type string;
      description
        "Auto-generated Index";
    }
  }

  grouping ncs_template_L2VPN-RD {
    description
      "L2VPN RD";
    container auto {
      // NCS drop when statement
      description
        "auto";
      uses ncs_template_L2VPN-RD-AUTO;
    }
    container two-byte-as {
      // NCS drop when statement
      description
        "two byte as";
      uses ncs_template_L2VPN-RD-2BYTE-AS;
    }
    container four-byte-as {
      // NCS drop when statement
      description
        "four byte as";
      uses ncs_template_L2VPN-RD-4BYTE-AS;
    }
    container v4-addr {
      // NCS drop when statement
      description
        "v4 addr";
      uses ncs_template_L2VPN-RD-V4ADDR;
    }
    leaf rd {
      type ncs_template_L2vpn-ad-rd;
      description
        "RD";
    }
  }

  grouping ncs_template_L2VPN-EVPN-FLOW-LABEL {
    description
      "L2VPN EVPN FLOW LABEL";
    leaf static-flow-label {
      type string;
      description
        "Static flow label";
    }
    leaf global-flow-label {
      type string;
      description
        "Globally configured flow label";
    }
  }

  grouping ncs_template_L2VPN-EVPN-EVI-DETAIL {
    description
      "EVPN E-VPN ID database detail information";
    container evpn-instance {
      description
        "EVPN Instance summary information";
      uses ncs_template_L2VPN-EVPN-EVI-SUMMARY;
    }
    container flow-label {
      description
        "Flow Label Information";
      uses ncs_template_L2VPN-EVPN-FLOW-LABEL;
    }
    container rd-auto {
      description
        "Automatic Route Distingtuisher";
      uses ncs_template_L2VPN-RD;
    }
    container rd-configured {
      description
        "Configured Route Distinguisher";
      uses ncs_template_L2VPN-RD;
    }
    container rt-auto {
      description
        "Automatic Route Target";
      uses ncs_template_L2VPN-RT;
    }
    leaf evi-xr {
      type string;
      description
        "E-VPN id";
    }
    leaf encapsulation-xr {
      type string;
      description
        "EVPN Instance encapsulation";
    }
    leaf bd-name {
      type string;
      description
        "Bridge domain name";
    }
    leaf type {
      type ncs_template_L2vpn-evpn;
      description
        "Service Type";
    }
    leaf description {
      type string;
      description
        "EVI description";
    }
    leaf unicast-label {
      type string;
      description
        "Unicast Label";
    }
    leaf multicast-label {
      type string;
      description
        "Multicast Label";
    }
    leaf reroute-label {
      type string;
      description
        "Reroute Label";
    }
    leaf cw-disable {
      type string;
      description
        "Control-Word Disable";
    }
    leaf mtu-mismatch-ignore {
      type string;
      description
        "Ignore MTU Mismatch";
    }
    leaf mtu-zero-transmit {
      type string;
      description
        "Transmit MTU Zero";
    }
    leaf table-policy-name {
      type string;
      description
        "Table-policy Name";
    }
    leaf export-route-policy {
      type string;
      description
        "Export Route Policy";
    }
    leaf import-route-policy {
      type string;
      description
        "Import Route Policy";
    }
    leaf forward-class {
      type string;
      description
        "Forward Class attribute";
    }
    leaf rt-import-block-set {
      type string;
      description
        "Is Import RT None set";
    }
    leaf rt-export-block-set {
      type string;
      description
        "Is Export RT None set";
    }
    leaf advertise-mac {
      type string;
      description
        "Advertise MAC-only routes on this EVI";
    }
    leaf etree-leaf {
      type string;
      description
        "E-Tree Leaf Indication";
    }
    leaf etree-rt-leaf {
      type string;
      description
        "E-Tree Route-Target Leaf Indication";
    }
    leaf advertise-bvi-mac {
      type string;
      description
        "Advertise BVI MACs routes on this EVI";
    }
    leaf aliasing-disabled {
      type string;
      description
        "Route Aliasing is disabled";
    }
    leaf unknown-unicast-flooding-disabled {
      type string;
      description
        "Unknown-unicast flooding is disabled";
    }
    leaf reoriginate-disabled {
      type string;
      description
        "Route Re-origination is disabled";
    }
    leaf stitching {
      type string;
      description
        "EVPN Instance is Regular/Stitching side";
    }
    leaf multicast-source-connected {
      type string;
      description
        "EVI is connected to multicast source";
    }
    leaf bgp-implicit-import-disabled {
      type string;
      description
        "BGP implicit import is disabled";
    }
    leaf vrf-name {
      type string;
      description
        "L3 VRF name from BVI";
    }
    leaf preferred-nh-mode {
      type ncs_template_Evpn-pref-ecmp-nh-mode;
      description
        "Preferred Nexthop Mode";
    }
    leaf srv6-locator-name {
      type string;
      description
        "SRv6 Locator Name";
    }
  }

  grouping ncs_template_L2VPN-EVPN-SUMMARY {
    description
      "EVPN Information Summary";
    leaf router-id {
      type string;
      description
        "EVPN Router ID";
    }
    leaf as {
      type string;
      description
        "BGP AS number";
    }
    leaf ev-is {
      type string;
      description
        "Number of EVI DB Entries";
    }
    leaf tunnel-endpoints {
      type string;
      description
        "Number of Tunnel Endpoint DB Entries";
    }
    leaf local-mac-routes {
      type string;
      description
        "Number of Local MAC Routes";
    }
    leaf local-ipv4-mac-routes {
      type string;
      description
        "Number of Local IPv4 MAC-IP Routes";
    }
    leaf local-ipv6-mac-routes {
      type string;
      description
        "Number of Local IPv6 MAC-IP Routes";
    }
    leaf es-global-mac-routes {
      type string;
      description
        "Number of ES:Global MAC Routes";
    }
    leaf remote-mac-routes {
      type string;
      description
        "Number of Remote MAC Routes";
    }
    leaf remote-sync-mac-routes {
      type string;
      description
        "Number of Remote SYNC MAC Routes";
    }
    leaf remote-ipv4-mac-routes {
      type string;
      description
        "Number of Remote IPv4 MAC-IP Routes";
    }
    leaf remote-ipv6-mac-routes {
      type string;
      description
        "Number of Remote IPv6 MAC-IP Routes";
    }
    leaf local-imcast-routes {
      type string;
      description
        "Number of Local IMCAST Routes";
    }
    leaf remote-imcast-routes {
      type string;
      description
        "Number of Remote IMCAST Routes";
    }
    leaf labels {
      type string;
      description
        "Number of Internal Labels";
    }
    leaf sh-internal-ids {
      type string;
      description
        "Number of single-homed Internal IDs";
    }
    leaf mh-internal-ids {
      type string;
      description
        "Number of multi-homed Internal IDs";
    }
    leaf es-entries {
      type string;
      description
        "Number of ES Entries in DB";
    }
    leaf neighbor-entries {
      type string;
      description
        "Number of neighbor Entries in DB";
    }
    leaf local-ead-routes {
      type string;
      description
        "Number of Local EAD Entries in DB";
    }
    leaf remote-ead-routes {
      type string;
      description
        "Number of Remote EAD Entries in DB";
    }
    leaf global-source-mac {
      type string;
      description
        "Global Source MAC Address";
    }
    leaf peering-time {
      type string;
      units "second";
      description
        "EVPN ES Peering Time (seconds)";
    }
    leaf recovery-time {
      type string;
      units "second";
      description
        "EVPN ES Recovery Time (seconds)";
    }
    leaf carving-time {
      type string;
      units "second";
      description
        "EVPN ES Carving Time (seconds)";
    }
    leaf cost-out-configured {
      type string;
      description
        "EVPN node cost out via manual configuration";
    }
    leaf bundle-convergence-in-progress {
      type string;
      description
        "Bundle convergence in progress";
    }
    leaf node-costed-out {
      type string;
      description
        "EVPN Services costed out on node and holding
         Bundle interfaces down";
    }
    leaf startup-cost-in-time {
      type string;
      units "second";
      description
        "EVPN Node startup cost-in Time (seconds)";
    }
    leaf startup-cost-in-time-left {
      type string;
      units "millisecond";
      description
        "Milliseconds left on EVPN Node startup cost-in";
    }
    leaf mac-postpone-timer {
      type string;
      units "second";
      description
        "Configured timer for postponing MAC withdraws
         (seconds)";
    }
    leaf mac-postpone-timer-left {
      type string;
      units "millisecond";
      description
        "Milliseconds left on MAC withdraw postpone timer";
    }
    leaf l2rib-throttle {
      type string;
      description
        "Send to L2RIB Throttled";
    }
    leaf logging-df-election-enabled {
      type string;
      description
        "Logging EVPN Designated Forwarder changes
         enabled";
    }
  }

  grouping ncs_template_L2VPN-EVPN-EVI-SUMMARY {
    description
      "EVPN Instance summary information";
    leaf ethernet-vpn-id {
      type string;
      description
        "Ethernet VPN id";
    }
    leaf encapsulation-xr {
      type string;
      description
        "EVPN Instance transport encapsulation";
    }
    leaf bd-name {
      type string;
      description
        "Bridge domain name";
    }
    leaf type {
      type ncs_template_L2vpn-evpn;
      description
        "Service Type";
    }
  }

  grouping ncs_template_L2VPN-EVPN-IGMP-SUBIF-INFO {
    description
      "L2VPN EVPN IGMP SUBIF INFO";
    leaf vrf-id {
      type string;
      description
        "VRF id";
    }
  }

  grouping ncs_template_L2VPN-EVPN-IGMP-FWD-INFO {
    description
      "L2VPN EVPN IGMP FWD INFO";
    leaf bd-id {
      type string;
      description
        "BD id";
    }
  }

  grouping ncs_template_EVPN-IGMP-CHILD-INFO {
    description
      "EVPN IGMP CHILD INFO";
    container fwd-info {
      // NCS drop when statement
      description
        "fwd info";
      uses ncs_template_L2VPN-EVPN-IGMP-FWD-INFO;
    }
    container subif-info {
      // NCS drop when statement
      description
        "subif info";
      uses ncs_template_L2VPN-EVPN-IGMP-SUBIF-INFO;
    }
    leaf child-type {
      type ncs_template_Evpn-child;
      description
        "ChildType";
    }
  }

  grouping ncs_template_L2VPN-EVPN-IGMP-LOCAL-INFO {
    description
      "L2VPN EVPN IGMP LOCAL INFO";
    leaf if-name {
      type string;
      description
        "Interface name internal format";
    }
  }

  grouping ncs_template_EVPN-IGMP-SRC-INFO {
    description
      "EVPN IGMP SRC INFO";
    container local-info {
      // NCS drop when statement
      description
        "local info";
      uses ncs_template_L2VPN-EVPN-IGMP-LOCAL-INFO;
    }
    leaf type {
      type ncs_template_Evpn-igmp-source;
      description
        "Type";
    }
    leaf remote-info {
      // NCS drop when statement
      type ncs_template_L2vpn-bag-in6-addr;
      description
        "remote info";
    }
  }

  grouping ncs_template_L2VPN-EVPN-IGMP {
    description
      "EVPN IGMP database information";
    container source-info {
      description
        "Source Info";
      uses ncs_template_EVPN-IGMP-SRC-INFO;
    }
    container child-info {
      description
        "Child Info";
      uses ncs_template_EVPN-IGMP-CHILD-INFO;
    }
    leaf evpn-client-type {
      type ncs_template_Evpn-client1;
      description
        "EVPN Client Type";
    }
    leaf ethernet-segment-name {
      type string;
      description
        "Ethernet Segment Name";
    }
    leaf evi-xr {
      type string;
      description
        "E-VPN id";
    }
    leaf route-type {
      type ncs_template_Evpn-igmp-msg;
      description
        "Route Type";
    }
    leaf source-addr {
      type string;
      description
        "Source IP Address";
    }
    leaf group-addr {
      type string;
      description
        "Group IP Address";
    }
    leaf ethernet-tag-id {
      type string;
      description
        "Ethernet Tag id";
    }
    leaf igmp-version {
      type ncs_template_Evpn-igmp-version;
      description
        "IGMP Version";
    }
    leaf igmp-group-type {
      type ncs_template_Evpn-igmp-grp;
      description
        "IGMP Group Type";
    }
    leaf max-response-time {
      type string;
      description
        "Max Response Time";
    }
    leaf resolved {
      type string;
      description
        "Resolved";
    }
    list ethernet-segment-identifier {
      // NCS patched for predictable order
      ordered-by user;
      description
        "Ethernet Segment id";
      leaf entry {
        type string;
        description
          "Ethernet Segment id";
      }
    }
  }

  grouping ncs_template_L2VPN-EVPN-CLIENT {
    description
      "EVPN Client Information";
    leaf client-type {
      type ncs_template_Evpn-client1;
      description
        "Client Type";
    }
  }

  grouping ncs_template_L2VPN-EVPN-REMOTE-SHG-INFO {
    description
      "L2VPN EVPN remote split horizon group labels";
    leaf next-hop {
      type string;
      description
        "Next-hop IP address (v6 format)";
    }
    leaf label {
      type string;
      description
        "Split horizon label associated with next-hop
         address";
    }
  }

  grouping ncs_template_L2VPN-EVPN-REMOTE-SHG {
    description
      "EVPN Remote SHG object";
    leaf ethernet-vpn-id {
      type string;
      description
        "Ethernet VPN id";
    }
    leaf encapsulation {
      type string;
      description
        "EVPN Instance transport encapsulation";
    }
    list ethernet-segment-identifier {
      // NCS patched for predictable order
      ordered-by user;
      description
        "Ethernet Segment id";
      leaf entry {
        type string;
        description
          "Ethernet Segment id";
      }
    }
    list remote-split-horizon-group-label {
      // NCS patched for predictable order
      ordered-by user;
      description
        "Remote split horizon group labels";
      uses ncs_template_L2VPN-EVPN-REMOTE-SHG-INFO;
    }
  }

  grouping ncs_template_EVPN-GRP-INTF-INFO {
    description
      "EVPN Group Interface Information";
    leaf interface-name {
      type string;
      description
        "Interface name";
    }
    leaf state {
      type ncs_template_Im-state-enum;
      description
        "Interface State";
    }
  }

  grouping ncs_template_EVPN-GRP-INFO {
    description
      "EVPN Group Information";
    leaf group-id {
      type string;
      description
        "EVPN Group ID";
    }
    leaf state {
      type ncs_template_Evpn-grp;
      description
        "EVPN Group State";
    }
    list core-interface {
      // NCS patched for predictable order
      ordered-by user;
      description
        "EVPN Group Core Interface table";
      uses ncs_template_EVPN-GRP-INTF-INFO;
    }
    list access-interface {
      // NCS patched for predictable order
      ordered-by user;
      description
        "EVPN Access Core Interface table";
      uses ncs_template_EVPN-GRP-INTF-INFO;
    }
  }

  grouping ncs_rpc_notif_L2VPN-ATOM-ACID {
    description
      "L2VPN ATOM ACID";
    leaf source-ac-id {
      type uint32;
      description
        "Source AC ID";
    }
    leaf target-ac-id {
      type uint32;
      description
        "Target AC ID";
    }
    leaf vpn-id {
      type uint32;
      description
        "VPN ID";
    }
    leaf taii-global-id {
      type uint32;
      description
        "TAII Global ID";
    }
    leaf taii-ac-id {
      type uint32;
      description
        "TAII AC ID";
    }
    leaf taii-prefix {
      type inet:ipv6-address;
      description
        "TAII Prefix";
    }
  }

  grouping ncs_rpc_notif_L2VPN-EVPN-EAD-SERVICE-INFO {
    description
      "L2VPN EVPN EAD Ethernet Tag";
    leaf vpn-id {
      type uint32;
      description
        "VPN ID";
    }
    leaf type {
      type ncs_rpc_notif_L2vpn-evpn;
      description
        "Service Type";
    }
    leaf ethernet-tag {
      type uint32;
      description
        "Ethernet Tag";
    }
  }

  grouping ncs_rpc_notif_L2VPN-BAG-TIMESPEC {
    description
      "L2VPN Timespec Data Structure";
    leaf tv-sec {
      type uint32;
      description
        "tv sec";
    }
    leaf tv-nsec {
      type uint32;
      description
        "tv nsec";
    }
  }

  grouping ncs_rpc_notif_L2VPN-STAT-ITEM {
    description
      "L2VPN EVPN Ethernet Segment (ES) private stats
       item";
    container last-time {
      description
        "last time";
      uses ncs_rpc_notif_L2VPN-BAG-TIMESPEC;
    }
    leaf count {
      type uint32;
      description
        "count";
    }
    leaf last-arg {
      type uint32;
      description
        "last arg";
    }
  }

  grouping ncs_rpc_notif_L2VPN-EVPN-ES-NH-BUFFER {
    description
      "L2VPN EVPN Ethernet Segment (ES) nexthops
       information";
    leaf next-hop {
      type inet:ipv6-address;
      description
        "Next-hop IP address (v6 format)";
    }
    leaf df-dont-preempt {
      type boolean;
      description
        "DF Dont Preemption";
    }
    leaf df-type {
      type uint8;
      description
        "DF Election Mode Configured";
    }
    leaf df-pref {
      type uint16;
      description
        "DF Election Preference Set";
    }
    leaf df-ntp-enabled {
      type boolean;
      description
        "NTP based DF Election Synchronization";
    }
    leaf ntp-sct-microseconds {
      type uint64;
      units "microsecond";
      description
        "NTP based SCT: represented in microseconds
         relative to Unix epoch: 1st Jan 1970";
    }
  }

  grouping ncs_rpc_notif_L2VPN-EVPN-ES {
    description
      "EVPN Ethernet Segment (ES) database information";
    container msti-flush-count {
      description
        "Statistics for Host-mobility driven flush
         operations";
      uses ncs_rpc_notif_L2VPN-STAT-ITEM;
    }
    leaf esi-type {
      type ncs_rpc_notif_L2vpn-evpn-esi;
      description
        "ESI Type";
    }
    leaf esi-system-identifier {
      type string;
      description
        "ESI System Identifier";
    }
    leaf esi-port-key {
      type uint32;
      description
        "ESI Port Key";
    }
    leaf esi-system-priority {
      type uint32;
      description
        "ESI System Priority";
    }
    leaf ethernet-segment-name {
      type string;
      description
        "Ethernet Segment Name";
    }
    leaf ethernet-segment-state {
      type ncs_rpc_notif_L2vpn-evpn-es-state;
      description
        "State of the ethernet segment";
    }
    leaf in-staggered-bringup {
      type boolean;
      description
        "Is this ES in the staggered bring-up queue?";
    }
    leaf if-handle {
      type xr:ncs_rpc_notif_Interface-name;
      description
        "Main port ifhandle";
    }
    leaf main-port-role {
      type ncs_rpc_notif_L2vpn-rg-role;
      description
        "Main port redundancy group role";
    }
    leaf main-port-mac {
      type yang:mac-address;
      description
        "Main Port MAC Address";
    }
    leaf num-up-p-ws {
      type uint32;
      description
        "Number of PWs in Up state";
    }
    leaf route-target {
      type yang:mac-address;
      description
        "ES-Import Route Target";
    }
    leaf rt-origin {
      type ncs_rpc_notif_L2vpn-evpn-rt-origin;
      description
        "Origin of operational ES-Import RT";
    }
    leaf es-bgp-gates {
      type string;
      description
        "ES BGP Gates";
    }
    leaf es-l2fib-gates {
      type string;
      description
        "ES L2FIB Gates";
    }
    leaf mac-flushing-mode-config {
      type ncs_rpc_notif_L2vpn-evpn-mf-mode;
      description
        "Configured MAC Flushing mode";
    }
    leaf load-balance-mode-config {
      type ncs_rpc_notif_L2vpn-evpn-lb-mode;
      description
        "Configured load balancing mode";
    }
    leaf load-balance-mode-is-default {
      type boolean;
      description
        "Load balancing mode is default";
    }
    leaf load-balance-mode-oper {
      type ncs_rpc_notif_L2vpn-evpn-lb-mode;
      description
        "Operational load balancing mode";
    }
    leaf force-single-home {
      type boolean;
      description
        "Ethernet-Segment forced to single home";
    }
    leaf convergence-mac-mobility {
      type boolean;
      description
        "Fast convergence mode based on MAC-mobility.";
    }
    leaf convergence-reroute {
      type boolean;
      description
        "Fast convergence mode based on reroute to backup
         peer.";
    }
    leaf convergence-nh-tracking {
      type boolean;
      description
        "Fast DF-Election based on tracking peer BGP
         Nexthop reachability";
    }
    leaf source-mac-oper {
      type yang:mac-address;
      description
        "Operational Source MAC address";
    }
    leaf source-mac-origin {
      type ncs_rpc_notif_L2vpn-evpn-smac-src;
      description
        "Origin of operational source MAC address";
    }
    leaf peering-timer {
      type uint32;
      units "second";
      description
        "Configured timer for triggering DF election
         (seconds)";
    }
    leaf peering-timer-left {
      type uint32;
      units "millisecond";
      description
        "Milliseconds left on DF election timer";
    }
    leaf recovery-timer {
      type uint32;
      units "second";
      description
        "Configured timer for (STP) recovery (seconds)";
    }
    leaf recovery-timer-left {
      type uint32;
      units "millisecond";
      description
        "Milliseconds left on (STP) recovery timer";
    }
    leaf carving-timer {
      type uint32;
      units "second";
      description
        "Configured timer for delaying DF election
         (seconds)";
    }
    leaf carving-timer-left {
      type uint32;
      units "millisecond";
      description
        "Milliseconds left on carving timer";
    }
    leaf hrw-reset-timer {
      type uint32;
      units "second";
      description
        "Configured timer for HRW reset (seconds)";
    }
    leaf hrw-reset-timer-left {
      type uint32;
      units "millisecond";
      description
        "Milliseconds left on HRW reset timer";
    }
    leaf service-carving-mode {
      type ncs_rpc_notif_L2vpn-evpn-sc-mode;
      description
        "Service carving mode";
    }
    leaf service-carving-synchronization-mode {
      type ncs_rpc_notif_L2vpn-evpn-sc-synchronization-mode;
      description
        "Service carving synchronization mode";
    }
    leaf service-carving-mcast-mode {
      type ncs_rpc_notif_L2vpn-evpn-sc-mcast-mode;
      description
        "Service carving multicast mode";
    }
    leaf primary-services-input {
      type string;
      description
        "Input string of Primary services ESI/I-SIDs";
    }
    leaf secondary-services-input {
      type string;
      description
        "Input string of Secondary services ESI/I-SIDs";
    }
    leaf preferential-df-configured-weight {
      type uint16;
      description
        "Configured Weight for Preferential DF Election";
    }
    leaf preferential-df-operational-weight {
      type uint16;
      description
        "Operational Weight for Preferential DF Election";
    }
    leaf access-driven-df-election {
      type boolean;
      description
        "Access Driven DF Election is active";
    }
    leaf forwarder-ports {
      type uint32;
      description
        "Count of Forwarders (AC, AC PW, VFI PW)";
    }
    leaf permanent-forwarder-ports {
      type uint32;
      description
        "Count of Forwarders with permanent service";
    }
    leaf elected-forwarder-ports {
      type uint32;
      description
        "Count of Forwarders with elected service";
    }
    leaf not-elected-forwarder-ports {
      type uint32;
      description
        "Count of Forwarders with not elected service";
    }
    leaf not-config-forwarder-ports {
      type uint32;
      description
        "Count of forwarders with missing config detected";
    }
    leaf mp-protected {
      type boolean;
      description
        "MP is protected and not under EVPN control";
    }
    leaf nve-anycast-vtep {
      type boolean;
      description
        "Anycast VTEP mode on NVE main-interface";
    }
    leaf nve-ingress-replication {
      type boolean;
      description
        "Ingress-Replication is configured on NVE
         main-interface";
    }
    leaf msti-flush-debounce {
      type uint32;
      description
        "Value of scale-dependant debouncing";
    }
    leaf tracked-bgp-nexthop {
      type inet:ipv6-address;
      description
        "Reachability-tracked BGP Nexthop";
    }
    leaf local-split-horizon-group-label-valid {
      type boolean;
      description
        "Local split horizon group label is valid";
    }
    leaf local-split-horizon-group-label {
      type uint32;
      description
        "Local split horizon group label";
    }
    leaf access-signal-mode {
      type ncs_rpc_notif_L2vpn-evpn-es-access-signal-mode;
      description
        "Operational access signal mode";
    }
    list ethernet-segment-identifier {
      description
        "Ethernet Segment id";
      leaf entry {
        type uint8;
        description
          "Ethernet Segment id";
      }
    }
    list primary-service {
      description
        "List of Primary services ESI/I-SIDs";
      leaf entry {
        type uint32;
        description
          "List of Primary services ESI/I-SIDs";
      }
    }
    list secondary-service {
      description
        "List of Secondary services ESI/I-SIDs";
      leaf entry {
        type uint32;
        description
          "List of Secondary services ESI/I-SIDs";
      }
    }
    list service-carving-i-sidelected-result {
      description
        "Elected ISID service carving results";
      leaf entry {
        type uint32;
        description
          "Elected ISID service carving results";
      }
    }
    list service-carving-isid-not-elected-result {
      description
        "Not elected ISID service carving results";
      leaf entry {
        type uint32;
        description
          "Not elected ISID service carving results";
      }
    }
    list service-carving-evi-elected-result {
      description
        "Elected EVI service carving results";
      leaf entry {
        type uint32;
        description
          "Elected EVI service carving results";
      }
    }
    list service-carving-evi-not-elected-result {
      description
        "Not elected EVI service carving results";
      leaf entry {
        type uint32;
        description
          "Not elected EVI service carving results";
      }
    }
    list service-carving-vni-elected-result {
      description
        "Elected VNI service carving results";
      leaf entry {
        type uint32;
        description
          "Elected VNI service carving results";
      }
    }
    list service-carving-vni-not-elected-result {
      description
        "Not elected VNI service carving results";
      leaf entry {
        type uint32;
        description
          "Not elected VNI service carving results";
      }
    }
    list next-hop {
      description
        "List of nexthop IPv6 addresses";
      uses ncs_rpc_notif_L2VPN-EVPN-ES-NH-BUFFER;
    }
    list service-carving-evpn-vpws-primary-result {
      description
        "EVPN VPWS service carving primary results";
      uses ncs_rpc_notif_L2VPN-EVPN-EAD-SERVICE-INFO;
    }
    list service-carving-evpn-vpws-backup-result {
      description
        "EVPN VPWS service carving backup results";
      uses ncs_rpc_notif_L2VPN-EVPN-EAD-SERVICE-INFO;
    }
    list service-carving-evpn-vpws-ndf-result {
      description
        "EVPN VPWS service carving non-DF results";
      uses ncs_rpc_notif_L2VPN-EVPN-EAD-SERVICE-INFO;
    }
    list remote-split-horizon-group-label {
      description
        "Remote split horizon group labels";
      uses ncs_rpc_notif_L2VPN-EVPN-REMOTE-SHG-INFO;
    }
  }

  grouping ncs_rpc_notif_EVPN-SRV6-LOCATOR-INFO {
    description
      "EVPN SRv6 Locator information";
    leaf locator-name {
      type string;
      description
        "SRv6 Locator name";
    }
    leaf locator-prefix {
      type inet:ipv6-address;
      description
        "SRv6 Locator prefix";
    }
    leaf locator-length {
      type uint8;
      description
        "SRv6 Locator length";
    }
    leaf oor-state {
      type boolean;
      description
        "Out of Resources state";
    }
    leaf in-use {
      type boolean;
      description
        "In use by services";
    }
    leaf service-count {
      type uint32;
      description
        "Number of services using this locator implicitly
         and explicitly";
    }
    leaf sid-count {
      type uint32;
      description
        "Number of SIDs allocated by services for this
         locator";
    }
    leaf is-default {
      type boolean;
      description
        "Configured default locator";
    }
    list evi {
      description
        "List of EVIs with this locator explicitly

         configured";
      leaf entry {
        type uint32;
        description
          "List of EVIs with this locator explicitly

           configured";
      }
    }
    list pw {
      description
        "List of VPWS services with this locator
         explicitly configured";
      uses ncs_rpc_notif_EVPN-SRV6-VPWS-KEY;
    }
  }

  grouping ncs_rpc_notif_EVPN-SRV6-VPWS-KEY {
    description
      "EVPN SRv6 VPWS service key";
    leaf evi {
      type uint32;
      description
        "EVI for the VPWS service";
    }
    leaf acid {
      type uint32;
      description
        "Attachment circuit ID for the VPWS service";
    }
  }

  grouping ncs_rpc_notif_L2VPN-EVPN-SRV6 {
    description
      "EVPN SRv6 info object";
    leaf enabled {
      type boolean;
      description
        "SRv6 Enabled";
    }
    leaf configured-default-locator {
      type string;
      description
        "Configured default SRv6 locator";
    }
    list unknown-locator-evi {
      description
        "List of EVIs with unknown locator names

         configured";
      leaf entry {
        type uint32;
        description
          "List of EVIs with unknown locator names

           configured";
      }
    }
    list unknown-locator-vpws {
      description
        "List of VPWS services with unknown locator names
         configured";
      uses ncs_rpc_notif_EVPN-SRV6-VPWS-KEY;
    }
    list locator {
      description
        "List of locators from L3RIB";
      uses ncs_rpc_notif_EVPN-SRV6-LOCATOR-INFO;
    }
  }

  grouping ncs_rpc_notif_L2VPN-EVPN-LABEL {
    description
      "EVPN Internal Label database information";
    container evpn-instance {
      description
        "EVPN Instance summary information";
      uses ncs_rpc_notif_L2VPN-EVPN-EVI-SUMMARY;
    }
    leaf esi {
      type yang:hex-string;
      description
        "Ethernet Segment id";
    }
    leaf tag {
      type uint32;
      description
        "Label Tag";
    }
    leaf internal-label {
      type uint32;
      description
        "MPLS Internal Label";
    }
    leaf alternate-internal-label {
      type uint32;
      description
        "Alternate MPLS Internal Label";
    }
    leaf internal-id {
      type uint32;
      description
        "SRv6 Internal ID";
    }
    leaf resolved {
      type boolean;
      description
        "Internal Label has resolved per-ES EAD and
         per-EVI EAD or MAC routes";
    }
    leaf unresolved-reason {
      type ncs_rpc_notif_Evpn-bag-label-unresolved-reason;
      description
        "Optional reason why the label entry has not been
         resolved";
    }
    leaf preferred-nh-mode {
      type ncs_rpc_notif_Evpn-pref-ecmp-nh-mode;
      description
        "Preferred ECMP Nexthop Mode";
    }
    leaf redundancy-single-active {
      type boolean;
      description
        "Single-active redundancy configured at remote ES";
    }
    leaf redundancy-single-flow-active {
      type boolean;
      description
        "Single-flow-active redundancy at remote ES
         (MST-AG)";
    }
    list mac-path-buffer {
      description
        "MAC Path list buffer";
      uses ncs_rpc_notif_L2VPN-LABEL-PATH-BUFFER;
    }
    list ead-path-buffer {
      description
        "EAD/ES Path list buffer";
      uses ncs_rpc_notif_L2VPN-LABEL-PATH-BUFFER;
    }
    list evi-path-buffer {
      description
        "EAD/EVI Path list buffer";
      uses ncs_rpc_notif_L2VPN-LABEL-PATH-BUFFER;
    }
    list union-path-buffer {
      description
        "Union Path list buffer";
      uses ncs_rpc_notif_L2VPN-LABEL-PATH-BUFFER;
    }
    list summary-path-buffer {
      description
        "Summary Path list buffer";
      uses ncs_rpc_notif_L2VPN-LABEL-PATH-BUFFER;
    }
    list alternate-summary-path-buffer {
      description
        "Alternate Summary Path list buffer";
      uses ncs_rpc_notif_L2VPN-LABEL-PATH-BUFFER;
    }
  }

  grouping ncs_rpc_notif_L2VPN-EVPN-TEP-INFO {
    description
      "L2VPN EVPN TEP INFO";
    leaf ethernet-vpn-id {
      type uint32;
      description
        "Ethernet VPN id";
    }
    leaf encapsulation {
      type uint8;
      description
        "EVPN Tunnel encapsulation";
    }
    leaf ip {
      type inet:ipv6-address;
      description
        "IP address (v6 format)";
    }
  }

  grouping ncs_rpc_notif_L2VPN-EVPN-TEP {
    description
      "EVPN Tunnel Endpoint database information";
    container local-info {
      description
        "Local TEP Information";
      uses ncs_rpc_notif_L2VPN-EVPN-TEP-INFO;
    }
    container remote-info {
      description
        "Remote TEP Information";
      uses ncs_rpc_notif_L2VPN-EVPN-TEP-INFO;
    }
    leaf tunnel-endpoint-id {
      type uint32;
      description
        "Tunnel Endpoint id";
    }
    leaf type {
      type uint8;
      description
        "EVPN Tunnel Endpoint Type";
    }
    leaf use-count {
      type uint32;
      description
        "in-use counter";
    }
    leaf vrf-name {
      type string;
      description
        "VRF Name";
    }
    leaf vrf-table-id {
      type uint32;
      description
        "VRF Table Id in RIB";
    }
    leaf udp-port {
      type uint16;
      description
        "UDP port";
    }
  }

  grouping ncs_rpc_notif_L2VPN-EVPN-TEP-NOTIFICATION-ENTRY {
    description
      "EVPN Tunnel Endpoint notification entry
       information";
    leaf entry-name {
      type string;
      description
        "Entry Name";
    }
  }

  grouping ncs_rpc_notif_L2VPN-EVPN-MAC {
    description
      "L2VPN EVPN MAC database information";
    container evpn-instance {
      description
        "EVPN Instance summary information";
      uses ncs_rpc_notif_L2VPN-EVPN-EVI-SUMMARY;
    }
    leaf ethernet-tag-xr {
      type uint32;
      description
        "Ethernet Tag";
    }
    leaf mac-address-xr {
      type yang:mac-address;
      description
        "MAC address";
    }
    leaf ip-address-xr {
      type inet:ipv6-address;
      description
        "IP address (v6 format)";
    }
    leaf local-label {
      type uint32;
      description
        "Associated local label";
    }
    leaf is-local-mac {
      type boolean;
      description
        "Indication of MAC being locally generated";
    }
    leaf is-proxy-entry {
      type boolean;
      description
        "Proxy entry";
    }
    leaf is-remote-mac {
      type boolean;
      description
        "Indication of MAC being remotely generated";
    }
    leaf soo-nexthop {
      type inet:ipv6-address;
      description
        "SOO nexthop (v6 format)";
    }
    leaf ipnh-address {
      type inet:ipv6-address;
      description
        "IP nexthop address (v6 format)";
    }
    leaf esi-port-key {
      type uint16;
      description
        "ESI port key";
    }
    leaf local-encap-type {
      type uint8;
      description
        "Encap type of local MAC";
    }
    leaf remote-encap-type {
      type uint8;
      description
        "Encap type of remote MAC";
    }
    leaf learned-bridge-port-name {
      type string;
      description
        "Port the MAC was learned on";
    }
    leaf local-seq-id {
      type uint32;
      description
        "local seq id";
    }
    leaf remote-seq-id {
      type uint32;
      description
        "remote seq id";
    }
    leaf local-l3-label {
      type uint32;
      description
        "local l3 label";
    }
    leaf router-mac-address {
      type yang:mac-address;
      description
        "Router MAC address";
    }
    leaf mac-flush-requested {
      type uint16;
      description
        "Number of flushes requested ";
    }
    leaf mac-flush-received {
      type uint16;
      description
        "Number of flushes received ";
    }
    leaf internal-label {
      type uint32;
      description
        "MPLS Internal Label";
    }
    leaf resolved {
      type boolean;
      description
        "Internal Label has resolved per-ES EAD and
         per-EVI EAD or MAC routes";
    }
    leaf local-is-static {
      type boolean;
      description
        "Indication if Local MAC is statically configured";
    }
    leaf remote-is-static {
      type boolean;
      description
        "Indication if Remote MAC is statically
         configured";
    }
    leaf local-etree-leaf {
      type boolean;
      description
        "Local E-Tree Leaf Indication";
    }
    leaf remote-etree-leaf {
      type boolean;
      description
        "Remote E-Tree Leaf Indication";
    }
    leaf remote-etree-rt-leaf {
      type boolean;
      description
        "Remote MAC matching E-Tree Route-Target Leaf";
    }
    leaf local-attachment-circuit-id {
      type uint32;
      description
        "Local Attachement Circuit ID used in
         ac-aware-vlan-bundling";
    }
    leaf remote-attachment-circuit-id {
      type uint32;
      description
        "Remote Attachement Circuit ID used in
         ac-aware-vlan-bundling";
    }
    list local-ethernet-segment-identifier {
      description
        "Local Ethernet Segment id";
      leaf entry {
        type uint8;
        description
          "Local Ethernet Segment id";
      }
    }
    list remote-ethernet-segment-identifier {
      description
        "Remote Ethernet Segment id";
      leaf entry {
        type uint8;
        description
          "Remote Ethernet Segment id";
      }
    }
    list path-buffer {
      description
        "Path List Buffer";
      uses ncs_rpc_notif_L2VPN-LABEL-PATH-BUFFER;
    }
  }

  grouping ncs_rpc_notif_L2VPN-EVPN-EVI-BGP-RT {
    description
      "EVPN Instance Route Target information";
    container evpn-instance {
      description
        "EVPN Instance summary information";
      uses ncs_rpc_notif_L2VPN-EVPN-EVI-SUMMARY;
    }
    container route-target {
      description
        "Route Target";
      uses ncs_rpc_notif_L2VPN-RT;
    }
    leaf route-target-role {
      type ncs_rpc_notif_L2vpn-ad-rt-role;
      description
        "RT Role";
    }
    leaf route-target-stitching {
      type boolean;
      description
        "RT Stitching";
    }
  }

  grouping ncs_rpc_notif_L2VPN-EVPN-IMCAST {
    description
      "L2VPN EVPN Inclusive Multicast database
       information";
    container evpn-instance {
      description
        "EVPN Instance summary information";
      uses ncs_rpc_notif_L2VPN-EVPN-EVI-SUMMARY;
    }
    container sr-te-info {
      description
        "SR(v6)-TE Policy info from ODN";
      uses ncs_rpc_notif_L2VPN-EVPN-SRTE-INFO;
    }
    leaf ethernet-tag-xr {
      type uint32;
      description
        "Ethernet Tag";
    }
    leaf originating-ip-xr {
      type inet:ipv6-address;
      description
        "Originating IP";
    }
    leaf tunnel-endpoint-id {
      type uint32;
      description
        "Tunnel Endpoint ID";
    }
    leaf pmsi-tunnel-type {
      type uint32;
      description
        "PMSI Tunnel Type";
    }
    leaf next-hop {
      type inet:ipv6-address;
      description
        "IP of nexthop";
    }
    leaf output-label {
      type uint32;
      description
        "Output label";
    }
    leaf is-local-entry {
      type boolean;
      description
        "Local entry";
    }
    leaf is-proxy-entry {
      type boolean;
      description
        "Proxy entry";
    }
    leaf etree-leaf {
      type boolean;
      description
        "E-Tree Leaf Indication";
    }
  }

  grouping ncs_rpc_notif_L2VPN-EVPN-L2-ATTRS {
    description
      "L2VPN EVPN L2 ATTRS";
    leaf mtu {
      type uint16;
      description
        "Maximum Transmission Unit";
    }
    leaf designated-forwarder-role {
      type ncs_rpc_notif_Evpn-bag-df-role;
      description
        "Designated Forwarder Role";
    }
    leaf control-word {
      type ncs_rpc_notif_Evpn-bag-l2-attr-cw;
      description
        "Control Word";
    }
  }

  grouping ncs_rpc_notif_L2VPN-EVPN-SRTE-INFO {
    description
      "L2VPN EVPN SRTE INFO";
    leaf sr-te-type {
      type uint8;
      description
        "Type of SR-TE Policy path from ODN";
    }
    leaf sr-te-interface-name {
      type xr:ncs_rpc_notif_Interface-name;
      description
        "SR Traffic Engineering Interface Name";
    }
    leaf sr-te-bsid {
      type uint32;
      description
        "SR Traffic Engineering Binding-SID (Label)";
    }
    leaf srv6-te-bsid {
      type inet:ipv6-address;
      description
        "SRv6 Traffic Engineering Binding-SID";
    }
  }

  grouping ncs_rpc_notif_L2VPN-LABEL-PATH-BUFFER {
    description
      "L2VPN LABEL PATH BUFFER";
    container sr-te-info {
      description
        "SR(v6)-TE Policy info from ODN";
      uses ncs_rpc_notif_L2VPN-EVPN-SRTE-INFO;
    }
    container layer2-attributes {
      description
        "Layer 2 Attributes";
      uses ncs_rpc_notif_L2VPN-EVPN-L2-ATTRS;
    }
    leaf tunnel-endpoint-id {
      type uint32;
      description
        "Tunnel Endpoint Identifier";
    }
    leaf next-hop {
      type inet:ipv6-address;
      description
        "Next-hop IP address (v6 format)";
    }
    leaf output-label {
      type uint32;
      description
        "Output Label";
    }
    leaf reroute-label {
      type uint32;
      description
        "Reroute Label";
    }
    list issue {
      description
        "Issues with this path item";
      leaf entry {
        type ncs_rpc_notif_Evpn-bag-path-issues;
        description
          "Issues with this path item";
      }
    }
    list srv6-sid-info {
      description
        "Array of SRv6 SID information";
      uses ncs_rpc_notif_L2VPN-EVPN-SRV6-SID-INFO;
    }
  }

  grouping ncs_rpc_notif_L2VPN-EVPN-SRV6-SID-INFO {
    description
      "SRv6 SID information for EVPN services";
    leaf srv6-sid {
      type inet:ipv6-address;
      description
        "SRv6 SID";
    }
  }

  grouping ncs_rpc_notif_L2VPN-EVPN-EAD {
    description
      "L2VPN EVPN EAD database information";
    container evpn-instance {
      description
        "EVPN Instance summary information";
      uses ncs_rpc_notif_L2VPN-EVPN-EVI-SUMMARY;
    }
    container layer2-attributes {
      description
        "Layer 2 Attributes";
      uses ncs_rpc_notif_L2VPN-EVPN-L2-ATTRS;
    }
    leaf ethernet-tag-xr {
      type uint32;
      description
        "Ethernet Tag";
    }
    leaf local-next-hop {
      type inet:ipv6-address;
      description
        "Local nexthop IP";
    }
    leaf local-label {
      type uint32;
      description
        "Associated local label";
    }
    leaf is-local-ead {
      type boolean;
      description
        "Indication of EthernetAutoDiscovery Route is
         local";
    }
    leaf redundancy-single-active {
      type boolean;
      description
        "Single-active redundancy configured at remote
         EAD";
    }
    leaf redundancy-single-flow-active {
      type boolean;
      description
        "Single-flow-active redundancy configured at
         remote EAD";
    }
    list ethernet-segment-identifier {
      description
        "Ethernet Segment id";
      leaf entry {
        type uint8;
        description
          "Ethernet Segment id";
      }
    }
    list local-sid-array {
      description
        "Associated local SIDs";
      uses ncs_rpc_notif_L2VPN-EVPN-SRV6-SID-INFO;
    }
    list path-buffer {
      description
        "Path List Buffer";
      uses ncs_rpc_notif_L2VPN-LABEL-PATH-BUFFER;
    }
  }

  grouping ncs_rpc_notif_L2VPN-EVPN-NEIGHBOR {
    description
      "L2VPN EVPN Neighbor database information";
    container evpn-instance {
      description
        "EVPN Instance summary information";
      uses ncs_rpc_notif_L2VPN-EVPN-EVI-SUMMARY;
    }
    leaf neighbor {
      type inet:ipv6-address;
      description
        "Neighbor IP";
    }
    list leaf-evis {
      description
        "Leaf EVIs";
      leaf entry {
        type uint32;
        description
          "Leaf EVIs";
      }
    }
  }

  grouping ncs_rpc_notif_L2VPN-RT-ES-IMPORT {
    description
      "L2VPN RT ES IMPORT";
    leaf high-bytes {
      type uint32;
      description
        "Top 4 bytes of ES Import";
    }
    leaf low-bytes {
      type uint16;
      description
        "Low 2 bytes of ES Import";
    }
  }

  grouping ncs_rpc_notif_L2VPN-RT-V4ADDR {
    description
      "L2VPN RT V4ADDR";
    leaf ipv4-address {
      type inet:ipv4-address;
      description
        "IPv4 Address";
    }
    leaf two-byte-index {
      type uint16;
      description
        "2 Byte Index";
    }
  }

  grouping ncs_rpc_notif_L2VPN-RT-4BYTE-AS {
    description
      "L2VPN RT 4BYTE AS";
    leaf four-byte-as {
      type uint32;
      description
        "4 Byte AS Number";
    }
    leaf two-byte-index {
      type uint16;
      description
        "2 Byte Index";
    }
  }

  grouping ncs_rpc_notif_L2VPN-RT-2BYTE-AS {
    description
      "L2VPN RT 2BYTE AS";
    leaf two-byte-as {
      type uint16;
      description
        "2 Byte AS Number";
    }
    leaf four-byte-index {
      type uint32;
      description
        "4 Byte Index";
    }
  }

  grouping ncs_rpc_notif_L2VPN-RT {
    description
      "L2VPN RT";
    container two-byte-as {
      when "../rt = 'l2vpn-ad-rt-as'" {
        tailf:xpath-root 3;
        description
          "../RT = 'L2VPN_AD_RT_AS'";
      }
      description
        "two byte as";
      uses ncs_rpc_notif_L2VPN-RT-2BYTE-AS;
    }
    container four-byte-as {
      when "../rt = 'l2vpn-ad-rt-4byte-as'" {
        tailf:xpath-root 3;
        description
          "../RT = 'L2VPN_AD_RT_4BYTE_AS'";
      }
      description
        "four byte as";
      uses ncs_rpc_notif_L2VPN-RT-4BYTE-AS;
    }
    container v4-addr {
      when "../rt = 'l2vpn-ad-rt-v4-addr'" {
        tailf:xpath-root 3;
        description
          "../RT = 'L2VPN_AD_RT_V4ADDR'";
      }
      description
        "v4 addr";
      uses ncs_rpc_notif_L2VPN-RT-V4ADDR;
    }
    container es-import {
      when "../rt = 'es-import'" {
        tailf:xpath-root 3;
        description
          "../RT = 'ES_Import'";
      }
      description
        "es import";
      uses ncs_rpc_notif_L2VPN-RT-ES-IMPORT;
    }
    leaf rt {
      type ncs_rpc_notif_L2vpn-ad-rt;
      description
        "RT";
    }
  }

  grouping ncs_rpc_notif_L2VPN-RD-V4ADDR {
    description
      "L2VPN RD V4ADDR";
    leaf ipv4-address {
      type inet:ipv4-address;
      description
        "IPv4 Address";
    }
    leaf two-byte-index {
      type uint16;
      description
        "2 Byte Index";
    }
  }

  grouping ncs_rpc_notif_L2VPN-RD-4BYTE-AS {
    description
      "L2VPN RD 4BYTE AS";
    leaf four-byte-as {
      type uint32;
      description
        "4 Byte AS Number";
    }
    leaf two-byte-index {
      type uint16;
      description
        "2 Byte Index";
    }
  }

  grouping ncs_rpc_notif_L2VPN-RD-2BYTE-AS {
    description
      "L2VPN RD 2BYTE AS";
    leaf two-byte-as {
      type uint16;
      description
        "2 Byte AS Number";
    }
    leaf four-byte-index {
      type uint32;
      description
        "4 Byte Index";
    }
  }

  grouping ncs_rpc_notif_L2VPN-RD-AUTO {
    description
      "L2VPN RD AUTO";
    leaf router-id {
      type inet:ipv4-address;
      description
        "BGP Router ID";
    }
    leaf auto-index {
      type uint16;
      description
        "Auto-generated Index";
    }
  }

  grouping ncs_rpc_notif_L2VPN-RD {
    description
      "L2VPN RD";
    container auto {
      when "../rd = 'l2vpn-ad-rd-auto'" {
        tailf:xpath-root 3;
        description
          "../RD = 'L2VPN_AD_RD_AUTO'";
      }
      description
        "auto";
      uses ncs_rpc_notif_L2VPN-RD-AUTO;
    }
    container two-byte-as {
      when "../rd = 'l2vpn-ad-rd-as'" {
        tailf:xpath-root 3;
        description
          "../RD = 'L2VPN_AD_RD_AS'";
      }
      description
        "two byte as";
      uses ncs_rpc_notif_L2VPN-RD-2BYTE-AS;
    }
    container four-byte-as {
      when "../rd = 'l2vpn-ad-rd-4byte-as'" {
        tailf:xpath-root 3;
        description
          "../RD = 'L2VPN_AD_RD_4BYTE_AS'";
      }
      description
        "four byte as";
      uses ncs_rpc_notif_L2VPN-RD-4BYTE-AS;
    }
    container v4-addr {
      when "../rd = 'l2vpn-ad-rd-v4-addr'" {
        tailf:xpath-root 3;
        description
          "../RD = 'L2VPN_AD_RD_V4ADDR'";
      }
      description
        "v4 addr";
      uses ncs_rpc_notif_L2VPN-RD-V4ADDR;
    }
    leaf rd {
      type ncs_rpc_notif_L2vpn-ad-rd;
      description
        "RD";
    }
  }

  grouping ncs_rpc_notif_L2VPN-EVPN-FLOW-LABEL {
    description
      "L2VPN EVPN FLOW LABEL";
    leaf static-flow-label {
      type boolean;
      description
        "Static flow label";
    }
    leaf global-flow-label {
      type boolean;
      description
        "Globally configured flow label";
    }
  }

  grouping ncs_rpc_notif_L2VPN-EVPN-EVI-DETAIL {
    description
      "EVPN E-VPN ID database detail information";
    container evpn-instance {
      description
        "EVPN Instance summary information";
      uses ncs_rpc_notif_L2VPN-EVPN-EVI-SUMMARY;
    }
    container flow-label {
      description
        "Flow Label Information";
      uses ncs_rpc_notif_L2VPN-EVPN-FLOW-LABEL;
    }
    container rd-auto {
      description
        "Automatic Route Distingtuisher";
      uses ncs_rpc_notif_L2VPN-RD;
    }
    container rd-configured {
      description
        "Configured Route Distinguisher";
      uses ncs_rpc_notif_L2VPN-RD;
    }
    container rt-auto {
      description
        "Automatic Route Target";
      uses ncs_rpc_notif_L2VPN-RT;
    }
    leaf evi-xr {
      type uint32;
      description
        "E-VPN id";
    }
    leaf encapsulation-xr {
      type uint8;
      description
        "EVPN Instance encapsulation";
    }
    leaf bd-name {
      type string;
      description
        "Bridge domain name";
    }
    leaf type {
      type ncs_rpc_notif_L2vpn-evpn;
      description
        "Service Type";
    }
    leaf description {
      type string;
      description
        "EVI description";
    }
    leaf unicast-label {
      type uint32;
      description
        "Unicast Label";
    }
    leaf multicast-label {
      type uint32;
      description
        "Multicast Label";
    }
    leaf reroute-label {
      type uint32;
      description
        "Reroute Label";
    }
    leaf cw-disable {
      type boolean;
      description
        "Control-Word Disable";
    }
    leaf mtu-mismatch-ignore {
      type boolean;
      description
        "Ignore MTU Mismatch";
    }
    leaf mtu-zero-transmit {
      type boolean;
      description
        "Transmit MTU Zero";
    }
    leaf table-policy-name {
      type string;
      description
        "Table-policy Name";
    }
    leaf export-route-policy {
      type string;
      description
        "Export Route Policy";
    }
    leaf import-route-policy {
      type string;
      description
        "Import Route Policy";
    }
    leaf forward-class {
      type uint8;
      description
        "Forward Class attribute";
    }
    leaf rt-import-block-set {
      type boolean;
      description
        "Is Import RT None set";
    }
    leaf rt-export-block-set {
      type boolean;
      description
        "Is Export RT None set";
    }
    leaf advertise-mac {
      type boolean;
      description
        "Advertise MAC-only routes on this EVI";
    }
    leaf etree-leaf {
      type boolean;
      description
        "E-Tree Leaf Indication";
    }
    leaf etree-rt-leaf {
      type boolean;
      description
        "E-Tree Route-Target Leaf Indication";
    }
    leaf advertise-bvi-mac {
      type boolean;
      description
        "Advertise BVI MACs routes on this EVI";
    }
    leaf aliasing-disabled {
      type boolean;
      description
        "Route Aliasing is disabled";
    }
    leaf unknown-unicast-flooding-disabled {
      type boolean;
      description
        "Unknown-unicast flooding is disabled";
    }
    leaf reoriginate-disabled {
      type boolean;
      description
        "Route Re-origination is disabled";
    }
    leaf stitching {
      type boolean;
      description
        "EVPN Instance is Regular/Stitching side";
    }
    leaf multicast-source-connected {
      type boolean;
      description
        "EVI is connected to multicast source";
    }
    leaf bgp-implicit-import-disabled {
      type boolean;
      description
        "BGP implicit import is disabled";
    }
    leaf vrf-name {
      type string;
      description
        "L3 VRF name from BVI";
    }
    leaf preferred-nh-mode {
      type ncs_rpc_notif_Evpn-pref-ecmp-nh-mode;
      description
        "Preferred Nexthop Mode";
    }
    leaf srv6-locator-name {
      type string;
      description
        "SRv6 Locator Name";
    }
  }

  grouping ncs_rpc_notif_L2VPN-EVPN-SUMMARY {
    description
      "EVPN Information Summary";
    leaf router-id {
      type inet:ipv6-address;
      description
        "EVPN Router ID";
    }
    leaf as {
      type uint32;
      description
        "BGP AS number";
    }
    leaf ev-is {
      type uint32;
      description
        "Number of EVI DB Entries";
    }
    leaf tunnel-endpoints {
      type uint32;
      description
        "Number of Tunnel Endpoint DB Entries";
    }
    leaf local-mac-routes {
      type uint32;
      description
        "Number of Local MAC Routes";
    }
    leaf local-ipv4-mac-routes {
      type uint32;
      description
        "Number of Local IPv4 MAC-IP Routes";
    }
    leaf local-ipv6-mac-routes {
      type uint32;
      description
        "Number of Local IPv6 MAC-IP Routes";
    }
    leaf es-global-mac-routes {
      type uint32;
      description
        "Number of ES:Global MAC Routes";
    }
    leaf remote-mac-routes {
      type uint32;
      description
        "Number of Remote MAC Routes";
    }
    leaf remote-sync-mac-routes {
      type uint32;
      description
        "Number of Remote SYNC MAC Routes";
    }
    leaf remote-ipv4-mac-routes {
      type uint32;
      description
        "Number of Remote IPv4 MAC-IP Routes";
    }
    leaf remote-ipv6-mac-routes {
      type uint32;
      description
        "Number of Remote IPv6 MAC-IP Routes";
    }
    leaf local-imcast-routes {
      type uint32;
      description
        "Number of Local IMCAST Routes";
    }
    leaf remote-imcast-routes {
      type uint32;
      description
        "Number of Remote IMCAST Routes";
    }
    leaf labels {
      type uint32;
      description
        "Number of Internal Labels";
    }
    leaf sh-internal-ids {
      type uint32;
      description
        "Number of single-homed Internal IDs";
    }
    leaf mh-internal-ids {
      type uint32;
      description
        "Number of multi-homed Internal IDs";
    }
    leaf es-entries {
      type uint32;
      description
        "Number of ES Entries in DB";
    }
    leaf neighbor-entries {
      type uint32;
      description
        "Number of neighbor Entries in DB";
    }
    leaf local-ead-routes {
      type uint32;
      description
        "Number of Local EAD Entries in DB";
    }
    leaf remote-ead-routes {
      type uint32;
      description
        "Number of Remote EAD Entries in DB";
    }
    leaf global-source-mac {
      type yang:mac-address;
      description
        "Global Source MAC Address";
    }
    leaf peering-time {
      type uint32;
      units "second";
      description
        "EVPN ES Peering Time (seconds)";
    }
    leaf recovery-time {
      type uint32;
      units "second";
      description
        "EVPN ES Recovery Time (seconds)";
    }
    leaf carving-time {
      type uint32;
      units "second";
      description
        "EVPN ES Carving Time (seconds)";
    }
    leaf cost-out-configured {
      type boolean;
      description
        "EVPN node cost out via manual configuration";
    }
    leaf bundle-convergence-in-progress {
      type boolean;
      description
        "Bundle convergence in progress";
    }
    leaf node-costed-out {
      type boolean;
      description
        "EVPN Services costed out on node and holding
         Bundle interfaces down";
    }
    leaf startup-cost-in-time {
      type uint32;
      units "second";
      description
        "EVPN Node startup cost-in Time (seconds)";
    }
    leaf startup-cost-in-time-left {
      type uint32;
      units "millisecond";
      description
        "Milliseconds left on EVPN Node startup cost-in";
    }
    leaf mac-postpone-timer {
      type uint32;
      units "second";
      description
        "Configured timer for postponing MAC withdraws
         (seconds)";
    }
    leaf mac-postpone-timer-left {
      type uint32;
      units "millisecond";
      description
        "Milliseconds left on MAC withdraw postpone timer";
    }
    leaf l2rib-throttle {
      type boolean;
      description
        "Send to L2RIB Throttled";
    }
    leaf logging-df-election-enabled {
      type boolean;
      description
        "Logging EVPN Designated Forwarder changes
         enabled";
    }
  }

  grouping ncs_rpc_notif_L2VPN-EVPN-EVI-SUMMARY {
    description
      "EVPN Instance summary information";
    leaf ethernet-vpn-id {
      type uint32;
      description
        "Ethernet VPN id";
    }
    leaf encapsulation-xr {
      type uint8;
      description
        "EVPN Instance transport encapsulation";
    }
    leaf bd-name {
      type string;
      description
        "Bridge domain name";
    }
    leaf type {
      type ncs_rpc_notif_L2vpn-evpn;
      description
        "Service Type";
    }
  }

  grouping ncs_rpc_notif_L2VPN-EVPN-IGMP-SUBIF-INFO {
    description
      "L2VPN EVPN IGMP SUBIF INFO";
    leaf vrf-id {
      type uint32;
      description
        "VRF id";
    }
  }

  grouping ncs_rpc_notif_L2VPN-EVPN-IGMP-FWD-INFO {
    description
      "L2VPN EVPN IGMP FWD INFO";
    leaf bd-id {
      type uint32;
      description
        "BD id";
    }
  }

  grouping ncs_rpc_notif_EVPN-IGMP-CHILD-INFO {
    description
      "EVPN IGMP CHILD INFO";
    container fwd-info {
      when "../child-type = 'l2-fwd'" {
        tailf:xpath-root 3;
        description
          "../ChildType = 'L2_FWD'";
      }
      description
        "fwd info";
      uses ncs_rpc_notif_L2VPN-EVPN-IGMP-FWD-INFO;
    }
    container subif-info {
      when "../child-type = 'l3-sub-if'" {
        tailf:xpath-root 3;
        description
          "../ChildType = 'L3_SUBIF'";
      }
      description
        "subif info";
      uses ncs_rpc_notif_L2VPN-EVPN-IGMP-SUBIF-INFO;
    }
    leaf child-type {
      type ncs_rpc_notif_Evpn-child;
      description
        "ChildType";
    }
  }

  grouping ncs_rpc_notif_L2VPN-EVPN-IGMP-LOCAL-INFO {
    description
      "L2VPN EVPN IGMP LOCAL INFO";
    leaf if-name {
      type string {
        length "0..65";
      }
      description
        "Interface name internal format";
    }
  }

  grouping ncs_rpc_notif_EVPN-IGMP-SRC-INFO {
    description
      "EVPN IGMP SRC INFO";
    container local-info {
      when "../type = 'local'" {
        tailf:xpath-root 3;
        description
          "../Type = 'Local'";
      }
      description
        "local info";
      uses ncs_rpc_notif_L2VPN-EVPN-IGMP-LOCAL-INFO;
    }
    leaf type {
      type ncs_rpc_notif_Evpn-igmp-source;
      description
        "Type";
    }
    leaf remote-info {
      when "../type = 'remote'" {
        tailf:xpath-root 3;
        description
          "../Type = 'Remote'";
      }
      type ncs_rpc_notif_L2vpn-bag-in6-addr;
      description
        "remote info";
    }
  }

  grouping ncs_rpc_notif_L2VPN-EVPN-IGMP {
    description
      "EVPN IGMP database information";
    container source-info {
      description
        "Source Info";
      uses ncs_rpc_notif_EVPN-IGMP-SRC-INFO;
    }
    container child-info {
      description
        "Child Info";
      uses ncs_rpc_notif_EVPN-IGMP-CHILD-INFO;
    }
    leaf evpn-client-type {
      type ncs_rpc_notif_Evpn-client1;
      description
        "EVPN Client Type";
    }
    leaf ethernet-segment-name {
      type string;
      description
        "Ethernet Segment Name";
    }
    leaf evi-xr {
      type uint32;
      description
        "E-VPN id";
    }
    leaf route-type {
      type ncs_rpc_notif_Evpn-igmp-msg;
      description
        "Route Type";
    }
    leaf source-addr {
      type inet:ipv6-address;
      description
        "Source IP Address";
    }
    leaf group-addr {
      type inet:ipv6-address;
      description
        "Group IP Address";
    }
    leaf ethernet-tag-id {
      type uint32;
      description
        "Ethernet Tag id";
    }
    leaf igmp-version {
      type ncs_rpc_notif_Evpn-igmp-version;
      description
        "IGMP Version";
    }
    leaf igmp-group-type {
      type ncs_rpc_notif_Evpn-igmp-grp;
      description
        "IGMP Group Type";
    }
    leaf max-response-time {
      type uint8;
      description
        "Max Response Time";
    }
    leaf resolved {
      type boolean;
      description
        "Resolved";
    }
    list ethernet-segment-identifier {
      description
        "Ethernet Segment id";
      leaf entry {
        type uint8;
        description
          "Ethernet Segment id";
      }
    }
  }

  grouping ncs_rpc_notif_L2VPN-EVPN-CLIENT {
    description
      "EVPN Client Information";
    leaf client-type {
      type ncs_rpc_notif_Evpn-client1;
      description
        "Client Type";
    }
  }

  grouping ncs_rpc_notif_L2VPN-EVPN-REMOTE-SHG-INFO {
    description
      "L2VPN EVPN remote split horizon group labels";
    leaf next-hop {
      type inet:ipv6-address;
      description
        "Next-hop IP address (v6 format)";
    }
    leaf label {
      type uint32;
      description
        "Split horizon label associated with next-hop
         address";
    }
  }

  grouping ncs_rpc_notif_L2VPN-EVPN-REMOTE-SHG {
    description
      "EVPN Remote SHG object";
    leaf ethernet-vpn-id {
      type uint32;
      description
        "Ethernet VPN id";
    }
    leaf encapsulation {
      type uint8;
      description
        "EVPN Instance transport encapsulation";
    }
    list ethernet-segment-identifier {
      description
        "Ethernet Segment id";
      leaf entry {
        type uint8;
        description
          "Ethernet Segment id";
      }
    }
    list remote-split-horizon-group-label {
      description
        "Remote split horizon group labels";
      uses ncs_rpc_notif_L2VPN-EVPN-REMOTE-SHG-INFO;
    }
  }

  grouping ncs_rpc_notif_EVPN-GRP-INTF-INFO {
    description
      "EVPN Group Interface Information";
    leaf interface-name {
      type string;
      description
        "Interface name";
    }
    leaf state {
      type ncs_rpc_notif_Im-state-enum;
      description
        "Interface State";
    }
  }

  grouping ncs_rpc_notif_EVPN-GRP-INFO {
    description
      "EVPN Group Information";
    leaf group-id {
      type uint32;
      description
        "EVPN Group ID";
    }
    leaf state {
      type ncs_rpc_notif_Evpn-grp;
      description
        "EVPN Group State";
    }
    list core-interface {
      description
        "EVPN Group Core Interface table";
      uses ncs_rpc_notif_EVPN-GRP-INTF-INFO;
    }
    list access-interface {
      description
        "EVPN Access Core Interface table";
      uses ncs_rpc_notif_EVPN-GRP-INTF-INFO;
    }
  }

  grouping live_ncs_L2VPN-ATOM-ACID {
    description
      "L2VPN ATOM ACID";
    leaf source-ac-id {
      type uint32;
      description
        "Source AC ID";
    }
    leaf target-ac-id {
      type uint32;
      description
        "Target AC ID";
    }
    leaf vpn-id {
      type uint32;
      description
        "VPN ID";
    }
    leaf taii-global-id {
      type uint32;
      description
        "TAII Global ID";
    }
    leaf taii-ac-id {
      type uint32;
      description
        "TAII AC ID";
    }
    leaf taii-prefix {
      type inet:ipv6-address;
      description
        "TAII Prefix";
    }
  }

  grouping live_ncs_L2VPN-EVPN-EAD-SERVICE-INFO {
    description
      "L2VPN EVPN EAD Ethernet Tag";
    leaf vpn-id {
      type uint32;
      description
        "VPN ID";
    }
    leaf type {
      type live_ncs_L2vpn-evpn;
      description
        "Service Type";
    }
    leaf ethernet-tag {
      type uint32;
      description
        "Ethernet Tag";
    }
  }

  grouping live_ncs_L2VPN-BAG-TIMESPEC {
    description
      "L2VPN Timespec Data Structure";
    leaf tv-sec {
      type uint32;
      description
        "tv sec";
    }
    leaf tv-nsec {
      type uint32;
      description
        "tv nsec";
    }
  }

  grouping live_ncs_L2VPN-STAT-ITEM {
    description
      "L2VPN EVPN Ethernet Segment (ES) private stats
       item";
    container last-time {
      description
        "last time";
      uses live_ncs_L2VPN-BAG-TIMESPEC;
    }
    leaf count {
      type uint32;
      description
        "count";
    }
    leaf last-arg {
      type uint32;
      description
        "last arg";
    }
  }

  grouping live_ncs_L2VPN-EVPN-ES-NH-BUFFER {
    description
      "L2VPN EVPN Ethernet Segment (ES) nexthops
       information";
    leaf next-hop {
      type inet:ipv6-address;
      description
        "Next-hop IP address (v6 format)";
    }
    leaf df-dont-preempt {
      type boolean;
      description
        "DF Dont Preemption";
    }
    leaf df-type {
      type uint8;
      description
        "DF Election Mode Configured";
    }
    leaf df-pref {
      type uint16;
      description
        "DF Election Preference Set";
    }
    leaf df-ntp-enabled {
      type boolean;
      description
        "NTP based DF Election Synchronization";
    }
    leaf ntp-sct-microseconds {
      type uint64;
      units "microsecond";
      description
        "NTP based SCT: represented in microseconds
         relative to Unix epoch: 1st Jan 1970";
    }
  }

  grouping live_ncs_L2VPN-EVPN-ES {
    description
      "EVPN Ethernet Segment (ES) database information";
    container msti-flush-count {
      description
        "Statistics for Host-mobility driven flush
         operations";
      uses live_ncs_L2VPN-STAT-ITEM;
    }
    leaf esi-type {
      type live_ncs_L2vpn-evpn-esi;
      description
        "ESI Type";
    }
    leaf esi-system-identifier {
      type string;
      description
        "ESI System Identifier";
    }
    leaf esi-port-key {
      type uint32;
      description
        "ESI Port Key";
    }
    leaf esi-system-priority {
      type uint32;
      description
        "ESI System Priority";
    }
    leaf ethernet-segment-name {
      type string;
      description
        "Ethernet Segment Name";
    }
    leaf ethernet-segment-state {
      type live_ncs_L2vpn-evpn-es-state;
      description
        "State of the ethernet segment";
    }
    leaf in-staggered-bringup {
      type boolean;
      description
        "Is this ES in the staggered bring-up queue?";
    }
    leaf if-handle {
      type xr:live_ncs_Interface-name;
      description
        "Main port ifhandle";
    }
    leaf main-port-role {
      type live_ncs_L2vpn-rg-role;
      description
        "Main port redundancy group role";
    }
    leaf main-port-mac {
      type yang:mac-address;
      description
        "Main Port MAC Address";
    }
    leaf num-up-p-ws {
      type uint32;
      description
        "Number of PWs in Up state";
    }
    leaf route-target {
      type yang:mac-address;
      description
        "ES-Import Route Target";
    }
    leaf rt-origin {
      type live_ncs_L2vpn-evpn-rt-origin;
      description
        "Origin of operational ES-Import RT";
    }
    leaf es-bgp-gates {
      type string;
      description
        "ES BGP Gates";
    }
    leaf es-l2fib-gates {
      type string;
      description
        "ES L2FIB Gates";
    }
    leaf mac-flushing-mode-config {
      type live_ncs_L2vpn-evpn-mf-mode;
      description
        "Configured MAC Flushing mode";
    }
    leaf load-balance-mode-config {
      type live_ncs_L2vpn-evpn-lb-mode;
      description
        "Configured load balancing mode";
    }
    leaf load-balance-mode-is-default {
      type boolean;
      description
        "Load balancing mode is default";
    }
    leaf load-balance-mode-oper {
      type live_ncs_L2vpn-evpn-lb-mode;
      description
        "Operational load balancing mode";
    }
    leaf force-single-home {
      type boolean;
      description
        "Ethernet-Segment forced to single home";
    }
    leaf convergence-mac-mobility {
      type boolean;
      description
        "Fast convergence mode based on MAC-mobility.";
    }
    leaf convergence-reroute {
      type boolean;
      description
        "Fast convergence mode based on reroute to backup
         peer.";
    }
    leaf convergence-nh-tracking {
      type boolean;
      description
        "Fast DF-Election based on tracking peer BGP
         Nexthop reachability";
    }
    leaf source-mac-oper {
      type yang:mac-address;
      description
        "Operational Source MAC address";
    }
    leaf source-mac-origin {
      type live_ncs_L2vpn-evpn-smac-src;
      description
        "Origin of operational source MAC address";
    }
    leaf peering-timer {
      type uint32;
      units "second";
      description
        "Configured timer for triggering DF election
         (seconds)";
    }
    leaf peering-timer-left {
      type uint32;
      units "millisecond";
      description
        "Milliseconds left on DF election timer";
    }
    leaf recovery-timer {
      type uint32;
      units "second";
      description
        "Configured timer for (STP) recovery (seconds)";
    }
    leaf recovery-timer-left {
      type uint32;
      units "millisecond";
      description
        "Milliseconds left on (STP) recovery timer";
    }
    leaf carving-timer {
      type uint32;
      units "second";
      description
        "Configured timer for delaying DF election
         (seconds)";
    }
    leaf carving-timer-left {
      type uint32;
      units "millisecond";
      description
        "Milliseconds left on carving timer";
    }
    leaf hrw-reset-timer {
      type uint32;
      units "second";
      description
        "Configured timer for HRW reset (seconds)";
    }
    leaf hrw-reset-timer-left {
      type uint32;
      units "millisecond";
      description
        "Milliseconds left on HRW reset timer";
    }
    leaf service-carving-mode {
      type live_ncs_L2vpn-evpn-sc-mode;
      description
        "Service carving mode";
    }
    leaf service-carving-synchronization-mode {
      type live_ncs_L2vpn-evpn-sc-synchronization-mode;
      description
        "Service carving synchronization mode";
    }
    leaf service-carving-mcast-mode {
      type live_ncs_L2vpn-evpn-sc-mcast-mode;
      description
        "Service carving multicast mode";
    }
    leaf primary-services-input {
      type string;
      description
        "Input string of Primary services ESI/I-SIDs";
    }
    leaf secondary-services-input {
      type string;
      description
        "Input string of Secondary services ESI/I-SIDs";
    }
    leaf preferential-df-configured-weight {
      type uint16;
      description
        "Configured Weight for Preferential DF Election";
    }
    leaf preferential-df-operational-weight {
      type uint16;
      description
        "Operational Weight for Preferential DF Election";
    }
    leaf access-driven-df-election {
      type boolean;
      description
        "Access Driven DF Election is active";
    }
    leaf forwarder-ports {
      type uint32;
      description
        "Count of Forwarders (AC, AC PW, VFI PW)";
    }
    leaf permanent-forwarder-ports {
      type uint32;
      description
        "Count of Forwarders with permanent service";
    }
    leaf elected-forwarder-ports {
      type uint32;
      description
        "Count of Forwarders with elected service";
    }
    leaf not-elected-forwarder-ports {
      type uint32;
      description
        "Count of Forwarders with not elected service";
    }
    leaf not-config-forwarder-ports {
      type uint32;
      description
        "Count of forwarders with missing config detected";
    }
    leaf mp-protected {
      type boolean;
      description
        "MP is protected and not under EVPN control";
    }
    leaf nve-anycast-vtep {
      type boolean;
      description
        "Anycast VTEP mode on NVE main-interface";
    }
    leaf nve-ingress-replication {
      type boolean;
      description
        "Ingress-Replication is configured on NVE
         main-interface";
    }
    leaf msti-flush-debounce {
      type uint32;
      description
        "Value of scale-dependant debouncing";
    }
    leaf tracked-bgp-nexthop {
      type inet:ipv6-address;
      description
        "Reachability-tracked BGP Nexthop";
    }
    leaf local-split-horizon-group-label-valid {
      type boolean;
      description
        "Local split horizon group label is valid";
    }
    leaf local-split-horizon-group-label {
      type uint32;
      description
        "Local split horizon group label";
    }
    leaf access-signal-mode {
      type live_ncs_L2vpn-evpn-es-access-signal-mode;
      description
        "Operational access signal mode";
    }
    list ethernet-segment-identifier {
      description
        "Ethernet Segment id";
      leaf entry {
        type uint8;
        description
          "Ethernet Segment id";
      }
    }
    list primary-service {
      description
        "List of Primary services ESI/I-SIDs";
      leaf entry {
        type uint32;
        description
          "List of Primary services ESI/I-SIDs";
      }
    }
    list secondary-service {
      description
        "List of Secondary services ESI/I-SIDs";
      leaf entry {
        type uint32;
        description
          "List of Secondary services ESI/I-SIDs";
      }
    }
    list service-carving-i-sidelected-result {
      description
        "Elected ISID service carving results";
      leaf entry {
        type uint32;
        description
          "Elected ISID service carving results";
      }
    }
    list service-carving-isid-not-elected-result {
      description
        "Not elected ISID service carving results";
      leaf entry {
        type uint32;
        description
          "Not elected ISID service carving results";
      }
    }
    list service-carving-evi-elected-result {
      description
        "Elected EVI service carving results";
      leaf entry {
        type uint32;
        description
          "Elected EVI service carving results";
      }
    }
    list service-carving-evi-not-elected-result {
      description
        "Not elected EVI service carving results";
      leaf entry {
        type uint32;
        description
          "Not elected EVI service carving results";
      }
    }
    list service-carving-vni-elected-result {
      description
        "Elected VNI service carving results";
      leaf entry {
        type uint32;
        description
          "Elected VNI service carving results";
      }
    }
    list service-carving-vni-not-elected-result {
      description
        "Not elected VNI service carving results";
      leaf entry {
        type uint32;
        description
          "Not elected VNI service carving results";
      }
    }
    list next-hop {
      description
        "List of nexthop IPv6 addresses";
      uses live_ncs_L2VPN-EVPN-ES-NH-BUFFER;
    }
    list service-carving-evpn-vpws-primary-result {
      description
        "EVPN VPWS service carving primary results";
      uses live_ncs_L2VPN-EVPN-EAD-SERVICE-INFO;
    }
    list service-carving-evpn-vpws-backup-result {
      description
        "EVPN VPWS service carving backup results";
      uses live_ncs_L2VPN-EVPN-EAD-SERVICE-INFO;
    }
    list service-carving-evpn-vpws-ndf-result {
      description
        "EVPN VPWS service carving non-DF results";
      uses live_ncs_L2VPN-EVPN-EAD-SERVICE-INFO;
    }
    list remote-split-horizon-group-label {
      description
        "Remote split horizon group labels";
      uses live_ncs_L2VPN-EVPN-REMOTE-SHG-INFO;
    }
  }

  grouping live_ncs_EVPN-SRV6-LOCATOR-INFO {
    description
      "EVPN SRv6 Locator information";
    leaf locator-name {
      type string;
      description
        "SRv6 Locator name";
    }
    leaf locator-prefix {
      type inet:ipv6-address;
      description
        "SRv6 Locator prefix";
    }
    leaf locator-length {
      type uint8;
      description
        "SRv6 Locator length";
    }
    leaf oor-state {
      type boolean;
      description
        "Out of Resources state";
    }
    leaf in-use {
      type boolean;
      description
        "In use by services";
    }
    leaf service-count {
      type uint32;
      description
        "Number of services using this locator implicitly
         and explicitly";
    }
    leaf sid-count {
      type uint32;
      description
        "Number of SIDs allocated by services for this
         locator";
    }
    leaf is-default {
      type boolean;
      description
        "Configured default locator";
    }
    list evi {
      description
        "List of EVIs with this locator explicitly

         configured";
      leaf entry {
        type uint32;
        description
          "List of EVIs with this locator explicitly

           configured";
      }
    }
    list pw {
      description
        "List of VPWS services with this locator
         explicitly configured";
      uses live_ncs_EVPN-SRV6-VPWS-KEY;
    }
  }

  grouping live_ncs_EVPN-SRV6-VPWS-KEY {
    description
      "EVPN SRv6 VPWS service key";
    leaf evi {
      type uint32;
      description
        "EVI for the VPWS service";
    }
    leaf acid {
      type uint32;
      description
        "Attachment circuit ID for the VPWS service";
    }
  }

  grouping live_ncs_L2VPN-EVPN-SRV6 {
    description
      "EVPN SRv6 info object";
    leaf enabled {
      type boolean;
      description
        "SRv6 Enabled";
    }
    leaf configured-default-locator {
      type string;
      description
        "Configured default SRv6 locator";
    }
    list unknown-locator-evi {
      description
        "List of EVIs with unknown locator names

         configured";
      leaf entry {
        type uint32;
        description
          "List of EVIs with unknown locator names

           configured";
      }
    }
    list unknown-locator-vpws {
      description
        "List of VPWS services with unknown locator names
         configured";
      uses live_ncs_EVPN-SRV6-VPWS-KEY;
    }
    list locator {
      description
        "List of locators from L3RIB";
      uses live_ncs_EVPN-SRV6-LOCATOR-INFO;
    }
  }

  grouping live_ncs_L2VPN-EVPN-LABEL {
    description
      "EVPN Internal Label database information";
    container evpn-instance {
      description
        "EVPN Instance summary information";
      uses live_ncs_L2VPN-EVPN-EVI-SUMMARY;
    }
    leaf esi {
      type yang:hex-string;
      description
        "Ethernet Segment id";
    }
    leaf tag {
      type uint32;
      description
        "Label Tag";
    }
    leaf internal-label {
      type uint32;
      description
        "MPLS Internal Label";
    }
    leaf alternate-internal-label {
      type uint32;
      description
        "Alternate MPLS Internal Label";
    }
    leaf internal-id {
      type uint32;
      description
        "SRv6 Internal ID";
    }
    leaf resolved {
      type boolean;
      description
        "Internal Label has resolved per-ES EAD and
         per-EVI EAD or MAC routes";
    }
    leaf unresolved-reason {
      type live_ncs_Evpn-bag-label-unresolved-reason;
      description
        "Optional reason why the label entry has not been
         resolved";
    }
    leaf preferred-nh-mode {
      type live_ncs_Evpn-pref-ecmp-nh-mode;
      description
        "Preferred ECMP Nexthop Mode";
    }
    leaf redundancy-single-active {
      type boolean;
      description
        "Single-active redundancy configured at remote ES";
    }
    leaf redundancy-single-flow-active {
      type boolean;
      description
        "Single-flow-active redundancy at remote ES
         (MST-AG)";
    }
    list mac-path-buffer {
      description
        "MAC Path list buffer";
      uses live_ncs_L2VPN-LABEL-PATH-BUFFER;
    }
    list ead-path-buffer {
      description
        "EAD/ES Path list buffer";
      uses live_ncs_L2VPN-LABEL-PATH-BUFFER;
    }
    list evi-path-buffer {
      description
        "EAD/EVI Path list buffer";
      uses live_ncs_L2VPN-LABEL-PATH-BUFFER;
    }
    list union-path-buffer {
      description
        "Union Path list buffer";
      uses live_ncs_L2VPN-LABEL-PATH-BUFFER;
    }
    list summary-path-buffer {
      description
        "Summary Path list buffer";
      uses live_ncs_L2VPN-LABEL-PATH-BUFFER;
    }
    list alternate-summary-path-buffer {
      description
        "Alternate Summary Path list buffer";
      uses live_ncs_L2VPN-LABEL-PATH-BUFFER;
    }
  }

  grouping live_ncs_L2VPN-EVPN-TEP-INFO {
    description
      "L2VPN EVPN TEP INFO";
    leaf ethernet-vpn-id {
      type uint32;
      description
        "Ethernet VPN id";
    }
    leaf encapsulation {
      type uint8;
      description
        "EVPN Tunnel encapsulation";
    }
    leaf ip {
      type inet:ipv6-address;
      description
        "IP address (v6 format)";
    }
  }

  grouping live_ncs_L2VPN-EVPN-TEP {
    description
      "EVPN Tunnel Endpoint database information";
    container local-info {
      description
        "Local TEP Information";
      uses live_ncs_L2VPN-EVPN-TEP-INFO;
    }
    container remote-info {
      description
        "Remote TEP Information";
      uses live_ncs_L2VPN-EVPN-TEP-INFO;
    }
    leaf tunnel-endpoint-id {
      type uint32;
      description
        "Tunnel Endpoint id";
    }
    leaf type {
      type uint8;
      description
        "EVPN Tunnel Endpoint Type";
    }
    leaf use-count {
      type uint32;
      description
        "in-use counter";
    }
    leaf vrf-name {
      type string;
      description
        "VRF Name";
    }
    leaf vrf-table-id {
      type uint32;
      description
        "VRF Table Id in RIB";
    }
    leaf udp-port {
      type uint16;
      description
        "UDP port";
    }
  }

  grouping live_ncs_L2VPN-EVPN-TEP-NOTIFICATION-ENTRY {
    description
      "EVPN Tunnel Endpoint notification entry
       information";
    leaf entry-name {
      type string;
      description
        "Entry Name";
    }
  }

  grouping live_ncs_L2VPN-EVPN-MAC {
    description
      "L2VPN EVPN MAC database information";
    container evpn-instance {
      description
        "EVPN Instance summary information";
      uses live_ncs_L2VPN-EVPN-EVI-SUMMARY;
    }
    leaf ethernet-tag-xr {
      type uint32;
      description
        "Ethernet Tag";
    }
    leaf mac-address-xr {
      type yang:mac-address;
      description
        "MAC address";
    }
    leaf ip-address-xr {
      type inet:ipv6-address;
      description
        "IP address (v6 format)";
    }
    leaf local-label {
      type uint32;
      description
        "Associated local label";
    }
    leaf is-local-mac {
      type boolean;
      description
        "Indication of MAC being locally generated";
    }
    leaf is-proxy-entry {
      type boolean;
      description
        "Proxy entry";
    }
    leaf is-remote-mac {
      type boolean;
      description
        "Indication of MAC being remotely generated";
    }
    leaf soo-nexthop {
      type inet:ipv6-address;
      description
        "SOO nexthop (v6 format)";
    }
    leaf ipnh-address {
      type inet:ipv6-address;
      description
        "IP nexthop address (v6 format)";
    }
    leaf esi-port-key {
      type uint16;
      description
        "ESI port key";
    }
    leaf local-encap-type {
      type uint8;
      description
        "Encap type of local MAC";
    }
    leaf remote-encap-type {
      type uint8;
      description
        "Encap type of remote MAC";
    }
    leaf learned-bridge-port-name {
      type string;
      description
        "Port the MAC was learned on";
    }
    leaf local-seq-id {
      type uint32;
      description
        "local seq id";
    }
    leaf remote-seq-id {
      type uint32;
      description
        "remote seq id";
    }
    leaf local-l3-label {
      type uint32;
      description
        "local l3 label";
    }
    leaf router-mac-address {
      type yang:mac-address;
      description
        "Router MAC address";
    }
    leaf mac-flush-requested {
      type uint16;
      description
        "Number of flushes requested ";
    }
    leaf mac-flush-received {
      type uint16;
      description
        "Number of flushes received ";
    }
    leaf internal-label {
      type uint32;
      description
        "MPLS Internal Label";
    }
    leaf resolved {
      type boolean;
      description
        "Internal Label has resolved per-ES EAD and
         per-EVI EAD or MAC routes";
    }
    leaf local-is-static {
      type boolean;
      description
        "Indication if Local MAC is statically configured";
    }
    leaf remote-is-static {
      type boolean;
      description
        "Indication if Remote MAC is statically
         configured";
    }
    leaf local-etree-leaf {
      type boolean;
      description
        "Local E-Tree Leaf Indication";
    }
    leaf remote-etree-leaf {
      type boolean;
      description
        "Remote E-Tree Leaf Indication";
    }
    leaf remote-etree-rt-leaf {
      type boolean;
      description
        "Remote MAC matching E-Tree Route-Target Leaf";
    }
    leaf local-attachment-circuit-id {
      type uint32;
      description
        "Local Attachement Circuit ID used in
         ac-aware-vlan-bundling";
    }
    leaf remote-attachment-circuit-id {
      type uint32;
      description
        "Remote Attachement Circuit ID used in
         ac-aware-vlan-bundling";
    }
    list local-ethernet-segment-identifier {
      description
        "Local Ethernet Segment id";
      leaf entry {
        type uint8;
        description
          "Local Ethernet Segment id";
      }
    }
    list remote-ethernet-segment-identifier {
      description
        "Remote Ethernet Segment id";
      leaf entry {
        type uint8;
        description
          "Remote Ethernet Segment id";
      }
    }
    list path-buffer {
      description
        "Path List Buffer";
      uses live_ncs_L2VPN-LABEL-PATH-BUFFER;
    }
  }

  grouping live_ncs_L2VPN-EVPN-EVI-BGP-RT {
    description
      "EVPN Instance Route Target information";
    container evpn-instance {
      description
        "EVPN Instance summary information";
      uses live_ncs_L2VPN-EVPN-EVI-SUMMARY;
    }
    container route-target {
      description
        "Route Target";
      uses live_ncs_L2VPN-RT;
    }
    leaf route-target-role {
      type live_ncs_L2vpn-ad-rt-role;
      description
        "RT Role";
    }
    leaf route-target-stitching {
      type boolean;
      description
        "RT Stitching";
    }
  }

  grouping live_ncs_L2VPN-EVPN-IMCAST {
    description
      "L2VPN EVPN Inclusive Multicast database
       information";
    container evpn-instance {
      description
        "EVPN Instance summary information";
      uses live_ncs_L2VPN-EVPN-EVI-SUMMARY;
    }
    container sr-te-info {
      description
        "SR(v6)-TE Policy info from ODN";
      uses live_ncs_L2VPN-EVPN-SRTE-INFO;
    }
    leaf ethernet-tag-xr {
      type uint32;
      description
        "Ethernet Tag";
    }
    leaf originating-ip-xr {
      type inet:ipv6-address;
      description
        "Originating IP";
    }
    leaf tunnel-endpoint-id {
      type uint32;
      description
        "Tunnel Endpoint ID";
    }
    leaf pmsi-tunnel-type {
      type uint32;
      description
        "PMSI Tunnel Type";
    }
    leaf next-hop {
      type inet:ipv6-address;
      description
        "IP of nexthop";
    }
    leaf output-label {
      type uint32;
      description
        "Output label";
    }
    leaf is-local-entry {
      type boolean;
      description
        "Local entry";
    }
    leaf is-proxy-entry {
      type boolean;
      description
        "Proxy entry";
    }
    leaf etree-leaf {
      type boolean;
      description
        "E-Tree Leaf Indication";
    }
  }

  grouping live_ncs_L2VPN-EVPN-L2-ATTRS {
    description
      "L2VPN EVPN L2 ATTRS";
    leaf mtu {
      type uint16;
      description
        "Maximum Transmission Unit";
    }
    leaf designated-forwarder-role {
      type live_ncs_Evpn-bag-df-role;
      description
        "Designated Forwarder Role";
    }
    leaf control-word {
      type live_ncs_Evpn-bag-l2-attr-cw;
      description
        "Control Word";
    }
  }

  grouping live_ncs_L2VPN-EVPN-SRTE-INFO {
    description
      "L2VPN EVPN SRTE INFO";
    leaf sr-te-type {
      type uint8;
      description
        "Type of SR-TE Policy path from ODN";
    }
    leaf sr-te-interface-name {
      type xr:live_ncs_Interface-name;
      description
        "SR Traffic Engineering Interface Name";
    }
    leaf sr-te-bsid {
      type uint32;
      description
        "SR Traffic Engineering Binding-SID (Label)";
    }
    leaf srv6-te-bsid {
      type inet:ipv6-address;
      description
        "SRv6 Traffic Engineering Binding-SID";
    }
  }

  grouping live_ncs_L2VPN-LABEL-PATH-BUFFER {
    description
      "L2VPN LABEL PATH BUFFER";
    container sr-te-info {
      description
        "SR(v6)-TE Policy info from ODN";
      uses live_ncs_L2VPN-EVPN-SRTE-INFO;
    }
    container layer2-attributes {
      description
        "Layer 2 Attributes";
      uses live_ncs_L2VPN-EVPN-L2-ATTRS;
    }
    leaf tunnel-endpoint-id {
      type uint32;
      description
        "Tunnel Endpoint Identifier";
    }
    leaf next-hop {
      type inet:ipv6-address;
      description
        "Next-hop IP address (v6 format)";
    }
    leaf output-label {
      type uint32;
      description
        "Output Label";
    }
    leaf reroute-label {
      type uint32;
      description
        "Reroute Label";
    }
    list issue {
      description
        "Issues with this path item";
      leaf entry {
        type live_ncs_Evpn-bag-path-issues;
        description
          "Issues with this path item";
      }
    }
    list srv6-sid-info {
      description
        "Array of SRv6 SID information";
      uses live_ncs_L2VPN-EVPN-SRV6-SID-INFO;
    }
  }

  grouping live_ncs_L2VPN-EVPN-SRV6-SID-INFO {
    description
      "SRv6 SID information for EVPN services";
    leaf srv6-sid {
      type inet:ipv6-address;
      description
        "SRv6 SID";
    }
  }

  grouping live_ncs_L2VPN-EVPN-EAD {
    description
      "L2VPN EVPN EAD database information";
    container evpn-instance {
      description
        "EVPN Instance summary information";
      uses live_ncs_L2VPN-EVPN-EVI-SUMMARY;
    }
    container layer2-attributes {
      description
        "Layer 2 Attributes";
      uses live_ncs_L2VPN-EVPN-L2-ATTRS;
    }
    leaf ethernet-tag-xr {
      type uint32;
      description
        "Ethernet Tag";
    }
    leaf local-next-hop {
      type inet:ipv6-address;
      description
        "Local nexthop IP";
    }
    leaf local-label {
      type uint32;
      description
        "Associated local label";
    }
    leaf is-local-ead {
      type boolean;
      description
        "Indication of EthernetAutoDiscovery Route is
         local";
    }
    leaf redundancy-single-active {
      type boolean;
      description
        "Single-active redundancy configured at remote
         EAD";
    }
    leaf redundancy-single-flow-active {
      type boolean;
      description
        "Single-flow-active redundancy configured at
         remote EAD";
    }
    list ethernet-segment-identifier {
      description
        "Ethernet Segment id";
      leaf entry {
        type uint8;
        description
          "Ethernet Segment id";
      }
    }
    list local-sid-array {
      description
        "Associated local SIDs";
      uses live_ncs_L2VPN-EVPN-SRV6-SID-INFO;
    }
    list path-buffer {
      description
        "Path List Buffer";
      uses live_ncs_L2VPN-LABEL-PATH-BUFFER;
    }
  }

  grouping live_ncs_L2VPN-EVPN-NEIGHBOR {
    description
      "L2VPN EVPN Neighbor database information";
    container evpn-instance {
      description
        "EVPN Instance summary information";
      uses live_ncs_L2VPN-EVPN-EVI-SUMMARY;
    }
    leaf neighbor {
      type inet:ipv6-address;
      description
        "Neighbor IP";
    }
    list leaf-evis {
      description
        "Leaf EVIs";
      leaf entry {
        type uint32;
        description
          "Leaf EVIs";
      }
    }
  }

  grouping live_ncs_L2VPN-RT-ES-IMPORT {
    description
      "L2VPN RT ES IMPORT";
    leaf high-bytes {
      type uint32;
      description
        "Top 4 bytes of ES Import";
    }
    leaf low-bytes {
      type uint16;
      description
        "Low 2 bytes of ES Import";
    }
  }

  grouping live_ncs_L2VPN-RT-V4ADDR {
    description
      "L2VPN RT V4ADDR";
    leaf ipv4-address {
      type inet:ipv4-address;
      description
        "IPv4 Address";
    }
    leaf two-byte-index {
      type uint16;
      description
        "2 Byte Index";
    }
  }

  grouping live_ncs_L2VPN-RT-4BYTE-AS {
    description
      "L2VPN RT 4BYTE AS";
    leaf four-byte-as {
      type uint32;
      description
        "4 Byte AS Number";
    }
    leaf two-byte-index {
      type uint16;
      description
        "2 Byte Index";
    }
  }

  grouping live_ncs_L2VPN-RT-2BYTE-AS {
    description
      "L2VPN RT 2BYTE AS";
    leaf two-byte-as {
      type uint16;
      description
        "2 Byte AS Number";
    }
    leaf four-byte-index {
      type uint32;
      description
        "4 Byte Index";
    }
  }

  grouping live_ncs_L2VPN-RT {
    description
      "L2VPN RT";
    container two-byte-as {
      // NCS drop when statement
      description
        "two byte as";
      uses live_ncs_L2VPN-RT-2BYTE-AS;
    }
    container four-byte-as {
      // NCS drop when statement
      description
        "four byte as";
      uses live_ncs_L2VPN-RT-4BYTE-AS;
    }
    container v4-addr {
      // NCS drop when statement
      description
        "v4 addr";
      uses live_ncs_L2VPN-RT-V4ADDR;
    }
    container es-import {
      // NCS drop when statement
      description
        "es import";
      uses live_ncs_L2VPN-RT-ES-IMPORT;
    }
    leaf rt {
      type live_ncs_L2vpn-ad-rt;
      description
        "RT";
    }
  }

  grouping live_ncs_L2VPN-RD-V4ADDR {
    description
      "L2VPN RD V4ADDR";
    leaf ipv4-address {
      type inet:ipv4-address;
      description
        "IPv4 Address";
    }
    leaf two-byte-index {
      type uint16;
      description
        "2 Byte Index";
    }
  }

  grouping live_ncs_L2VPN-RD-4BYTE-AS {
    description
      "L2VPN RD 4BYTE AS";
    leaf four-byte-as {
      type uint32;
      description
        "4 Byte AS Number";
    }
    leaf two-byte-index {
      type uint16;
      description
        "2 Byte Index";
    }
  }

  grouping live_ncs_L2VPN-RD-2BYTE-AS {
    description
      "L2VPN RD 2BYTE AS";
    leaf two-byte-as {
      type uint16;
      description
        "2 Byte AS Number";
    }
    leaf four-byte-index {
      type uint32;
      description
        "4 Byte Index";
    }
  }

  grouping live_ncs_L2VPN-RD-AUTO {
    description
      "L2VPN RD AUTO";
    leaf router-id {
      type inet:ipv4-address;
      description
        "BGP Router ID";
    }
    leaf auto-index {
      type uint16;
      description
        "Auto-generated Index";
    }
  }

  grouping live_ncs_L2VPN-RD {
    description
      "L2VPN RD";
    container auto {
      // NCS drop when statement
      description
        "auto";
      uses live_ncs_L2VPN-RD-AUTO;
    }
    container two-byte-as {
      // NCS drop when statement
      description
        "two byte as";
      uses live_ncs_L2VPN-RD-2BYTE-AS;
    }
    container four-byte-as {
      // NCS drop when statement
      description
        "four byte as";
      uses live_ncs_L2VPN-RD-4BYTE-AS;
    }
    container v4-addr {
      // NCS drop when statement
      description
        "v4 addr";
      uses live_ncs_L2VPN-RD-V4ADDR;
    }
    leaf rd {
      type live_ncs_L2vpn-ad-rd;
      description
        "RD";
    }
  }

  grouping live_ncs_L2VPN-EVPN-FLOW-LABEL {
    description
      "L2VPN EVPN FLOW LABEL";
    leaf static-flow-label {
      type boolean;
      description
        "Static flow label";
    }
    leaf global-flow-label {
      type boolean;
      description
        "Globally configured flow label";
    }
  }

  grouping live_ncs_L2VPN-EVPN-EVI-DETAIL {
    description
      "EVPN E-VPN ID database detail information";
    container evpn-instance {
      description
        "EVPN Instance summary information";
      uses live_ncs_L2VPN-EVPN-EVI-SUMMARY;
    }
    container flow-label {
      description
        "Flow Label Information";
      uses live_ncs_L2VPN-EVPN-FLOW-LABEL;
    }
    container rd-auto {
      description
        "Automatic Route Distingtuisher";
      uses live_ncs_L2VPN-RD;
    }
    container rd-configured {
      description
        "Configured Route Distinguisher";
      uses live_ncs_L2VPN-RD;
    }
    container rt-auto {
      description
        "Automatic Route Target";
      uses live_ncs_L2VPN-RT;
    }
    leaf evi-xr {
      type uint32;
      description
        "E-VPN id";
    }
    leaf encapsulation-xr {
      type uint8;
      description
        "EVPN Instance encapsulation";
    }
    leaf bd-name {
      type string;
      description
        "Bridge domain name";
    }
    leaf type {
      type live_ncs_L2vpn-evpn;
      description
        "Service Type";
    }
    leaf description {
      type string;
      description
        "EVI description";
    }
    leaf unicast-label {
      type uint32;
      description
        "Unicast Label";
    }
    leaf multicast-label {
      type uint32;
      description
        "Multicast Label";
    }
    leaf reroute-label {
      type uint32;
      description
        "Reroute Label";
    }
    leaf cw-disable {
      type boolean;
      description
        "Control-Word Disable";
    }
    leaf mtu-mismatch-ignore {
      type boolean;
      description
        "Ignore MTU Mismatch";
    }
    leaf mtu-zero-transmit {
      type boolean;
      description
        "Transmit MTU Zero";
    }
    leaf table-policy-name {
      type string;
      description
        "Table-policy Name";
    }
    leaf export-route-policy {
      type string;
      description
        "Export Route Policy";
    }
    leaf import-route-policy {
      type string;
      description
        "Import Route Policy";
    }
    leaf forward-class {
      type uint8;
      description
        "Forward Class attribute";
    }
    leaf rt-import-block-set {
      type boolean;
      description
        "Is Import RT None set";
    }
    leaf rt-export-block-set {
      type boolean;
      description
        "Is Export RT None set";
    }
    leaf advertise-mac {
      type boolean;
      description
        "Advertise MAC-only routes on this EVI";
    }
    leaf etree-leaf {
      type boolean;
      description
        "E-Tree Leaf Indication";
    }
    leaf etree-rt-leaf {
      type boolean;
      description
        "E-Tree Route-Target Leaf Indication";
    }
    leaf advertise-bvi-mac {
      type boolean;
      description
        "Advertise BVI MACs routes on this EVI";
    }
    leaf aliasing-disabled {
      type boolean;
      description
        "Route Aliasing is disabled";
    }
    leaf unknown-unicast-flooding-disabled {
      type boolean;
      description
        "Unknown-unicast flooding is disabled";
    }
    leaf reoriginate-disabled {
      type boolean;
      description
        "Route Re-origination is disabled";
    }
    leaf stitching {
      type boolean;
      description
        "EVPN Instance is Regular/Stitching side";
    }
    leaf multicast-source-connected {
      type boolean;
      description
        "EVI is connected to multicast source";
    }
    leaf bgp-implicit-import-disabled {
      type boolean;
      description
        "BGP implicit import is disabled";
    }
    leaf vrf-name {
      type string;
      description
        "L3 VRF name from BVI";
    }
    leaf preferred-nh-mode {
      type live_ncs_Evpn-pref-ecmp-nh-mode;
      description
        "Preferred Nexthop Mode";
    }
    leaf srv6-locator-name {
      type string;
      description
        "SRv6 Locator Name";
    }
  }

  grouping live_ncs_L2VPN-EVPN-SUMMARY {
    description
      "EVPN Information Summary";
    leaf router-id {
      type inet:ipv6-address;
      description
        "EVPN Router ID";
    }
    leaf as {
      type uint32;
      description
        "BGP AS number";
    }
    leaf ev-is {
      type uint32;
      description
        "Number of EVI DB Entries";
    }
    leaf tunnel-endpoints {
      type uint32;
      description
        "Number of Tunnel Endpoint DB Entries";
    }
    leaf local-mac-routes {
      type uint32;
      description
        "Number of Local MAC Routes";
    }
    leaf local-ipv4-mac-routes {
      type uint32;
      description
        "Number of Local IPv4 MAC-IP Routes";
    }
    leaf local-ipv6-mac-routes {
      type uint32;
      description
        "Number of Local IPv6 MAC-IP Routes";
    }
    leaf es-global-mac-routes {
      type uint32;
      description
        "Number of ES:Global MAC Routes";
    }
    leaf remote-mac-routes {
      type uint32;
      description
        "Number of Remote MAC Routes";
    }
    leaf remote-sync-mac-routes {
      type uint32;
      description
        "Number of Remote SYNC MAC Routes";
    }
    leaf remote-ipv4-mac-routes {
      type uint32;
      description
        "Number of Remote IPv4 MAC-IP Routes";
    }
    leaf remote-ipv6-mac-routes {
      type uint32;
      description
        "Number of Remote IPv6 MAC-IP Routes";
    }
    leaf local-imcast-routes {
      type uint32;
      description
        "Number of Local IMCAST Routes";
    }
    leaf remote-imcast-routes {
      type uint32;
      description
        "Number of Remote IMCAST Routes";
    }
    leaf labels {
      type uint32;
      description
        "Number of Internal Labels";
    }
    leaf sh-internal-ids {
      type uint32;
      description
        "Number of single-homed Internal IDs";
    }
    leaf mh-internal-ids {
      type uint32;
      description
        "Number of multi-homed Internal IDs";
    }
    leaf es-entries {
      type uint32;
      description
        "Number of ES Entries in DB";
    }
    leaf neighbor-entries {
      type uint32;
      description
        "Number of neighbor Entries in DB";
    }
    leaf local-ead-routes {
      type uint32;
      description
        "Number of Local EAD Entries in DB";
    }
    leaf remote-ead-routes {
      type uint32;
      description
        "Number of Remote EAD Entries in DB";
    }
    leaf global-source-mac {
      type yang:mac-address;
      description
        "Global Source MAC Address";
    }
    leaf peering-time {
      type uint32;
      units "second";
      description
        "EVPN ES Peering Time (seconds)";
    }
    leaf recovery-time {
      type uint32;
      units "second";
      description
        "EVPN ES Recovery Time (seconds)";
    }
    leaf carving-time {
      type uint32;
      units "second";
      description
        "EVPN ES Carving Time (seconds)";
    }
    leaf cost-out-configured {
      type boolean;
      description
        "EVPN node cost out via manual configuration";
    }
    leaf bundle-convergence-in-progress {
      type boolean;
      description
        "Bundle convergence in progress";
    }
    leaf node-costed-out {
      type boolean;
      description
        "EVPN Services costed out on node and holding
         Bundle interfaces down";
    }
    leaf startup-cost-in-time {
      type uint32;
      units "second";
      description
        "EVPN Node startup cost-in Time (seconds)";
    }
    leaf startup-cost-in-time-left {
      type uint32;
      units "millisecond";
      description
        "Milliseconds left on EVPN Node startup cost-in";
    }
    leaf mac-postpone-timer {
      type uint32;
      units "second";
      description
        "Configured timer for postponing MAC withdraws
         (seconds)";
    }
    leaf mac-postpone-timer-left {
      type uint32;
      units "millisecond";
      description
        "Milliseconds left on MAC withdraw postpone timer";
    }
    leaf l2rib-throttle {
      type boolean;
      description
        "Send to L2RIB Throttled";
    }
    leaf logging-df-election-enabled {
      type boolean;
      description
        "Logging EVPN Designated Forwarder changes
         enabled";
    }
  }

  grouping live_ncs_L2VPN-EVPN-EVI-SUMMARY {
    description
      "EVPN Instance summary information";
    leaf ethernet-vpn-id {
      type uint32;
      description
        "Ethernet VPN id";
    }
    leaf encapsulation-xr {
      type uint8;
      description
        "EVPN Instance transport encapsulation";
    }
    leaf bd-name {
      type string;
      description
        "Bridge domain name";
    }
    leaf type {
      type live_ncs_L2vpn-evpn;
      description
        "Service Type";
    }
  }

  grouping live_ncs_L2VPN-EVPN-IGMP-SUBIF-INFO {
    description
      "L2VPN EVPN IGMP SUBIF INFO";
    leaf vrf-id {
      type uint32;
      description
        "VRF id";
    }
  }

  grouping live_ncs_L2VPN-EVPN-IGMP-FWD-INFO {
    description
      "L2VPN EVPN IGMP FWD INFO";
    leaf bd-id {
      type uint32;
      description
        "BD id";
    }
  }

  grouping live_ncs_EVPN-IGMP-CHILD-INFO {
    description
      "EVPN IGMP CHILD INFO";
    container fwd-info {
      // NCS drop when statement
      description
        "fwd info";
      uses live_ncs_L2VPN-EVPN-IGMP-FWD-INFO;
    }
    container subif-info {
      // NCS drop when statement
      description
        "subif info";
      uses live_ncs_L2VPN-EVPN-IGMP-SUBIF-INFO;
    }
    leaf child-type {
      type live_ncs_Evpn-child;
      description
        "ChildType";
    }
  }

  grouping live_ncs_L2VPN-EVPN-IGMP-LOCAL-INFO {
    description
      "L2VPN EVPN IGMP LOCAL INFO";
    leaf if-name {
      type string {
        length "0..65";
      }
      description
        "Interface name internal format";
    }
  }

  grouping live_ncs_EVPN-IGMP-SRC-INFO {
    description
      "EVPN IGMP SRC INFO";
    container local-info {
      // NCS drop when statement
      description
        "local info";
      uses live_ncs_L2VPN-EVPN-IGMP-LOCAL-INFO;
    }
    leaf type {
      type live_ncs_Evpn-igmp-source;
      description
        "Type";
    }
    leaf remote-info {
      // NCS drop when statement
      type live_ncs_L2vpn-bag-in6-addr;
      description
        "remote info";
    }
  }

  grouping live_ncs_L2VPN-EVPN-IGMP {
    description
      "EVPN IGMP database information";
    container source-info {
      description
        "Source Info";
      uses live_ncs_EVPN-IGMP-SRC-INFO;
    }
    container child-info {
      description
        "Child Info";
      uses live_ncs_EVPN-IGMP-CHILD-INFO;
    }
    leaf evpn-client-type {
      type live_ncs_Evpn-client1;
      description
        "EVPN Client Type";
    }
    leaf ethernet-segment-name {
      type string;
      description
        "Ethernet Segment Name";
    }
    leaf evi-xr {
      type uint32;
      description
        "E-VPN id";
    }
    leaf route-type {
      type live_ncs_Evpn-igmp-msg;
      description
        "Route Type";
    }
    leaf source-addr {
      type inet:ipv6-address;
      description
        "Source IP Address";
    }
    leaf group-addr {
      type inet:ipv6-address;
      description
        "Group IP Address";
    }
    leaf ethernet-tag-id {
      type uint32;
      description
        "Ethernet Tag id";
    }
    leaf igmp-version {
      type live_ncs_Evpn-igmp-version;
      description
        "IGMP Version";
    }
    leaf igmp-group-type {
      type live_ncs_Evpn-igmp-grp;
      description
        "IGMP Group Type";
    }
    leaf max-response-time {
      type uint8;
      description
        "Max Response Time";
    }
    leaf resolved {
      type boolean;
      description
        "Resolved";
    }
    list ethernet-segment-identifier {
      description
        "Ethernet Segment id";
      leaf entry {
        type uint8;
        description
          "Ethernet Segment id";
      }
    }
  }

  grouping live_ncs_L2VPN-EVPN-CLIENT {
    description
      "EVPN Client Information";
    leaf client-type {
      type live_ncs_Evpn-client1;
      description
        "Client Type";
    }
  }

  grouping live_ncs_L2VPN-EVPN-REMOTE-SHG-INFO {
    description
      "L2VPN EVPN remote split horizon group labels";
    leaf next-hop {
      type inet:ipv6-address;
      description
        "Next-hop IP address (v6 format)";
    }
    leaf label {
      type uint32;
      description
        "Split horizon label associated with next-hop
         address";
    }
  }

  grouping live_ncs_L2VPN-EVPN-REMOTE-SHG {
    description
      "EVPN Remote SHG object";
    leaf ethernet-vpn-id {
      type uint32;
      description
        "Ethernet VPN id";
    }
    leaf encapsulation {
      type uint8;
      description
        "EVPN Instance transport encapsulation";
    }
    list ethernet-segment-identifier {
      description
        "Ethernet Segment id";
      leaf entry {
        type uint8;
        description
          "Ethernet Segment id";
      }
    }
    list remote-split-horizon-group-label {
      description
        "Remote split horizon group labels";
      uses live_ncs_L2VPN-EVPN-REMOTE-SHG-INFO;
    }
  }

  grouping live_ncs_EVPN-GRP-INTF-INFO {
    description
      "EVPN Group Interface Information";
    leaf interface-name {
      type string;
      description
        "Interface name";
    }
    leaf state {
      type live_ncs_Im-state-enum;
      description
        "Interface State";
    }
  }

  grouping live_ncs_EVPN-GRP-INFO {
    description
      "EVPN Group Information";
    leaf group-id {
      type uint32;
      description
        "EVPN Group ID";
    }
    leaf state {
      type live_ncs_Evpn-grp;
      description
        "EVPN Group State";
    }
    list core-interface {
      description
        "EVPN Group Core Interface table";
      uses live_ncs_EVPN-GRP-INTF-INFO;
    }
    list access-interface {
      description
        "EVPN Access Core Interface table";
      uses live_ncs_EVPN-GRP-INTF-INFO;
    }
  }

  grouping L2VPN-ATOM-ACID {
    description
      "L2VPN ATOM ACID";
    leaf source-ac-id {
      type uint32;
      description
        "Source AC ID";
    }
    leaf target-ac-id {
      type uint32;
      description
        "Target AC ID";
    }
    leaf vpn-id {
      type uint32;
      description
        "VPN ID";
    }
    leaf taii-global-id {
      type uint32;
      description
        "TAII Global ID";
    }
    leaf taii-ac-id {
      type uint32;
      description
        "TAII AC ID";
    }
    leaf taii-prefix {
      type inet:ipv6-address;
      description
        "TAII Prefix";
    }
  }

  grouping L2VPN-EVPN-EAD-SERVICE-INFO {
    description
      "L2VPN EVPN EAD Ethernet Tag";
    leaf vpn-id {
      type uint32;
      description
        "VPN ID";
    }
    leaf type {
      type L2vpn-evpn;
      description
        "Service Type";
    }
    leaf ethernet-tag {
      type uint32;
      description
        "Ethernet Tag";
    }
  }

  grouping L2VPN-BAG-TIMESPEC {
    description
      "L2VPN Timespec Data Structure";
    leaf tv-sec {
      type uint32;
      description
        "tv sec";
    }
    leaf tv-nsec {
      type uint32;
      description
        "tv nsec";
    }
  }

  grouping L2VPN-STAT-ITEM {
    description
      "L2VPN EVPN Ethernet Segment (ES) private stats
       item";
    container last-time {
      description
        "last time";
      uses L2VPN-BAG-TIMESPEC;
    }
    leaf count {
      type uint32;
      description
        "count";
    }
    leaf last-arg {
      type uint32;
      description
        "last arg";
    }
  }

  grouping L2VPN-EVPN-ES-NH-BUFFER {
    description
      "L2VPN EVPN Ethernet Segment (ES) nexthops
       information";
    leaf next-hop {
      type inet:ipv6-address;
      description
        "Next-hop IP address (v6 format)";
    }
    leaf df-dont-preempt {
      type boolean;
      description
        "DF Dont Preemption";
    }
    leaf df-type {
      type uint8;
      description
        "DF Election Mode Configured";
    }
    leaf df-pref {
      type uint16;
      description
        "DF Election Preference Set";
    }
    leaf df-ntp-enabled {
      type boolean;
      description
        "NTP based DF Election Synchronization";
    }
    leaf ntp-sct-microseconds {
      type uint64;
      units "microsecond";
      description
        "NTP based SCT: represented in microseconds
         relative to Unix epoch: 1st Jan 1970";
    }
  }

  grouping L2VPN-EVPN-ES {
    description
      "EVPN Ethernet Segment (ES) database information";
    container msti-flush-count {
      description
        "Statistics for Host-mobility driven flush
         operations";
      uses L2VPN-STAT-ITEM;
    }
    leaf esi-type {
      type L2vpn-evpn-esi;
      description
        "ESI Type";
    }
    leaf esi-system-identifier {
      type string;
      description
        "ESI System Identifier";
    }
    leaf esi-port-key {
      type uint32;
      description
        "ESI Port Key";
    }
    leaf esi-system-priority {
      type uint32;
      description
        "ESI System Priority";
    }
    leaf ethernet-segment-name {
      type string;
      description
        "Ethernet Segment Name";
    }
    leaf ethernet-segment-state {
      type L2vpn-evpn-es-state;
      description
        "State of the ethernet segment";
    }
    leaf in-staggered-bringup {
      type boolean;
      description
        "Is this ES in the staggered bring-up queue?";
    }
    leaf if-handle {
      type xr:Interface-name;
      description
        "Main port ifhandle";
    }
    leaf main-port-role {
      type L2vpn-rg-role;
      description
        "Main port redundancy group role";
    }
    leaf main-port-mac {
      type yang:mac-address;
      description
        "Main Port MAC Address";
    }
    leaf num-up-p-ws {
      type uint32;
      description
        "Number of PWs in Up state";
    }
    leaf route-target {
      type yang:mac-address;
      description
        "ES-Import Route Target";
    }
    leaf rt-origin {
      type L2vpn-evpn-rt-origin;
      description
        "Origin of operational ES-Import RT";
    }
    leaf es-bgp-gates {
      type string;
      description
        "ES BGP Gates";
    }
    leaf es-l2fib-gates {
      type string;
      description
        "ES L2FIB Gates";
    }
    leaf mac-flushing-mode-config {
      type L2vpn-evpn-mf-mode;
      description
        "Configured MAC Flushing mode";
    }
    leaf load-balance-mode-config {
      type L2vpn-evpn-lb-mode;
      description
        "Configured load balancing mode";
    }
    leaf load-balance-mode-is-default {
      type boolean;
      description
        "Load balancing mode is default";
    }
    leaf load-balance-mode-oper {
      type L2vpn-evpn-lb-mode;
      description
        "Operational load balancing mode";
    }
    leaf force-single-home {
      type boolean;
      description
        "Ethernet-Segment forced to single home";
    }
    leaf convergence-mac-mobility {
      type boolean;
      description
        "Fast convergence mode based on MAC-mobility.";
    }
    leaf convergence-reroute {
      type boolean;
      description
        "Fast convergence mode based on reroute to backup
         peer.";
    }
    leaf convergence-nh-tracking {
      type boolean;
      description
        "Fast DF-Election based on tracking peer BGP
         Nexthop reachability";
    }
    leaf source-mac-oper {
      type yang:mac-address;
      description
        "Operational Source MAC address";
    }
    leaf source-mac-origin {
      type L2vpn-evpn-smac-src;
      description
        "Origin of operational source MAC address";
    }
    leaf peering-timer {
      type uint32;
      units "second";
      description
        "Configured timer for triggering DF election
         (seconds)";
    }
    leaf peering-timer-left {
      type uint32;
      units "millisecond";
      description
        "Milliseconds left on DF election timer";
    }
    leaf recovery-timer {
      type uint32;
      units "second";
      description
        "Configured timer for (STP) recovery (seconds)";
    }
    leaf recovery-timer-left {
      type uint32;
      units "millisecond";
      description
        "Milliseconds left on (STP) recovery timer";
    }
    leaf carving-timer {
      type uint32;
      units "second";
      description
        "Configured timer for delaying DF election
         (seconds)";
    }
    leaf carving-timer-left {
      type uint32;
      units "millisecond";
      description
        "Milliseconds left on carving timer";
    }
    leaf hrw-reset-timer {
      type uint32;
      units "second";
      description
        "Configured timer for HRW reset (seconds)";
    }
    leaf hrw-reset-timer-left {
      type uint32;
      units "millisecond";
      description
        "Milliseconds left on HRW reset timer";
    }
    leaf service-carving-mode {
      type L2vpn-evpn-sc-mode;
      description
        "Service carving mode";
    }
    leaf service-carving-synchronization-mode {
      type L2vpn-evpn-sc-synchronization-mode;
      description
        "Service carving synchronization mode";
    }
    leaf service-carving-mcast-mode {
      type L2vpn-evpn-sc-mcast-mode;
      description
        "Service carving multicast mode";
    }
    leaf primary-services-input {
      type string;
      description
        "Input string of Primary services ESI/I-SIDs";
    }
    leaf secondary-services-input {
      type string;
      description
        "Input string of Secondary services ESI/I-SIDs";
    }
    leaf preferential-df-configured-weight {
      type uint16;
      description
        "Configured Weight for Preferential DF Election";
    }
    leaf preferential-df-operational-weight {
      type uint16;
      description
        "Operational Weight for Preferential DF Election";
    }
    leaf access-driven-df-election {
      type boolean;
      description
        "Access Driven DF Election is active";
    }
    leaf forwarder-ports {
      type uint32;
      description
        "Count of Forwarders (AC, AC PW, VFI PW)";
    }
    leaf permanent-forwarder-ports {
      type uint32;
      description
        "Count of Forwarders with permanent service";
    }
    leaf elected-forwarder-ports {
      type uint32;
      description
        "Count of Forwarders with elected service";
    }
    leaf not-elected-forwarder-ports {
      type uint32;
      description
        "Count of Forwarders with not elected service";
    }
    leaf not-config-forwarder-ports {
      type uint32;
      description
        "Count of forwarders with missing config detected";
    }
    leaf mp-protected {
      type boolean;
      description
        "MP is protected and not under EVPN control";
    }
    leaf nve-anycast-vtep {
      type boolean;
      description
        "Anycast VTEP mode on NVE main-interface";
    }
    leaf nve-ingress-replication {
      type boolean;
      description
        "Ingress-Replication is configured on NVE
         main-interface";
    }
    leaf msti-flush-debounce {
      type uint32;
      description
        "Value of scale-dependant debouncing";
    }
    leaf tracked-bgp-nexthop {
      type inet:ipv6-address;
      description
        "Reachability-tracked BGP Nexthop";
    }
    leaf local-split-horizon-group-label-valid {
      type boolean;
      description
        "Local split horizon group label is valid";
    }
    leaf local-split-horizon-group-label {
      type uint32;
      description
        "Local split horizon group label";
    }
    leaf access-signal-mode {
      type L2vpn-evpn-es-access-signal-mode;
      description
        "Operational access signal mode";
    }
    list ethernet-segment-identifier {
      description
        "Ethernet Segment id";
      leaf entry {
        type uint8;
        description
          "Ethernet Segment id";
      }
    }
    list primary-service {
      description
        "List of Primary services ESI/I-SIDs";
      leaf entry {
        type uint32;
        description
          "List of Primary services ESI/I-SIDs";
      }
    }
    list secondary-service {
      description
        "List of Secondary services ESI/I-SIDs";
      leaf entry {
        type uint32;
        description
          "List of Secondary services ESI/I-SIDs";
      }
    }
    list service-carving-i-sidelected-result {
      description
        "Elected ISID service carving results";
      leaf entry {
        type uint32;
        description
          "Elected ISID service carving results";
      }
    }
    list service-carving-isid-not-elected-result {
      description
        "Not elected ISID service carving results";
      leaf entry {
        type uint32;
        description
          "Not elected ISID service carving results";
      }
    }
    list service-carving-evi-elected-result {
      description
        "Elected EVI service carving results";
      leaf entry {
        type uint32;
        description
          "Elected EVI service carving results";
      }
    }
    list service-carving-evi-not-elected-result {
      description
        "Not elected EVI service carving results";
      leaf entry {
        type uint32;
        description
          "Not elected EVI service carving results";
      }
    }
    list service-carving-vni-elected-result {
      description
        "Elected VNI service carving results";
      leaf entry {
        type uint32;
        description
          "Elected VNI service carving results";
      }
    }
    list service-carving-vni-not-elected-result {
      description
        "Not elected VNI service carving results";
      leaf entry {
        type uint32;
        description
          "Not elected VNI service carving results";
      }
    }
    list next-hop {
      description
        "List of nexthop IPv6 addresses";
      uses L2VPN-EVPN-ES-NH-BUFFER;
    }
    list service-carving-evpn-vpws-primary-result {
      description
        "EVPN VPWS service carving primary results";
      uses L2VPN-EVPN-EAD-SERVICE-INFO;
    }
    list service-carving-evpn-vpws-backup-result {
      description
        "EVPN VPWS service carving backup results";
      uses L2VPN-EVPN-EAD-SERVICE-INFO;
    }
    list service-carving-evpn-vpws-ndf-result {
      description
        "EVPN VPWS service carving non-DF results";
      uses L2VPN-EVPN-EAD-SERVICE-INFO;
    }
    list remote-split-horizon-group-label {
      description
        "Remote split horizon group labels";
      uses L2VPN-EVPN-REMOTE-SHG-INFO;
    }
  }

  grouping EVPN-SRV6-LOCATOR-INFO {
    description
      "EVPN SRv6 Locator information";
    leaf locator-name {
      type string;
      description
        "SRv6 Locator name";
    }
    leaf locator-prefix {
      type inet:ipv6-address;
      description
        "SRv6 Locator prefix";
    }
    leaf locator-length {
      type uint8;
      description
        "SRv6 Locator length";
    }
    leaf oor-state {
      type boolean;
      description
        "Out of Resources state";
    }
    leaf in-use {
      type boolean;
      description
        "In use by services";
    }
    leaf service-count {
      type uint32;
      description
        "Number of services using this locator implicitly
         and explicitly";
    }
    leaf sid-count {
      type uint32;
      description
        "Number of SIDs allocated by services for this
         locator";
    }
    leaf is-default {
      type boolean;
      description
        "Configured default locator";
    }
    list evi {
      description
        "List of EVIs with this locator explicitly

         configured";
      leaf entry {
        type uint32;
        description
          "List of EVIs with this locator explicitly

           configured";
      }
    }
    list pw {
      description
        "List of VPWS services with this locator
         explicitly configured";
      uses EVPN-SRV6-VPWS-KEY;
    }
  }

  grouping EVPN-SRV6-VPWS-KEY {
    description
      "EVPN SRv6 VPWS service key";
    leaf evi {
      type uint32;
      description
        "EVI for the VPWS service";
    }
    leaf acid {
      type uint32;
      description
        "Attachment circuit ID for the VPWS service";
    }
  }

  grouping L2VPN-EVPN-SRV6 {
    description
      "EVPN SRv6 info object";
    leaf enabled {
      type boolean;
      description
        "SRv6 Enabled";
    }
    leaf configured-default-locator {
      type string;
      description
        "Configured default SRv6 locator";
    }
    list unknown-locator-evi {
      description
        "List of EVIs with unknown locator names

         configured";
      leaf entry {
        type uint32;
        description
          "List of EVIs with unknown locator names

           configured";
      }
    }
    list unknown-locator-vpws {
      description
        "List of VPWS services with unknown locator names
         configured";
      uses EVPN-SRV6-VPWS-KEY;
    }
    list locator {
      description
        "List of locators from L3RIB";
      uses EVPN-SRV6-LOCATOR-INFO;
    }
  }

  grouping L2VPN-EVPN-LABEL {
    description
      "EVPN Internal Label database information";
    container evpn-instance {
      description
        "EVPN Instance summary information";
      uses L2VPN-EVPN-EVI-SUMMARY;
    }
    leaf esi {
      type yang:hex-string;
      description
        "Ethernet Segment id";
    }
    leaf tag {
      type uint32;
      description
        "Label Tag";
    }
    leaf internal-label {
      type uint32;
      description
        "MPLS Internal Label";
    }
    leaf alternate-internal-label {
      type uint32;
      description
        "Alternate MPLS Internal Label";
    }
    leaf internal-id {
      type uint32;
      description
        "SRv6 Internal ID";
    }
    leaf resolved {
      type boolean;
      description
        "Internal Label has resolved per-ES EAD and
         per-EVI EAD or MAC routes";
    }
    leaf unresolved-reason {
      type Evpn-bag-label-unresolved-reason;
      description
        "Optional reason why the label entry has not been
         resolved";
    }
    leaf preferred-nh-mode {
      type Evpn-pref-ecmp-nh-mode;
      description
        "Preferred ECMP Nexthop Mode";
    }
    leaf redundancy-single-active {
      type boolean;
      description
        "Single-active redundancy configured at remote ES";
    }
    leaf redundancy-single-flow-active {
      type boolean;
      description
        "Single-flow-active redundancy at remote ES
         (MST-AG)";
    }
    list mac-path-buffer {
      description
        "MAC Path list buffer";
      uses L2VPN-LABEL-PATH-BUFFER;
    }
    list ead-path-buffer {
      description
        "EAD/ES Path list buffer";
      uses L2VPN-LABEL-PATH-BUFFER;
    }
    list evi-path-buffer {
      description
        "EAD/EVI Path list buffer";
      uses L2VPN-LABEL-PATH-BUFFER;
    }
    list union-path-buffer {
      description
        "Union Path list buffer";
      uses L2VPN-LABEL-PATH-BUFFER;
    }
    list summary-path-buffer {
      description
        "Summary Path list buffer";
      uses L2VPN-LABEL-PATH-BUFFER;
    }
    list alternate-summary-path-buffer {
      description
        "Alternate Summary Path list buffer";
      uses L2VPN-LABEL-PATH-BUFFER;
    }
  }

  grouping L2VPN-EVPN-TEP-INFO {
    description
      "L2VPN EVPN TEP INFO";
    leaf ethernet-vpn-id {
      type uint32;
      description
        "Ethernet VPN id";
    }
    leaf encapsulation {
      type uint8;
      description
        "EVPN Tunnel encapsulation";
    }
    leaf ip {
      type inet:ipv6-address;
      description
        "IP address (v6 format)";
    }
  }

  grouping L2VPN-EVPN-TEP {
    description
      "EVPN Tunnel Endpoint database information";
    container local-info {
      description
        "Local TEP Information";
      uses L2VPN-EVPN-TEP-INFO;
    }
    container remote-info {
      description
        "Remote TEP Information";
      uses L2VPN-EVPN-TEP-INFO;
    }
    leaf tunnel-endpoint-id {
      type uint32;
      description
        "Tunnel Endpoint id";
    }
    leaf type {
      type uint8;
      description
        "EVPN Tunnel Endpoint Type";
    }
    leaf use-count {
      type uint32;
      description
        "in-use counter";
    }
    leaf vrf-name {
      type string;
      description
        "VRF Name";
    }
    leaf vrf-table-id {
      type uint32;
      description
        "VRF Table Id in RIB";
    }
    leaf udp-port {
      type uint16;
      description
        "UDP port";
    }
  }

  grouping L2VPN-EVPN-TEP-NOTIFICATION-ENTRY {
    description
      "EVPN Tunnel Endpoint notification entry
       information";
    leaf entry-name {
      type string;
      description
        "Entry Name";
    }
  }

  grouping L2VPN-EVPN-MAC {
    description
      "L2VPN EVPN MAC database information";
    container evpn-instance {
      description
        "EVPN Instance summary information";
      uses L2VPN-EVPN-EVI-SUMMARY;
    }
    leaf ethernet-tag-xr {
      type uint32;
      description
        "Ethernet Tag";
    }
    leaf mac-address-xr {
      type yang:mac-address;
      description
        "MAC address";
    }
    leaf ip-address-xr {
      type inet:ipv6-address;
      description
        "IP address (v6 format)";
    }
    leaf local-label {
      type uint32;
      description
        "Associated local label";
    }
    leaf is-local-mac {
      type boolean;
      description
        "Indication of MAC being locally generated";
    }
    leaf is-proxy-entry {
      type boolean;
      description
        "Proxy entry";
    }
    leaf is-remote-mac {
      type boolean;
      description
        "Indication of MAC being remotely generated";
    }
    leaf soo-nexthop {
      type inet:ipv6-address;
      description
        "SOO nexthop (v6 format)";
    }
    leaf ipnh-address {
      type inet:ipv6-address;
      description
        "IP nexthop address (v6 format)";
    }
    leaf esi-port-key {
      type uint16;
      description
        "ESI port key";
    }
    leaf local-encap-type {
      type uint8;
      description
        "Encap type of local MAC";
    }
    leaf remote-encap-type {
      type uint8;
      description
        "Encap type of remote MAC";
    }
    leaf learned-bridge-port-name {
      type string;
      description
        "Port the MAC was learned on";
    }
    leaf local-seq-id {
      type uint32;
      description
        "local seq id";
    }
    leaf remote-seq-id {
      type uint32;
      description
        "remote seq id";
    }
    leaf local-l3-label {
      type uint32;
      description
        "local l3 label";
    }
    leaf router-mac-address {
      type yang:mac-address;
      description
        "Router MAC address";
    }
    leaf mac-flush-requested {
      type uint16;
      description
        "Number of flushes requested ";
    }
    leaf mac-flush-received {
      type uint16;
      description
        "Number of flushes received ";
    }
    leaf internal-label {
      type uint32;
      description
        "MPLS Internal Label";
    }
    leaf resolved {
      type boolean;
      description
        "Internal Label has resolved per-ES EAD and
         per-EVI EAD or MAC routes";
    }
    leaf local-is-static {
      type boolean;
      description
        "Indication if Local MAC is statically configured";
    }
    leaf remote-is-static {
      type boolean;
      description
        "Indication if Remote MAC is statically
         configured";
    }
    leaf local-etree-leaf {
      type boolean;
      description
        "Local E-Tree Leaf Indication";
    }
    leaf remote-etree-leaf {
      type boolean;
      description
        "Remote E-Tree Leaf Indication";
    }
    leaf remote-etree-rt-leaf {
      type boolean;
      description
        "Remote MAC matching E-Tree Route-Target Leaf";
    }
    leaf local-attachment-circuit-id {
      type uint32;
      description
        "Local Attachement Circuit ID used in
         ac-aware-vlan-bundling";
    }
    leaf remote-attachment-circuit-id {
      type uint32;
      description
        "Remote Attachement Circuit ID used in
         ac-aware-vlan-bundling";
    }
    list local-ethernet-segment-identifier {
      description
        "Local Ethernet Segment id";
      leaf entry {
        type uint8;
        description
          "Local Ethernet Segment id";
      }
    }
    list remote-ethernet-segment-identifier {
      description
        "Remote Ethernet Segment id";
      leaf entry {
        type uint8;
        description
          "Remote Ethernet Segment id";
      }
    }
    list path-buffer {
      description
        "Path List Buffer";
      uses L2VPN-LABEL-PATH-BUFFER;
    }
  }

  grouping L2VPN-EVPN-EVI-BGP-RT {
    description
      "EVPN Instance Route Target information";
    container evpn-instance {
      description
        "EVPN Instance summary information";
      uses L2VPN-EVPN-EVI-SUMMARY;
    }
    container route-target {
      description
        "Route Target";
      uses L2VPN-RT;
    }
    leaf route-target-role {
      type L2vpn-ad-rt-role;
      description
        "RT Role";
    }
    leaf route-target-stitching {
      type boolean;
      description
        "RT Stitching";
    }
  }

  grouping L2VPN-EVPN-IMCAST {
    description
      "L2VPN EVPN Inclusive Multicast database
       information";
    container evpn-instance {
      description
        "EVPN Instance summary information";
      uses L2VPN-EVPN-EVI-SUMMARY;
    }
    container sr-te-info {
      description
        "SR(v6)-TE Policy info from ODN";
      uses L2VPN-EVPN-SRTE-INFO;
    }
    leaf ethernet-tag-xr {
      type uint32;
      description
        "Ethernet Tag";
    }
    leaf originating-ip-xr {
      type inet:ipv6-address;
      description
        "Originating IP";
    }
    leaf tunnel-endpoint-id {
      type uint32;
      description
        "Tunnel Endpoint ID";
    }
    leaf pmsi-tunnel-type {
      type uint32;
      description
        "PMSI Tunnel Type";
    }
    leaf next-hop {
      type inet:ipv6-address;
      description
        "IP of nexthop";
    }
    leaf output-label {
      type uint32;
      description
        "Output label";
    }
    leaf is-local-entry {
      type boolean;
      description
        "Local entry";
    }
    leaf is-proxy-entry {
      type boolean;
      description
        "Proxy entry";
    }
    leaf etree-leaf {
      type boolean;
      description
        "E-Tree Leaf Indication";
    }
  }

  grouping L2VPN-EVPN-L2-ATTRS {
    description
      "L2VPN EVPN L2 ATTRS";
    leaf mtu {
      type uint16;
      description
        "Maximum Transmission Unit";
    }
    leaf designated-forwarder-role {
      type Evpn-bag-df-role;
      description
        "Designated Forwarder Role";
    }
    leaf control-word {
      type Evpn-bag-l2-attr-cw;
      description
        "Control Word";
    }
  }

  grouping L2VPN-EVPN-SRTE-INFO {
    description
      "L2VPN EVPN SRTE INFO";
    leaf sr-te-type {
      type uint8;
      description
        "Type of SR-TE Policy path from ODN";
    }
    leaf sr-te-interface-name {
      type xr:Interface-name;
      description
        "SR Traffic Engineering Interface Name";
    }
    leaf sr-te-bsid {
      type uint32;
      description
        "SR Traffic Engineering Binding-SID (Label)";
    }
    leaf srv6-te-bsid {
      type inet:ipv6-address;
      description
        "SRv6 Traffic Engineering Binding-SID";
    }
  }

  grouping L2VPN-LABEL-PATH-BUFFER {
    description
      "L2VPN LABEL PATH BUFFER";
    container sr-te-info {
      description
        "SR(v6)-TE Policy info from ODN";
      uses L2VPN-EVPN-SRTE-INFO;
    }
    container layer2-attributes {
      description
        "Layer 2 Attributes";
      uses L2VPN-EVPN-L2-ATTRS;
    }
    leaf tunnel-endpoint-id {
      type uint32;
      description
        "Tunnel Endpoint Identifier";
    }
    leaf next-hop {
      type inet:ipv6-address;
      description
        "Next-hop IP address (v6 format)";
    }
    leaf output-label {
      type uint32;
      description
        "Output Label";
    }
    leaf reroute-label {
      type uint32;
      description
        "Reroute Label";
    }
    list issue {
      description
        "Issues with this path item";
      leaf entry {
        type Evpn-bag-path-issues;
        description
          "Issues with this path item";
      }
    }
    list srv6-sid-info {
      description
        "Array of SRv6 SID information";
      uses L2VPN-EVPN-SRV6-SID-INFO;
    }
  }

  grouping L2VPN-EVPN-SRV6-SID-INFO {
    description
      "SRv6 SID information for EVPN services";
    leaf srv6-sid {
      type inet:ipv6-address;
      description
        "SRv6 SID";
    }
  }

  grouping L2VPN-EVPN-EAD {
    description
      "L2VPN EVPN EAD database information";
    container evpn-instance {
      description
        "EVPN Instance summary information";
      uses L2VPN-EVPN-EVI-SUMMARY;
    }
    container layer2-attributes {
      description
        "Layer 2 Attributes";
      uses L2VPN-EVPN-L2-ATTRS;
    }
    leaf ethernet-tag-xr {
      type uint32;
      description
        "Ethernet Tag";
    }
    leaf local-next-hop {
      type inet:ipv6-address;
      description
        "Local nexthop IP";
    }
    leaf local-label {
      type uint32;
      description
        "Associated local label";
    }
    leaf is-local-ead {
      type boolean;
      description
        "Indication of EthernetAutoDiscovery Route is
         local";
    }
    leaf redundancy-single-active {
      type boolean;
      description
        "Single-active redundancy configured at remote
         EAD";
    }
    leaf redundancy-single-flow-active {
      type boolean;
      description
        "Single-flow-active redundancy configured at
         remote EAD";
    }
    list ethernet-segment-identifier {
      description
        "Ethernet Segment id";
      leaf entry {
        type uint8;
        description
          "Ethernet Segment id";
      }
    }
    list local-sid-array {
      description
        "Associated local SIDs";
      uses L2VPN-EVPN-SRV6-SID-INFO;
    }
    list path-buffer {
      description
        "Path List Buffer";
      uses L2VPN-LABEL-PATH-BUFFER;
    }
  }

  grouping L2VPN-EVPN-NEIGHBOR {
    description
      "L2VPN EVPN Neighbor database information";
    container evpn-instance {
      description
        "EVPN Instance summary information";
      uses L2VPN-EVPN-EVI-SUMMARY;
    }
    leaf neighbor {
      type inet:ipv6-address;
      description
        "Neighbor IP";
    }
    list leaf-evis {
      description
        "Leaf EVIs";
      leaf entry {
        type uint32;
        description
          "Leaf EVIs";
      }
    }
  }

  grouping L2VPN-RT-ES-IMPORT {
    description
      "L2VPN RT ES IMPORT";
    leaf high-bytes {
      type uint32;
      description
        "Top 4 bytes of ES Import";
    }
    leaf low-bytes {
      type uint16;
      description
        "Low 2 bytes of ES Import";
    }
  }

  grouping L2VPN-RT-V4ADDR {
    description
      "L2VPN RT V4ADDR";
    leaf ipv4-address {
      type inet:ipv4-address;
      description
        "IPv4 Address";
    }
    leaf two-byte-index {
      type uint16;
      description
        "2 Byte Index";
    }
  }

  grouping L2VPN-RT-4BYTE-AS {
    description
      "L2VPN RT 4BYTE AS";
    leaf four-byte-as {
      type uint32;
      description
        "4 Byte AS Number";
    }
    leaf two-byte-index {
      type uint16;
      description
        "2 Byte Index";
    }
  }

  grouping L2VPN-RT-2BYTE-AS {
    description
      "L2VPN RT 2BYTE AS";
    leaf two-byte-as {
      type uint16;
      description
        "2 Byte AS Number";
    }
    leaf four-byte-index {
      type uint32;
      description
        "4 Byte Index";
    }
  }

  grouping L2VPN-RT {
    description
      "L2VPN RT";
    container two-byte-as {
      when "../rt = 'l2vpn-ad-rt-as'" {
        tailf:xpath-root 3;
        description
          "../RT = 'L2VPN_AD_RT_AS'";
      }
      description
        "two byte as";
      uses L2VPN-RT-2BYTE-AS;
    }
    container four-byte-as {
      when "../rt = 'l2vpn-ad-rt-4byte-as'" {
        tailf:xpath-root 3;
        description
          "../RT = 'L2VPN_AD_RT_4BYTE_AS'";
      }
      description
        "four byte as";
      uses L2VPN-RT-4BYTE-AS;
    }
    container v4-addr {
      when "../rt = 'l2vpn-ad-rt-v4-addr'" {
        tailf:xpath-root 3;
        description
          "../RT = 'L2VPN_AD_RT_V4ADDR'";
      }
      description
        "v4 addr";
      uses L2VPN-RT-V4ADDR;
    }
    container es-import {
      when "../rt = 'es-import'" {
        tailf:xpath-root 3;
        description
          "../RT = 'ES_Import'";
      }
      description
        "es import";
      uses L2VPN-RT-ES-IMPORT;
    }
    leaf rt {
      type L2vpn-ad-rt;
      description
        "RT";
    }
  }

  grouping L2VPN-RD-V4ADDR {
    description
      "L2VPN RD V4ADDR";
    leaf ipv4-address {
      type inet:ipv4-address;
      description
        "IPv4 Address";
    }
    leaf two-byte-index {
      type uint16;
      description
        "2 Byte Index";
    }
  }

  grouping L2VPN-RD-4BYTE-AS {
    description
      "L2VPN RD 4BYTE AS";
    leaf four-byte-as {
      type uint32;
      description
        "4 Byte AS Number";
    }
    leaf two-byte-index {
      type uint16;
      description
        "2 Byte Index";
    }
  }

  grouping L2VPN-RD-2BYTE-AS {
    description
      "L2VPN RD 2BYTE AS";
    leaf two-byte-as {
      type uint16;
      description
        "2 Byte AS Number";
    }
    leaf four-byte-index {
      type uint32;
      description
        "4 Byte Index";
    }
  }

  grouping L2VPN-RD-AUTO {
    description
      "L2VPN RD AUTO";
    leaf router-id {
      type inet:ipv4-address;
      description
        "BGP Router ID";
    }
    leaf auto-index {
      type uint16;
      description
        "Auto-generated Index";
    }
  }

  grouping L2VPN-RD {
    description
      "L2VPN RD";
    container auto {
      when "../rd = 'l2vpn-ad-rd-auto'" {
        tailf:xpath-root 3;
        description
          "../RD = 'L2VPN_AD_RD_AUTO'";
      }
      description
        "auto";
      uses L2VPN-RD-AUTO;
    }
    container two-byte-as {
      when "../rd = 'l2vpn-ad-rd-as'" {
        tailf:xpath-root 3;
        description
          "../RD = 'L2VPN_AD_RD_AS'";
      }
      description
        "two byte as";
      uses L2VPN-RD-2BYTE-AS;
    }
    container four-byte-as {
      when "../rd = 'l2vpn-ad-rd-4byte-as'" {
        tailf:xpath-root 3;
        description
          "../RD = 'L2VPN_AD_RD_4BYTE_AS'";
      }
      description
        "four byte as";
      uses L2VPN-RD-4BYTE-AS;
    }
    container v4-addr {
      when "../rd = 'l2vpn-ad-rd-v4-addr'" {
        tailf:xpath-root 3;
        description
          "../RD = 'L2VPN_AD_RD_V4ADDR'";
      }
      description
        "v4 addr";
      uses L2VPN-RD-V4ADDR;
    }
    leaf rd {
      type L2vpn-ad-rd;
      description
        "RD";
    }
  }

  grouping L2VPN-EVPN-FLOW-LABEL {
    description
      "L2VPN EVPN FLOW LABEL";
    leaf static-flow-label {
      type boolean;
      description
        "Static flow label";
    }
    leaf global-flow-label {
      type boolean;
      description
        "Globally configured flow label";
    }
  }

  grouping L2VPN-EVPN-EVI-DETAIL {
    description
      "EVPN E-VPN ID database detail information";
    container evpn-instance {
      description
        "EVPN Instance summary information";
      uses L2VPN-EVPN-EVI-SUMMARY;
    }
    container flow-label {
      description
        "Flow Label Information";
      uses L2VPN-EVPN-FLOW-LABEL;
    }
    container rd-auto {
      description
        "Automatic Route Distingtuisher";
      uses L2VPN-RD;
    }
    container rd-configured {
      description
        "Configured Route Distinguisher";
      uses L2VPN-RD;
    }
    container rt-auto {
      description
        "Automatic Route Target";
      uses L2VPN-RT;
    }
    leaf evi-xr {
      type uint32;
      description
        "E-VPN id";
    }
    leaf encapsulation-xr {
      type uint8;
      description
        "EVPN Instance encapsulation";
    }
    leaf bd-name {
      type string;
      description
        "Bridge domain name";
    }
    leaf type {
      type L2vpn-evpn;
      description
        "Service Type";
    }
    leaf description {
      type string;
      description
        "EVI description";
    }
    leaf unicast-label {
      type uint32;
      description
        "Unicast Label";
    }
    leaf multicast-label {
      type uint32;
      description
        "Multicast Label";
    }
    leaf reroute-label {
      type uint32;
      description
        "Reroute Label";
    }
    leaf cw-disable {
      type boolean;
      description
        "Control-Word Disable";
    }
    leaf mtu-mismatch-ignore {
      type boolean;
      description
        "Ignore MTU Mismatch";
    }
    leaf mtu-zero-transmit {
      type boolean;
      description
        "Transmit MTU Zero";
    }
    leaf table-policy-name {
      type string;
      description
        "Table-policy Name";
    }
    leaf export-route-policy {
      type string;
      description
        "Export Route Policy";
    }
    leaf import-route-policy {
      type string;
      description
        "Import Route Policy";
    }
    leaf forward-class {
      type uint8;
      description
        "Forward Class attribute";
    }
    leaf rt-import-block-set {
      type boolean;
      description
        "Is Import RT None set";
    }
    leaf rt-export-block-set {
      type boolean;
      description
        "Is Export RT None set";
    }
    leaf advertise-mac {
      type boolean;
      description
        "Advertise MAC-only routes on this EVI";
    }
    leaf etree-leaf {
      type boolean;
      description
        "E-Tree Leaf Indication";
    }
    leaf etree-rt-leaf {
      type boolean;
      description
        "E-Tree Route-Target Leaf Indication";
    }
    leaf advertise-bvi-mac {
      type boolean;
      description
        "Advertise BVI MACs routes on this EVI";
    }
    leaf aliasing-disabled {
      type boolean;
      description
        "Route Aliasing is disabled";
    }
    leaf unknown-unicast-flooding-disabled {
      type boolean;
      description
        "Unknown-unicast flooding is disabled";
    }
    leaf reoriginate-disabled {
      type boolean;
      description
        "Route Re-origination is disabled";
    }
    leaf stitching {
      type boolean;
      description
        "EVPN Instance is Regular/Stitching side";
    }
    leaf multicast-source-connected {
      type boolean;
      description
        "EVI is connected to multicast source";
    }
    leaf bgp-implicit-import-disabled {
      type boolean;
      description
        "BGP implicit import is disabled";
    }
    leaf vrf-name {
      type string;
      description
        "L3 VRF name from BVI";
    }
    leaf preferred-nh-mode {
      type Evpn-pref-ecmp-nh-mode;
      description
        "Preferred Nexthop Mode";
    }
    leaf srv6-locator-name {
      type string;
      description
        "SRv6 Locator Name";
    }
  }

  grouping L2VPN-EVPN-SUMMARY {
    description
      "EVPN Information Summary";
    leaf router-id {
      type inet:ipv6-address;
      description
        "EVPN Router ID";
    }
    leaf as {
      type uint32;
      description
        "BGP AS number";
    }
    leaf ev-is {
      type uint32;
      description
        "Number of EVI DB Entries";
    }
    leaf tunnel-endpoints {
      type uint32;
      description
        "Number of Tunnel Endpoint DB Entries";
    }
    leaf local-mac-routes {
      type uint32;
      description
        "Number of Local MAC Routes";
    }
    leaf local-ipv4-mac-routes {
      type uint32;
      description
        "Number of Local IPv4 MAC-IP Routes";
    }
    leaf local-ipv6-mac-routes {
      type uint32;
      description
        "Number of Local IPv6 MAC-IP Routes";
    }
    leaf es-global-mac-routes {
      type uint32;
      description
        "Number of ES:Global MAC Routes";
    }
    leaf remote-mac-routes {
      type uint32;
      description
        "Number of Remote MAC Routes";
    }
    leaf remote-sync-mac-routes {
      type uint32;
      description
        "Number of Remote SYNC MAC Routes";
    }
    leaf remote-ipv4-mac-routes {
      type uint32;
      description
        "Number of Remote IPv4 MAC-IP Routes";
    }
    leaf remote-ipv6-mac-routes {
      type uint32;
      description
        "Number of Remote IPv6 MAC-IP Routes";
    }
    leaf local-imcast-routes {
      type uint32;
      description
        "Number of Local IMCAST Routes";
    }
    leaf remote-imcast-routes {
      type uint32;
      description
        "Number of Remote IMCAST Routes";
    }
    leaf labels {
      type uint32;
      description
        "Number of Internal Labels";
    }
    leaf sh-internal-ids {
      type uint32;
      description
        "Number of single-homed Internal IDs";
    }
    leaf mh-internal-ids {
      type uint32;
      description
        "Number of multi-homed Internal IDs";
    }
    leaf es-entries {
      type uint32;
      description
        "Number of ES Entries in DB";
    }
    leaf neighbor-entries {
      type uint32;
      description
        "Number of neighbor Entries in DB";
    }
    leaf local-ead-routes {
      type uint32;
      description
        "Number of Local EAD Entries in DB";
    }
    leaf remote-ead-routes {
      type uint32;
      description
        "Number of Remote EAD Entries in DB";
    }
    leaf global-source-mac {
      type yang:mac-address;
      description
        "Global Source MAC Address";
    }
    leaf peering-time {
      type uint32;
      units "second";
      description
        "EVPN ES Peering Time (seconds)";
    }
    leaf recovery-time {
      type uint32;
      units "second";
      description
        "EVPN ES Recovery Time (seconds)";
    }
    leaf carving-time {
      type uint32;
      units "second";
      description
        "EVPN ES Carving Time (seconds)";
    }
    leaf cost-out-configured {
      type boolean;
      description
        "EVPN node cost out via manual configuration";
    }
    leaf bundle-convergence-in-progress {
      type boolean;
      description
        "Bundle convergence in progress";
    }
    leaf node-costed-out {
      type boolean;
      description
        "EVPN Services costed out on node and holding
         Bundle interfaces down";
    }
    leaf startup-cost-in-time {
      type uint32;
      units "second";
      description
        "EVPN Node startup cost-in Time (seconds)";
    }
    leaf startup-cost-in-time-left {
      type uint32;
      units "millisecond";
      description
        "Milliseconds left on EVPN Node startup cost-in";
    }
    leaf mac-postpone-timer {
      type uint32;
      units "second";
      description
        "Configured timer for postponing MAC withdraws
         (seconds)";
    }
    leaf mac-postpone-timer-left {
      type uint32;
      units "millisecond";
      description
        "Milliseconds left on MAC withdraw postpone timer";
    }
    leaf l2rib-throttle {
      type boolean;
      description
        "Send to L2RIB Throttled";
    }
    leaf logging-df-election-enabled {
      type boolean;
      description
        "Logging EVPN Designated Forwarder changes
         enabled";
    }
  }

  grouping L2VPN-EVPN-EVI-SUMMARY {
    description
      "EVPN Instance summary information";
    leaf ethernet-vpn-id {
      type uint32;
      description
        "Ethernet VPN id";
    }
    leaf encapsulation-xr {
      type uint8;
      description
        "EVPN Instance transport encapsulation";
    }
    leaf bd-name {
      type string;
      description
        "Bridge domain name";
    }
    leaf type {
      type L2vpn-evpn;
      description
        "Service Type";
    }
  }

  grouping L2VPN-EVPN-IGMP-SUBIF-INFO {
    description
      "L2VPN EVPN IGMP SUBIF INFO";
    leaf vrf-id {
      type uint32;
      description
        "VRF id";
    }
  }

  grouping L2VPN-EVPN-IGMP-FWD-INFO {
    description
      "L2VPN EVPN IGMP FWD INFO";
    leaf bd-id {
      type uint32;
      description
        "BD id";
    }
  }

  grouping EVPN-IGMP-CHILD-INFO {
    description
      "EVPN IGMP CHILD INFO";
    container fwd-info {
      when "../child-type = 'l2-fwd'" {
        tailf:xpath-root 3;
        description
          "../ChildType = 'L2_FWD'";
      }
      description
        "fwd info";
      uses L2VPN-EVPN-IGMP-FWD-INFO;
    }
    container subif-info {
      when "../child-type = 'l3-sub-if'" {
        tailf:xpath-root 3;
        description
          "../ChildType = 'L3_SUBIF'";
      }
      description
        "subif info";
      uses L2VPN-EVPN-IGMP-SUBIF-INFO;
    }
    leaf child-type {
      type Evpn-child;
      description
        "ChildType";
    }
  }

  grouping L2VPN-EVPN-IGMP-LOCAL-INFO {
    description
      "L2VPN EVPN IGMP LOCAL INFO";
    leaf if-name {
      type string {
        length "0..65";
      }
      description
        "Interface name internal format";
    }
  }

  grouping EVPN-IGMP-SRC-INFO {
    description
      "EVPN IGMP SRC INFO";
    container local-info {
      when "../type = 'local'" {
        tailf:xpath-root 3;
        description
          "../Type = 'Local'";
      }
      description
        "local info";
      uses L2VPN-EVPN-IGMP-LOCAL-INFO;
    }
    leaf type {
      type Evpn-igmp-source;
      description
        "Type";
    }
    leaf remote-info {
      when "../type = 'remote'" {
        tailf:xpath-root 3;
        description
          "../Type = 'Remote'";
      }
      type L2vpn-bag-in6-addr;
      description
        "remote info";
    }
  }

  grouping L2VPN-EVPN-IGMP {
    description
      "EVPN IGMP database information";
    container source-info {
      description
        "Source Info";
      uses EVPN-IGMP-SRC-INFO;
    }
    container child-info {
      description
        "Child Info";
      uses EVPN-IGMP-CHILD-INFO;
    }
    leaf evpn-client-type {
      type Evpn-client1;
      description
        "EVPN Client Type";
    }
    leaf ethernet-segment-name {
      type string;
      description
        "Ethernet Segment Name";
    }
    leaf evi-xr {
      type uint32;
      description
        "E-VPN id";
    }
    leaf route-type {
      type Evpn-igmp-msg;
      description
        "Route Type";
    }
    leaf source-addr {
      type inet:ipv6-address;
      description
        "Source IP Address";
    }
    leaf group-addr {
      type inet:ipv6-address;
      description
        "Group IP Address";
    }
    leaf ethernet-tag-id {
      type uint32;
      description
        "Ethernet Tag id";
    }
    leaf igmp-version {
      type Evpn-igmp-version;
      description
        "IGMP Version";
    }
    leaf igmp-group-type {
      type Evpn-igmp-grp;
      description
        "IGMP Group Type";
    }
    leaf max-response-time {
      type uint8;
      description
        "Max Response Time";
    }
    leaf resolved {
      type boolean;
      description
        "Resolved";
    }
    list ethernet-segment-identifier {
      description
        "Ethernet Segment id";
      leaf entry {
        type uint8;
        description
          "Ethernet Segment id";
      }
    }
  }

  grouping L2VPN-EVPN-CLIENT {
    description
      "EVPN Client Information";
    leaf client-type {
      type Evpn-client1;
      description
        "Client Type";
    }
  }

  grouping L2VPN-EVPN-REMOTE-SHG-INFO {
    description
      "L2VPN EVPN remote split horizon group labels";
    leaf next-hop {
      type inet:ipv6-address;
      description
        "Next-hop IP address (v6 format)";
    }
    leaf label {
      type uint32;
      description
        "Split horizon label associated with next-hop
         address";
    }
  }

  grouping L2VPN-EVPN-REMOTE-SHG {
    description
      "EVPN Remote SHG object";
    leaf ethernet-vpn-id {
      type uint32;
      description
        "Ethernet VPN id";
    }
    leaf encapsulation {
      type uint8;
      description
        "EVPN Instance transport encapsulation";
    }
    list ethernet-segment-identifier {
      description
        "Ethernet Segment id";
      leaf entry {
        type uint8;
        description
          "Ethernet Segment id";
      }
    }
    list remote-split-horizon-group-label {
      description
        "Remote split horizon group labels";
      uses L2VPN-EVPN-REMOTE-SHG-INFO;
    }
  }

  grouping EVPN-GRP-INTF-INFO {
    description
      "EVPN Group Interface Information";
    leaf interface-name {
      type string;
      description
        "Interface name";
    }
    leaf state {
      type Im-state-enum;
      description
        "Interface State";
    }
  }

  grouping EVPN-GRP-INFO {
    description
      "EVPN Group Information";
    leaf group-id {
      type uint32;
      description
        "EVPN Group ID";
    }
    leaf state {
      type Evpn-grp;
      description
        "EVPN Group State";
    }
    list core-interface {
      description
        "EVPN Group Core Interface table";
      uses EVPN-GRP-INTF-INFO;
    }
    list access-interface {
      description
        "EVPN Access Core Interface table";
      uses EVPN-GRP-INTF-INFO;
    }
  }
}

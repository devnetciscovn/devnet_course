module Cisco-IOS-XR-attestation-agent-cfg {
  // Generated by yanger -t ncs
  tailf:mount-id "cisco-iosxr-nc-7.3:cisco-iosxr-nc-7.3";
  tailf:ncs-device-type "netconf";

  namespace "http://cisco.com/ns/yang/Cisco-IOS-XR-attestation-agent-cfg";
  prefix attestation-agent-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR attestation-agent package configuration.

     This module contains definitions
     for the following management objects:
       attestation: Attestation Agent configuration

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    container attestation {
      tailf:ncs-device-type "netconf";
      tailf:display-when "not(../../ncs:module) or ../../ncs:module[ncs:name='Cisco-IOS-XR-attestation-agent-cfg']";
      description
        "Attestation Agent configuration";
      container ima {
        description
          "Runtime Integrity configuration";
        container cache {
          description
            "IMA cache related configuration";
          container job {
            description
              "Cache CRON Job configuration";
            leaf disable {
              type boolean;
              default "false";
              description
                "Disable the cache job";
            }
            leaf interval {
              type uint32 {
                range "5..1440";
              }
              default "240";
              description
                "Interval for CRON Job 5-1440 mins, must be
                 multiple or factor of 60, default 240";
            }
          }
        }
      }
    }
  }
  augment "/ncs:devices/ncs:device/ncs:live-status" {
    container attestation {
      tailf:ncs-device-type "netconf";
      tailf:display-when "not(../../ncs:module) or ../../ncs:module[ncs:name='Cisco-IOS-XR-attestation-agent-cfg'] or (../../ncs:live-status-protocol[not(ncs:capability)]) or (../../ncs:live-status-protocol/ncs:capability/ncs:module[.='Cisco-IOS-XR-attestation-agent-cfg'])";
      description
        "Attestation Agent configuration";
      container ima {
        description
          "Runtime Integrity configuration";
        container cache {
          description
            "IMA cache related configuration";
          container job {
            description
              "Cache CRON Job configuration";
            leaf disable {
              type boolean;
              // NCS drop default statement
              description
                "Disable the cache job";
            }
            leaf interval {
              type uint32 {
                range "5..1440";
              }
              // NCS drop default statement
              description
                "Interval for CRON Job 5-1440 mins, must be
                 multiple or factor of 60, default 240";
            }
          }
        }
      }
    }
  }
  augment "/ncs:devices/ncs:template/ncs:ned-id/ncs:config" {
    container attestation {
      description
        "Attestation Agent configuration";
      container ima {
        description
          "Runtime Integrity configuration";
        container cache {
          description
            "IMA cache related configuration";
          container job {
            description
              "Cache CRON Job configuration";
            leaf disable {
              type string;
              // NCS drop default statement
              description
                "Disable the cache job";
            }
            leaf interval {
              type string;
              // NCS drop default statement
              description
                "Interval for CRON Job 5-1440 mins, must be
                 multiple or factor of 60, default 240";
            }
          }
        }
      }
    }
  }
}

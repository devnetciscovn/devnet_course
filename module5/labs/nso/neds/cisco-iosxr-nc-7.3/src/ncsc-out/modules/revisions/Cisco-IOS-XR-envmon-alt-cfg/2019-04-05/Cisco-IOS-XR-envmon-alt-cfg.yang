module Cisco-IOS-XR-envmon-alt-cfg {
  // Generated by yanger -t ncs
  tailf:mount-id "cisco-iosxr-nc-7.3:cisco-iosxr-nc-7.3";
  tailf:ncs-device-type "netconf";

  namespace "http://cisco.com/ns/yang/Cisco-IOS-XR-envmon-alt-cfg";
  prefix envmon-alt-cfg;

  import cisco-semver {
    prefix semver;
  }
  import Cisco-IOS-XR-envmon-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR envmon-alt package configuration.

     This YANG module augments the
       Cisco-IOS-XR-envmon-cfg
     module with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:template/ncs:ned-id/ncs:config/a1:environmental-monitoring" {
    description
      "This augment extends the configuration data of
       'Cisco-IOS-XR-envmon-cfg'";
    leaf altitude {
      type string;
      description
        "Altitude value in meters";
    }
  }
  augment "/ncs:devices/ncs:device/ncs:live-status/a1:environmental-monitoring" {
    description
      "This augment extends the configuration data of
       'Cisco-IOS-XR-envmon-cfg'";
    leaf altitude {
      tailf:ncs-device-type "netconf";
      tailf:display-when "not(../../../ncs:module) or ../../../ncs:module[ncs:name='Cisco-IOS-XR-envmon-alt-cfg'] or (../../../ncs:live-status-protocol[not(ncs:capability)]) or (../../../ncs:live-status-protocol/ncs:capability/ncs:module[.='Cisco-IOS-XR-envmon-alt-cfg'])";
      type uint32 {
        range "0..4000";
      }
      description
        "Altitude value in meters";
    }
  }
  augment "/ncs:devices/ncs:device/ncs:config/a1:environmental-monitoring" {
    description
      "This augment extends the configuration data of
       'Cisco-IOS-XR-envmon-cfg'";
    leaf altitude {
      tailf:ncs-device-type "netconf";
      tailf:display-when "not(../../../ncs:module) or ../../../ncs:module[ncs:name='Cisco-IOS-XR-envmon-alt-cfg']";
      type uint32 {
        range "0..4000";
      }
      description
        "Altitude value in meters";
    }
  }
}

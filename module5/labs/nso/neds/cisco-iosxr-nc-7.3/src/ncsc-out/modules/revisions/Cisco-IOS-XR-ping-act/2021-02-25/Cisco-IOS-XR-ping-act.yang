module Cisco-IOS-XR-ping-act {
  // Generated by yanger -t ncs
  tailf:mount-id "cisco-iosxr-nc-7.3:cisco-iosxr-nc-7.3";
  tailf:ncs-device-type "netconf";

  namespace "http://cisco.com/ns/yang/Cisco-IOS-XR-ping-act";
  prefix ping-act;

  import cisco-semver {
    prefix semver;
  }
  include Cisco-IOS-XR-ipv4-ping-act;
  include Cisco-IOS-XR-ipv6-ping-act;
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ping action package configuration.

     Copyright (c) 2016-2019, 2021 by Cisco Systems, Inc.
     All rights reserved.";

  revision 2021-02-25 {
    description
      "Removed ping segment-routing commands
       2020-10-29
         Added ping segment-routing commands";
    semver:module-version "1.1.0";
  }
  revision 2019-10-01 {
    description
      "Made changes to be RFC6087 compliant";
    semver:module-version "1.1.0";
  }
  revision 2019-04-05 {
    description
      "Establish semantic version baseline.";
    semver:module-version "1.0.0";
  }
  revision 2018-10-01 {
    description
      "IOS XR 6.2.1 revision.";
  }

  augment "/ncs:devices/ncs:device/ncs:rpc" {
    container rpc-ping {
      tailf:ncs-device-type "netconf";
      tailf:display-when "not(../../ncs:module) or ../../ncs:module[ncs:name='Cisco-IOS-XR-ping-act']";
      tailf:action ping {
        tailf:actionpoint ncsproxy {
          tailf:internal;
        }
        description
          "Send echo messages";
        input {
          container destination {
            presence "ping input";
            description
              "Ping destination";
            uses ncs_rpc_notif_PING-OPTIONS;
            uses ncs_rpc_notif_IPV4-SPECIFIC-OPTIONS;
            uses ncs_rpc_notif_IPV6-SPECIFIC-OPTIONS;
          }
          list ipv4 {
            key "destination";
            description
              "Ping IPv4";
            uses ncs_rpc_notif_IPV4-PING-INPUT;
          }
          container ipv6 {
            presence "ipv6 ping input";
            description
              "Ping IPv6";
            uses ncs_rpc_notif_IPV6-PING-INPUT;
          }
        }
        output {
          container ping-response {
            description
              "Ping response";
            list ipv4 {
              key "destination";
              description
                "Ping IPv4 response";
              uses ncs_rpc_notif_IPV4-PING-OUTPUT;
            }
            container ipv6 {
              presence "ipv6 ping output";
              description
                "Ping IPv6 response";
              uses ncs_rpc_notif_IPV6-PING-OUTPUT;
            }
          }
        }
      }
    }
  }
  augment "/ncs:devices/ncs:device-group/ncs:ned-id/ncs:rpc" {
    container rpc-ping {
      tailf:ncs-device-type "netconf";
      tailf:display-when "/ncs:devices/ncs:device[ncs:name=current()/../../../ncs:member]/ncs:module[ncs:name='Cisco-IOS-XR-ping-act']";
      tailf:action ping {
        tailf:actionpoint ncsproxy {
          tailf:internal;
        }
        description
          "Send echo messages";
        input {
          container destination {
            presence "ping input";
            description
              "Ping destination";
            uses ncs_rpc_notif_PING-OPTIONS;
            uses ncs_rpc_notif_IPV4-SPECIFIC-OPTIONS;
            uses ncs_rpc_notif_IPV6-SPECIFIC-OPTIONS;
          }
          list ipv4 {
            key "destination";
            description
              "Ping IPv4";
            uses ncs_rpc_notif_IPV4-PING-INPUT;
          }
          container ipv6 {
            presence "ipv6 ping input";
            description
              "Ping IPv6";
            uses ncs_rpc_notif_IPV6-PING-INPUT;
          }
        }
        output {
          container "device" {
            leaf "name" {
              type string;
            }
            leaf "info" {
              type string;
            }
            container "result" {
              container ping-response {
                description
                  "Ping response";
                list ipv4 {
                  key "destination";
                  description
                    "Ping IPv4 response";
                  uses ncs_rpc_notif_IPV4-PING-OUTPUT;
                }
                container ipv6 {
                  presence "ipv6 ping output";
                  description
                    "Ping IPv6 response";
                  uses ncs_rpc_notif_IPV6-PING-OUTPUT;
                }
              }
            }
          }
        }
      }
    }
  }
}

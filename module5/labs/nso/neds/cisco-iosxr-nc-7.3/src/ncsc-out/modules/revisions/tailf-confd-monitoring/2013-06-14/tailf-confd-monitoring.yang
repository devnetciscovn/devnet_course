module tailf-confd-monitoring {
  // Generated by yanger -t ncs
  tailf:mount-id "cisco-iosxr-nc-7.3:cisco-iosxr-nc-7.3";
  tailf:ncs-device-type "netconf";

  namespace "http://tail-f.com/yang/confd-monitoring";
  prefix tfcm;

  import tailf-common-monitoring {
    prefix tfcg;
    revision-date 2013-06-14;
  }
  import tailf-common {
    prefix tailf;
  }
  import tailf-ncs {
    prefix ncs;
  }

  organization
    "Tail-f Systems";
  description
    "This module defines status objects for monitoring of ConfD.";

  revision 2013-06-14 {
    description
      "Released as part of ConfD-4.3.

       Imported latest tailf-common-monitoring module.";
  }
  revision 2013-03-07 {
    description
      "Released as part of ConfD-4.2.

       Imported latest tailf-common-monitoring module.";
  }
  revision 2012-11-08 {
    description
      "Released as part of ConfD-4.1.

       Imported latest tailf-common-monitoring module.";
  }
  revision 2012-03-08 {
    description
      "Released as part of ConfD-3.9.

       Imported latest tailf-common-monitoring module.";
  }
  revision 2011-12-08 {
    description
      "Released as part of ConfD-3.8.

       Imported latest tailf-common-monitoring module.";
  }
  revision 2011-09-22 {
    description
      "Released as part of ConfD-3.7.";
  }

  augment "/ncs:devices/ncs:device/ncs:config" {
    // NCS drop config false container 'confd-state'
  }
  augment "/ncs:devices/ncs:device/ncs:live-status" {
    container confd-state {
      tailf:ncs-device-type "netconf";
      tailf:display-when "not(../../ncs:module) or ../../ncs:module[ncs:name='tailf-confd-monitoring'] or (../../ncs:live-status-protocol[not(ncs:capability)]) or (../../ncs:live-status-protocol/ncs:capability/ncs:module[.='tailf-confd-monitoring'])";
      uses tfcg:live_ncs_common-monitoring-objects;
    }
  }
  augment "/ncs:devices/ncs:template/ncs:ned-id/ncs:config" {
    // NCS drop config false container 'confd-state'
  }
}

module Cisco-IOS-XR-mvpn-oper {
  // Generated by yanger -t ncs
  tailf:mount-id "cisco-iosxr-nc-7.3:cisco-iosxr-nc-7.3";
  tailf:ncs-device-type "netconf";

  namespace "http://cisco.com/ns/yang/Cisco-IOS-XR-mvpn-oper";
  prefix mvpn-oper;

  import ietf-inet-types {
    prefix inet;
  }
  import Cisco-IOS-XR-types {
    prefix xr;
  }
  import cisco-semver {
    prefix semver;
  }
  include Cisco-IOS-XR-mvpn-oper-sub1 {
    revision-date 2020-04-02;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mvpn package operational data.

     This module contains definitions
     for the following management objects:
       mvpn: MVPN operational data
       ipv6-mvpn: IPv6 MVPN operational data

     Copyright (c) 2013-2020 by Cisco Systems, Inc.
     All rights reserved.";

  revision 2020-04-02 {
    description
      "MVPN TreeSID information added.";
    semver:module-version "1.0.0";
  }
  revision 2019-08-27 {
    description
      "Providing MVPN information.";
  }
  revision 2019-04-05 {
    description
      "Establish semantic version baseline.";
  }
  revision 2015-11-09 {
    description
      "IOS XR 6.0 revision.";
  }

  typedef ncs_template_Pim-mldp-opaque {
    type string;
    description
      "Pim mldp opaque";
  }

  typedef ncs_template_Pim-mdt-mldp {
    type string;
    description
      "Pim mdt mldp";
  }

  typedef ncs_template_Mdt-core {
    type string;
    description
      "Mdt core";
  }

  typedef ncs_template_Route-distinguisher {
    type string;
    description
      "Route distinguisher";
  }

  typedef ncs_rpc_notif_Pim-mldp-opaque {
    type enumeration {
      enum "mldp-global-identifier" {
        value 1;
        description
          "Opaque Global Identifier";
      }
      enum "mldpvpn-identifier" {
        value 2;
        description
          "Opaque VPN Identifier";
      }
    }
    description
      "Pim mldp opaque";
  }

  typedef ncs_rpc_notif_Pim-mdt-mldp {
    type enumeration {
      enum "mldpp2mp" {
        value 6;
        description
          "P2MP Tree";
      }
      enum "mldpmp2mp" {
        value 8;
        description
          "MP2MP Tree";
      }
    }
    description
      "Pim mdt mldp";
  }

  typedef ncs_rpc_notif_Mdt-core {
    type enumeration {
      enum "inband" {
        value 0;
        description
          "Inband MDT Type";
      }
      enum "gre" {
        value 1;
        description
          "GRE MDT Type";
      }
      enum "mldp" {
        value 2;
        description
          "MLDP MDT Type";
      }
      enum "rsvp-te" {
        value 3;
        description
          "RSVP_TE MDT Type";
      }
      enum "ir" {
        value 4;
        description
          "IR MDT Type";
      }
      enum "vxlan" {
        value 5;
        description
          "VXLAN MDT Type";
      }
      enum "g-inband" {
        value 6;
        description
          "G_Inband MDT Type";
      }
      enum "max" {
        value 8;
        description
          "MAX MDT Type";
      }
    }
    description
      "Mdt core";
  }

  typedef ncs_rpc_notif_Route-distinguisher {
    type string;
    description
      "Route distinguisher";
  }

  typedef live_ncs_Pim-mldp-opaque {
    type enumeration {
      enum "mldp-global-identifier" {
        value 1;
        description
          "Opaque Global Identifier";
      }
      enum "mldpvpn-identifier" {
        value 2;
        description
          "Opaque VPN Identifier";
      }
    }
    description
      "Pim mldp opaque";
  }

  typedef live_ncs_Pim-mdt-mldp {
    type enumeration {
      enum "mldpp2mp" {
        value 6;
        description
          "P2MP Tree";
      }
      enum "mldpmp2mp" {
        value 8;
        description
          "MP2MP Tree";
      }
    }
    description
      "Pim mdt mldp";
  }

  typedef live_ncs_Mdt-core {
    type enumeration {
      enum "inband" {
        value 0;
        description
          "Inband MDT Type";
      }
      enum "gre" {
        value 1;
        description
          "GRE MDT Type";
      }
      enum "mldp" {
        value 2;
        description
          "MLDP MDT Type";
      }
      enum "rsvp-te" {
        value 3;
        description
          "RSVP_TE MDT Type";
      }
      enum "ir" {
        value 4;
        description
          "IR MDT Type";
      }
      enum "vxlan" {
        value 5;
        description
          "VXLAN MDT Type";
      }
      enum "g-inband" {
        value 6;
        description
          "G_Inband MDT Type";
      }
      enum "max" {
        value 8;
        description
          "MAX MDT Type";
      }
    }
    description
      "Mdt core";
  }

  typedef live_ncs_Route-distinguisher {
    type string;
    description
      "Route distinguisher";
  }

  typedef Pim-mldp-opaque {
    type enumeration {
      enum "mldp-global-identifier" {
        value 1;
        description
          "Opaque Global Identifier";
      }
      enum "mldpvpn-identifier" {
        value 2;
        description
          "Opaque VPN Identifier";
      }
    }
    description
      "Pim mldp opaque";
  }

  typedef Pim-mdt-mldp {
    type enumeration {
      enum "mldpp2mp" {
        value 6;
        description
          "P2MP Tree";
      }
      enum "mldpmp2mp" {
        value 8;
        description
          "MP2MP Tree";
      }
    }
    description
      "Pim mdt mldp";
  }

  typedef Mdt-core {
    type enumeration {
      enum "inband" {
        value 0;
        description
          "Inband MDT Type";
      }
      enum "gre" {
        value 1;
        description
          "GRE MDT Type";
      }
      enum "mldp" {
        value 2;
        description
          "MLDP MDT Type";
      }
      enum "rsvp-te" {
        value 3;
        description
          "RSVP_TE MDT Type";
      }
      enum "ir" {
        value 4;
        description
          "IR MDT Type";
      }
      enum "vxlan" {
        value 5;
        description
          "VXLAN MDT Type";
      }
      enum "g-inband" {
        value 6;
        description
          "G_Inband MDT Type";
      }
      enum "max" {
        value 8;
        description
          "MAX MDT Type";
      }
    }
    description
      "Mdt core";
  }

  typedef Route-distinguisher {
    type string;
    description
      "Route distinguisher";
  }

  grouping ncs_template_LOCAL-ENTRY-TABLE {
    description
      "Common node of vrf, default-context";
    container local-entries {
      description
        "PIM MDT mldp local table";
      list local-entry {
        // NCS patched for predictable order
        ordered-by user;
        key "tree-type opaque-type oui vpn-index core-id";
        description
          "PIM MDT mldp local table";
        leaf tree-type {
          type ncs_template_Pim-mdt-mldp;
          description
            "Tree Type";
        }
        leaf opaque-type {
          type ncs_template_Pim-mldp-opaque;
          description
            "Opaque Type";
        }
        leaf oui {
          type string;
          description
            "OUI";
        }
        leaf vpn-index {
          type string;
          description
            "VPN Index";
        }
        leaf core-id {
          type string;
          description
            "Core ID";
        }
        uses ncs_template_PIM-MDT-DATA-MLDP-BAG;
      }
    }
  }

  grouping ncs_template_AUTO-RP {
    description
      "Common node of vrf, default-context";
    container auto-rp {
      description
        "PIM Auto-RP information";
      uses ncs_template_RP-RELAY-TABLE;
    }
  }

  grouping ncs_template_MDT-CACHE-TABLE {
    description
      "Common node of vrf, default-context";
    container mdt-caches {
      description
        "PIM MDT cache";
      list mdt-cache {
        // NCS patched for predictable order
        ordered-by user;
        key "core-type core-source-address customer-source-address customer-group-address";
        description
          "PIM MDT cache information";
        leaf core-type {
          type ncs_template_Mdt-core;
          description
            "MDT Core type";
        }
        leaf core-source-address {
          type string;
          description
            "Core source IP address";
        }
        leaf customer-source-address {
          type string;
          description
            "Customer source IP address";
        }
        leaf customer-group-address {
          type string;
          description
            "Customer group IP address";
        }
        uses ncs_template_PIM-MDT-CACHE-BAG;
      }
    }
  }

  grouping ncs_template_MDT-IR-LOCAL-ENTRY-TABLE {
    description
      "Common node of vrf, default-context";
    container ir-local-entries {
      description
        "PIM MDT ir local table";
      list ir-local-entry {
        // NCS patched for predictable order
        ordered-by user;
        key "core-id";
        description
          "PIM MDT ir local table";
        leaf core-id {
          type string;
          description
            "Core ID";
        }
        uses ncs_template_PIM-MDT-DATA-IR-BAG;
      }
    }
  }

  grouping ncs_template_MDT-RSVP-TE-CACHE-TABLE {
    description
      "Common node of vrf, default-context";
    container mdt-rsvp-te-caches {
      description
        "RSVPTE MDT cache";
      list mdt-rsvp-te-cache {
        // NCS patched for predictable order
        ordered-by user;
        key "core-source-address customer-source-address customer-group-address";
        description
          "RSVPTE MDT cache information";
        leaf core-source-address {
          type string;
          description
            "Core source IP address";
        }
        leaf customer-source-address {
          type string;
          description
            "Customer source IP address";
        }
        leaf customer-group-address {
          type string;
          description
            "Customer group IP address";
        }
        uses ncs_template_PIM-MDT-CACHE-BAG;
      }
    }
  }

  grouping ncs_template_MDT-INTERFACE {
    description
      "Common node of vrf, default-context";
    container mdt-interface {
      description
        "MDT interface information";
      uses ncs_template_PIM-MDT-INTERFACE-BAG;
    }
  }

  grouping ncs_template_MDT-GRE-CACHE-TABLE {
    description
      "Common node of vrf, default-context";
    container mdt-gre-caches {
      description
        "GRE MDT cache";
      list mdt-gre-cache {
        // NCS patched for predictable order
        ordered-by user;
        key "core-source-address customer-source-address customer-group-address";
        description
          "GRE MDT cache information";
        leaf core-source-address {
          type string;
          description
            "Core source IP address";
        }
        leaf customer-source-address {
          type string;
          description
            "Customer source IP address";
        }
        leaf customer-group-address {
          type string;
          description
            "Customer group IP address";
        }
        uses ncs_template_PIM-MDT-CACHE-BAG;
      }
    }
  }

  grouping ncs_template_BGP-AF-TABLE {
    description
      "Common node of vrf, default-context";
    container bgp-afs {
      description
        "PIM BGP SAFI table";
      list bgp-af {
        // NCS patched for predictable order
        ordered-by user;
        key "source-address group-address";
        description
          "PIM BGP SAFI information";
        leaf source-address {
          type string;
          description
            "Source IP address";
        }
        leaf group-address {
          type string;
          description
            "Group IP address";
        }
        uses ncs_template_PIM-BGP-SAFI-BAG;
      }
    }
  }

  grouping ncs_template_VRF-TABLE {
    description
      "Common node of active, standby";
    container vrfs {
      description
        "VRF Table";
      list vrf {
        // NCS patched for predictable order
        ordered-by user;
        key "vrf-name";
        description
          "VRF name";
        container mvpn-sr-p2mp-entries {
          description
            "MVPN SR P2MP database table";
          list mvpn-sr-p2mp-entry {
            // NCS patched for predictable order
            ordered-by user;
            key "policy-name";
            description
              "MVPN SR P2MP database entry";
            leaf policy-name {
              type xr:ncs_template_Cisco-ios-xr-string;
              description
                "Policy Name";
            }
            uses ncs_template_PIM-SRP2MP-MDT-TUNNEL-DB-BAG;
          }
        }
        container mvpn-database-segment-routing {
          description
            "MVPN MDT Segment Routing tunnel database";
          uses ncs_template_PIM-TREESID-MDT-TUNNEL-DB-BAG;
        }
        container mvpn-database-rsvp-te {
          description
            "MVPN MDT RSVPTE tunnel database";
          uses ncs_template_PIM-P2MPTE-MDT-TUNNEL-DB-BAG;
        }
        container mvpn-context {
          description
            "MVPN context information";
          uses ncs_template_PIM-CONTEXT-BAG;
        }
        container mvpn-pes {
          description
            "MVPN PE Information";
          list mvpn-pe {
            // NCS patched for predictable order
            ordered-by user;
            key "pe-prefix";
            description
              "MVPN PE Address information";
            leaf pe-prefix {
              type string;
              description
                "PE address";
            }
            uses ncs_template_PIM-PE-BAG;
          }
        }
        container mvpn-database-ir {
          description
            "MVPN MDT IR tunnel database";
          uses ncs_template_PIM-MDT-TUNNEL-DB-BAG;
        }
        leaf vrf-name {
          type xr:ncs_template_Cisco-ios-xr-string;
          description
            "VRF name ";
        }
        uses ncs_template_MDT-INTERFACE;
        uses ncs_template_LOCAL-ENTRY-TABLE;
        uses ncs_template_MDT-RSVP-TE-REMOTE-ENTRY-TABLE;
        uses ncs_template_MDT-CACHE-SUMMARY;
        uses ncs_template_MDT-DATABASE-IR;
        uses ncs_template_MDT-GRE-CACHE-TABLE;
        uses ncs_template_MDT-IR-REMOTE-ENTRY-TABLE;
        uses ncs_template_MDT-DATABASE-RSVP-TE;
        uses ncs_template_BSR;
        uses ncs_template_BGP-AF-TABLE;
        uses ncs_template_MDT-RSVP-TE-LOCAL-ENTRY-TABLE;
        uses ncs_template_MDT-PREFIX-REMOTE-TABLE;
        uses ncs_template_MDT-CACHE-TABLE;
        uses ncs_template_MDT-RSVP-TE-CACHE-TABLE;
        uses ncs_template_AUTO-RP;
        uses ncs_template_MDT-SEGMENT-ROUTING-LOCAL-ENTRY-TABLE;
        uses ncs_template_REMOTE-ENTRY-TABLE;
        uses ncs_template_MDT-IR-CACHE-TABLE;
        uses ncs_template_PE-TABLE;
        uses ncs_template_MDT-SEGMENT-ROUTING-REMOTE-ENTRY-TABLE;
        uses ncs_template_MDT-MLDP-CACHE-TABLE;
        uses ncs_template_MDT-IR-LOCAL-ENTRY-TABLE;
        uses ncs_template_MDT-PREFIX-LOCAL-TABLE;
      }
    }
  }

  grouping ncs_template_BSR {
    description
      "Common node of vrf, default-context";
    container bsr {
      description
        "PIM BSR information";
      uses ncs_template_RP-RELAY-TABLE;
    }
  }

  grouping ncs_template_MDT-IR-CACHE-TABLE {
    description
      "Common node of vrf, default-context";
    container mdt-ir-caches {
      description
        "IR MDT cache";
      list mdt-ir-cache {
        // NCS patched for predictable order
        ordered-by user;
        key "core-source-address customer-source-address customer-group-address";
        description
          "IR MDT cache information";
        leaf core-source-address {
          type string;
          description
            "Core source IP address";
        }
        leaf customer-source-address {
          type string;
          description
            "Customer source IP address";
        }
        leaf customer-group-address {
          type string;
          description
            "Customer group IP address";
        }
        uses ncs_template_PIM-MDT-CACHE-BAG;
      }
    }
  }

  grouping ncs_template_MDT-PREFIX-REMOTE-TABLE {
    description
      "Common node of vrf, default-context";
    container mdt-prefix-remotes {
      description
        "PIM MDT prefix remote table";
      list mdt-prefix-remote {
        // NCS patched for predictable order
        ordered-by user;
        key "mdt-prefix";
        description
          "PIM MDT prefix information";
        leaf mdt-prefix {
          type string;
          description
            "MDT data prefix address";
        }
        uses ncs_template_PIM-MDT-DATA-PFX-BAG;
      }
    }
  }

  grouping ncs_template_MDT-DATABASE-RSVP-TE {
    description
      "Common node of vrf, default-context";
    container mdt-database-rsvp-te {
      description
        "PIM MDT RSVPTE tunnel database";
      uses ncs_template_PIM-P2MPTE-MDT-TUNNEL-DB-BAG;
    }
  }

  grouping ncs_template_PROCESS {
    description
      "Common node of active, standby";
    container process {
      description
        "Process";
      container mvpn-identifiers {
        description
          "MVPN Identifier Table";
        list mvpn-identifier {
          // NCS patched for predictable order
          ordered-by user;
          key "mvpn-identifier";
          description
            "MVPN Identifier";
          leaf mvpn-identifier {
            type string;
            description
              "MVPN Identifier";
          }
          uses ncs_template_PIM-MVPN-ID-INFO;
        }
      }
      container mvpn-segmenteds {
        description
          "MVPN SEGMENT DB Table";
        list mvpn-segmented {
          // NCS patched for predictable order
          ordered-by user;
          key "rd network";
          description
            "MVPN SEGMENT DB Entry";
          leaf rd {
            type ncs_template_Route-distinguisher;
            description
              "Route Distinguisher value";
          }
          leaf network {
            type string;
            description
              "Network in prefix/length format";
          }
          uses ncs_template_PIM-SEGMENT-DB-BAG;
        }
      }
    }
  }

  grouping ncs_template_MDT-IR-REMOTE-ENTRY-TABLE {
    description
      "Common node of vrf, default-context";
    container ir-remote-entries {
      description
        "PIM MDT ir remote table";
      list ir-remote-entry {
        // NCS patched for predictable order
        ordered-by user;
        key "tunnel-type label";
        description
          "PIM MDT ir remote table";
        leaf tunnel-type {
          type string;
          description
            "Tunnel Type";
        }
        leaf label {
          type string;
          description
            "Label";
        }
        uses ncs_template_PIM-MDT-DATA-IR-BAG;
      }
    }
  }

  grouping ncs_template_MDT-RSVP-TE-LOCAL-ENTRY-TABLE {
    description
      "Common node of vrf, default-context";
    container rsvp-te-local-entries {
      description
        "PIM MDT RSVP-TE local table";
      list rsvp-te-local-entry {
        // NCS patched for predictable order
        ordered-by user;
        key "p2mp-id tunnel-id extended-tunnel-d core-id";
        description
          "PIM MDT RSVP-TE local table";
        leaf p2mp-id {
          type string;
          description
            "Core ID";
        }
        leaf tunnel-id {
          type string;
          description
            "Tunnel ID";
        }
        leaf extended-tunnel-d {
          type string;
          description
            "Extended Tunnel ID";
        }
        leaf core-id {
          type string;
          description
            "Core ID";
        }
        uses ncs_template_PIM-MDT-DATA-RSVPTE-BAG;
      }
    }
  }

  grouping ncs_template_MDT-PREFIX-LOCAL-TABLE {
    description
      "Common node of vrf, default-context";
    container mdt-prefix-locals {
      description
        "PIM MDT prefix local table";
      list mdt-prefix-local {
        // NCS patched for predictable order
        ordered-by user;
        key "mdt-prefix";
        description
          "PIM MDT prefix information";
        leaf mdt-prefix {
          type string;
          description
            "MDT data prefix address";
        }
        uses ncs_template_PIM-MDT-DATA-PFX-BAG;
      }
    }
  }

  grouping ncs_template_MDT-MLDP-CACHE-TABLE {
    description
      "Common node of vrf, default-context";
    container mdt-mldp-caches {
      description
        "MLDP MDT cache";
      list mdt-mldp-cache {
        // NCS patched for predictable order
        ordered-by user;
        key "core-source-address customer-source-address customer-group-address";
        description
          "MLDP MDT cache information";
        leaf core-source-address {
          type string;
          description
            "Core source IP address";
        }
        leaf customer-source-address {
          type string;
          description
            "Customer source IP address";
        }
        leaf customer-group-address {
          type string;
          description
            "Customer group IP address";
        }
        uses ncs_template_PIM-MDT-CACHE-BAG;
      }
    }
  }

  grouping ncs_template_PE-TABLE {
    description
      "Common node of vrf, default-context";
    container pes {
      description
        "PIM MVPN PE Information";
      list pe {
        // NCS patched for predictable order
        ordered-by user;
        key "pe-prefix";
        description
          "PIM PE Address information";
        leaf pe-prefix {
          type string;
          description
            "PE address";
        }
        uses ncs_template_PIM-PE-BAG;
      }
    }
  }

  grouping ncs_template_RP-RELAY-TABLE {
    description
      "Common node of auto-rp, bsr";
    container rp-relays {
      description
        "PIM rp-relay database";
      list rp-relay {
        // NCS patched for predictable order
        ordered-by user;
        key "vrf-name";
        description
          "PIM Relay";
        leaf vrf-name {
          type xr:ncs_template_Cisco-ios-xr-string;
          description
            "VRF name ";
        }
        uses ncs_template_PIM-RELAY-BAG;
      }
    }
  }

  grouping ncs_template_ACTIVE {
    description
      "Common node of mvpn, ipv6-mvpn";
    container active {
      description
        "Active Process";
      uses ncs_template_VRF-TABLE;
      uses ncs_template_DEFAULT-CONTEXT;
      uses ncs_template_PROCESS;
    }
  }

  grouping ncs_template_MDT-RSVP-TE-REMOTE-ENTRY-TABLE {
    description
      "Common node of vrf, default-context";
    container rsvp-te-remote-entries {
      description
        "PIM MDT RSVP-TE remote table";
      list rsvp-te-remote-entry {
        // NCS patched for predictable order
        ordered-by user;
        key "p2mp-id tunnel-id extended-tunnel-id";
        description
          "PIM MDT RSVP-TE remote table";
        leaf p2mp-id {
          type string;
          description
            "Core ID";
        }
        leaf tunnel-id {
          type string;
          description
            "Tunnel ID";
        }
        leaf extended-tunnel-id {
          type string;
          description
            "Extended Tunnel ID";
        }
        uses ncs_template_PIM-MDT-DATA-RSVPTE-BAG;
      }
    }
  }

  grouping ncs_template_MDT-DATABASE-IR {
    description
      "Common node of vrf, default-context";
    container mdt-database-ir {
      description
        "PIM MDT IR tunnel database";
      uses ncs_template_PIM-MDT-TUNNEL-DB-BAG;
    }
  }

  grouping ncs_template_REMOTE-ENTRY-TABLE {
    description
      "Common node of vrf, default-context";
    container remote-entries {
      description
        "PIM MDT mldp remote table";
      list remote-entry {
        // NCS patched for predictable order
        ordered-by user;
        key "tree-type opaque-type oui vpn-index core-id";
        description
          "PIM MDT mldp remote table";
        leaf tree-type {
          type ncs_template_Pim-mdt-mldp;
          description
            "Tree Type";
        }
        leaf opaque-type {
          type ncs_template_Pim-mldp-opaque;
          description
            "Opaque Type";
        }
        leaf oui {
          type string;
          description
            "OUI";
        }
        leaf vpn-index {
          type string;
          description
            "VPN Index";
        }
        leaf core-id {
          type string;
          description
            "Core ID";
        }
        uses ncs_template_PIM-MDT-DATA-MLDP-BAG;
      }
    }
  }

  grouping ncs_template_MDT-SEGMENT-ROUTING-LOCAL-ENTRY-TABLE {
    description
      "Common node of vrf, default-context";
    container mdt-segment-routing-local-entries {
      description
        "PIM MDT Segment Routing local table";
      list mdt-segment-routing-local-entry {
        // NCS patched for predictable order
        ordered-by user;
        key "tree-id";
        description
          "PIM MDT Segment Routing local entry";
        leaf tree-id {
          type string;
          description
            "Tree ID";
        }
        uses ncs_template_PIM-MDT-DATA-TREESID-BAG;
      }
    }
  }

  grouping ncs_template_DEFAULT-CONTEXT {
    description
      "Common node of active, standby";
    container default-context {
      description
        "Default Context";
      uses ncs_template_MDT-INTERFACE;
      uses ncs_template_LOCAL-ENTRY-TABLE;
      uses ncs_template_MDT-RSVP-TE-REMOTE-ENTRY-TABLE;
      uses ncs_template_MDT-CACHE-SUMMARY;
      uses ncs_template_MDT-DATABASE-IR;
      uses ncs_template_MDT-GRE-CACHE-TABLE;
      uses ncs_template_MDT-IR-REMOTE-ENTRY-TABLE;
      uses ncs_template_MDT-DATABASE-RSVP-TE;
      uses ncs_template_BSR;
      uses ncs_template_BGP-AF-TABLE;
      uses ncs_template_MDT-RSVP-TE-LOCAL-ENTRY-TABLE;
      uses ncs_template_MDT-PREFIX-REMOTE-TABLE;
      uses ncs_template_MDT-CACHE-TABLE;
      uses ncs_template_MDT-RSVP-TE-CACHE-TABLE;
      uses ncs_template_AUTO-RP;
      uses ncs_template_MDT-SEGMENT-ROUTING-LOCAL-ENTRY-TABLE;
      uses ncs_template_REMOTE-ENTRY-TABLE;
      uses ncs_template_MDT-IR-CACHE-TABLE;
      uses ncs_template_PE-TABLE;
      uses ncs_template_MDT-SEGMENT-ROUTING-REMOTE-ENTRY-TABLE;
      uses ncs_template_MDT-MLDP-CACHE-TABLE;
      uses ncs_template_MDT-IR-LOCAL-ENTRY-TABLE;
      uses ncs_template_MDT-PREFIX-LOCAL-TABLE;
    }
  }

  grouping ncs_template_MDT-CACHE-SUMMARY {
    description
      "Common node of vrf, default-context";
    container mdt-cache-summary {
      description
        "PIM MDT cache summary";
      uses ncs_template_PIM-MDT-CACHE-SUMM-BAG;
    }
  }

  grouping ncs_template_STANDBY {
    description
      "Common node of mvpn, ipv6-mvpn";
    container standby {
      description
        "Standby Process";
      uses ncs_template_VRF-TABLE;
      uses ncs_template_DEFAULT-CONTEXT;
      uses ncs_template_PROCESS;
    }
  }

  grouping ncs_template_MDT-SEGMENT-ROUTING-REMOTE-ENTRY-TABLE {
    description
      "Common node of vrf, default-context";
    container mdt-segment-routing-remote-entries {
      description
        "PIM MDT Segment Routing remote table";
      list mdt-segment-routing-remote-entry {
        // NCS patched for predictable order
        ordered-by user;
        key "tree-id";
        description
          "PIM MDT Segment Routing remote table";
        leaf tree-id {
          type string;
          description
            "Tree ID";
        }
        uses ncs_template_PIM-MDT-DATA-TREESID-BAG;
      }
    }
  }

  grouping ncs_rpc_notif_LOCAL-ENTRY-TABLE {
    description
      "Common node of vrf, default-context";
    container local-entries {
      description
        "PIM MDT mldp local table";
      list local-entry {
        key "tree-type opaque-type oui vpn-index core-id";
        description
          "PIM MDT mldp local table";
        leaf tree-type {
          type ncs_rpc_notif_Pim-mdt-mldp;
          description
            "Tree Type";
        }
        leaf opaque-type {
          type ncs_rpc_notif_Pim-mldp-opaque;
          description
            "Opaque Type";
        }
        leaf oui {
          type uint32;
          description
            "OUI";
        }
        leaf vpn-index {
          type uint32;
          description
            "VPN Index";
        }
        leaf core-id {
          type uint32;
          description
            "Core ID";
        }
        uses ncs_rpc_notif_PIM-MDT-DATA-MLDP-BAG;
      }
    }
  }

  grouping ncs_rpc_notif_AUTO-RP {
    description
      "Common node of vrf, default-context";
    container auto-rp {
      description
        "PIM Auto-RP information";
      uses ncs_rpc_notif_RP-RELAY-TABLE;
    }
  }

  grouping ncs_rpc_notif_MDT-CACHE-TABLE {
    description
      "Common node of vrf, default-context";
    container mdt-caches {
      description
        "PIM MDT cache";
      list mdt-cache {
        key "core-type core-source-address customer-source-address customer-group-address";
        description
          "PIM MDT cache information";
        leaf core-type {
          type ncs_rpc_notif_Mdt-core;
          description
            "MDT Core type";
        }
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses ncs_rpc_notif_PIM-MDT-CACHE-BAG;
      }
    }
  }

  grouping ncs_rpc_notif_MDT-IR-LOCAL-ENTRY-TABLE {
    description
      "Common node of vrf, default-context";
    container ir-local-entries {
      description
        "PIM MDT ir local table";
      list ir-local-entry {
        key "core-id";
        description
          "PIM MDT ir local table";
        leaf core-id {
          type uint32;
          description
            "Core ID";
        }
        uses ncs_rpc_notif_PIM-MDT-DATA-IR-BAG;
      }
    }
  }

  grouping ncs_rpc_notif_MDT-RSVP-TE-CACHE-TABLE {
    description
      "Common node of vrf, default-context";
    container mdt-rsvp-te-caches {
      description
        "RSVPTE MDT cache";
      list mdt-rsvp-te-cache {
        key "core-source-address customer-source-address customer-group-address";
        description
          "RSVPTE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses ncs_rpc_notif_PIM-MDT-CACHE-BAG;
      }
    }
  }

  grouping ncs_rpc_notif_MDT-INTERFACE {
    description
      "Common node of vrf, default-context";
    container mdt-interface {
      description
        "MDT interface information";
      uses ncs_rpc_notif_PIM-MDT-INTERFACE-BAG;
    }
  }

  grouping ncs_rpc_notif_MDT-GRE-CACHE-TABLE {
    description
      "Common node of vrf, default-context";
    container mdt-gre-caches {
      description
        "GRE MDT cache";
      list mdt-gre-cache {
        key "core-source-address customer-source-address customer-group-address";
        description
          "GRE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses ncs_rpc_notif_PIM-MDT-CACHE-BAG;
      }
    }
  }

  grouping ncs_rpc_notif_BGP-AF-TABLE {
    description
      "Common node of vrf, default-context";
    container bgp-afs {
      description
        "PIM BGP SAFI table";
      list bgp-af {
        key "source-address group-address";
        description
          "PIM BGP SAFI information";
        leaf source-address {
          type inet:ip-address-no-zone;
          description
            "Source IP address";
        }
        leaf group-address {
          type inet:ip-address-no-zone;
          description
            "Group IP address";
        }
        uses ncs_rpc_notif_PIM-BGP-SAFI-BAG;
      }
    }
  }

  grouping ncs_rpc_notif_VRF-TABLE {
    description
      "Common node of active, standby";
    container vrfs {
      description
        "VRF Table";
      list vrf {
        key "vrf-name";
        description
          "VRF name";
        container mvpn-sr-p2mp-entries {
          description
            "MVPN SR P2MP database table";
          list mvpn-sr-p2mp-entry {
            key "policy-name";
            description
              "MVPN SR P2MP database entry";
            leaf policy-name {
              type xr:ncs_rpc_notif_Cisco-ios-xr-string;
              description
                "Policy Name";
            }
            uses ncs_rpc_notif_PIM-SRP2MP-MDT-TUNNEL-DB-BAG;
          }
        }
        container mvpn-database-segment-routing {
          description
            "MVPN MDT Segment Routing tunnel database";
          uses ncs_rpc_notif_PIM-TREESID-MDT-TUNNEL-DB-BAG;
        }
        container mvpn-database-rsvp-te {
          description
            "MVPN MDT RSVPTE tunnel database";
          uses ncs_rpc_notif_PIM-P2MPTE-MDT-TUNNEL-DB-BAG;
        }
        container mvpn-context {
          description
            "MVPN context information";
          uses ncs_rpc_notif_PIM-CONTEXT-BAG;
        }
        container mvpn-pes {
          description
            "MVPN PE Information";
          list mvpn-pe {
            key "pe-prefix";
            description
              "MVPN PE Address information";
            leaf pe-prefix {
              type inet:ip-address-no-zone;
              description
                "PE address";
            }
            uses ncs_rpc_notif_PIM-PE-BAG;
          }
        }
        container mvpn-database-ir {
          description
            "MVPN MDT IR tunnel database";
          uses ncs_rpc_notif_PIM-MDT-TUNNEL-DB-BAG;
        }
        leaf vrf-name {
          type xr:ncs_rpc_notif_Cisco-ios-xr-string;
          description
            "VRF name ";
        }
        uses ncs_rpc_notif_MDT-INTERFACE;
        uses ncs_rpc_notif_LOCAL-ENTRY-TABLE;
        uses ncs_rpc_notif_MDT-RSVP-TE-REMOTE-ENTRY-TABLE;
        uses ncs_rpc_notif_MDT-CACHE-SUMMARY;
        uses ncs_rpc_notif_MDT-DATABASE-IR;
        uses ncs_rpc_notif_MDT-GRE-CACHE-TABLE;
        uses ncs_rpc_notif_MDT-IR-REMOTE-ENTRY-TABLE;
        uses ncs_rpc_notif_MDT-DATABASE-RSVP-TE;
        uses ncs_rpc_notif_BSR;
        uses ncs_rpc_notif_BGP-AF-TABLE;
        uses ncs_rpc_notif_MDT-RSVP-TE-LOCAL-ENTRY-TABLE;
        uses ncs_rpc_notif_MDT-PREFIX-REMOTE-TABLE;
        uses ncs_rpc_notif_MDT-CACHE-TABLE;
        uses ncs_rpc_notif_MDT-RSVP-TE-CACHE-TABLE;
        uses ncs_rpc_notif_AUTO-RP;
        uses ncs_rpc_notif_MDT-SEGMENT-ROUTING-LOCAL-ENTRY-TABLE;
        uses ncs_rpc_notif_REMOTE-ENTRY-TABLE;
        uses ncs_rpc_notif_MDT-IR-CACHE-TABLE;
        uses ncs_rpc_notif_PE-TABLE;
        uses ncs_rpc_notif_MDT-SEGMENT-ROUTING-REMOTE-ENTRY-TABLE;
        uses ncs_rpc_notif_MDT-MLDP-CACHE-TABLE;
        uses ncs_rpc_notif_MDT-IR-LOCAL-ENTRY-TABLE;
        uses ncs_rpc_notif_MDT-PREFIX-LOCAL-TABLE;
      }
    }
  }

  grouping ncs_rpc_notif_BSR {
    description
      "Common node of vrf, default-context";
    container bsr {
      description
        "PIM BSR information";
      uses ncs_rpc_notif_RP-RELAY-TABLE;
    }
  }

  grouping ncs_rpc_notif_MDT-IR-CACHE-TABLE {
    description
      "Common node of vrf, default-context";
    container mdt-ir-caches {
      description
        "IR MDT cache";
      list mdt-ir-cache {
        key "core-source-address customer-source-address customer-group-address";
        description
          "IR MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses ncs_rpc_notif_PIM-MDT-CACHE-BAG;
      }
    }
  }

  grouping ncs_rpc_notif_MDT-PREFIX-REMOTE-TABLE {
    description
      "Common node of vrf, default-context";
    container mdt-prefix-remotes {
      description
        "PIM MDT prefix remote table";
      list mdt-prefix-remote {
        key "mdt-prefix";
        description
          "PIM MDT prefix information";
        leaf mdt-prefix {
          type inet:ip-address-no-zone;
          description
            "MDT data prefix address";
        }
        uses ncs_rpc_notif_PIM-MDT-DATA-PFX-BAG;
      }
    }
  }

  grouping ncs_rpc_notif_MDT-DATABASE-RSVP-TE {
    description
      "Common node of vrf, default-context";
    container mdt-database-rsvp-te {
      description
        "PIM MDT RSVPTE tunnel database";
      uses ncs_rpc_notif_PIM-P2MPTE-MDT-TUNNEL-DB-BAG;
    }
  }

  grouping ncs_rpc_notif_PROCESS {
    description
      "Common node of active, standby";
    container process {
      description
        "Process";
      container mvpn-identifiers {
        description
          "MVPN Identifier Table";
        list mvpn-identifier {
          key "mvpn-identifier";
          description
            "MVPN Identifier";
          leaf mvpn-identifier {
            type uint32;
            description
              "MVPN Identifier";
          }
          uses ncs_rpc_notif_PIM-MVPN-ID-INFO;
        }
      }
      container mvpn-segmenteds {
        description
          "MVPN SEGMENT DB Table";
        list mvpn-segmented {
          key "rd network";
          description
            "MVPN SEGMENT DB Entry";
          leaf rd {
            type ncs_rpc_notif_Route-distinguisher;
            description
              "Route Distinguisher value";
          }
          leaf network {
            type inet:ip-prefix;
            description
              "Network in prefix/length format";
          }
          uses ncs_rpc_notif_PIM-SEGMENT-DB-BAG;
        }
      }
    }
  }

  grouping ncs_rpc_notif_MDT-IR-REMOTE-ENTRY-TABLE {
    description
      "Common node of vrf, default-context";
    container ir-remote-entries {
      description
        "PIM MDT ir remote table";
      list ir-remote-entry {
        key "tunnel-type label";
        description
          "PIM MDT ir remote table";
        leaf tunnel-type {
          type uint32;
          description
            "Tunnel Type";
        }
        leaf label {
          type uint32;
          description
            "Label";
        }
        uses ncs_rpc_notif_PIM-MDT-DATA-IR-BAG;
      }
    }
  }

  grouping ncs_rpc_notif_MDT-RSVP-TE-LOCAL-ENTRY-TABLE {
    description
      "Common node of vrf, default-context";
    container rsvp-te-local-entries {
      description
        "PIM MDT RSVP-TE local table";
      list rsvp-te-local-entry {
        key "p2mp-id tunnel-id extended-tunnel-d core-id";
        description
          "PIM MDT RSVP-TE local table";
        leaf p2mp-id {
          type uint32;
          description
            "Core ID";
        }
        leaf tunnel-id {
          type uint32;
          description
            "Tunnel ID";
        }
        leaf extended-tunnel-d {
          type inet:ip-address-no-zone;
          description
            "Extended Tunnel ID";
        }
        leaf core-id {
          type uint32;
          description
            "Core ID";
        }
        uses ncs_rpc_notif_PIM-MDT-DATA-RSVPTE-BAG;
      }
    }
  }

  grouping ncs_rpc_notif_MDT-PREFIX-LOCAL-TABLE {
    description
      "Common node of vrf, default-context";
    container mdt-prefix-locals {
      description
        "PIM MDT prefix local table";
      list mdt-prefix-local {
        key "mdt-prefix";
        description
          "PIM MDT prefix information";
        leaf mdt-prefix {
          type inet:ip-address-no-zone;
          description
            "MDT data prefix address";
        }
        uses ncs_rpc_notif_PIM-MDT-DATA-PFX-BAG;
      }
    }
  }

  grouping ncs_rpc_notif_MDT-MLDP-CACHE-TABLE {
    description
      "Common node of vrf, default-context";
    container mdt-mldp-caches {
      description
        "MLDP MDT cache";
      list mdt-mldp-cache {
        key "core-source-address customer-source-address customer-group-address";
        description
          "MLDP MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses ncs_rpc_notif_PIM-MDT-CACHE-BAG;
      }
    }
  }

  grouping ncs_rpc_notif_PE-TABLE {
    description
      "Common node of vrf, default-context";
    container pes {
      description
        "PIM MVPN PE Information";
      list pe {
        key "pe-prefix";
        description
          "PIM PE Address information";
        leaf pe-prefix {
          type inet:ip-address-no-zone;
          description
            "PE address";
        }
        uses ncs_rpc_notif_PIM-PE-BAG;
      }
    }
  }

  grouping ncs_rpc_notif_RP-RELAY-TABLE {
    description
      "Common node of auto-rp, bsr";
    container rp-relays {
      description
        "PIM rp-relay database";
      list rp-relay {
        key "vrf-name";
        description
          "PIM Relay";
        leaf vrf-name {
          type xr:ncs_rpc_notif_Cisco-ios-xr-string;
          description
            "VRF name ";
        }
        uses ncs_rpc_notif_PIM-RELAY-BAG;
      }
    }
  }

  grouping ncs_rpc_notif_ACTIVE {
    description
      "Common node of mvpn, ipv6-mvpn";
    container active {
      description
        "Active Process";
      uses ncs_rpc_notif_VRF-TABLE;
      uses ncs_rpc_notif_DEFAULT-CONTEXT;
      uses ncs_rpc_notif_PROCESS;
    }
  }

  grouping ncs_rpc_notif_MDT-RSVP-TE-REMOTE-ENTRY-TABLE {
    description
      "Common node of vrf, default-context";
    container rsvp-te-remote-entries {
      description
        "PIM MDT RSVP-TE remote table";
      list rsvp-te-remote-entry {
        key "p2mp-id tunnel-id extended-tunnel-id";
        description
          "PIM MDT RSVP-TE remote table";
        leaf p2mp-id {
          type uint32;
          description
            "Core ID";
        }
        leaf tunnel-id {
          type uint32;
          description
            "Tunnel ID";
        }
        leaf extended-tunnel-id {
          type inet:ip-address-no-zone;
          description
            "Extended Tunnel ID";
        }
        uses ncs_rpc_notif_PIM-MDT-DATA-RSVPTE-BAG;
      }
    }
  }

  grouping ncs_rpc_notif_MDT-DATABASE-IR {
    description
      "Common node of vrf, default-context";
    container mdt-database-ir {
      description
        "PIM MDT IR tunnel database";
      uses ncs_rpc_notif_PIM-MDT-TUNNEL-DB-BAG;
    }
  }

  grouping ncs_rpc_notif_REMOTE-ENTRY-TABLE {
    description
      "Common node of vrf, default-context";
    container remote-entries {
      description
        "PIM MDT mldp remote table";
      list remote-entry {
        key "tree-type opaque-type oui vpn-index core-id";
        description
          "PIM MDT mldp remote table";
        leaf tree-type {
          type ncs_rpc_notif_Pim-mdt-mldp;
          description
            "Tree Type";
        }
        leaf opaque-type {
          type ncs_rpc_notif_Pim-mldp-opaque;
          description
            "Opaque Type";
        }
        leaf oui {
          type uint32;
          description
            "OUI";
        }
        leaf vpn-index {
          type uint32;
          description
            "VPN Index";
        }
        leaf core-id {
          type uint32;
          description
            "Core ID";
        }
        uses ncs_rpc_notif_PIM-MDT-DATA-MLDP-BAG;
      }
    }
  }

  grouping ncs_rpc_notif_MDT-SEGMENT-ROUTING-LOCAL-ENTRY-TABLE {
    description
      "Common node of vrf, default-context";
    container mdt-segment-routing-local-entries {
      description
        "PIM MDT Segment Routing local table";
      list mdt-segment-routing-local-entry {
        key "tree-id";
        description
          "PIM MDT Segment Routing local entry";
        leaf tree-id {
          type uint32;
          description
            "Tree ID";
        }
        uses ncs_rpc_notif_PIM-MDT-DATA-TREESID-BAG;
      }
    }
  }

  grouping ncs_rpc_notif_DEFAULT-CONTEXT {
    description
      "Common node of active, standby";
    container default-context {
      description
        "Default Context";
      uses ncs_rpc_notif_MDT-INTERFACE;
      uses ncs_rpc_notif_LOCAL-ENTRY-TABLE;
      uses ncs_rpc_notif_MDT-RSVP-TE-REMOTE-ENTRY-TABLE;
      uses ncs_rpc_notif_MDT-CACHE-SUMMARY;
      uses ncs_rpc_notif_MDT-DATABASE-IR;
      uses ncs_rpc_notif_MDT-GRE-CACHE-TABLE;
      uses ncs_rpc_notif_MDT-IR-REMOTE-ENTRY-TABLE;
      uses ncs_rpc_notif_MDT-DATABASE-RSVP-TE;
      uses ncs_rpc_notif_BSR;
      uses ncs_rpc_notif_BGP-AF-TABLE;
      uses ncs_rpc_notif_MDT-RSVP-TE-LOCAL-ENTRY-TABLE;
      uses ncs_rpc_notif_MDT-PREFIX-REMOTE-TABLE;
      uses ncs_rpc_notif_MDT-CACHE-TABLE;
      uses ncs_rpc_notif_MDT-RSVP-TE-CACHE-TABLE;
      uses ncs_rpc_notif_AUTO-RP;
      uses ncs_rpc_notif_MDT-SEGMENT-ROUTING-LOCAL-ENTRY-TABLE;
      uses ncs_rpc_notif_REMOTE-ENTRY-TABLE;
      uses ncs_rpc_notif_MDT-IR-CACHE-TABLE;
      uses ncs_rpc_notif_PE-TABLE;
      uses ncs_rpc_notif_MDT-SEGMENT-ROUTING-REMOTE-ENTRY-TABLE;
      uses ncs_rpc_notif_MDT-MLDP-CACHE-TABLE;
      uses ncs_rpc_notif_MDT-IR-LOCAL-ENTRY-TABLE;
      uses ncs_rpc_notif_MDT-PREFIX-LOCAL-TABLE;
    }
  }

  grouping ncs_rpc_notif_MDT-CACHE-SUMMARY {
    description
      "Common node of vrf, default-context";
    container mdt-cache-summary {
      description
        "PIM MDT cache summary";
      uses ncs_rpc_notif_PIM-MDT-CACHE-SUMM-BAG;
    }
  }

  grouping ncs_rpc_notif_STANDBY {
    description
      "Common node of mvpn, ipv6-mvpn";
    container standby {
      description
        "Standby Process";
      uses ncs_rpc_notif_VRF-TABLE;
      uses ncs_rpc_notif_DEFAULT-CONTEXT;
      uses ncs_rpc_notif_PROCESS;
    }
  }

  grouping ncs_rpc_notif_MDT-SEGMENT-ROUTING-REMOTE-ENTRY-TABLE {
    description
      "Common node of vrf, default-context";
    container mdt-segment-routing-remote-entries {
      description
        "PIM MDT Segment Routing remote table";
      list mdt-segment-routing-remote-entry {
        key "tree-id";
        description
          "PIM MDT Segment Routing remote table";
        leaf tree-id {
          type uint32;
          description
            "Tree ID";
        }
        uses ncs_rpc_notif_PIM-MDT-DATA-TREESID-BAG;
      }
    }
  }

  grouping live_ncs_LOCAL-ENTRY-TABLE {
    description
      "Common node of vrf, default-context";
    container local-entries {
      description
        "PIM MDT mldp local table";
      list local-entry {
        key "tree-type opaque-type oui vpn-index core-id";
        description
          "PIM MDT mldp local table";
        leaf tree-type {
          type live_ncs_Pim-mdt-mldp;
          description
            "Tree Type";
        }
        leaf opaque-type {
          type live_ncs_Pim-mldp-opaque;
          description
            "Opaque Type";
        }
        leaf oui {
          type uint32;
          description
            "OUI";
        }
        leaf vpn-index {
          type uint32;
          description
            "VPN Index";
        }
        leaf core-id {
          type uint32;
          description
            "Core ID";
        }
        uses live_ncs_PIM-MDT-DATA-MLDP-BAG;
      }
    }
  }

  grouping live_ncs_AUTO-RP {
    description
      "Common node of vrf, default-context";
    container auto-rp {
      description
        "PIM Auto-RP information";
      uses live_ncs_RP-RELAY-TABLE;
    }
  }

  grouping live_ncs_MDT-CACHE-TABLE {
    description
      "Common node of vrf, default-context";
    container mdt-caches {
      description
        "PIM MDT cache";
      list mdt-cache {
        key "core-type core-source-address customer-source-address customer-group-address";
        description
          "PIM MDT cache information";
        leaf core-type {
          type live_ncs_Mdt-core;
          description
            "MDT Core type";
        }
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses live_ncs_PIM-MDT-CACHE-BAG;
      }
    }
  }

  grouping live_ncs_MDT-IR-LOCAL-ENTRY-TABLE {
    description
      "Common node of vrf, default-context";
    container ir-local-entries {
      description
        "PIM MDT ir local table";
      list ir-local-entry {
        key "core-id";
        description
          "PIM MDT ir local table";
        leaf core-id {
          type uint32;
          description
            "Core ID";
        }
        uses live_ncs_PIM-MDT-DATA-IR-BAG;
      }
    }
  }

  grouping live_ncs_MDT-RSVP-TE-CACHE-TABLE {
    description
      "Common node of vrf, default-context";
    container mdt-rsvp-te-caches {
      description
        "RSVPTE MDT cache";
      list mdt-rsvp-te-cache {
        key "core-source-address customer-source-address customer-group-address";
        description
          "RSVPTE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses live_ncs_PIM-MDT-CACHE-BAG;
      }
    }
  }

  grouping live_ncs_MDT-INTERFACE {
    description
      "Common node of vrf, default-context";
    container mdt-interface {
      description
        "MDT interface information";
      uses live_ncs_PIM-MDT-INTERFACE-BAG;
    }
  }

  grouping live_ncs_MDT-GRE-CACHE-TABLE {
    description
      "Common node of vrf, default-context";
    container mdt-gre-caches {
      description
        "GRE MDT cache";
      list mdt-gre-cache {
        key "core-source-address customer-source-address customer-group-address";
        description
          "GRE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses live_ncs_PIM-MDT-CACHE-BAG;
      }
    }
  }

  grouping live_ncs_BGP-AF-TABLE {
    description
      "Common node of vrf, default-context";
    container bgp-afs {
      description
        "PIM BGP SAFI table";
      list bgp-af {
        key "source-address group-address";
        description
          "PIM BGP SAFI information";
        leaf source-address {
          type inet:ip-address-no-zone;
          description
            "Source IP address";
        }
        leaf group-address {
          type inet:ip-address-no-zone;
          description
            "Group IP address";
        }
        uses live_ncs_PIM-BGP-SAFI-BAG;
      }
    }
  }

  grouping live_ncs_VRF-TABLE {
    description
      "Common node of active, standby";
    container vrfs {
      description
        "VRF Table";
      list vrf {
        key "vrf-name";
        description
          "VRF name";
        container mvpn-sr-p2mp-entries {
          description
            "MVPN SR P2MP database table";
          list mvpn-sr-p2mp-entry {
            key "policy-name";
            description
              "MVPN SR P2MP database entry";
            leaf policy-name {
              type xr:live_ncs_Cisco-ios-xr-string;
              description
                "Policy Name";
            }
            uses live_ncs_PIM-SRP2MP-MDT-TUNNEL-DB-BAG;
          }
        }
        container mvpn-database-segment-routing {
          description
            "MVPN MDT Segment Routing tunnel database";
          uses live_ncs_PIM-TREESID-MDT-TUNNEL-DB-BAG;
        }
        container mvpn-database-rsvp-te {
          description
            "MVPN MDT RSVPTE tunnel database";
          uses live_ncs_PIM-P2MPTE-MDT-TUNNEL-DB-BAG;
        }
        container mvpn-context {
          description
            "MVPN context information";
          uses live_ncs_PIM-CONTEXT-BAG;
        }
        container mvpn-pes {
          description
            "MVPN PE Information";
          list mvpn-pe {
            key "pe-prefix";
            description
              "MVPN PE Address information";
            leaf pe-prefix {
              type inet:ip-address-no-zone;
              description
                "PE address";
            }
            uses live_ncs_PIM-PE-BAG;
          }
        }
        container mvpn-database-ir {
          description
            "MVPN MDT IR tunnel database";
          uses live_ncs_PIM-MDT-TUNNEL-DB-BAG;
        }
        leaf vrf-name {
          type xr:live_ncs_Cisco-ios-xr-string;
          description
            "VRF name ";
        }
        uses live_ncs_MDT-INTERFACE;
        uses live_ncs_LOCAL-ENTRY-TABLE;
        uses live_ncs_MDT-RSVP-TE-REMOTE-ENTRY-TABLE;
        uses live_ncs_MDT-CACHE-SUMMARY;
        uses live_ncs_MDT-DATABASE-IR;
        uses live_ncs_MDT-GRE-CACHE-TABLE;
        uses live_ncs_MDT-IR-REMOTE-ENTRY-TABLE;
        uses live_ncs_MDT-DATABASE-RSVP-TE;
        uses live_ncs_BSR;
        uses live_ncs_BGP-AF-TABLE;
        uses live_ncs_MDT-RSVP-TE-LOCAL-ENTRY-TABLE;
        uses live_ncs_MDT-PREFIX-REMOTE-TABLE;
        uses live_ncs_MDT-CACHE-TABLE;
        uses live_ncs_MDT-RSVP-TE-CACHE-TABLE;
        uses live_ncs_AUTO-RP;
        uses live_ncs_MDT-SEGMENT-ROUTING-LOCAL-ENTRY-TABLE;
        uses live_ncs_REMOTE-ENTRY-TABLE;
        uses live_ncs_MDT-IR-CACHE-TABLE;
        uses live_ncs_PE-TABLE;
        uses live_ncs_MDT-SEGMENT-ROUTING-REMOTE-ENTRY-TABLE;
        uses live_ncs_MDT-MLDP-CACHE-TABLE;
        uses live_ncs_MDT-IR-LOCAL-ENTRY-TABLE;
        uses live_ncs_MDT-PREFIX-LOCAL-TABLE;
      }
    }
  }

  grouping live_ncs_BSR {
    description
      "Common node of vrf, default-context";
    container bsr {
      description
        "PIM BSR information";
      uses live_ncs_RP-RELAY-TABLE;
    }
  }

  grouping live_ncs_MDT-IR-CACHE-TABLE {
    description
      "Common node of vrf, default-context";
    container mdt-ir-caches {
      description
        "IR MDT cache";
      list mdt-ir-cache {
        key "core-source-address customer-source-address customer-group-address";
        description
          "IR MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses live_ncs_PIM-MDT-CACHE-BAG;
      }
    }
  }

  grouping live_ncs_MDT-PREFIX-REMOTE-TABLE {
    description
      "Common node of vrf, default-context";
    container mdt-prefix-remotes {
      description
        "PIM MDT prefix remote table";
      list mdt-prefix-remote {
        key "mdt-prefix";
        description
          "PIM MDT prefix information";
        leaf mdt-prefix {
          type inet:ip-address-no-zone;
          description
            "MDT data prefix address";
        }
        uses live_ncs_PIM-MDT-DATA-PFX-BAG;
      }
    }
  }

  grouping live_ncs_MDT-DATABASE-RSVP-TE {
    description
      "Common node of vrf, default-context";
    container mdt-database-rsvp-te {
      description
        "PIM MDT RSVPTE tunnel database";
      uses live_ncs_PIM-P2MPTE-MDT-TUNNEL-DB-BAG;
    }
  }

  grouping live_ncs_PROCESS {
    description
      "Common node of active, standby";
    container process {
      description
        "Process";
      container mvpn-identifiers {
        description
          "MVPN Identifier Table";
        list mvpn-identifier {
          key "mvpn-identifier";
          description
            "MVPN Identifier";
          leaf mvpn-identifier {
            type uint32;
            description
              "MVPN Identifier";
          }
          uses live_ncs_PIM-MVPN-ID-INFO;
        }
      }
      container mvpn-segmenteds {
        description
          "MVPN SEGMENT DB Table";
        list mvpn-segmented {
          key "rd network";
          description
            "MVPN SEGMENT DB Entry";
          leaf rd {
            type live_ncs_Route-distinguisher;
            description
              "Route Distinguisher value";
          }
          leaf network {
            type inet:ip-prefix;
            description
              "Network in prefix/length format";
          }
          uses live_ncs_PIM-SEGMENT-DB-BAG;
        }
      }
    }
  }

  grouping live_ncs_MDT-IR-REMOTE-ENTRY-TABLE {
    description
      "Common node of vrf, default-context";
    container ir-remote-entries {
      description
        "PIM MDT ir remote table";
      list ir-remote-entry {
        key "tunnel-type label";
        description
          "PIM MDT ir remote table";
        leaf tunnel-type {
          type uint32;
          description
            "Tunnel Type";
        }
        leaf label {
          type uint32;
          description
            "Label";
        }
        uses live_ncs_PIM-MDT-DATA-IR-BAG;
      }
    }
  }

  grouping live_ncs_MDT-RSVP-TE-LOCAL-ENTRY-TABLE {
    description
      "Common node of vrf, default-context";
    container rsvp-te-local-entries {
      description
        "PIM MDT RSVP-TE local table";
      list rsvp-te-local-entry {
        key "p2mp-id tunnel-id extended-tunnel-d core-id";
        description
          "PIM MDT RSVP-TE local table";
        leaf p2mp-id {
          type uint32;
          description
            "Core ID";
        }
        leaf tunnel-id {
          type uint32;
          description
            "Tunnel ID";
        }
        leaf extended-tunnel-d {
          type inet:ip-address-no-zone;
          description
            "Extended Tunnel ID";
        }
        leaf core-id {
          type uint32;
          description
            "Core ID";
        }
        uses live_ncs_PIM-MDT-DATA-RSVPTE-BAG;
      }
    }
  }

  grouping live_ncs_MDT-PREFIX-LOCAL-TABLE {
    description
      "Common node of vrf, default-context";
    container mdt-prefix-locals {
      description
        "PIM MDT prefix local table";
      list mdt-prefix-local {
        key "mdt-prefix";
        description
          "PIM MDT prefix information";
        leaf mdt-prefix {
          type inet:ip-address-no-zone;
          description
            "MDT data prefix address";
        }
        uses live_ncs_PIM-MDT-DATA-PFX-BAG;
      }
    }
  }

  grouping live_ncs_MDT-MLDP-CACHE-TABLE {
    description
      "Common node of vrf, default-context";
    container mdt-mldp-caches {
      description
        "MLDP MDT cache";
      list mdt-mldp-cache {
        key "core-source-address customer-source-address customer-group-address";
        description
          "MLDP MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses live_ncs_PIM-MDT-CACHE-BAG;
      }
    }
  }

  grouping live_ncs_PE-TABLE {
    description
      "Common node of vrf, default-context";
    container pes {
      description
        "PIM MVPN PE Information";
      list pe {
        key "pe-prefix";
        description
          "PIM PE Address information";
        leaf pe-prefix {
          type inet:ip-address-no-zone;
          description
            "PE address";
        }
        uses live_ncs_PIM-PE-BAG;
      }
    }
  }

  grouping live_ncs_RP-RELAY-TABLE {
    description
      "Common node of auto-rp, bsr";
    container rp-relays {
      description
        "PIM rp-relay database";
      list rp-relay {
        key "vrf-name";
        description
          "PIM Relay";
        leaf vrf-name {
          type xr:live_ncs_Cisco-ios-xr-string;
          description
            "VRF name ";
        }
        uses live_ncs_PIM-RELAY-BAG;
      }
    }
  }

  grouping live_ncs_ACTIVE {
    description
      "Common node of mvpn, ipv6-mvpn";
    container active {
      description
        "Active Process";
      uses live_ncs_VRF-TABLE;
      uses live_ncs_DEFAULT-CONTEXT;
      uses live_ncs_PROCESS;
    }
  }

  grouping live_ncs_MDT-RSVP-TE-REMOTE-ENTRY-TABLE {
    description
      "Common node of vrf, default-context";
    container rsvp-te-remote-entries {
      description
        "PIM MDT RSVP-TE remote table";
      list rsvp-te-remote-entry {
        key "p2mp-id tunnel-id extended-tunnel-id";
        description
          "PIM MDT RSVP-TE remote table";
        leaf p2mp-id {
          type uint32;
          description
            "Core ID";
        }
        leaf tunnel-id {
          type uint32;
          description
            "Tunnel ID";
        }
        leaf extended-tunnel-id {
          type inet:ip-address-no-zone;
          description
            "Extended Tunnel ID";
        }
        uses live_ncs_PIM-MDT-DATA-RSVPTE-BAG;
      }
    }
  }

  grouping live_ncs_MDT-DATABASE-IR {
    description
      "Common node of vrf, default-context";
    container mdt-database-ir {
      description
        "PIM MDT IR tunnel database";
      uses live_ncs_PIM-MDT-TUNNEL-DB-BAG;
    }
  }

  grouping live_ncs_REMOTE-ENTRY-TABLE {
    description
      "Common node of vrf, default-context";
    container remote-entries {
      description
        "PIM MDT mldp remote table";
      list remote-entry {
        key "tree-type opaque-type oui vpn-index core-id";
        description
          "PIM MDT mldp remote table";
        leaf tree-type {
          type live_ncs_Pim-mdt-mldp;
          description
            "Tree Type";
        }
        leaf opaque-type {
          type live_ncs_Pim-mldp-opaque;
          description
            "Opaque Type";
        }
        leaf oui {
          type uint32;
          description
            "OUI";
        }
        leaf vpn-index {
          type uint32;
          description
            "VPN Index";
        }
        leaf core-id {
          type uint32;
          description
            "Core ID";
        }
        uses live_ncs_PIM-MDT-DATA-MLDP-BAG;
      }
    }
  }

  grouping live_ncs_MDT-SEGMENT-ROUTING-LOCAL-ENTRY-TABLE {
    description
      "Common node of vrf, default-context";
    container mdt-segment-routing-local-entries {
      description
        "PIM MDT Segment Routing local table";
      list mdt-segment-routing-local-entry {
        key "tree-id";
        description
          "PIM MDT Segment Routing local entry";
        leaf tree-id {
          type uint32;
          description
            "Tree ID";
        }
        uses live_ncs_PIM-MDT-DATA-TREESID-BAG;
      }
    }
  }

  grouping live_ncs_DEFAULT-CONTEXT {
    description
      "Common node of active, standby";
    container default-context {
      description
        "Default Context";
      uses live_ncs_MDT-INTERFACE;
      uses live_ncs_LOCAL-ENTRY-TABLE;
      uses live_ncs_MDT-RSVP-TE-REMOTE-ENTRY-TABLE;
      uses live_ncs_MDT-CACHE-SUMMARY;
      uses live_ncs_MDT-DATABASE-IR;
      uses live_ncs_MDT-GRE-CACHE-TABLE;
      uses live_ncs_MDT-IR-REMOTE-ENTRY-TABLE;
      uses live_ncs_MDT-DATABASE-RSVP-TE;
      uses live_ncs_BSR;
      uses live_ncs_BGP-AF-TABLE;
      uses live_ncs_MDT-RSVP-TE-LOCAL-ENTRY-TABLE;
      uses live_ncs_MDT-PREFIX-REMOTE-TABLE;
      uses live_ncs_MDT-CACHE-TABLE;
      uses live_ncs_MDT-RSVP-TE-CACHE-TABLE;
      uses live_ncs_AUTO-RP;
      uses live_ncs_MDT-SEGMENT-ROUTING-LOCAL-ENTRY-TABLE;
      uses live_ncs_REMOTE-ENTRY-TABLE;
      uses live_ncs_MDT-IR-CACHE-TABLE;
      uses live_ncs_PE-TABLE;
      uses live_ncs_MDT-SEGMENT-ROUTING-REMOTE-ENTRY-TABLE;
      uses live_ncs_MDT-MLDP-CACHE-TABLE;
      uses live_ncs_MDT-IR-LOCAL-ENTRY-TABLE;
      uses live_ncs_MDT-PREFIX-LOCAL-TABLE;
    }
  }

  grouping live_ncs_MDT-CACHE-SUMMARY {
    description
      "Common node of vrf, default-context";
    container mdt-cache-summary {
      description
        "PIM MDT cache summary";
      uses live_ncs_PIM-MDT-CACHE-SUMM-BAG;
    }
  }

  grouping live_ncs_STANDBY {
    description
      "Common node of mvpn, ipv6-mvpn";
    container standby {
      description
        "Standby Process";
      uses live_ncs_VRF-TABLE;
      uses live_ncs_DEFAULT-CONTEXT;
      uses live_ncs_PROCESS;
    }
  }

  grouping live_ncs_MDT-SEGMENT-ROUTING-REMOTE-ENTRY-TABLE {
    description
      "Common node of vrf, default-context";
    container mdt-segment-routing-remote-entries {
      description
        "PIM MDT Segment Routing remote table";
      list mdt-segment-routing-remote-entry {
        key "tree-id";
        description
          "PIM MDT Segment Routing remote table";
        leaf tree-id {
          type uint32;
          description
            "Tree ID";
        }
        uses live_ncs_PIM-MDT-DATA-TREESID-BAG;
      }
    }
  }

  grouping LOCAL-ENTRY-TABLE {
    description
      "Common node of vrf, default-context";
    container local-entries {
      description
        "PIM MDT mldp local table";
      list local-entry {
        key "tree-type opaque-type oui vpn-index core-id";
        description
          "PIM MDT mldp local table";
        leaf tree-type {
          type Pim-mdt-mldp;
          description
            "Tree Type";
        }
        leaf opaque-type {
          type Pim-mldp-opaque;
          description
            "Opaque Type";
        }
        leaf oui {
          type uint32;
          description
            "OUI";
        }
        leaf vpn-index {
          type uint32;
          description
            "VPN Index";
        }
        leaf core-id {
          type uint32;
          description
            "Core ID";
        }
        uses PIM-MDT-DATA-MLDP-BAG;
      }
    }
  }

  grouping AUTO-RP {
    description
      "Common node of vrf, default-context";
    container auto-rp {
      description
        "PIM Auto-RP information";
      uses RP-RELAY-TABLE;
    }
  }

  grouping MDT-CACHE-TABLE {
    description
      "Common node of vrf, default-context";
    container mdt-caches {
      description
        "PIM MDT cache";
      list mdt-cache {
        key "core-type core-source-address customer-source-address customer-group-address";
        description
          "PIM MDT cache information";
        leaf core-type {
          type Mdt-core;
          description
            "MDT Core type";
        }
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-IR-LOCAL-ENTRY-TABLE {
    description
      "Common node of vrf, default-context";
    container ir-local-entries {
      description
        "PIM MDT ir local table";
      list ir-local-entry {
        key "core-id";
        description
          "PIM MDT ir local table";
        leaf core-id {
          type uint32;
          description
            "Core ID";
        }
        uses PIM-MDT-DATA-IR-BAG;
      }
    }
  }

  grouping MDT-RSVP-TE-CACHE-TABLE {
    description
      "Common node of vrf, default-context";
    container mdt-rsvp-te-caches {
      description
        "RSVPTE MDT cache";
      list mdt-rsvp-te-cache {
        key "core-source-address customer-source-address customer-group-address";
        description
          "RSVPTE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-INTERFACE {
    description
      "Common node of vrf, default-context";
    container mdt-interface {
      description
        "MDT interface information";
      uses PIM-MDT-INTERFACE-BAG;
    }
  }

  grouping MDT-GRE-CACHE-TABLE {
    description
      "Common node of vrf, default-context";
    container mdt-gre-caches {
      description
        "GRE MDT cache";
      list mdt-gre-cache {
        key "core-source-address customer-source-address customer-group-address";
        description
          "GRE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping BGP-AF-TABLE {
    description
      "Common node of vrf, default-context";
    container bgp-afs {
      description
        "PIM BGP SAFI table";
      list bgp-af {
        key "source-address group-address";
        description
          "PIM BGP SAFI information";
        leaf source-address {
          type inet:ip-address-no-zone;
          description
            "Source IP address";
        }
        leaf group-address {
          type inet:ip-address-no-zone;
          description
            "Group IP address";
        }
        uses PIM-BGP-SAFI-BAG;
      }
    }
  }

  grouping VRF-TABLE {
    description
      "Common node of active, standby";
    container vrfs {
      description
        "VRF Table";
      list vrf {
        key "vrf-name";
        description
          "VRF name";
        container mvpn-sr-p2mp-entries {
          description
            "MVPN SR P2MP database table";
          list mvpn-sr-p2mp-entry {
            key "policy-name";
            description
              "MVPN SR P2MP database entry";
            leaf policy-name {
              type xr:Cisco-ios-xr-string;
              description
                "Policy Name";
            }
            uses PIM-SRP2MP-MDT-TUNNEL-DB-BAG;
          }
        }
        container mvpn-database-segment-routing {
          description
            "MVPN MDT Segment Routing tunnel database";
          uses PIM-TREESID-MDT-TUNNEL-DB-BAG;
        }
        container mvpn-database-rsvp-te {
          description
            "MVPN MDT RSVPTE tunnel database";
          uses PIM-P2MPTE-MDT-TUNNEL-DB-BAG;
        }
        container mvpn-context {
          description
            "MVPN context information";
          uses PIM-CONTEXT-BAG;
        }
        container mvpn-pes {
          description
            "MVPN PE Information";
          list mvpn-pe {
            key "pe-prefix";
            description
              "MVPN PE Address information";
            leaf pe-prefix {
              type inet:ip-address-no-zone;
              description
                "PE address";
            }
            uses PIM-PE-BAG;
          }
        }
        container mvpn-database-ir {
          description
            "MVPN MDT IR tunnel database";
          uses PIM-MDT-TUNNEL-DB-BAG;
        }
        leaf vrf-name {
          type xr:Cisco-ios-xr-string {
            length "1..32";
          }
          description
            "VRF name ";
        }
        uses MDT-INTERFACE;
        uses LOCAL-ENTRY-TABLE;
        uses MDT-RSVP-TE-REMOTE-ENTRY-TABLE;
        uses MDT-CACHE-SUMMARY;
        uses MDT-DATABASE-IR;
        uses MDT-GRE-CACHE-TABLE;
        uses MDT-IR-REMOTE-ENTRY-TABLE;
        uses MDT-DATABASE-RSVP-TE;
        uses BSR;
        uses BGP-AF-TABLE;
        uses MDT-RSVP-TE-LOCAL-ENTRY-TABLE;
        uses MDT-PREFIX-REMOTE-TABLE;
        uses MDT-CACHE-TABLE;
        uses MDT-RSVP-TE-CACHE-TABLE;
        uses AUTO-RP;
        uses MDT-SEGMENT-ROUTING-LOCAL-ENTRY-TABLE;
        uses REMOTE-ENTRY-TABLE;
        uses MDT-IR-CACHE-TABLE;
        uses PE-TABLE;
        uses MDT-SEGMENT-ROUTING-REMOTE-ENTRY-TABLE;
        uses MDT-MLDP-CACHE-TABLE;
        uses MDT-IR-LOCAL-ENTRY-TABLE;
        uses MDT-PREFIX-LOCAL-TABLE;
      }
    }
  }

  grouping BSR {
    description
      "Common node of vrf, default-context";
    container bsr {
      description
        "PIM BSR information";
      uses RP-RELAY-TABLE;
    }
  }

  grouping MDT-IR-CACHE-TABLE {
    description
      "Common node of vrf, default-context";
    container mdt-ir-caches {
      description
        "IR MDT cache";
      list mdt-ir-cache {
        key "core-source-address customer-source-address customer-group-address";
        description
          "IR MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-PREFIX-REMOTE-TABLE {
    description
      "Common node of vrf, default-context";
    container mdt-prefix-remotes {
      description
        "PIM MDT prefix remote table";
      list mdt-prefix-remote {
        key "mdt-prefix";
        description
          "PIM MDT prefix information";
        leaf mdt-prefix {
          type inet:ip-address-no-zone;
          description
            "MDT data prefix address";
        }
        uses PIM-MDT-DATA-PFX-BAG;
      }
    }
  }

  grouping MDT-DATABASE-RSVP-TE {
    description
      "Common node of vrf, default-context";
    container mdt-database-rsvp-te {
      description
        "PIM MDT RSVPTE tunnel database";
      uses PIM-P2MPTE-MDT-TUNNEL-DB-BAG;
    }
  }

  grouping PROCESS {
    description
      "Common node of active, standby";
    container process {
      description
        "Process";
      container mvpn-identifiers {
        description
          "MVPN Identifier Table";
        list mvpn-identifier {
          key "mvpn-identifier";
          description
            "MVPN Identifier";
          leaf mvpn-identifier {
            type uint32;
            description
              "MVPN Identifier";
          }
          uses PIM-MVPN-ID-INFO;
        }
      }
      container mvpn-segmenteds {
        description
          "MVPN SEGMENT DB Table";
        list mvpn-segmented {
          key "rd network";
          description
            "MVPN SEGMENT DB Entry";
          leaf rd {
            type Route-distinguisher;
            description
              "Route Distinguisher value";
          }
          leaf network {
            type inet:ip-prefix;
            description
              "Network in prefix/length format";
          }
          uses PIM-SEGMENT-DB-BAG;
        }
      }
    }
  }

  grouping MDT-IR-REMOTE-ENTRY-TABLE {
    description
      "Common node of vrf, default-context";
    container ir-remote-entries {
      description
        "PIM MDT ir remote table";
      list ir-remote-entry {
        key "tunnel-type label";
        description
          "PIM MDT ir remote table";
        leaf tunnel-type {
          type uint32;
          description
            "Tunnel Type";
        }
        leaf label {
          type uint32;
          description
            "Label";
        }
        uses PIM-MDT-DATA-IR-BAG;
      }
    }
  }

  grouping MDT-RSVP-TE-LOCAL-ENTRY-TABLE {
    description
      "Common node of vrf, default-context";
    container rsvp-te-local-entries {
      description
        "PIM MDT RSVP-TE local table";
      list rsvp-te-local-entry {
        key "p2mp-id tunnel-id extended-tunnel-d core-id";
        description
          "PIM MDT RSVP-TE local table";
        leaf p2mp-id {
          type uint32;
          description
            "Core ID";
        }
        leaf tunnel-id {
          type uint32;
          description
            "Tunnel ID";
        }
        leaf extended-tunnel-d {
          type inet:ip-address-no-zone;
          description
            "Extended Tunnel ID";
        }
        leaf core-id {
          type uint32;
          description
            "Core ID";
        }
        uses PIM-MDT-DATA-RSVPTE-BAG;
      }
    }
  }

  grouping MDT-PREFIX-LOCAL-TABLE {
    description
      "Common node of vrf, default-context";
    container mdt-prefix-locals {
      description
        "PIM MDT prefix local table";
      list mdt-prefix-local {
        key "mdt-prefix";
        description
          "PIM MDT prefix information";
        leaf mdt-prefix {
          type inet:ip-address-no-zone;
          description
            "MDT data prefix address";
        }
        uses PIM-MDT-DATA-PFX-BAG;
      }
    }
  }

  grouping MDT-MLDP-CACHE-TABLE {
    description
      "Common node of vrf, default-context";
    container mdt-mldp-caches {
      description
        "MLDP MDT cache";
      list mdt-mldp-cache {
        key "core-source-address customer-source-address customer-group-address";
        description
          "MLDP MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping PE-TABLE {
    description
      "Common node of vrf, default-context";
    container pes {
      description
        "PIM MVPN PE Information";
      list pe {
        key "pe-prefix";
        description
          "PIM PE Address information";
        leaf pe-prefix {
          type inet:ip-address-no-zone;
          description
            "PE address";
        }
        uses PIM-PE-BAG;
      }
    }
  }

  grouping RP-RELAY-TABLE {
    description
      "Common node of auto-rp, bsr";
    container rp-relays {
      description
        "PIM rp-relay database";
      list rp-relay {
        key "vrf-name";
        description
          "PIM Relay";
        leaf vrf-name {
          type xr:Cisco-ios-xr-string {
            length "1..32";
          }
          description
            "VRF name ";
        }
        uses PIM-RELAY-BAG;
      }
    }
  }

  grouping ACTIVE {
    description
      "Common node of mvpn, ipv6-mvpn";
    container active {
      description
        "Active Process";
      uses VRF-TABLE;
      uses DEFAULT-CONTEXT;
      uses PROCESS;
    }
  }

  grouping MDT-RSVP-TE-REMOTE-ENTRY-TABLE {
    description
      "Common node of vrf, default-context";
    container rsvp-te-remote-entries {
      description
        "PIM MDT RSVP-TE remote table";
      list rsvp-te-remote-entry {
        key "p2mp-id tunnel-id extended-tunnel-id";
        description
          "PIM MDT RSVP-TE remote table";
        leaf p2mp-id {
          type uint32;
          description
            "Core ID";
        }
        leaf tunnel-id {
          type uint32;
          description
            "Tunnel ID";
        }
        leaf extended-tunnel-id {
          type inet:ip-address-no-zone;
          description
            "Extended Tunnel ID";
        }
        uses PIM-MDT-DATA-RSVPTE-BAG;
      }
    }
  }

  grouping MDT-DATABASE-IR {
    description
      "Common node of vrf, default-context";
    container mdt-database-ir {
      description
        "PIM MDT IR tunnel database";
      uses PIM-MDT-TUNNEL-DB-BAG;
    }
  }

  grouping REMOTE-ENTRY-TABLE {
    description
      "Common node of vrf, default-context";
    container remote-entries {
      description
        "PIM MDT mldp remote table";
      list remote-entry {
        key "tree-type opaque-type oui vpn-index core-id";
        description
          "PIM MDT mldp remote table";
        leaf tree-type {
          type Pim-mdt-mldp;
          description
            "Tree Type";
        }
        leaf opaque-type {
          type Pim-mldp-opaque;
          description
            "Opaque Type";
        }
        leaf oui {
          type uint32;
          description
            "OUI";
        }
        leaf vpn-index {
          type uint32;
          description
            "VPN Index";
        }
        leaf core-id {
          type uint32;
          description
            "Core ID";
        }
        uses PIM-MDT-DATA-MLDP-BAG;
      }
    }
  }

  grouping MDT-SEGMENT-ROUTING-LOCAL-ENTRY-TABLE {
    description
      "Common node of vrf, default-context";
    container mdt-segment-routing-local-entries {
      description
        "PIM MDT Segment Routing local table";
      list mdt-segment-routing-local-entry {
        key "tree-id";
        description
          "PIM MDT Segment Routing local entry";
        leaf tree-id {
          type uint32;
          description
            "Tree ID";
        }
        uses PIM-MDT-DATA-TREESID-BAG;
      }
    }
  }

  grouping DEFAULT-CONTEXT {
    description
      "Common node of active, standby";
    container default-context {
      description
        "Default Context";
      uses MDT-INTERFACE;
      uses LOCAL-ENTRY-TABLE;
      uses MDT-RSVP-TE-REMOTE-ENTRY-TABLE;
      uses MDT-CACHE-SUMMARY;
      uses MDT-DATABASE-IR;
      uses MDT-GRE-CACHE-TABLE;
      uses MDT-IR-REMOTE-ENTRY-TABLE;
      uses MDT-DATABASE-RSVP-TE;
      uses BSR;
      uses BGP-AF-TABLE;
      uses MDT-RSVP-TE-LOCAL-ENTRY-TABLE;
      uses MDT-PREFIX-REMOTE-TABLE;
      uses MDT-CACHE-TABLE;
      uses MDT-RSVP-TE-CACHE-TABLE;
      uses AUTO-RP;
      uses MDT-SEGMENT-ROUTING-LOCAL-ENTRY-TABLE;
      uses REMOTE-ENTRY-TABLE;
      uses MDT-IR-CACHE-TABLE;
      uses PE-TABLE;
      uses MDT-SEGMENT-ROUTING-REMOTE-ENTRY-TABLE;
      uses MDT-MLDP-CACHE-TABLE;
      uses MDT-IR-LOCAL-ENTRY-TABLE;
      uses MDT-PREFIX-LOCAL-TABLE;
    }
  }

  grouping MDT-CACHE-SUMMARY {
    description
      "Common node of vrf, default-context";
    container mdt-cache-summary {
      description
        "PIM MDT cache summary";
      uses PIM-MDT-CACHE-SUMM-BAG;
    }
  }

  grouping STANDBY {
    description
      "Common node of mvpn, ipv6-mvpn";
    container standby {
      description
        "Standby Process";
      uses VRF-TABLE;
      uses DEFAULT-CONTEXT;
      uses PROCESS;
    }
  }

  grouping MDT-SEGMENT-ROUTING-REMOTE-ENTRY-TABLE {
    description
      "Common node of vrf, default-context";
    container mdt-segment-routing-remote-entries {
      description
        "PIM MDT Segment Routing remote table";
      list mdt-segment-routing-remote-entry {
        key "tree-id";
        description
          "PIM MDT Segment Routing remote table";
        leaf tree-id {
          type uint32;
          description
            "Tree ID";
        }
        uses PIM-MDT-DATA-TREESID-BAG;
      }
    }
  }

  augment "/ncs:devices/ncs:device/ncs:config" {
    // NCS drop config false container mvpn
    // NCS drop config false container 'ipv6-mvpn'
  }
  augment "/ncs:devices/ncs:device/ncs:live-status" {
    container mvpn {
      tailf:ncs-device-type "netconf";
      tailf:display-when "not(../../ncs:module) or ../../ncs:module[ncs:name='Cisco-IOS-XR-mvpn-oper'] or (../../ncs:live-status-protocol[not(ncs:capability)]) or (../../ncs:live-status-protocol/ncs:capability/ncs:module[.='Cisco-IOS-XR-mvpn-oper'])";
      description
        "MVPN operational data";
      uses live_ncs_ACTIVE;
      uses live_ncs_STANDBY;
    }
    container ipv6-mvpn {
      tailf:ncs-device-type "netconf";
      tailf:display-when "not(../../ncs:module) or ../../ncs:module[ncs:name='Cisco-IOS-XR-mvpn-oper'] or (../../ncs:live-status-protocol[not(ncs:capability)]) or (../../ncs:live-status-protocol/ncs:capability/ncs:module[.='Cisco-IOS-XR-mvpn-oper'])";
      description
        "IPv6 MVPN operational data";
      uses live_ncs_ACTIVE;
      uses live_ncs_STANDBY;
    }
  }
  augment "/ncs:devices/ncs:template/ncs:ned-id/ncs:config" {
    // NCS drop config false container mvpn
    // NCS drop config false container 'ipv6-mvpn'
  }
}

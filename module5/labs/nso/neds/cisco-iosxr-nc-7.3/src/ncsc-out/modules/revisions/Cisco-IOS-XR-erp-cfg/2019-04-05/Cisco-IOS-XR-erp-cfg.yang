module Cisco-IOS-XR-erp-cfg {
  // Generated by yanger -t ncs
  tailf:mount-id "cisco-iosxr-nc-7.3:cisco-iosxr-nc-7.3";
  tailf:ncs-device-type "netconf";

  namespace "http://cisco.com/ns/yang/Cisco-IOS-XR-erp-cfg";
  prefix erp-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR erp package configuration.

     This module contains definitions
     for the following management objects:
       erp: Ethernet Ring Protection

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    container erp {
      tailf:ncs-device-type "netconf";
      tailf:display-when "not(../../ncs:module) or ../../ncs:module[ncs:name='Cisco-IOS-XR-erp-cfg']";
      description
        "Ethernet Ring Protection";
      container profiles {
        description
          "G.8032 Ethernet Ring Protection";
        list profile {
          key "profile-name";
          description
            "G.8032 ring profile configuration";
          container timer {
            description
              "G.8032 timer";
            leaf guard-timer {
              type uint32 {
                range "10..2000";
              }
              units "millisecond";
              description
                "milliseconds";
            }
            leaf hold-off-timer {
              type uint32 {
                range "0..10";
              }
              units "second";
              description
                "Hold off timer";
            }
            leaf wtr-timer {
              type uint32 {
                range "1..12";
              }
              units "minute";
              description
                "Wait-to-Restore timer";
            }
          }
          leaf non-revertive {
            type empty;
            description
              "Non-revertive ring instance";
          }
          leaf profile-name {
            type xr:Cisco-ios-xr-string {
              length "1..32";
            }
            description
              "ERP profile name string";
          }
        }
      }
    }
  }
  augment "/ncs:devices/ncs:device/ncs:live-status" {
    container erp {
      tailf:ncs-device-type "netconf";
      tailf:display-when "not(../../ncs:module) or ../../ncs:module[ncs:name='Cisco-IOS-XR-erp-cfg'] or (../../ncs:live-status-protocol[not(ncs:capability)]) or (../../ncs:live-status-protocol/ncs:capability/ncs:module[.='Cisco-IOS-XR-erp-cfg'])";
      description
        "Ethernet Ring Protection";
      container profiles {
        description
          "G.8032 Ethernet Ring Protection";
        list profile {
          key "profile-name";
          description
            "G.8032 ring profile configuration";
          container timer {
            description
              "G.8032 timer";
            leaf guard-timer {
              type uint32 {
                range "10..2000";
              }
              units "millisecond";
              description
                "milliseconds";
            }
            leaf hold-off-timer {
              type uint32 {
                range "0..10";
              }
              units "second";
              description
                "Hold off timer";
            }
            leaf wtr-timer {
              type uint32 {
                range "1..12";
              }
              units "minute";
              description
                "Wait-to-Restore timer";
            }
          }
          leaf non-revertive {
            type empty;
            description
              "Non-revertive ring instance";
          }
          leaf profile-name {
            type xr:live_ncs_Cisco-ios-xr-string;
            description
              "ERP profile name string";
          }
        }
      }
    }
  }
  augment "/ncs:devices/ncs:template/ncs:ned-id/ncs:config" {
    container erp {
      description
        "Ethernet Ring Protection";
      container profiles {
        description
          "G.8032 Ethernet Ring Protection";
        list profile {
          // NCS patched for predictable order
          ordered-by user;
          key "profile-name";
          description
            "G.8032 ring profile configuration";
          container timer {
            description
              "G.8032 timer";
            leaf guard-timer {
              type string;
              units "millisecond";
              description
                "milliseconds";
            }
            leaf hold-off-timer {
              type string;
              units "second";
              description
                "Hold off timer";
            }
            leaf wtr-timer {
              type string;
              units "minute";
              description
                "Wait-to-Restore timer";
            }
          }
          leaf non-revertive {
            type empty;
            description
              "Non-revertive ring instance";
          }
          leaf profile-name {
            type xr:ncs_template_Cisco-ios-xr-string;
            description
              "ERP profile name string";
          }
        }
      }
    }
  }
}

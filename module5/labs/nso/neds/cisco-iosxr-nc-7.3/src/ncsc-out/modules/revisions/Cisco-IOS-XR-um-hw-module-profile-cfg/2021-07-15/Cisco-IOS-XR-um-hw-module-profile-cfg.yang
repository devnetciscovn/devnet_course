module Cisco-IOS-XR-um-hw-module-profile-cfg {
  // Generated by yanger -t ncs
  tailf:mount-id "cisco-iosxr-nc-7.3:cisco-iosxr-nc-7.3";
  tailf:ncs-device-type "netconf";

  namespace "http://cisco.com/ns/yang/Cisco-IOS-XR-um-hw-module-profile-cfg";
  prefix um-hw-module-profile-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hw-module-profile package configuration.

     This YANG module augments the
     modules with configuration data.

     Copyright (c) 2021 by Cisco Systems, Inc.
     All rights reserved.";

  revision 2021-07-15 {
    description
      "Initial release";
    semver:module-version "1.0.0";
  }

  augment "/ncs:devices/ncs:device/ncs:config" {
    container hw-module {
      tailf:ncs-device-type "netconf";
      tailf:display-when "not(../../ncs:module) or ../../ncs:module[ncs:name='Cisco-IOS-XR-um-hw-module-profile-cfg']";
      description
        "Configure h/w module";
      container profile-tcam {
        description
          "Configure profile for TCAM LC cards";
        container fib {
          description
            "Forwarding table to configure";
          container ipv4 {
            description
              "Configure ipv4 addresses in TCAM";
            container unicast {
              description
                "Unicast address";
              leaf percent {
                type uint32 {
                  range "1..100" {
                    description
                      "value in percent";
                  }
                }
                description
                  "percent to configure";
              }
              container prefixes {
                description
                  "ip prefix length";
                list prefix {
                  key "prefix-length";
                  description
                    "ip prefix length";
                  leaf prefix-length {
                    type uint32 {
                      range "0..32" {
                        description
                          "IPv4 prefix length.";
                      }
                    }
                    description
                      "ip prefix length";
                  }
                  leaf percent {
                    type xr:Cisco-ios-xr-string {
                      length "1..9" {
                        description
                          "prefix precent 0.0-100.00000";
                      }
                      pattern '100([.]0{0,5})?|([0-9]{1,2}[0]?)([.][0-9]{0,5})?';
                    }
                    mandatory true;
                    description
                      "prefix percentage to configure";
                  }
                }
              }
            }
          }
          container ipv6 {
            description
              "Configure ipv6 addresses in TCAM";
            container unicast {
              description
                "Unicast address";
              leaf percent {
                type uint32 {
                  range "0..100" {
                    description
                      "value in percent";
                  }
                }
                description
                  "percent to configure";
              }
              container prefixes {
                description
                  "ip prefix length";
                list prefix {
                  key "prefix-length";
                  description
                    "ip prefix length";
                  leaf prefix-length {
                    type uint32 {
                      range "0..128" {
                        description
                          "IPv6 prefix length.";
                      }
                    }
                    description
                      "ip prefix length";
                  }
                  leaf percent {
                    type xr:Cisco-ios-xr-string {
                      length "1..9" {
                        description
                          "prefix precent 0.0-100.00000";
                      }
                      pattern '100([.]0{0,5})?|([0-9]{1,2}[0]?)([.][0-9]{0,5})?';
                    }
                    mandatory true;
                    description
                      "prefix percentage to configure";
                  }
                }
              }
            }
          }
          container v6mcast {
            description
              "Multicast address";
            leaf percent {
              type uint32 {
                range "0..100" {
                  description
                    "value in percent";
                }
              }
              description
                "percent to configure";
            }
          }
        }
        container acl-prefix {
          description
            "ACL table to configure";
          leaf percent {
            type uint32 {
              range "0..100" {
                description
                  "value in percent";
              }
            }
            description
              "percent to configure";
          }
        }
        container format {
          description
            "format of the tcam entry";
          container access-list {
            description
              "Access List format";
            container ipv4 {
              presence "Indicates a ipv4 node is configured.";
              description
                "IPv4";
              container src-addr {
                presence "Indicates a src-addr node is configured.";
                description
                  "source address, 32 bit qualifier";
              }
              container dst-addr {
                presence "Indicates a dst-addr node is configured.";
                description
                  "destination address, 32 bit qualifier";
              }
              container src-port {
                must '../frag-bit' {
                  tailf:xpath-root 3;
                }
                presence "Indicates a src-port node is configured.";
                description
                  "source L4 port, 16 bit qualifier";
              }
              container dst-port {
                must '../frag-bit' {
                  tailf:xpath-root 3;
                }
                presence "Indicates a dst-port node is configured.";
                description
                  "destination L4 Port, 16 bit qualifier";
              }
              container proto {
                presence "Indicates a proto node is configured.";
                description
                  "protocol type, 8 bit qualifier";
              }
              container tcp-flags {
                must '../frag-bit' {
                  tailf:xpath-root 3;
                }
                presence "Indicates a tcp-flags node is configured.";
                description
                  "tcp-flags, 6 bit qualifier";
              }
              container packet-length {
                presence "Indicates a packet-length node is configured.";
                description
                  "packet length, 16 bit qualifier";
              }
              container frag-bit {
                presence "Indicates a frag-bit node is configured.";
                description
                  "fragment-bit, 1 bit qualifier";
              }
              container common-acl {
                presence "Indicates a common-acl node is configured.";
                description
                  "enable common-acl, 1 bit qualifier";
              }
              container precedence {
                presence "Indicates a precedence node is configured.";
                description
                  "precedence/dscp, 8 bit qualifier";
              }
              container port-range {
                must '../frag-bit' {
                  tailf:xpath-root 3;
                }
                presence "Indicates a port-range node is configured.";
                description
                  "ipv4 port range qualifier, 24 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container ttl-match {
                presence "Indicates a ttl-match node is configured.";
                description
                  "Enable matching on TTL field";
              }
              container interface-based {
                presence "Indicates a interface-based node is configured.";
                description
                  "Enable non-shared interface based ACL";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
            container ipv4-locations {
              description
                "Location of format access-list ipv4 config";
              list location {
                key "location-name location-name2";
                description
                  "Location of format access-list ipv4 config";
                leaf location-name {
                  type xr:Node-id;
                  description
                    "Location of format access-list ipv4 config";
                }
                leaf location-name2 {
                  type xr:Node-id;
                  description
                    "Location of format access-list ipv4 config";
                }
                container src-addr {
                  presence "Indicates a src-addr node is configured.";
                  description
                    "source address, 32 bit qualifier";
                }
                container dst-addr {
                  presence "Indicates a dst-addr node is configured.";
                  description
                    "destination address, 32 bit qualifier";
                }
                container src-port {
                  must '../frag-bit' {
                    tailf:xpath-root 3;
                  }
                  presence "Indicates a src-port node is configured.";
                  description
                    "source L4 port, 16 bit qualifier";
                }
                container dst-port {
                  must '../frag-bit' {
                    tailf:xpath-root 3;
                  }
                  presence "Indicates a dst-port node is configured.";
                  description
                    "destination L4 Port, 16 bit qualifier";
                }
                container proto {
                  presence "Indicates a proto node is configured.";
                  description
                    "protocol type, 8 bit qualifier";
                }
                container tcp-flags {
                  must '../frag-bit' {
                    tailf:xpath-root 3;
                  }
                  presence "Indicates a tcp-flags node is configured.";
                  description
                    "tcp-flags, 6 bit qualifier";
                }
                container packet-length {
                  presence "Indicates a packet-length node is configured.";
                  description
                    "packet length, 16 bit qualifier";
                }
                container frag-bit {
                  presence "Indicates a frag-bit node is configured.";
                  description
                    "fragment-bit, 1 bit qualifier";
                }
                container common-acl {
                  presence "Indicates a common-acl node is configured.";
                  description
                    "enable common-acl, 1 bit qualifier";
                }
                container precedence {
                  presence "Indicates a precedence node is configured.";
                  description
                    "precedence/dscp, 8 bit qualifier";
                }
                container port-range {
                  must '../frag-bit' {
                    tailf:xpath-root 3;
                  }
                  presence "Indicates a port-range node is configured.";
                  description
                    "ipv4 port range qualifier, 24 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:Cisco-ios-xr-string {
                    length "1..1024" {
                      description
                        "UDF name";
                    }
                  }
                  description
                    "user defined filter";
                }
                leaf udf2 {
                  type xr:Cisco-ios-xr-string {
                    length "1..1024" {
                      description
                        "UDF name";
                    }
                  }
                  description
                    "user defined filter";
                }
                leaf udf3 {
                  type xr:Cisco-ios-xr-string {
                    length "1..1024" {
                      description
                        "UDF name";
                    }
                  }
                  description
                    "user defined filter";
                }
                leaf udf4 {
                  type xr:Cisco-ios-xr-string {
                    length "1..1024" {
                      description
                        "UDF name";
                    }
                  }
                  description
                    "user defined filter";
                }
                leaf udf5 {
                  type xr:Cisco-ios-xr-string {
                    length "1..1024" {
                      description
                        "UDF name";
                    }
                  }
                  description
                    "user defined filter";
                }
                leaf udf6 {
                  type xr:Cisco-ios-xr-string {
                    length "1..1024" {
                      description
                        "UDF name";
                    }
                  }
                  description
                    "user defined filter";
                }
                leaf udf7 {
                  type xr:Cisco-ios-xr-string {
                    length "1..1024" {
                      description
                        "UDF name";
                    }
                  }
                  description
                    "user defined filter";
                }
                leaf udf8 {
                  type xr:Cisco-ios-xr-string {
                    length "1..1024" {
                      description
                        "UDF name";
                    }
                  }
                  description
                    "user defined filter";
                }
              }
            }
            container ipv6 {
              must 'src-port and next-hdr' {
                tailf:xpath-root 3;
              }
              presence "Indicates a ipv6 node is configured.";
              description
                "IPv6";
              container src-addr {
                presence "Indicates a src-addr node is configured.";
                description
                  "source address, 128 bit qualifier";
              }
              container src-port {
                presence "Indicates a src-port node is configured.";
                description
                  "source L4 Port, 16 bit qualifier (manditory field)";
              }
              container dst-addr {
                presence "Indicates a dst-addr node is configured.";
                description
                  "destination address, 128 bit qualifier";
              }
              container dst-port {
                presence "Indicates a dst-port node is configured.";
                description
                  "destination L4 Port, 16 bit qualifier";
              }
              container next-hdr {
                presence "Indicates a next-hdr node is configured.";
                description
                  "next header, 8 bit qualifier (manditory field)";
              }
              container tcp-flags {
                presence "Indicates a tcp-flags node is configured.";
                description
                  "tcp-flags, 8 bit qualifier";
              }
              container payload-length {
                presence "Indicates a payload-length node is configured.";
                description
                  "payload length, 16 bit qualifier";
              }
              container frag-bit {
                presence "Indicates a frag-bit node is configured.";
                description
                  "fragment-bit, 1 bit qualifier";
              }
              container traffic-class {
                presence "Indicates a traffic-class node is configured.";
                description
                  "Traffic Class, 8 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container common-acl {
                presence "Indicates a common-acl node is configured.";
                description
                  "enable common-acl, 1 bit qualifier";
              }
              container ttl-match {
                presence "Indicates a ttl-match node is configured.";
                description
                  "Enable matching on TTL field";
              }
              container interface-based {
                presence "Indicates a interface-based node is configured.";
                description
                  "Enable non-shared interface based ACL";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
            container ipv6-locations {
              description
                "Location of format access-list ipv6 config";
              list location {
                must 'src-port and next-hdr' {
                  tailf:xpath-root 3;
                }
                key "location-name location-name2";
                description
                  "Location of format access-list ipv6 config";
                leaf location-name {
                  type xr:Node-id;
                  description
                    "Location of format access-list ipv6 config";
                }
                leaf location-name2 {
                  type xr:Node-id;
                  description
                    "Location of format access-list ipv6 config";
                }
                container src-addr {
                  presence "Indicates a src-addr node is configured.";
                  description
                    "source address, 32 bit qualifier";
                }
                container src-port {
                  presence "Indicates a src-port node is configured.";
                  description
                    "source L4 port, 16 bit qualifier";
                }
                container dst-addr {
                  presence "Indicates a dst-addr node is configured.";
                  description
                    "destination address, 32 bit qualifier";
                }
                container dst-port {
                  presence "Indicates a dst-port node is configured.";
                  description
                    "destination L4 Port, 16 bit qualifier";
                }
                container next-hdr {
                  presence "Indicates a next-hdr node is configured.";
                  description
                    "next header, 8 bit qualifier (manditory field)";
                }
                container tcp-flags {
                  presence "Indicates a tcp-flags node is configured.";
                  description
                    "tcp-flags, 6 bit qualifier";
                }
                container payload-length {
                  presence "Indicates a packet-length node is configured.";
                  description
                    "packet length, 16 bit qualifier";
                }
                container frag-bit {
                  presence "Indicates a frag-bit node is configured.";
                  description
                    "fragment-bit, 1 bit qualifier";
                }
                container traffic-class {
                  presence "Indicates a traffic-class node is configured.";
                  description
                    "Traffic Class, 8 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container common-acl {
                  presence "Indicates a common-acl node is configured.";
                  description
                    "enable common-acl, 1 bit qualifier";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:Cisco-ios-xr-string {
                    length "1..1024" {
                      description
                        "UDF name";
                    }
                  }
                  description
                    "user defined filter";
                }
                leaf udf2 {
                  type xr:Cisco-ios-xr-string {
                    length "1..1024" {
                      description
                        "UDF name";
                    }
                  }
                  description
                    "user defined filter";
                }
                leaf udf3 {
                  type xr:Cisco-ios-xr-string {
                    length "1..1024" {
                      description
                        "UDF name";
                    }
                  }
                  description
                    "user defined filter";
                }
                leaf udf4 {
                  type xr:Cisco-ios-xr-string {
                    length "1..1024" {
                      description
                        "UDF name";
                    }
                  }
                  description
                    "user defined filter";
                }
                leaf udf5 {
                  type xr:Cisco-ios-xr-string {
                    length "1..1024" {
                      description
                        "UDF name";
                    }
                  }
                  description
                    "user defined filter";
                }
                leaf udf6 {
                  type xr:Cisco-ios-xr-string {
                    length "1..1024" {
                      description
                        "UDF name";
                    }
                  }
                  description
                    "user defined filter";
                }
                leaf udf7 {
                  type xr:Cisco-ios-xr-string {
                    length "1..1024" {
                      description
                        "UDF name";
                    }
                  }
                  description
                    "user defined filter";
                }
                leaf udf8 {
                  type xr:Cisco-ios-xr-string {
                    length "1..1024" {
                      description
                        "UDF name";
                    }
                  }
                  description
                    "user defined filter";
                }
              }
            }
          }
        }
      }
      container profile-acl {
        description
          "Configure acl profile";
        container egress {
          description
            "egress acl";
          container layer3 {
            description
              "egress layer3 acl";
            container interface-based {
              presence "Indicates a interface-based node is configured.";
              description
                "egress layer3 interface-based acl";
            }
          }
        }
        container ipv6 {
          description
            "ipv6 protocol specific options";
          container ext-header {
            description
              "ipv6 extension header related options";
            container permit {
              presence "Indicates a permit node is configured.";
              description
                "allow permit of extension header packets";
            }
          }
        }
        container ingress {
          description
            "ingress acl";
          container compress {
            description
              "Specify ACL compression in hardware";
            container enable {
              presence "Indicates a enable node is configured.";
              description
                "Enable ACL compression in hardware";
            }
            container enable-locations {
              description
                "Location of acl config";
              list location {
                key "location-name location-name2";
                description
                  "Location of acl config";
                leaf location-name {
                  type xr:Node-id;
                  description
                    "Location of acl config";
                }
                leaf location-name2 {
                  type xr:Node-id;
                  description
                    "Location of acl config";
                }
              }
            }
          }
          container layer3 {
            description
              "ingress layer3 acl";
            container ipv4 {
              description
                "ipv4 protocol";
              container interface-based {
                presence "Indicates a interface-based node is configured.";
                description
                  "ipv4 ingress layer3 interface-based acl";
              }
              container interface-based-locations {
                description
                  "Location of acl config";
                list location {
                  key "location-name location-name2";
                  description
                    "Location of acl config";
                  leaf location-name {
                    type xr:Node-id;
                    description
                      "Location of acl config";
                  }
                  leaf location-name2 {
                    type xr:Node-id;
                    description
                      "Location of acl config";
                  }
                }
              }
            }
            container ipv6 {
              description
                "ipv6 protocol";
              container interface-based {
                presence "Indicates a interface-based node is configured.";
                description
                  "ipv6 ingress layer3 interface-based acl";
              }
              container interface-based-locations {
                description
                  "Location of acl config";
                list location {
                  key "location-name location-name2";
                  description
                    "Location of acl config";
                  leaf location-name {
                    type xr:Node-id;
                    description
                      "Location of acl config";
                  }
                  leaf location-name2 {
                    type xr:Node-id;
                    description
                      "Location of acl config";
                  }
                }
              }
            }
          }
        }
      }
      container profile-load-balance {
        description
          "Configure load balance parameters";
        container algorithm {
          description
            "Configure hashing algorithm profiles";
          container layer2 {
            must 'not(../ip-tunnel or ../mpls-safe-speculative-parsing
or ../l3-only or ../gtp
or ../gtp-mpls)' {
              tailf:xpath-root 3;
            }
            presence "Indicates a layer2 node is configured.";
            description
              "Layer 2 optimized.";
          }
          container ip-tunnel {
            must 'not(../layer2 or ../mpls-safe-speculative-parsing
or ../l3-only or ../gtp
or ../gtp-mpls)' {
              tailf:xpath-root 3;
            }
            presence "Indicates a ip-tunnel node is configured.";
            description
              "IP tunnel optimized.";
          }
          container mpls-safe-speculative-parsing {
            must 'not(../layer2 or ../ip-tunnel
or ../l3-only or ../gtp
or ../gtp-mpls)' {
              tailf:xpath-root 3;
            }
            presence "Indicates a mpls-safe-speculative-parsing node is configured.";
            description
              "MPLS safe Speculative parsing.";
          }
          container l3-only {
            must 'not(../layer2 or ../ip-tunnel
or ../mpls-safe-speculative-parsing or ../gtp
or ../gtp-mpls)' {
              tailf:xpath-root 3;
            }
            presence "Indicates a l3-only node is configured.";
            description
              "L3 Header only Hash.";
          }
          container gtp {
            must 'not(../layer2 or ../ip-tunnel
or ../mpls-safe-speculative-parsing or ../l3-only
or ../gtp-mpls)' {
              tailf:xpath-root 3;
            }
            presence "Indicates a gtp node is configured.";
            description
              "GTP optimized.";
          }
          container gtp-mpls {
            must 'not(../layer2 or ../ip-tunnel
or ../mpls-safe-speculative-parsing or ../l3-only
or ../gtp)' {
              tailf:xpath-root 3;
            }
            presence "Indicates a gtp-mpls node is configured.";
            description
              "GTP over MPLS optimized hash.";
          }
        }
      }
      container profile-bundle-hash {
        description
          "Adjust bundle-hash algorithm";
        container hash-index {
          description
            "configure which polynomial to use in bundle-hash";
          container locations {
            description
              "Location of bundle-hash polynomial config";
            list location {
              key "location-name location-name2";
              description
                "Location of bundle-hash polynomial config";
              leaf location-name {
                type xr:Node-id;
                description
                  "Location of bundle-hash polynomial config";
              }
              leaf location-name2 {
                type xr:Node-id;
                description
                  "Location of bundle-hash polynomial config";
              }
              leaf index {
                type enumeration {
                  enum "1" {
                    value 1;
                    description
                      "Use Polynomial value 0x8011";
                  }
                  enum "2" {
                    value 2;
                    description
                      "Use Polynomial value 0x8423";
                  }
                  enum "3" {
                    value 3;
                    description
                      "Use Polynomial value 0x8101";
                  }
                  enum "4" {
                    value 4;
                    description
                      "Use Polynomial value 0x84A1";
                  }
                  enum "5" {
                    value 5;
                    description
                      "Use Polynomial value 0x9019";
                  }
                  enum "10" {
                    value 10;
                    description
                      "Use LB-Key-Pkt-Data directly";
                  }
                  enum "11" {
                    value 11;
                    description
                      "Use counter incremented every packet";
                  }
                  enum "12" {
                    value 12;
                    description
                      "Use counter incremented every two clocks";
                  }
                }
                mandatory true;
                description
                  "Configure hash index";
              }
            }
          }
        }
        container ignore-ingress-port {
          presence "Indicates a ignore-ingress-port node is configured.";
          description
            "Disable ingress port during bundle hash computation";
        }
        container per-packet-round-robin {
          presence "Indicates a per-packet-round-robin node is configured.";
          description
            "Enable per-packet round robin loadbalancing for all bundles in system";
        }
      }
      container profile-qos {
        description
          "Configure qos profile";
        leaf max-classmap-size {
          type enumeration {
            enum "32" {
              value 32;
              description
                "Max 32 class-maps per policy";
            }
            enum "16" {
              value 16;
              description
                "Max 16 class-maps per policy";
            }
            enum "8" {
              value 8;
              description
                "Max 8 class-maps per policy";
            }
            enum "4" {
              value 4;
              description
                "Max 4 class-maps per policy";
            }
          }
          description
            "max class map size";
        }
        container max-classmap-size-locations {
          description
            "Location of QoS config";
          list location {
            key "location-name location-name2";
            description
              "Location of QoS config";
            leaf location-name {
              type xr:Node-id;
              description
                "Location of QoS config";
            }
            leaf location-name2 {
              type xr:Node-id;
              description
                "Location of QoS config";
            }
            leaf max-classmap-size {
              type enumeration {
                enum "32" {
                  value 32;
                  description
                    "Max 32 class-maps per policy";
                }
                enum "16" {
                  value 16;
                  description
                    "Max 16 class-maps per policy";
                }
                enum "8" {
                  value 8;
                  description
                    "Max 8 class-maps per policy";
                }
                enum "4" {
                  value 4;
                  description
                    "Max 4 class-maps per policy";
                }
              }
              mandatory true;
              description
                "max class map size";
            }
          }
        }
        container ingress-model {
          description
            "QoS model for ingress feature";
          container peering {
            presence "Indicates a peering node is configured.";
            description
              "Peering model for ingress QoS";
          }
          container peering-locations {
            description
              "Peering model for ingress QoS with location";
            list location {
              key "location-name location-name2";
              description
                "Location of QoS config";
              leaf location-name {
                type xr:Node-id;
                description
                  "Location of QoS config";
              }
              leaf location-name2 {
                type xr:Node-id;
                description
                  "Location of QoS config";
              }
            }
          }
        }
        container qosg-dscp-mark-enable {
          presence "Indicates a qosg-dscp-mark-enable node is configured.";
          description
            "Enable both 'set qos-group' and 'set dscp/precedence' actions in the same ingress QoS policy";
          leaf first-dscp-precedence-value {
            type uint32 {
              range "0..63" {
                description
                  "First DSCP/Precedence value";
              }
            }
            mandatory true;
            description
              "Enable both 'set qos-group' and 'set dscp/precedence' actions in the same ingress QoS policy";
          }
          leaf second-dscp-precedence-value {
            type uint32 {
              range "0..63" {
                description
                  "Second DSCP/Precedence value";
              }
            }
            must '../first-dscp-precedence-value' {
              tailf:xpath-root 3;
            }
            description
              "Second DSCP/Precedence value";
          }
          leaf third-dscp-precedence-value {
            type uint32 {
              range "0..63" {
                description
                  "Third DSCP/Precedence value";
              }
            }
            must '../second-dscp-precedence-value' {
              tailf:xpath-root 3;
            }
            must '../second-dscp-precedence-value' {
              tailf:xpath-root 3;
            }
            description
              "Third DSCP/Precedence value";
          }
          leaf fourth-dscp-precedence-value {
            type uint32 {
              range "0..63" {
                description
                  "Fourth DSCP/Precedence value";
              }
            }
            must '../third-dscp-precedence-value' {
              tailf:xpath-root 3;
            }
            must '../third-dscp-precedence-value' {
              tailf:xpath-root 3;
            }
            description
              "Fourth DSCP/Precedence value";
          }
          leaf fifth-dscp-precedence-value {
            type uint32 {
              range "0..63" {
                description
                  "Fifth DSCP/Precedence value";
              }
            }
            must '../fourth-dscp-precedence-value' {
              tailf:xpath-root 3;
            }
            must '../fourth-dscp-precedence-value' {
              tailf:xpath-root 3;
            }
            description
              "Fifth DSCP/Precedence value";
          }
          leaf sixth-dscp-precedence-value {
            type uint32 {
              range "0..63" {
                description
                  "Sixth DSCP/Precedence value";
              }
            }
            must '../fifth-dscp-precedence-value' {
              tailf:xpath-root 3;
            }
            must '../fifth-dscp-precedence-value' {
              tailf:xpath-root 3;
            }
            description
              "Sixth DSCP/Precedence value";
          }
          leaf seventh-dscp-precedence-value {
            type uint32 {
              range "0..63" {
                description
                  "Seventh DSCP/Precedence value";
              }
            }
            must '../sixth-dscp-precedence-value' {
              tailf:xpath-root 3;
            }
            must '../sixth-dscp-precedence-value' {
              tailf:xpath-root 3;
            }
            description
              "Seventh DSCP/Precedence value";
          }
          leaf eighth-dscp-precedence-value {
            type uint32 {
              range "0..63" {
                description
                  "Eighth DSCP/Precedence value";
              }
            }
            must '../seventh-dscp-precedence-value' {
              tailf:xpath-root 3;
            }
            must '../seventh-dscp-precedence-value' {
              tailf:xpath-root 3;
            }
            description
              "Eighth DSCP/Precedence value";
          }
        }
        container hqos-enable {
          presence "Indicates a hqos-enable node is configured.";
          description
            "Enable Hierarchical QoS";
        }
        container ecn-marking-stats {
          presence "Indicates a ecn-marking-stats node is configured.";
          description
            "Enable ECN marking stats mode";
        }
        container shared-policer-per-class-stats {
          presence "Indicates a shared-policer-per-class-stats node is configured.";
          description
            "Enable shared policer (per class stats) mode";
        }
        container ipv6 {
          description
            "Configure ipv6 protocol";
          container short {
            presence "Indicates a short node is configured.";
            description
              "Configure ipv6 source short address tcam lookup";
          }
          container short-l2qos-enable {
            presence "Indicates a short-l2qos-enable node is configured.";
            description
              "Enable l2qos feature which requires to reduce ipv6 dest mask to 96 bits";
          }
        }
        container conform-aware-policer {
          presence "Indicates a conform-aware-policer node is configured.";
          description
            "Configure Conform Aware Policer mode";
        }
        container arp-isis-priority-enable {
          presence "Indicates a arp-isis-priority-enable node is configured.";
          description
            "Prioritize ISIS and ARP packets";
        }
      }
      leaf profile-bundle-scale {
        type enumeration {
          enum "256" {
            value 256;
            description
              "Max 256 trunks, Max 64 members";
          }
          enum "512" {
            value 512;
            description
              "Max 512 trunks, Max 32 members";
          }
          enum "1024" {
            value 1024;
            description
              "Max 1024 trunks, Max 16 members";
          }
        }
        description
          "Max number of bundles supported";
      }
      container profile-npu {
        description
          "Configure operating profiles for NPUs";
        container native-mode-enable {
          presence "Indicates a native-mode-enable node is configured.";
          description
            "Enable NPUs to operate in native mode";
        }
      }
      container profile-mdb {
        description
          "Different MDB profiles supported";
        container balanced {
          must 'not(../balanced-l2 or ../balanced-se
or ../l2max or ../l2max-se)' {
            tailf:xpath-root 3;
          }
          presence "Indicates a balanced node is configured.";
          description
            "balanced profile for router containing non-TCAM cards";
        }
        container balanced-l2 {
          must 'not(../balanced or ../balanced-se
or ../l2max or ../l2max-se)' {
            tailf:xpath-root 3;
          }
          presence "Indicates a balanced-l2 node is configured.";
          description
            "balanced-l2 profile for router containing non-TCAM cards";
        }
        container balanced-se {
          must 'not(../balanced or ../balanced-l2
or ../l2max or ../l2max-se)' {
            tailf:xpath-root 3;
          }
          presence "Indicates a balanced-se node is configured.";
          description
            "balanced-se profile for router containing only TCAM cards";
        }
        container l2max {
          must 'not(../balanced or ../balanced-l2
or ../balanced-se or ../l2max-se)' {
            tailf:xpath-root 3;
          }
          presence "Indicates a l2max node is configured.";
          description
            "l2max profile for router containing non-TCAM cards";
        }
        container l2max-se {
          must 'not(../balanced or ../balanced-l2
or ../balanced-se or ../l2max)' {
            tailf:xpath-root 3;
          }
          presence "Indicates a l2max-se node is configured.";
          description
            "l2max-se profile for router containing only TCAM cards";
        }
      }
      container profile-netflow {
        description
          "Configure Netflow profile.";
        container ipfix315-enable {
          presence "Indicates a ipfix315-enable node is configured.";
          description
            "IPFIX 315 enable ";
        }
        container ipfix315-enable-locations {
          description
            "Location of NETFLOW config";
          list location {
            key "location-name location-name2";
            description
              "Location of NETFLOW config";
            leaf location-name {
              type xr:Node-id;
              description
                "Location of NETFLOW config";
            }
            leaf location-name2 {
              type xr:Node-id;
              description
                "Location of NETFLOW config";
            }
          }
        }
        container sflow-enable {
          presence "Indicates a sflow-enable node is configured.";
          description
            "SFLOW enable ";
        }
        container sflow-enable-locations {
          description
            "Location of NETFLOW config";
          list location {
            key "location-name location-name2";
            description
              "Location of NETFLOW config";
            leaf location-name {
              type xr:Node-id;
              description
                "Location of NETFLOW config";
            }
            leaf location-name2 {
              type xr:Node-id;
              description
                "Location of NETFLOW config";
            }
          }
        }
        container fpc-enable {
          presence "Indicates a fpc-enable node is configured.";
          description
            "Netflow full packet capture enable ";
        }
        container fpc-enable-locations {
          description
            "Location of NETFLOW config";
          list location {
            key "location-name location-name2";
            description
              "Location of NETFLOW config";
            leaf location-name {
              type xr:Node-id;
              description
                "Location of NETFLOW config";
            }
            leaf location-name2 {
              type xr:Node-id;
              description
                "Location of NETFLOW config";
            }
          }
        }
      }
      container profile-stats {
        description
          "Configure stats profile.";
        container acl-permit {
          // NCS dropped bad must statement - YANG_ERR_XPATH_BAD_REF
          presence "Indicates a acl-permit node is configured.";
          description
            "Enable ACL permit stats.";
        }
        container qos-enhanced {
          // NCS dropped bad must statement - YANG_ERR_XPATH_BAD_REF
          presence "Indicates a qos-enhanced node is configured.";
          description
            "Enable enhanced QoS stats.";
        }
        container ingress-sr {
          // NCS dropped bad must statement - YANG_ERR_XPATH_BAD_REF
          presence "Indicates a ingress-sr node is configured.";
          description
            "Enable ingress SR stats profile counter.";
        }
        container enh-sr-policy {
          // NCS dropped bad must statement - YANG_ERR_XPATH_BAD_REF
          presence "Indicates a enh-sr-policy node is configured.";
          description
            "Enable Enhanced_SR_Policy_Scale stats profile counter.";
        }
        container ingress-sr-mspw {
          // NCS dropped bad must statement - YANG_ERR_XPATH_BAD_REF
          presence "Indicates a ingress-sr-mspw node is configured.";
          description
            "Enable ingress SR & MSPW stats profile counter.";
        }
        container egress-stats-scale {
          presence "Indicates a egress-stats-scale node is configured.";
          description
            "Enable Egress Stats_Scale profile counter.";
        }
        container tx-scale-enhanced {
          // NCS dropped bad must statement - YANG_ERR_XPATH_BAD_REF
          presence "Indicates a tx-scale-enhanced node is configured.";
          description
            "Enable enhanced TX stats scale (Non L2 stats).";
          container acl-permit {
            must 'not(../qos-enhanced or ../ingress-sr)' {
              tailf:xpath-root 3;
            }
            presence "Indicates a acl-permit node is configured.";
            description
              "Enable ACL permit stats.";
          }
          container qos-enhanced {
            must 'not(../acl-permit or ../ingress-sr)' {
              tailf:xpath-root 3;
            }
            presence "Indicates a qos-enhanced node is configured.";
            description
              "Enable enhanced QoS stats.";
          }
          container ingress-sr {
            must 'not(../qos-enhanced or ../acl-permit)' {
              tailf:xpath-root 3;
            }
            presence "Indicates a ingress-sr node is configured.";
            description
              "Enable ingress SR stats profile counter.";
          }
        }
      }
      container profile-flowspec {
        description
          "Configure support for v6 flowspec";
        container v6-enable {
          presence "Indicates a v6-enable node is configured.";
          description
            "Configure support for v6 flowspec";
        }
        container v6-enable-locations {
          description
            "Location of flowspec config";
          list location {
            key "location-name location-name2";
            description
              "Location of flowspec config";
            leaf location-name {
              type xr:Node-id;
              description
                "Location of flowspec config";
            }
            leaf location-name2 {
              type xr:Node-id;
              description
                "Location of flowspec config";
            }
          }
        }
      }
      container profile-segment-routing {
        description
          "Segment routing options";
        container srv6 {
          presence "Indicates a srv6 node is configured.";
          description
            "Configure support for SRv6 and its paramaters";
          container mode {
            description
              "Mode of operation";
            container base {
              // NCS dropped bad must statement - YANG_ERR_XPATH_BAD_REF
              presence "Indicates a base node is configured.";
              description
                "Base SRv6 (Format-1) support only";
              container encapsulation {
                description
                  "Configure encapsulation parameters";
                container traffic-class {
                  description
                    "Control traffic-class field on IPv6 header";
                  container propagate {
                    must 'not(../traffic-class-value)' {
                      tailf:xpath-root 3;
                    }
                    presence "Indicates a propagate node is configured.";
                    description
                      "Propagate traffic-class from incoming packet/frame";
                  }
                  leaf traffic-class-value {
                    type uint32 {
                      range "0..255" {
                        description
                          "Traffic-class value (specified as 2 hexadecimal nibbles)";
                      }
                    }
                    must 'not(../propagate)' {
                      tailf:xpath-root 3;
                    }
                    description
                      "Traffic-class value (specified as 2 hexadecimal nibbles)";
                  }
                }
              }
            }
            container micro-segment {
              description
                "Micro-segment support only";
              container format {
                description
                  "Specify carrier format";
                container f3216 {
                  // NCS dropped bad must statement - YANG_ERR_XPATH_BAD_REF
                  presence "Indicates a f3216 node is configured.";
                  description
                    "32-bit block and 16-bit IDs";
                  container encapsulation {
                    description
                      "Configure encapsulation parameters";
                    container traffic-class {
                      description
                        "Control traffic-class field on IPv6 header";
                      container propagate {
                        must 'not(../traffic-class-value)' {
                          tailf:xpath-root 3;
                        }
                        presence "Indicates a propagate node is configured.";
                        description
                          "Propagate traffic-class from incoming packet/frame";
                      }
                      leaf traffic-class-value {
                        type uint32 {
                          range "0..255" {
                            description
                              "Traffic-class value (specified as 2 hexadecimal nibbles)";
                          }
                        }
                        must 'not(../propagate)' {
                          tailf:xpath-root 3;
                        }
                        description
                          "Traffic-class value (specified as 2 hexadecimal nibbles)";
                      }
                    }
                  }
                }
              }
            }
          }
        }
      }
      container profile-offload {
        description
          "Offload profile in NCS5501-SE";
        container one {
          must 'not(../two or ../three)' {
            tailf:xpath-root 3;
          }
          presence "Indicates a one node is configured.";
          description
            "BFDv6 and Bsync";
        }
        container two {
          must 'not(../one or ../three)' {
            tailf:xpath-root 3;
          }
          presence "Indicates a two node is configured.";
          description
            "BFDv6 and Route download";
        }
        container three {
          must 'not(../one or ../two)' {
            tailf:xpath-root 3;
          }
          presence "Indicates a three node is configured.";
          description
            "Route download and Bsync";
        }
      }
      container profile-sr-policy {
        description
          "SR Policy options";
        container v6-null-label-autopush {
          presence "Indicates a v6-null-label-autopush node is configured.";
          description
            "Configure IPV6 NULL label autopush for SR policy";
        }
      }
      leaf profile-bw-threshold {
        type xr:Cisco-ios-xr-string {
          length "1..3" {
            description
              "value in percent: 0-100,in increments of 10";
          }
          pattern '(100|[1-9]?0|0)';
        }
        description
          "Asic Fabric Link Bandwidth Availability Threshold";
      }
      container profile-oam {
        description
          "Configure oam profile";
        container sat-enable {
          presence "Indicates a sat-enable node is configured.";
          description
            "enable SAT feature";
        }
      }
      container mpls-ext-dscp-preserve {
        description
          "Preserve dscp with large label stack";
        container v4uc-enable {
          presence "Indicates a v4uc-enable node is configured.";
          description
            "Enable to preseve dscp for ipv4 unicast traffic";
        }
      }
      container profile-priority-flow-control {
        description
          "Configure priority-flow-control parameters";
        container traffic-classes {
          description
            "configure traffic-class";
          list traffic-class {
            key "traffic-class-id";
            description
              "configure traffic-class";
            leaf traffic-class-id {
              type uint32 {
                range "0..7" {
                  description
                    "Traffic-class";
                }
              }
              description
                "configure traffic-class";
            }
            leaf pause-threshold {
              type uint32 {
                range "1..4294967295" {
                  description
                    "pause-threshold (bytes)";
                }
              }
              mandatory true;
              description
                "configure pause-threshold";
            }
            leaf resume-threshold {
              type uint32 {
                range "1..4294967295" {
                  description
                    "resume-threshold (bytes)";
                }
              }
              mandatory true;
              description
                "configure resume-threshold";
            }
            leaf headroom {
              type uint32 {
                range "1..4294967295" {
                  description
                    "headroom (bytes)";
                }
              }
              mandatory true;
              description
                "configure headroom";
            }
          }
        }
        container traffic-class-locations {
          description
            "Location to apply PFC configuration";
          list traffic-class-location {
            key "location-name location-name2 traffic-class-id";
            description
              "Location to apply PFC configuration";
            leaf location-name {
              type xr:Node-id;
              description
                "Location to apply PFC configuration";
            }
            leaf location-name2 {
              type xr:Node-id;
              description
                "Location to apply PFC configuration";
            }
            leaf traffic-class-id {
              type uint32 {
                range "0..7" {
                  description
                    "Traffic-class";
                }
              }
              description
                "configure traffic-class";
            }
            leaf pause-threshold {
              type uint32 {
                range "1..4294967295" {
                  description
                    "pause-threshold (bytes)";
                }
              }
              mandatory true;
              description
                "configure pause-threshold";
            }
            leaf resume-threshold {
              type uint32 {
                range "1..4294967295" {
                  description
                    "resume-threshold (bytes)";
                }
              }
              mandatory true;
              description
                "configure resume-threshold";
            }
            leaf headroom {
              type uint32 {
                range "1..4294967295" {
                  description
                    "headroom (bytes)";
                }
              }
              mandatory true;
              description
                "configure headroom";
            }
          }
        }
      }
      container profile-routing {
        description
          "Configure the node's routing profile";
        leaf role {
          type enumeration {
            enum "core" {
              value 3;
              description
                "Configure the routing role as a core router";
            }
          }
          description
            "Configure the node's routing role";
        }
      }
      container bundle-pindown-bum-optimization {
        description
          "To configure bundle-pindown-bum-optimization";
        container enable {
          presence "Indicates a enable node is configured.";
          description
            "Enable bundle pindown bum-optimization mode";
        }
      }
      container tcam {
        description
          "Configure profile for TCAM LC cards";
        container fib {
          description
            "Forwarding table to configure";
          container ipv4 {
            description
              "Configure ipv4 protocol";
            container scaledisable {
              presence "Indicates a scaledisable node is configured.";
              description
                "Configure scale mode for TCAM card";
            }
          }
        }
      }
      container fib {
        description
          "Forwarding table to configure";
        container ipv4 {
          description
            "Configure ipv4 protocol";
          container scale {
            description
              "Configure scale mode for no-TCAM card";
            container host-optimized-disable {
              presence "Indicates a host-optimized-disable node is configured.";
              description
                "Configure Host optimization by default";
            }
          }
        }
        container ipv6 {
          description
            "Configure ipv6 protocol";
          container scale {
            description
              "Configure scale mode for no-TCAM card";
            leaf custom-lem {
              type uint32 {
                range "40..64" {
                  description
                    "IPv6 prefix length.";
                }
              }
              description
                "Customise the prefix distribution to LEM";
            }
          }
        }
        container mpls {
          description
            "Configure mpls protocol";
          container ldp {
            presence "Indicates a ldp node is configured.";
            description
              "Configure signalling protocol for MPLS";
            container lsr-optimized {
              presence "Indicates a lsr-optimized node is configured.";
              description
                "Configure optimization for LSR role";
            }
          }
          container label {
            description
              "Configure MPLS label convergence optimization for LDP/SR labels";
            container lsr-optimized {
              presence "Indicates a lsr-optimized node is configured.";
              description
                "Configure LSR optimization";
            }
            container tcam-optimized {
              presence "Indicates a tcam-optimized node is configured.";
              description
                "Configure push label in tcam optimization";
            }
          }
        }
        container recycle {
          description
            "Recycle traffic";
          container service-over-rsvpte {
            presence "Indicates a service-over-rsvpte node is configured.";
            description
              "Recycle traffic for BGP services going over RSVP TE";
          }
        }
      }
      container oversubscription {
        description
          "Configure oversubscription";
        container prioritize {
          description
            "Setting prioritization of CoS values";
          list interface {
            must 'cos/cos-value or untagged' {
              tailf:xpath-root 3;
            }
            key "interface-name";
            leaf interface-name {
              type xr:Interface-name;
              description
                "Interface name";
            }
            container cos {
              description
                "CoS values between 0-5";
              list cos-value {
                key "value";
                description
                  "CoS values between 0-5";
                leaf value {
                  type uint32 {
                    range "0..5" {
                      description
                        "configure CoS number 0-5";
                    }
                  }
                  description
                    "CoS values between 0-5";
                }
              }
            }
            container untagged {
              presence "Indicates a untagged node is configured.";
              description
                "Prioritize untagged packets";
            }
          }
        }
      }
      container vrrpscale {
        description
          "to scale VRRP sessions";
        container enable {
          presence "Indicates a enable node is configured.";
          description
            "enable VRRP scaling";
        }
      }
      container fib-bgp-pic {
        description
          "Prefix Independent Convergnce";
        container multipath-core {
          description
            "Multipath pic core in forwarding chain";
          container enable {
            presence "Indicates a enable node is configured.";
            description
              "Enable pic core in forwarding chain";
          }
        }
      }
      container fib-dlb {
        description
          "Destination Based Load balancing";
        container level-1 {
          description
            "DLB at level 1 of forwarding chain";
          container enable {
            presence "Indicates a enable node is configured.";
            description
              "DLB at level 1 of forwarding chain";
          }
        }
      }
    }
  }
  augment "/ncs:devices/ncs:device/ncs:live-status" {
    container hw-module {
      tailf:ncs-device-type "netconf";
      tailf:display-when "not(../../ncs:module) or ../../ncs:module[ncs:name='Cisco-IOS-XR-um-hw-module-profile-cfg'] or (../../ncs:live-status-protocol[not(ncs:capability)]) or (../../ncs:live-status-protocol/ncs:capability/ncs:module[.='Cisco-IOS-XR-um-hw-module-profile-cfg'])";
      description
        "Configure h/w module";
      container profile-tcam {
        description
          "Configure profile for TCAM LC cards";
        container fib {
          description
            "Forwarding table to configure";
          container ipv4 {
            description
              "Configure ipv4 addresses in TCAM";
            container unicast {
              description
                "Unicast address";
              leaf percent {
                type uint32 {
                  range "1..100" {
                    description
                      "value in percent";
                  }
                }
                description
                  "percent to configure";
              }
              container prefixes {
                description
                  "ip prefix length";
                list prefix {
                  key "prefix-length";
                  description
                    "ip prefix length";
                  leaf prefix-length {
                    type uint32 {
                      range "0..32" {
                        description
                          "IPv4 prefix length.";
                      }
                    }
                    description
                      "ip prefix length";
                  }
                  leaf percent {
                    type xr:live_ncs_Cisco-ios-xr-string;
                    // NCS drop mandatory statement
                    description
                      "prefix percentage to configure";
                  }
                }
              }
            }
          }
          container ipv6 {
            description
              "Configure ipv6 addresses in TCAM";
            container unicast {
              description
                "Unicast address";
              leaf percent {
                type uint32 {
                  range "0..100" {
                    description
                      "value in percent";
                  }
                }
                description
                  "percent to configure";
              }
              container prefixes {
                description
                  "ip prefix length";
                list prefix {
                  key "prefix-length";
                  description
                    "ip prefix length";
                  leaf prefix-length {
                    type uint32 {
                      range "0..128" {
                        description
                          "IPv6 prefix length.";
                      }
                    }
                    description
                      "ip prefix length";
                  }
                  leaf percent {
                    type xr:live_ncs_Cisco-ios-xr-string;
                    // NCS drop mandatory statement
                    description
                      "prefix percentage to configure";
                  }
                }
              }
            }
          }
          container v6mcast {
            description
              "Multicast address";
            leaf percent {
              type uint32 {
                range "0..100" {
                  description
                    "value in percent";
                }
              }
              description
                "percent to configure";
            }
          }
        }
        container acl-prefix {
          description
            "ACL table to configure";
          leaf percent {
            type uint32 {
              range "0..100" {
                description
                  "value in percent";
              }
            }
            description
              "percent to configure";
          }
        }
        container format {
          description
            "format of the tcam entry";
          container access-list {
            description
              "Access List format";
            container ipv4 {
              presence "Indicates a ipv4 node is configured.";
              description
                "IPv4";
              container src-addr {
                presence "Indicates a src-addr node is configured.";
                description
                  "source address, 32 bit qualifier";
              }
              container dst-addr {
                presence "Indicates a dst-addr node is configured.";
                description
                  "destination address, 32 bit qualifier";
              }
              container src-port {
                // NCS drop must statement
                presence "Indicates a src-port node is configured.";
                description
                  "source L4 port, 16 bit qualifier";
              }
              container dst-port {
                // NCS drop must statement
                presence "Indicates a dst-port node is configured.";
                description
                  "destination L4 Port, 16 bit qualifier";
              }
              container proto {
                presence "Indicates a proto node is configured.";
                description
                  "protocol type, 8 bit qualifier";
              }
              container tcp-flags {
                // NCS drop must statement
                presence "Indicates a tcp-flags node is configured.";
                description
                  "tcp-flags, 6 bit qualifier";
              }
              container packet-length {
                presence "Indicates a packet-length node is configured.";
                description
                  "packet length, 16 bit qualifier";
              }
              container frag-bit {
                presence "Indicates a frag-bit node is configured.";
                description
                  "fragment-bit, 1 bit qualifier";
              }
              container common-acl {
                presence "Indicates a common-acl node is configured.";
                description
                  "enable common-acl, 1 bit qualifier";
              }
              container precedence {
                presence "Indicates a precedence node is configured.";
                description
                  "precedence/dscp, 8 bit qualifier";
              }
              container port-range {
                // NCS drop must statement
                presence "Indicates a port-range node is configured.";
                description
                  "ipv4 port range qualifier, 24 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container ttl-match {
                presence "Indicates a ttl-match node is configured.";
                description
                  "Enable matching on TTL field";
              }
              container interface-based {
                presence "Indicates a interface-based node is configured.";
                description
                  "Enable non-shared interface based ACL";
              }
              leaf udf1 {
                type xr:live_ncs_Cisco-ios-xr-string;
                description
                  "user defined filter";
              }
              leaf udf2 {
                type xr:live_ncs_Cisco-ios-xr-string;
                description
                  "user defined filter";
              }
              leaf udf3 {
                type xr:live_ncs_Cisco-ios-xr-string;
                description
                  "user defined filter";
              }
              leaf udf4 {
                type xr:live_ncs_Cisco-ios-xr-string;
                description
                  "user defined filter";
              }
              leaf udf5 {
                type xr:live_ncs_Cisco-ios-xr-string;
                description
                  "user defined filter";
              }
              leaf udf6 {
                type xr:live_ncs_Cisco-ios-xr-string;
                description
                  "user defined filter";
              }
              leaf udf7 {
                type xr:live_ncs_Cisco-ios-xr-string;
                description
                  "user defined filter";
              }
              leaf udf8 {
                type xr:live_ncs_Cisco-ios-xr-string;
                description
                  "user defined filter";
              }
            }
            container ipv4-locations {
              description
                "Location of format access-list ipv4 config";
              list location {
                key "location-name location-name2";
                description
                  "Location of format access-list ipv4 config";
                leaf location-name {
                  type xr:live_ncs_Node-id;
                  description
                    "Location of format access-list ipv4 config";
                }
                leaf location-name2 {
                  type xr:live_ncs_Node-id;
                  description
                    "Location of format access-list ipv4 config";
                }
                container src-addr {
                  presence "Indicates a src-addr node is configured.";
                  description
                    "source address, 32 bit qualifier";
                }
                container dst-addr {
                  presence "Indicates a dst-addr node is configured.";
                  description
                    "destination address, 32 bit qualifier";
                }
                container src-port {
                  // NCS drop must statement
                  presence "Indicates a src-port node is configured.";
                  description
                    "source L4 port, 16 bit qualifier";
                }
                container dst-port {
                  // NCS drop must statement
                  presence "Indicates a dst-port node is configured.";
                  description
                    "destination L4 Port, 16 bit qualifier";
                }
                container proto {
                  presence "Indicates a proto node is configured.";
                  description
                    "protocol type, 8 bit qualifier";
                }
                container tcp-flags {
                  // NCS drop must statement
                  presence "Indicates a tcp-flags node is configured.";
                  description
                    "tcp-flags, 6 bit qualifier";
                }
                container packet-length {
                  presence "Indicates a packet-length node is configured.";
                  description
                    "packet length, 16 bit qualifier";
                }
                container frag-bit {
                  presence "Indicates a frag-bit node is configured.";
                  description
                    "fragment-bit, 1 bit qualifier";
                }
                container common-acl {
                  presence "Indicates a common-acl node is configured.";
                  description
                    "enable common-acl, 1 bit qualifier";
                }
                container precedence {
                  presence "Indicates a precedence node is configured.";
                  description
                    "precedence/dscp, 8 bit qualifier";
                }
                container port-range {
                  // NCS drop must statement
                  presence "Indicates a port-range node is configured.";
                  description
                    "ipv4 port range qualifier, 24 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:live_ncs_Cisco-ios-xr-string;
                  description
                    "user defined filter";
                }
                leaf udf2 {
                  type xr:live_ncs_Cisco-ios-xr-string;
                  description
                    "user defined filter";
                }
                leaf udf3 {
                  type xr:live_ncs_Cisco-ios-xr-string;
                  description
                    "user defined filter";
                }
                leaf udf4 {
                  type xr:live_ncs_Cisco-ios-xr-string;
                  description
                    "user defined filter";
                }
                leaf udf5 {
                  type xr:live_ncs_Cisco-ios-xr-string;
                  description
                    "user defined filter";
                }
                leaf udf6 {
                  type xr:live_ncs_Cisco-ios-xr-string;
                  description
                    "user defined filter";
                }
                leaf udf7 {
                  type xr:live_ncs_Cisco-ios-xr-string;
                  description
                    "user defined filter";
                }
                leaf udf8 {
                  type xr:live_ncs_Cisco-ios-xr-string;
                  description
                    "user defined filter";
                }
              }
            }
            container ipv6 {
              // NCS drop must statement
              presence "Indicates a ipv6 node is configured.";
              description
                "IPv6";
              container src-addr {
                presence "Indicates a src-addr node is configured.";
                description
                  "source address, 128 bit qualifier";
              }
              container src-port {
                presence "Indicates a src-port node is configured.";
                description
                  "source L4 Port, 16 bit qualifier (manditory field)";
              }
              container dst-addr {
                presence "Indicates a dst-addr node is configured.";
                description
                  "destination address, 128 bit qualifier";
              }
              container dst-port {
                presence "Indicates a dst-port node is configured.";
                description
                  "destination L4 Port, 16 bit qualifier";
              }
              container next-hdr {
                presence "Indicates a next-hdr node is configured.";
                description
                  "next header, 8 bit qualifier (manditory field)";
              }
              container tcp-flags {
                presence "Indicates a tcp-flags node is configured.";
                description
                  "tcp-flags, 8 bit qualifier";
              }
              container payload-length {
                presence "Indicates a payload-length node is configured.";
                description
                  "payload length, 16 bit qualifier";
              }
              container frag-bit {
                presence "Indicates a frag-bit node is configured.";
                description
                  "fragment-bit, 1 bit qualifier";
              }
              container traffic-class {
                presence "Indicates a traffic-class node is configured.";
                description
                  "Traffic Class, 8 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container common-acl {
                presence "Indicates a common-acl node is configured.";
                description
                  "enable common-acl, 1 bit qualifier";
              }
              container ttl-match {
                presence "Indicates a ttl-match node is configured.";
                description
                  "Enable matching on TTL field";
              }
              container interface-based {
                presence "Indicates a interface-based node is configured.";
                description
                  "Enable non-shared interface based ACL";
              }
              leaf udf1 {
                type xr:live_ncs_Cisco-ios-xr-string;
                description
                  "user defined filter";
              }
              leaf udf2 {
                type xr:live_ncs_Cisco-ios-xr-string;
                description
                  "user defined filter";
              }
              leaf udf3 {
                type xr:live_ncs_Cisco-ios-xr-string;
                description
                  "user defined filter";
              }
              leaf udf4 {
                type xr:live_ncs_Cisco-ios-xr-string;
                description
                  "user defined filter";
              }
              leaf udf5 {
                type xr:live_ncs_Cisco-ios-xr-string;
                description
                  "user defined filter";
              }
              leaf udf6 {
                type xr:live_ncs_Cisco-ios-xr-string;
                description
                  "user defined filter";
              }
              leaf udf7 {
                type xr:live_ncs_Cisco-ios-xr-string;
                description
                  "user defined filter";
              }
              leaf udf8 {
                type xr:live_ncs_Cisco-ios-xr-string;
                description
                  "user defined filter";
              }
            }
            container ipv6-locations {
              description
                "Location of format access-list ipv6 config";
              list location {
                // NCS drop must statement
                key "location-name location-name2";
                description
                  "Location of format access-list ipv6 config";
                leaf location-name {
                  type xr:live_ncs_Node-id;
                  description
                    "Location of format access-list ipv6 config";
                }
                leaf location-name2 {
                  type xr:live_ncs_Node-id;
                  description
                    "Location of format access-list ipv6 config";
                }
                container src-addr {
                  presence "Indicates a src-addr node is configured.";
                  description
                    "source address, 32 bit qualifier";
                }
                container src-port {
                  presence "Indicates a src-port node is configured.";
                  description
                    "source L4 port, 16 bit qualifier";
                }
                container dst-addr {
                  presence "Indicates a dst-addr node is configured.";
                  description
                    "destination address, 32 bit qualifier";
                }
                container dst-port {
                  presence "Indicates a dst-port node is configured.";
                  description
                    "destination L4 Port, 16 bit qualifier";
                }
                container next-hdr {
                  presence "Indicates a next-hdr node is configured.";
                  description
                    "next header, 8 bit qualifier (manditory field)";
                }
                container tcp-flags {
                  presence "Indicates a tcp-flags node is configured.";
                  description
                    "tcp-flags, 6 bit qualifier";
                }
                container payload-length {
                  presence "Indicates a packet-length node is configured.";
                  description
                    "packet length, 16 bit qualifier";
                }
                container frag-bit {
                  presence "Indicates a frag-bit node is configured.";
                  description
                    "fragment-bit, 1 bit qualifier";
                }
                container traffic-class {
                  presence "Indicates a traffic-class node is configured.";
                  description
                    "Traffic Class, 8 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container common-acl {
                  presence "Indicates a common-acl node is configured.";
                  description
                    "enable common-acl, 1 bit qualifier";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:live_ncs_Cisco-ios-xr-string;
                  description
                    "user defined filter";
                }
                leaf udf2 {
                  type xr:live_ncs_Cisco-ios-xr-string;
                  description
                    "user defined filter";
                }
                leaf udf3 {
                  type xr:live_ncs_Cisco-ios-xr-string;
                  description
                    "user defined filter";
                }
                leaf udf4 {
                  type xr:live_ncs_Cisco-ios-xr-string;
                  description
                    "user defined filter";
                }
                leaf udf5 {
                  type xr:live_ncs_Cisco-ios-xr-string;
                  description
                    "user defined filter";
                }
                leaf udf6 {
                  type xr:live_ncs_Cisco-ios-xr-string;
                  description
                    "user defined filter";
                }
                leaf udf7 {
                  type xr:live_ncs_Cisco-ios-xr-string;
                  description
                    "user defined filter";
                }
                leaf udf8 {
                  type xr:live_ncs_Cisco-ios-xr-string;
                  description
                    "user defined filter";
                }
              }
            }
          }
        }
      }
      container profile-acl {
        description
          "Configure acl profile";
        container egress {
          description
            "egress acl";
          container layer3 {
            description
              "egress layer3 acl";
            container interface-based {
              presence "Indicates a interface-based node is configured.";
              description
                "egress layer3 interface-based acl";
            }
          }
        }
        container ipv6 {
          description
            "ipv6 protocol specific options";
          container ext-header {
            description
              "ipv6 extension header related options";
            container permit {
              presence "Indicates a permit node is configured.";
              description
                "allow permit of extension header packets";
            }
          }
        }
        container ingress {
          description
            "ingress acl";
          container compress {
            description
              "Specify ACL compression in hardware";
            container enable {
              presence "Indicates a enable node is configured.";
              description
                "Enable ACL compression in hardware";
            }
            container enable-locations {
              description
                "Location of acl config";
              list location {
                key "location-name location-name2";
                description
                  "Location of acl config";
                leaf location-name {
                  type xr:live_ncs_Node-id;
                  description
                    "Location of acl config";
                }
                leaf location-name2 {
                  type xr:live_ncs_Node-id;
                  description
                    "Location of acl config";
                }
              }
            }
          }
          container layer3 {
            description
              "ingress layer3 acl";
            container ipv4 {
              description
                "ipv4 protocol";
              container interface-based {
                presence "Indicates a interface-based node is configured.";
                description
                  "ipv4 ingress layer3 interface-based acl";
              }
              container interface-based-locations {
                description
                  "Location of acl config";
                list location {
                  key "location-name location-name2";
                  description
                    "Location of acl config";
                  leaf location-name {
                    type xr:live_ncs_Node-id;
                    description
                      "Location of acl config";
                  }
                  leaf location-name2 {
                    type xr:live_ncs_Node-id;
                    description
                      "Location of acl config";
                  }
                }
              }
            }
            container ipv6 {
              description
                "ipv6 protocol";
              container interface-based {
                presence "Indicates a interface-based node is configured.";
                description
                  "ipv6 ingress layer3 interface-based acl";
              }
              container interface-based-locations {
                description
                  "Location of acl config";
                list location {
                  key "location-name location-name2";
                  description
                    "Location of acl config";
                  leaf location-name {
                    type xr:live_ncs_Node-id;
                    description
                      "Location of acl config";
                  }
                  leaf location-name2 {
                    type xr:live_ncs_Node-id;
                    description
                      "Location of acl config";
                  }
                }
              }
            }
          }
        }
      }
      container profile-load-balance {
        description
          "Configure load balance parameters";
        container algorithm {
          description
            "Configure hashing algorithm profiles";
          container layer2 {
            // NCS drop must statement
            presence "Indicates a layer2 node is configured.";
            description
              "Layer 2 optimized.";
          }
          container ip-tunnel {
            // NCS drop must statement
            presence "Indicates a ip-tunnel node is configured.";
            description
              "IP tunnel optimized.";
          }
          container mpls-safe-speculative-parsing {
            // NCS drop must statement
            presence "Indicates a mpls-safe-speculative-parsing node is configured.";
            description
              "MPLS safe Speculative parsing.";
          }
          container l3-only {
            // NCS drop must statement
            presence "Indicates a l3-only node is configured.";
            description
              "L3 Header only Hash.";
          }
          container gtp {
            // NCS drop must statement
            presence "Indicates a gtp node is configured.";
            description
              "GTP optimized.";
          }
          container gtp-mpls {
            // NCS drop must statement
            presence "Indicates a gtp-mpls node is configured.";
            description
              "GTP over MPLS optimized hash.";
          }
        }
      }
      container profile-bundle-hash {
        description
          "Adjust bundle-hash algorithm";
        container hash-index {
          description
            "configure which polynomial to use in bundle-hash";
          container locations {
            description
              "Location of bundle-hash polynomial config";
            list location {
              key "location-name location-name2";
              description
                "Location of bundle-hash polynomial config";
              leaf location-name {
                type xr:live_ncs_Node-id;
                description
                  "Location of bundle-hash polynomial config";
              }
              leaf location-name2 {
                type xr:live_ncs_Node-id;
                description
                  "Location of bundle-hash polynomial config";
              }
              leaf index {
                type enumeration {
                  enum "1" {
                    value 1;
                    description
                      "Use Polynomial value 0x8011";
                  }
                  enum "2" {
                    value 2;
                    description
                      "Use Polynomial value 0x8423";
                  }
                  enum "3" {
                    value 3;
                    description
                      "Use Polynomial value 0x8101";
                  }
                  enum "4" {
                    value 4;
                    description
                      "Use Polynomial value 0x84A1";
                  }
                  enum "5" {
                    value 5;
                    description
                      "Use Polynomial value 0x9019";
                  }
                  enum "10" {
                    value 10;
                    description
                      "Use LB-Key-Pkt-Data directly";
                  }
                  enum "11" {
                    value 11;
                    description
                      "Use counter incremented every packet";
                  }
                  enum "12" {
                    value 12;
                    description
                      "Use counter incremented every two clocks";
                  }
                }
                // NCS drop mandatory statement
                description
                  "Configure hash index";
              }
            }
          }
        }
        container ignore-ingress-port {
          presence "Indicates a ignore-ingress-port node is configured.";
          description
            "Disable ingress port during bundle hash computation";
        }
        container per-packet-round-robin {
          presence "Indicates a per-packet-round-robin node is configured.";
          description
            "Enable per-packet round robin loadbalancing for all bundles in system";
        }
      }
      container profile-qos {
        description
          "Configure qos profile";
        leaf max-classmap-size {
          type enumeration {
            enum "32" {
              value 32;
              description
                "Max 32 class-maps per policy";
            }
            enum "16" {
              value 16;
              description
                "Max 16 class-maps per policy";
            }
            enum "8" {
              value 8;
              description
                "Max 8 class-maps per policy";
            }
            enum "4" {
              value 4;
              description
                "Max 4 class-maps per policy";
            }
          }
          description
            "max class map size";
        }
        container max-classmap-size-locations {
          description
            "Location of QoS config";
          list location {
            key "location-name location-name2";
            description
              "Location of QoS config";
            leaf location-name {
              type xr:live_ncs_Node-id;
              description
                "Location of QoS config";
            }
            leaf location-name2 {
              type xr:live_ncs_Node-id;
              description
                "Location of QoS config";
            }
            leaf max-classmap-size {
              type enumeration {
                enum "32" {
                  value 32;
                  description
                    "Max 32 class-maps per policy";
                }
                enum "16" {
                  value 16;
                  description
                    "Max 16 class-maps per policy";
                }
                enum "8" {
                  value 8;
                  description
                    "Max 8 class-maps per policy";
                }
                enum "4" {
                  value 4;
                  description
                    "Max 4 class-maps per policy";
                }
              }
              // NCS drop mandatory statement
              description
                "max class map size";
            }
          }
        }
        container ingress-model {
          description
            "QoS model for ingress feature";
          container peering {
            presence "Indicates a peering node is configured.";
            description
              "Peering model for ingress QoS";
          }
          container peering-locations {
            description
              "Peering model for ingress QoS with location";
            list location {
              key "location-name location-name2";
              description
                "Location of QoS config";
              leaf location-name {
                type xr:live_ncs_Node-id;
                description
                  "Location of QoS config";
              }
              leaf location-name2 {
                type xr:live_ncs_Node-id;
                description
                  "Location of QoS config";
              }
            }
          }
        }
        container qosg-dscp-mark-enable {
          presence "Indicates a qosg-dscp-mark-enable node is configured.";
          description
            "Enable both 'set qos-group' and 'set dscp/precedence' actions in the same ingress QoS policy";
          leaf first-dscp-precedence-value {
            type uint32 {
              range "0..63" {
                description
                  "First DSCP/Precedence value";
              }
            }
            // NCS drop mandatory statement
            description
              "Enable both 'set qos-group' and 'set dscp/precedence' actions in the same ingress QoS policy";
          }
          leaf second-dscp-precedence-value {
            type uint32 {
              range "0..63" {
                description
                  "Second DSCP/Precedence value";
              }
            }
            // NCS drop must statement
            description
              "Second DSCP/Precedence value";
          }
          leaf third-dscp-precedence-value {
            type uint32 {
              range "0..63" {
                description
                  "Third DSCP/Precedence value";
              }
            }
            // NCS drop must statement
            // NCS drop must statement
            description
              "Third DSCP/Precedence value";
          }
          leaf fourth-dscp-precedence-value {
            type uint32 {
              range "0..63" {
                description
                  "Fourth DSCP/Precedence value";
              }
            }
            // NCS drop must statement
            // NCS drop must statement
            description
              "Fourth DSCP/Precedence value";
          }
          leaf fifth-dscp-precedence-value {
            type uint32 {
              range "0..63" {
                description
                  "Fifth DSCP/Precedence value";
              }
            }
            // NCS drop must statement
            // NCS drop must statement
            description
              "Fifth DSCP/Precedence value";
          }
          leaf sixth-dscp-precedence-value {
            type uint32 {
              range "0..63" {
                description
                  "Sixth DSCP/Precedence value";
              }
            }
            // NCS drop must statement
            // NCS drop must statement
            description
              "Sixth DSCP/Precedence value";
          }
          leaf seventh-dscp-precedence-value {
            type uint32 {
              range "0..63" {
                description
                  "Seventh DSCP/Precedence value";
              }
            }
            // NCS drop must statement
            // NCS drop must statement
            description
              "Seventh DSCP/Precedence value";
          }
          leaf eighth-dscp-precedence-value {
            type uint32 {
              range "0..63" {
                description
                  "Eighth DSCP/Precedence value";
              }
            }
            // NCS drop must statement
            // NCS drop must statement
            description
              "Eighth DSCP/Precedence value";
          }
        }
        container hqos-enable {
          presence "Indicates a hqos-enable node is configured.";
          description
            "Enable Hierarchical QoS";
        }
        container ecn-marking-stats {
          presence "Indicates a ecn-marking-stats node is configured.";
          description
            "Enable ECN marking stats mode";
        }
        container shared-policer-per-class-stats {
          presence "Indicates a shared-policer-per-class-stats node is configured.";
          description
            "Enable shared policer (per class stats) mode";
        }
        container ipv6 {
          description
            "Configure ipv6 protocol";
          container short {
            presence "Indicates a short node is configured.";
            description
              "Configure ipv6 source short address tcam lookup";
          }
          container short-l2qos-enable {
            presence "Indicates a short-l2qos-enable node is configured.";
            description
              "Enable l2qos feature which requires to reduce ipv6 dest mask to 96 bits";
          }
        }
        container conform-aware-policer {
          presence "Indicates a conform-aware-policer node is configured.";
          description
            "Configure Conform Aware Policer mode";
        }
        container arp-isis-priority-enable {
          presence "Indicates a arp-isis-priority-enable node is configured.";
          description
            "Prioritize ISIS and ARP packets";
        }
      }
      leaf profile-bundle-scale {
        type enumeration {
          enum "256" {
            value 256;
            description
              "Max 256 trunks, Max 64 members";
          }
          enum "512" {
            value 512;
            description
              "Max 512 trunks, Max 32 members";
          }
          enum "1024" {
            value 1024;
            description
              "Max 1024 trunks, Max 16 members";
          }
        }
        description
          "Max number of bundles supported";
      }
      container profile-npu {
        description
          "Configure operating profiles for NPUs";
        container native-mode-enable {
          presence "Indicates a native-mode-enable node is configured.";
          description
            "Enable NPUs to operate in native mode";
        }
      }
      container profile-mdb {
        description
          "Different MDB profiles supported";
        container balanced {
          // NCS drop must statement
          presence "Indicates a balanced node is configured.";
          description
            "balanced profile for router containing non-TCAM cards";
        }
        container balanced-l2 {
          // NCS drop must statement
          presence "Indicates a balanced-l2 node is configured.";
          description
            "balanced-l2 profile for router containing non-TCAM cards";
        }
        container balanced-se {
          // NCS drop must statement
          presence "Indicates a balanced-se node is configured.";
          description
            "balanced-se profile for router containing only TCAM cards";
        }
        container l2max {
          // NCS drop must statement
          presence "Indicates a l2max node is configured.";
          description
            "l2max profile for router containing non-TCAM cards";
        }
        container l2max-se {
          // NCS drop must statement
          presence "Indicates a l2max-se node is configured.";
          description
            "l2max-se profile for router containing only TCAM cards";
        }
      }
      container profile-netflow {
        description
          "Configure Netflow profile.";
        container ipfix315-enable {
          presence "Indicates a ipfix315-enable node is configured.";
          description
            "IPFIX 315 enable ";
        }
        container ipfix315-enable-locations {
          description
            "Location of NETFLOW config";
          list location {
            key "location-name location-name2";
            description
              "Location of NETFLOW config";
            leaf location-name {
              type xr:live_ncs_Node-id;
              description
                "Location of NETFLOW config";
            }
            leaf location-name2 {
              type xr:live_ncs_Node-id;
              description
                "Location of NETFLOW config";
            }
          }
        }
        container sflow-enable {
          presence "Indicates a sflow-enable node is configured.";
          description
            "SFLOW enable ";
        }
        container sflow-enable-locations {
          description
            "Location of NETFLOW config";
          list location {
            key "location-name location-name2";
            description
              "Location of NETFLOW config";
            leaf location-name {
              type xr:live_ncs_Node-id;
              description
                "Location of NETFLOW config";
            }
            leaf location-name2 {
              type xr:live_ncs_Node-id;
              description
                "Location of NETFLOW config";
            }
          }
        }
        container fpc-enable {
          presence "Indicates a fpc-enable node is configured.";
          description
            "Netflow full packet capture enable ";
        }
        container fpc-enable-locations {
          description
            "Location of NETFLOW config";
          list location {
            key "location-name location-name2";
            description
              "Location of NETFLOW config";
            leaf location-name {
              type xr:live_ncs_Node-id;
              description
                "Location of NETFLOW config";
            }
            leaf location-name2 {
              type xr:live_ncs_Node-id;
              description
                "Location of NETFLOW config";
            }
          }
        }
      }
      container profile-stats {
        description
          "Configure stats profile.";
        container acl-permit {
          // NCS drop must statement
          presence "Indicates a acl-permit node is configured.";
          description
            "Enable ACL permit stats.";
        }
        container qos-enhanced {
          // NCS drop must statement
          presence "Indicates a qos-enhanced node is configured.";
          description
            "Enable enhanced QoS stats.";
        }
        container ingress-sr {
          // NCS drop must statement
          presence "Indicates a ingress-sr node is configured.";
          description
            "Enable ingress SR stats profile counter.";
        }
        container enh-sr-policy {
          // NCS drop must statement
          presence "Indicates a enh-sr-policy node is configured.";
          description
            "Enable Enhanced_SR_Policy_Scale stats profile counter.";
        }
        container ingress-sr-mspw {
          // NCS drop must statement
          presence "Indicates a ingress-sr-mspw node is configured.";
          description
            "Enable ingress SR & MSPW stats profile counter.";
        }
        container egress-stats-scale {
          presence "Indicates a egress-stats-scale node is configured.";
          description
            "Enable Egress Stats_Scale profile counter.";
        }
        container tx-scale-enhanced {
          // NCS drop must statement
          presence "Indicates a tx-scale-enhanced node is configured.";
          description
            "Enable enhanced TX stats scale (Non L2 stats).";
          container acl-permit {
            // NCS drop must statement
            presence "Indicates a acl-permit node is configured.";
            description
              "Enable ACL permit stats.";
          }
          container qos-enhanced {
            // NCS drop must statement
            presence "Indicates a qos-enhanced node is configured.";
            description
              "Enable enhanced QoS stats.";
          }
          container ingress-sr {
            // NCS drop must statement
            presence "Indicates a ingress-sr node is configured.";
            description
              "Enable ingress SR stats profile counter.";
          }
        }
      }
      container profile-flowspec {
        description
          "Configure support for v6 flowspec";
        container v6-enable {
          presence "Indicates a v6-enable node is configured.";
          description
            "Configure support for v6 flowspec";
        }
        container v6-enable-locations {
          description
            "Location of flowspec config";
          list location {
            key "location-name location-name2";
            description
              "Location of flowspec config";
            leaf location-name {
              type xr:live_ncs_Node-id;
              description
                "Location of flowspec config";
            }
            leaf location-name2 {
              type xr:live_ncs_Node-id;
              description
                "Location of flowspec config";
            }
          }
        }
      }
      container profile-segment-routing {
        description
          "Segment routing options";
        container srv6 {
          presence "Indicates a srv6 node is configured.";
          description
            "Configure support for SRv6 and its paramaters";
          container mode {
            description
              "Mode of operation";
            container base {
              // NCS drop must statement
              presence "Indicates a base node is configured.";
              description
                "Base SRv6 (Format-1) support only";
              container encapsulation {
                description
                  "Configure encapsulation parameters";
                container traffic-class {
                  description
                    "Control traffic-class field on IPv6 header";
                  container propagate {
                    // NCS drop must statement
                    presence "Indicates a propagate node is configured.";
                    description
                      "Propagate traffic-class from incoming packet/frame";
                  }
                  leaf traffic-class-value {
                    type uint32 {
                      range "0..255" {
                        description
                          "Traffic-class value (specified as 2 hexadecimal nibbles)";
                      }
                    }
                    // NCS drop must statement
                    description
                      "Traffic-class value (specified as 2 hexadecimal nibbles)";
                  }
                }
              }
            }
            container micro-segment {
              description
                "Micro-segment support only";
              container format {
                description
                  "Specify carrier format";
                container f3216 {
                  // NCS drop must statement
                  presence "Indicates a f3216 node is configured.";
                  description
                    "32-bit block and 16-bit IDs";
                  container encapsulation {
                    description
                      "Configure encapsulation parameters";
                    container traffic-class {
                      description
                        "Control traffic-class field on IPv6 header";
                      container propagate {
                        // NCS drop must statement
                        presence "Indicates a propagate node is configured.";
                        description
                          "Propagate traffic-class from incoming packet/frame";
                      }
                      leaf traffic-class-value {
                        type uint32 {
                          range "0..255" {
                            description
                              "Traffic-class value (specified as 2 hexadecimal nibbles)";
                          }
                        }
                        // NCS drop must statement
                        description
                          "Traffic-class value (specified as 2 hexadecimal nibbles)";
                      }
                    }
                  }
                }
              }
            }
          }
        }
      }
      container profile-offload {
        description
          "Offload profile in NCS5501-SE";
        container one {
          // NCS drop must statement
          presence "Indicates a one node is configured.";
          description
            "BFDv6 and Bsync";
        }
        container two {
          // NCS drop must statement
          presence "Indicates a two node is configured.";
          description
            "BFDv6 and Route download";
        }
        container three {
          // NCS drop must statement
          presence "Indicates a three node is configured.";
          description
            "Route download and Bsync";
        }
      }
      container profile-sr-policy {
        description
          "SR Policy options";
        container v6-null-label-autopush {
          presence "Indicates a v6-null-label-autopush node is configured.";
          description
            "Configure IPV6 NULL label autopush for SR policy";
        }
      }
      leaf profile-bw-threshold {
        type xr:live_ncs_Cisco-ios-xr-string;
        description
          "Asic Fabric Link Bandwidth Availability Threshold";
      }
      container profile-oam {
        description
          "Configure oam profile";
        container sat-enable {
          presence "Indicates a sat-enable node is configured.";
          description
            "enable SAT feature";
        }
      }
      container mpls-ext-dscp-preserve {
        description
          "Preserve dscp with large label stack";
        container v4uc-enable {
          presence "Indicates a v4uc-enable node is configured.";
          description
            "Enable to preseve dscp for ipv4 unicast traffic";
        }
      }
      container profile-priority-flow-control {
        description
          "Configure priority-flow-control parameters";
        container traffic-classes {
          description
            "configure traffic-class";
          list traffic-class {
            key "traffic-class-id";
            description
              "configure traffic-class";
            leaf traffic-class-id {
              type uint32 {
                range "0..7" {
                  description
                    "Traffic-class";
                }
              }
              description
                "configure traffic-class";
            }
            leaf pause-threshold {
              type uint32 {
                range "1..4294967295" {
                  description
                    "pause-threshold (bytes)";
                }
              }
              // NCS drop mandatory statement
              description
                "configure pause-threshold";
            }
            leaf resume-threshold {
              type uint32 {
                range "1..4294967295" {
                  description
                    "resume-threshold (bytes)";
                }
              }
              // NCS drop mandatory statement
              description
                "configure resume-threshold";
            }
            leaf headroom {
              type uint32 {
                range "1..4294967295" {
                  description
                    "headroom (bytes)";
                }
              }
              // NCS drop mandatory statement
              description
                "configure headroom";
            }
          }
        }
        container traffic-class-locations {
          description
            "Location to apply PFC configuration";
          list traffic-class-location {
            key "location-name location-name2 traffic-class-id";
            description
              "Location to apply PFC configuration";
            leaf location-name {
              type xr:live_ncs_Node-id;
              description
                "Location to apply PFC configuration";
            }
            leaf location-name2 {
              type xr:live_ncs_Node-id;
              description
                "Location to apply PFC configuration";
            }
            leaf traffic-class-id {
              type uint32 {
                range "0..7" {
                  description
                    "Traffic-class";
                }
              }
              description
                "configure traffic-class";
            }
            leaf pause-threshold {
              type uint32 {
                range "1..4294967295" {
                  description
                    "pause-threshold (bytes)";
                }
              }
              // NCS drop mandatory statement
              description
                "configure pause-threshold";
            }
            leaf resume-threshold {
              type uint32 {
                range "1..4294967295" {
                  description
                    "resume-threshold (bytes)";
                }
              }
              // NCS drop mandatory statement
              description
                "configure resume-threshold";
            }
            leaf headroom {
              type uint32 {
                range "1..4294967295" {
                  description
                    "headroom (bytes)";
                }
              }
              // NCS drop mandatory statement
              description
                "configure headroom";
            }
          }
        }
      }
      container profile-routing {
        description
          "Configure the node's routing profile";
        leaf role {
          type enumeration {
            enum "core" {
              value 3;
              description
                "Configure the routing role as a core router";
            }
          }
          description
            "Configure the node's routing role";
        }
      }
      container bundle-pindown-bum-optimization {
        description
          "To configure bundle-pindown-bum-optimization";
        container enable {
          presence "Indicates a enable node is configured.";
          description
            "Enable bundle pindown bum-optimization mode";
        }
      }
      container tcam {
        description
          "Configure profile for TCAM LC cards";
        container fib {
          description
            "Forwarding table to configure";
          container ipv4 {
            description
              "Configure ipv4 protocol";
            container scaledisable {
              presence "Indicates a scaledisable node is configured.";
              description
                "Configure scale mode for TCAM card";
            }
          }
        }
      }
      container fib {
        description
          "Forwarding table to configure";
        container ipv4 {
          description
            "Configure ipv4 protocol";
          container scale {
            description
              "Configure scale mode for no-TCAM card";
            container host-optimized-disable {
              presence "Indicates a host-optimized-disable node is configured.";
              description
                "Configure Host optimization by default";
            }
          }
        }
        container ipv6 {
          description
            "Configure ipv6 protocol";
          container scale {
            description
              "Configure scale mode for no-TCAM card";
            leaf custom-lem {
              type uint32 {
                range "40..64" {
                  description
                    "IPv6 prefix length.";
                }
              }
              description
                "Customise the prefix distribution to LEM";
            }
          }
        }
        container mpls {
          description
            "Configure mpls protocol";
          container ldp {
            presence "Indicates a ldp node is configured.";
            description
              "Configure signalling protocol for MPLS";
            container lsr-optimized {
              presence "Indicates a lsr-optimized node is configured.";
              description
                "Configure optimization for LSR role";
            }
          }
          container label {
            description
              "Configure MPLS label convergence optimization for LDP/SR labels";
            container lsr-optimized {
              presence "Indicates a lsr-optimized node is configured.";
              description
                "Configure LSR optimization";
            }
            container tcam-optimized {
              presence "Indicates a tcam-optimized node is configured.";
              description
                "Configure push label in tcam optimization";
            }
          }
        }
        container recycle {
          description
            "Recycle traffic";
          container service-over-rsvpte {
            presence "Indicates a service-over-rsvpte node is configured.";
            description
              "Recycle traffic for BGP services going over RSVP TE";
          }
        }
      }
      container oversubscription {
        description
          "Configure oversubscription";
        container prioritize {
          description
            "Setting prioritization of CoS values";
          list interface {
            // NCS drop must statement
            key "interface-name";
            leaf interface-name {
              type xr:live_ncs_Interface-name;
              description
                "Interface name";
            }
            container cos {
              description
                "CoS values between 0-5";
              list cos-value {
                key "value";
                description
                  "CoS values between 0-5";
                leaf value {
                  type uint32 {
                    range "0..5" {
                      description
                        "configure CoS number 0-5";
                    }
                  }
                  description
                    "CoS values between 0-5";
                }
              }
            }
            container untagged {
              presence "Indicates a untagged node is configured.";
              description
                "Prioritize untagged packets";
            }
          }
        }
      }
      container vrrpscale {
        description
          "to scale VRRP sessions";
        container enable {
          presence "Indicates a enable node is configured.";
          description
            "enable VRRP scaling";
        }
      }
      container fib-bgp-pic {
        description
          "Prefix Independent Convergnce";
        container multipath-core {
          description
            "Multipath pic core in forwarding chain";
          container enable {
            presence "Indicates a enable node is configured.";
            description
              "Enable pic core in forwarding chain";
          }
        }
      }
      container fib-dlb {
        description
          "Destination Based Load balancing";
        container level-1 {
          description
            "DLB at level 1 of forwarding chain";
          container enable {
            presence "Indicates a enable node is configured.";
            description
              "DLB at level 1 of forwarding chain";
          }
        }
      }
    }
  }
  augment "/ncs:devices/ncs:template/ncs:ned-id/ncs:config" {
    container hw-module {
      description
        "Configure h/w module";
      container profile-tcam {
        description
          "Configure profile for TCAM LC cards";
        container fib {
          description
            "Forwarding table to configure";
          container ipv4 {
            description
              "Configure ipv4 addresses in TCAM";
            container unicast {
              description
                "Unicast address";
              leaf percent {
                type string;
                description
                  "percent to configure";
              }
              container prefixes {
                description
                  "ip prefix length";
                list prefix {
                  // NCS patched for predictable order
                  ordered-by user;
                  key "prefix-length";
                  description
                    "ip prefix length";
                  leaf prefix-length {
                    type string;
                    description
                      "ip prefix length";
                  }
                  leaf percent {
                    type xr:ncs_template_Cisco-ios-xr-string;
                    // NCS drop mandatory statement
                    description
                      "prefix percentage to configure";
                  }
                }
              }
            }
          }
          container ipv6 {
            description
              "Configure ipv6 addresses in TCAM";
            container unicast {
              description
                "Unicast address";
              leaf percent {
                type string;
                description
                  "percent to configure";
              }
              container prefixes {
                description
                  "ip prefix length";
                list prefix {
                  // NCS patched for predictable order
                  ordered-by user;
                  key "prefix-length";
                  description
                    "ip prefix length";
                  leaf prefix-length {
                    type string;
                    description
                      "ip prefix length";
                  }
                  leaf percent {
                    type xr:ncs_template_Cisco-ios-xr-string;
                    // NCS drop mandatory statement
                    description
                      "prefix percentage to configure";
                  }
                }
              }
            }
          }
          container v6mcast {
            description
              "Multicast address";
            leaf percent {
              type string;
              description
                "percent to configure";
            }
          }
        }
        container acl-prefix {
          description
            "ACL table to configure";
          leaf percent {
            type string;
            description
              "percent to configure";
          }
        }
        container format {
          description
            "format of the tcam entry";
          container access-list {
            description
              "Access List format";
            container ipv4 {
              presence "Indicates a ipv4 node is configured.";
              description
                "IPv4";
              container src-addr {
                presence "Indicates a src-addr node is configured.";
                description
                  "source address, 32 bit qualifier";
              }
              container dst-addr {
                presence "Indicates a dst-addr node is configured.";
                description
                  "destination address, 32 bit qualifier";
              }
              container src-port {
                // NCS drop must statement
                presence "Indicates a src-port node is configured.";
                description
                  "source L4 port, 16 bit qualifier";
              }
              container dst-port {
                // NCS drop must statement
                presence "Indicates a dst-port node is configured.";
                description
                  "destination L4 Port, 16 bit qualifier";
              }
              container proto {
                presence "Indicates a proto node is configured.";
                description
                  "protocol type, 8 bit qualifier";
              }
              container tcp-flags {
                // NCS drop must statement
                presence "Indicates a tcp-flags node is configured.";
                description
                  "tcp-flags, 6 bit qualifier";
              }
              container packet-length {
                presence "Indicates a packet-length node is configured.";
                description
                  "packet length, 16 bit qualifier";
              }
              container frag-bit {
                presence "Indicates a frag-bit node is configured.";
                description
                  "fragment-bit, 1 bit qualifier";
              }
              container common-acl {
                presence "Indicates a common-acl node is configured.";
                description
                  "enable common-acl, 1 bit qualifier";
              }
              container precedence {
                presence "Indicates a precedence node is configured.";
                description
                  "precedence/dscp, 8 bit qualifier";
              }
              container port-range {
                // NCS drop must statement
                presence "Indicates a port-range node is configured.";
                description
                  "ipv4 port range qualifier, 24 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container ttl-match {
                presence "Indicates a ttl-match node is configured.";
                description
                  "Enable matching on TTL field";
              }
              container interface-based {
                presence "Indicates a interface-based node is configured.";
                description
                  "Enable non-shared interface based ACL";
              }
              leaf udf1 {
                type xr:ncs_template_Cisco-ios-xr-string;
                description
                  "user defined filter";
              }
              leaf udf2 {
                type xr:ncs_template_Cisco-ios-xr-string;
                description
                  "user defined filter";
              }
              leaf udf3 {
                type xr:ncs_template_Cisco-ios-xr-string;
                description
                  "user defined filter";
              }
              leaf udf4 {
                type xr:ncs_template_Cisco-ios-xr-string;
                description
                  "user defined filter";
              }
              leaf udf5 {
                type xr:ncs_template_Cisco-ios-xr-string;
                description
                  "user defined filter";
              }
              leaf udf6 {
                type xr:ncs_template_Cisco-ios-xr-string;
                description
                  "user defined filter";
              }
              leaf udf7 {
                type xr:ncs_template_Cisco-ios-xr-string;
                description
                  "user defined filter";
              }
              leaf udf8 {
                type xr:ncs_template_Cisco-ios-xr-string;
                description
                  "user defined filter";
              }
            }
            container ipv4-locations {
              description
                "Location of format access-list ipv4 config";
              list location {
                // NCS patched for predictable order
                ordered-by user;
                key "location-name location-name2";
                description
                  "Location of format access-list ipv4 config";
                leaf location-name {
                  type xr:ncs_template_Node-id;
                  description
                    "Location of format access-list ipv4 config";
                }
                leaf location-name2 {
                  type xr:ncs_template_Node-id;
                  description
                    "Location of format access-list ipv4 config";
                }
                container src-addr {
                  presence "Indicates a src-addr node is configured.";
                  description
                    "source address, 32 bit qualifier";
                }
                container dst-addr {
                  presence "Indicates a dst-addr node is configured.";
                  description
                    "destination address, 32 bit qualifier";
                }
                container src-port {
                  // NCS drop must statement
                  presence "Indicates a src-port node is configured.";
                  description
                    "source L4 port, 16 bit qualifier";
                }
                container dst-port {
                  // NCS drop must statement
                  presence "Indicates a dst-port node is configured.";
                  description
                    "destination L4 Port, 16 bit qualifier";
                }
                container proto {
                  presence "Indicates a proto node is configured.";
                  description
                    "protocol type, 8 bit qualifier";
                }
                container tcp-flags {
                  // NCS drop must statement
                  presence "Indicates a tcp-flags node is configured.";
                  description
                    "tcp-flags, 6 bit qualifier";
                }
                container packet-length {
                  presence "Indicates a packet-length node is configured.";
                  description
                    "packet length, 16 bit qualifier";
                }
                container frag-bit {
                  presence "Indicates a frag-bit node is configured.";
                  description
                    "fragment-bit, 1 bit qualifier";
                }
                container common-acl {
                  presence "Indicates a common-acl node is configured.";
                  description
                    "enable common-acl, 1 bit qualifier";
                }
                container precedence {
                  presence "Indicates a precedence node is configured.";
                  description
                    "precedence/dscp, 8 bit qualifier";
                }
                container port-range {
                  // NCS drop must statement
                  presence "Indicates a port-range node is configured.";
                  description
                    "ipv4 port range qualifier, 24 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:ncs_template_Cisco-ios-xr-string;
                  description
                    "user defined filter";
                }
                leaf udf2 {
                  type xr:ncs_template_Cisco-ios-xr-string;
                  description
                    "user defined filter";
                }
                leaf udf3 {
                  type xr:ncs_template_Cisco-ios-xr-string;
                  description
                    "user defined filter";
                }
                leaf udf4 {
                  type xr:ncs_template_Cisco-ios-xr-string;
                  description
                    "user defined filter";
                }
                leaf udf5 {
                  type xr:ncs_template_Cisco-ios-xr-string;
                  description
                    "user defined filter";
                }
                leaf udf6 {
                  type xr:ncs_template_Cisco-ios-xr-string;
                  description
                    "user defined filter";
                }
                leaf udf7 {
                  type xr:ncs_template_Cisco-ios-xr-string;
                  description
                    "user defined filter";
                }
                leaf udf8 {
                  type xr:ncs_template_Cisco-ios-xr-string;
                  description
                    "user defined filter";
                }
              }
            }
            container ipv6 {
              // NCS drop must statement
              presence "Indicates a ipv6 node is configured.";
              description
                "IPv6";
              container src-addr {
                presence "Indicates a src-addr node is configured.";
                description
                  "source address, 128 bit qualifier";
              }
              container src-port {
                presence "Indicates a src-port node is configured.";
                description
                  "source L4 Port, 16 bit qualifier (manditory field)";
              }
              container dst-addr {
                presence "Indicates a dst-addr node is configured.";
                description
                  "destination address, 128 bit qualifier";
              }
              container dst-port {
                presence "Indicates a dst-port node is configured.";
                description
                  "destination L4 Port, 16 bit qualifier";
              }
              container next-hdr {
                presence "Indicates a next-hdr node is configured.";
                description
                  "next header, 8 bit qualifier (manditory field)";
              }
              container tcp-flags {
                presence "Indicates a tcp-flags node is configured.";
                description
                  "tcp-flags, 8 bit qualifier";
              }
              container payload-length {
                presence "Indicates a payload-length node is configured.";
                description
                  "payload length, 16 bit qualifier";
              }
              container frag-bit {
                presence "Indicates a frag-bit node is configured.";
                description
                  "fragment-bit, 1 bit qualifier";
              }
              container traffic-class {
                presence "Indicates a traffic-class node is configured.";
                description
                  "Traffic Class, 8 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container common-acl {
                presence "Indicates a common-acl node is configured.";
                description
                  "enable common-acl, 1 bit qualifier";
              }
              container ttl-match {
                presence "Indicates a ttl-match node is configured.";
                description
                  "Enable matching on TTL field";
              }
              container interface-based {
                presence "Indicates a interface-based node is configured.";
                description
                  "Enable non-shared interface based ACL";
              }
              leaf udf1 {
                type xr:ncs_template_Cisco-ios-xr-string;
                description
                  "user defined filter";
              }
              leaf udf2 {
                type xr:ncs_template_Cisco-ios-xr-string;
                description
                  "user defined filter";
              }
              leaf udf3 {
                type xr:ncs_template_Cisco-ios-xr-string;
                description
                  "user defined filter";
              }
              leaf udf4 {
                type xr:ncs_template_Cisco-ios-xr-string;
                description
                  "user defined filter";
              }
              leaf udf5 {
                type xr:ncs_template_Cisco-ios-xr-string;
                description
                  "user defined filter";
              }
              leaf udf6 {
                type xr:ncs_template_Cisco-ios-xr-string;
                description
                  "user defined filter";
              }
              leaf udf7 {
                type xr:ncs_template_Cisco-ios-xr-string;
                description
                  "user defined filter";
              }
              leaf udf8 {
                type xr:ncs_template_Cisco-ios-xr-string;
                description
                  "user defined filter";
              }
            }
            container ipv6-locations {
              description
                "Location of format access-list ipv6 config";
              list location {
                // NCS patched for predictable order
                ordered-by user;
                // NCS drop must statement
                key "location-name location-name2";
                description
                  "Location of format access-list ipv6 config";
                leaf location-name {
                  type xr:ncs_template_Node-id;
                  description
                    "Location of format access-list ipv6 config";
                }
                leaf location-name2 {
                  type xr:ncs_template_Node-id;
                  description
                    "Location of format access-list ipv6 config";
                }
                container src-addr {
                  presence "Indicates a src-addr node is configured.";
                  description
                    "source address, 32 bit qualifier";
                }
                container src-port {
                  presence "Indicates a src-port node is configured.";
                  description
                    "source L4 port, 16 bit qualifier";
                }
                container dst-addr {
                  presence "Indicates a dst-addr node is configured.";
                  description
                    "destination address, 32 bit qualifier";
                }
                container dst-port {
                  presence "Indicates a dst-port node is configured.";
                  description
                    "destination L4 Port, 16 bit qualifier";
                }
                container next-hdr {
                  presence "Indicates a next-hdr node is configured.";
                  description
                    "next header, 8 bit qualifier (manditory field)";
                }
                container tcp-flags {
                  presence "Indicates a tcp-flags node is configured.";
                  description
                    "tcp-flags, 6 bit qualifier";
                }
                container payload-length {
                  presence "Indicates a packet-length node is configured.";
                  description
                    "packet length, 16 bit qualifier";
                }
                container frag-bit {
                  presence "Indicates a frag-bit node is configured.";
                  description
                    "fragment-bit, 1 bit qualifier";
                }
                container traffic-class {
                  presence "Indicates a traffic-class node is configured.";
                  description
                    "Traffic Class, 8 bit qualifier";
                }
                container enable-capture {
                  presence "Indicates a enable-capture node is configured.";
                  description
                    "Enable ACL based mirroring (Included by default)";
                }
                container enable-set-ttl {
                  presence "Indicates a enable-set-ttl node is configured.";
                  description
                    "Enable Setting TTL field (Included by default)";
                }
                container common-acl {
                  presence "Indicates a common-acl node is configured.";
                  description
                    "enable common-acl, 1 bit qualifier";
                }
                container ttl-match {
                  presence "Indicates a ttl-match node is configured.";
                  description
                    "Enable matching on TTL field";
                }
                container interface-based {
                  presence "Indicates a interface-based node is configured.";
                  description
                    "Enable non-shared interface based ACL";
                }
                leaf udf1 {
                  type xr:ncs_template_Cisco-ios-xr-string;
                  description
                    "user defined filter";
                }
                leaf udf2 {
                  type xr:ncs_template_Cisco-ios-xr-string;
                  description
                    "user defined filter";
                }
                leaf udf3 {
                  type xr:ncs_template_Cisco-ios-xr-string;
                  description
                    "user defined filter";
                }
                leaf udf4 {
                  type xr:ncs_template_Cisco-ios-xr-string;
                  description
                    "user defined filter";
                }
                leaf udf5 {
                  type xr:ncs_template_Cisco-ios-xr-string;
                  description
                    "user defined filter";
                }
                leaf udf6 {
                  type xr:ncs_template_Cisco-ios-xr-string;
                  description
                    "user defined filter";
                }
                leaf udf7 {
                  type xr:ncs_template_Cisco-ios-xr-string;
                  description
                    "user defined filter";
                }
                leaf udf8 {
                  type xr:ncs_template_Cisco-ios-xr-string;
                  description
                    "user defined filter";
                }
              }
            }
          }
        }
      }
      container profile-acl {
        description
          "Configure acl profile";
        container egress {
          description
            "egress acl";
          container layer3 {
            description
              "egress layer3 acl";
            container interface-based {
              presence "Indicates a interface-based node is configured.";
              description
                "egress layer3 interface-based acl";
            }
          }
        }
        container ipv6 {
          description
            "ipv6 protocol specific options";
          container ext-header {
            description
              "ipv6 extension header related options";
            container permit {
              presence "Indicates a permit node is configured.";
              description
                "allow permit of extension header packets";
            }
          }
        }
        container ingress {
          description
            "ingress acl";
          container compress {
            description
              "Specify ACL compression in hardware";
            container enable {
              presence "Indicates a enable node is configured.";
              description
                "Enable ACL compression in hardware";
            }
            container enable-locations {
              description
                "Location of acl config";
              list location {
                // NCS patched for predictable order
                ordered-by user;
                key "location-name location-name2";
                description
                  "Location of acl config";
                leaf location-name {
                  type xr:ncs_template_Node-id;
                  description
                    "Location of acl config";
                }
                leaf location-name2 {
                  type xr:ncs_template_Node-id;
                  description
                    "Location of acl config";
                }
              }
            }
          }
          container layer3 {
            description
              "ingress layer3 acl";
            container ipv4 {
              description
                "ipv4 protocol";
              container interface-based {
                presence "Indicates a interface-based node is configured.";
                description
                  "ipv4 ingress layer3 interface-based acl";
              }
              container interface-based-locations {
                description
                  "Location of acl config";
                list location {
                  // NCS patched for predictable order
                  ordered-by user;
                  key "location-name location-name2";
                  description
                    "Location of acl config";
                  leaf location-name {
                    type xr:ncs_template_Node-id;
                    description
                      "Location of acl config";
                  }
                  leaf location-name2 {
                    type xr:ncs_template_Node-id;
                    description
                      "Location of acl config";
                  }
                }
              }
            }
            container ipv6 {
              description
                "ipv6 protocol";
              container interface-based {
                presence "Indicates a interface-based node is configured.";
                description
                  "ipv6 ingress layer3 interface-based acl";
              }
              container interface-based-locations {
                description
                  "Location of acl config";
                list location {
                  // NCS patched for predictable order
                  ordered-by user;
                  key "location-name location-name2";
                  description
                    "Location of acl config";
                  leaf location-name {
                    type xr:ncs_template_Node-id;
                    description
                      "Location of acl config";
                  }
                  leaf location-name2 {
                    type xr:ncs_template_Node-id;
                    description
                      "Location of acl config";
                  }
                }
              }
            }
          }
        }
      }
      container profile-load-balance {
        description
          "Configure load balance parameters";
        container algorithm {
          description
            "Configure hashing algorithm profiles";
          container layer2 {
            // NCS drop must statement
            presence "Indicates a layer2 node is configured.";
            description
              "Layer 2 optimized.";
          }
          container ip-tunnel {
            // NCS drop must statement
            presence "Indicates a ip-tunnel node is configured.";
            description
              "IP tunnel optimized.";
          }
          container mpls-safe-speculative-parsing {
            // NCS drop must statement
            presence "Indicates a mpls-safe-speculative-parsing node is configured.";
            description
              "MPLS safe Speculative parsing.";
          }
          container l3-only {
            // NCS drop must statement
            presence "Indicates a l3-only node is configured.";
            description
              "L3 Header only Hash.";
          }
          container gtp {
            // NCS drop must statement
            presence "Indicates a gtp node is configured.";
            description
              "GTP optimized.";
          }
          container gtp-mpls {
            // NCS drop must statement
            presence "Indicates a gtp-mpls node is configured.";
            description
              "GTP over MPLS optimized hash.";
          }
        }
      }
      container profile-bundle-hash {
        description
          "Adjust bundle-hash algorithm";
        container hash-index {
          description
            "configure which polynomial to use in bundle-hash";
          container locations {
            description
              "Location of bundle-hash polynomial config";
            list location {
              // NCS patched for predictable order
              ordered-by user;
              key "location-name location-name2";
              description
                "Location of bundle-hash polynomial config";
              leaf location-name {
                type xr:ncs_template_Node-id;
                description
                  "Location of bundle-hash polynomial config";
              }
              leaf location-name2 {
                type xr:ncs_template_Node-id;
                description
                  "Location of bundle-hash polynomial config";
              }
              leaf index {
                type string;
                // NCS drop mandatory statement
                description
                  "Configure hash index";
              }
            }
          }
        }
        container ignore-ingress-port {
          presence "Indicates a ignore-ingress-port node is configured.";
          description
            "Disable ingress port during bundle hash computation";
        }
        container per-packet-round-robin {
          presence "Indicates a per-packet-round-robin node is configured.";
          description
            "Enable per-packet round robin loadbalancing for all bundles in system";
        }
      }
      container profile-qos {
        description
          "Configure qos profile";
        leaf max-classmap-size {
          type string;
          description
            "max class map size";
        }
        container max-classmap-size-locations {
          description
            "Location of QoS config";
          list location {
            // NCS patched for predictable order
            ordered-by user;
            key "location-name location-name2";
            description
              "Location of QoS config";
            leaf location-name {
              type xr:ncs_template_Node-id;
              description
                "Location of QoS config";
            }
            leaf location-name2 {
              type xr:ncs_template_Node-id;
              description
                "Location of QoS config";
            }
            leaf max-classmap-size {
              type string;
              // NCS drop mandatory statement
              description
                "max class map size";
            }
          }
        }
        container ingress-model {
          description
            "QoS model for ingress feature";
          container peering {
            presence "Indicates a peering node is configured.";
            description
              "Peering model for ingress QoS";
          }
          container peering-locations {
            description
              "Peering model for ingress QoS with location";
            list location {
              // NCS patched for predictable order
              ordered-by user;
              key "location-name location-name2";
              description
                "Location of QoS config";
              leaf location-name {
                type xr:ncs_template_Node-id;
                description
                  "Location of QoS config";
              }
              leaf location-name2 {
                type xr:ncs_template_Node-id;
                description
                  "Location of QoS config";
              }
            }
          }
        }
        container qosg-dscp-mark-enable {
          presence "Indicates a qosg-dscp-mark-enable node is configured.";
          description
            "Enable both 'set qos-group' and 'set dscp/precedence' actions in the same ingress QoS policy";
          leaf first-dscp-precedence-value {
            type string;
            // NCS drop mandatory statement
            description
              "Enable both 'set qos-group' and 'set dscp/precedence' actions in the same ingress QoS policy";
          }
          leaf second-dscp-precedence-value {
            type string;
            // NCS drop must statement
            description
              "Second DSCP/Precedence value";
          }
          leaf third-dscp-precedence-value {
            type string;
            // NCS drop must statement
            // NCS drop must statement
            description
              "Third DSCP/Precedence value";
          }
          leaf fourth-dscp-precedence-value {
            type string;
            // NCS drop must statement
            // NCS drop must statement
            description
              "Fourth DSCP/Precedence value";
          }
          leaf fifth-dscp-precedence-value {
            type string;
            // NCS drop must statement
            // NCS drop must statement
            description
              "Fifth DSCP/Precedence value";
          }
          leaf sixth-dscp-precedence-value {
            type string;
            // NCS drop must statement
            // NCS drop must statement
            description
              "Sixth DSCP/Precedence value";
          }
          leaf seventh-dscp-precedence-value {
            type string;
            // NCS drop must statement
            // NCS drop must statement
            description
              "Seventh DSCP/Precedence value";
          }
          leaf eighth-dscp-precedence-value {
            type string;
            // NCS drop must statement
            // NCS drop must statement
            description
              "Eighth DSCP/Precedence value";
          }
        }
        container hqos-enable {
          presence "Indicates a hqos-enable node is configured.";
          description
            "Enable Hierarchical QoS";
        }
        container ecn-marking-stats {
          presence "Indicates a ecn-marking-stats node is configured.";
          description
            "Enable ECN marking stats mode";
        }
        container shared-policer-per-class-stats {
          presence "Indicates a shared-policer-per-class-stats node is configured.";
          description
            "Enable shared policer (per class stats) mode";
        }
        container ipv6 {
          description
            "Configure ipv6 protocol";
          container short {
            presence "Indicates a short node is configured.";
            description
              "Configure ipv6 source short address tcam lookup";
          }
          container short-l2qos-enable {
            presence "Indicates a short-l2qos-enable node is configured.";
            description
              "Enable l2qos feature which requires to reduce ipv6 dest mask to 96 bits";
          }
        }
        container conform-aware-policer {
          presence "Indicates a conform-aware-policer node is configured.";
          description
            "Configure Conform Aware Policer mode";
        }
        container arp-isis-priority-enable {
          presence "Indicates a arp-isis-priority-enable node is configured.";
          description
            "Prioritize ISIS and ARP packets";
        }
      }
      leaf profile-bundle-scale {
        type string;
        description
          "Max number of bundles supported";
      }
      container profile-npu {
        description
          "Configure operating profiles for NPUs";
        container native-mode-enable {
          presence "Indicates a native-mode-enable node is configured.";
          description
            "Enable NPUs to operate in native mode";
        }
      }
      container profile-mdb {
        description
          "Different MDB profiles supported";
        container balanced {
          // NCS drop must statement
          presence "Indicates a balanced node is configured.";
          description
            "balanced profile for router containing non-TCAM cards";
        }
        container balanced-l2 {
          // NCS drop must statement
          presence "Indicates a balanced-l2 node is configured.";
          description
            "balanced-l2 profile for router containing non-TCAM cards";
        }
        container balanced-se {
          // NCS drop must statement
          presence "Indicates a balanced-se node is configured.";
          description
            "balanced-se profile for router containing only TCAM cards";
        }
        container l2max {
          // NCS drop must statement
          presence "Indicates a l2max node is configured.";
          description
            "l2max profile for router containing non-TCAM cards";
        }
        container l2max-se {
          // NCS drop must statement
          presence "Indicates a l2max-se node is configured.";
          description
            "l2max-se profile for router containing only TCAM cards";
        }
      }
      container profile-netflow {
        description
          "Configure Netflow profile.";
        container ipfix315-enable {
          presence "Indicates a ipfix315-enable node is configured.";
          description
            "IPFIX 315 enable ";
        }
        container ipfix315-enable-locations {
          description
            "Location of NETFLOW config";
          list location {
            // NCS patched for predictable order
            ordered-by user;
            key "location-name location-name2";
            description
              "Location of NETFLOW config";
            leaf location-name {
              type xr:ncs_template_Node-id;
              description
                "Location of NETFLOW config";
            }
            leaf location-name2 {
              type xr:ncs_template_Node-id;
              description
                "Location of NETFLOW config";
            }
          }
        }
        container sflow-enable {
          presence "Indicates a sflow-enable node is configured.";
          description
            "SFLOW enable ";
        }
        container sflow-enable-locations {
          description
            "Location of NETFLOW config";
          list location {
            // NCS patched for predictable order
            ordered-by user;
            key "location-name location-name2";
            description
              "Location of NETFLOW config";
            leaf location-name {
              type xr:ncs_template_Node-id;
              description
                "Location of NETFLOW config";
            }
            leaf location-name2 {
              type xr:ncs_template_Node-id;
              description
                "Location of NETFLOW config";
            }
          }
        }
        container fpc-enable {
          presence "Indicates a fpc-enable node is configured.";
          description
            "Netflow full packet capture enable ";
        }
        container fpc-enable-locations {
          description
            "Location of NETFLOW config";
          list location {
            // NCS patched for predictable order
            ordered-by user;
            key "location-name location-name2";
            description
              "Location of NETFLOW config";
            leaf location-name {
              type xr:ncs_template_Node-id;
              description
                "Location of NETFLOW config";
            }
            leaf location-name2 {
              type xr:ncs_template_Node-id;
              description
                "Location of NETFLOW config";
            }
          }
        }
      }
      container profile-stats {
        description
          "Configure stats profile.";
        container acl-permit {
          // NCS drop must statement
          presence "Indicates a acl-permit node is configured.";
          description
            "Enable ACL permit stats.";
        }
        container qos-enhanced {
          // NCS drop must statement
          presence "Indicates a qos-enhanced node is configured.";
          description
            "Enable enhanced QoS stats.";
        }
        container ingress-sr {
          // NCS drop must statement
          presence "Indicates a ingress-sr node is configured.";
          description
            "Enable ingress SR stats profile counter.";
        }
        container enh-sr-policy {
          // NCS drop must statement
          presence "Indicates a enh-sr-policy node is configured.";
          description
            "Enable Enhanced_SR_Policy_Scale stats profile counter.";
        }
        container ingress-sr-mspw {
          // NCS drop must statement
          presence "Indicates a ingress-sr-mspw node is configured.";
          description
            "Enable ingress SR & MSPW stats profile counter.";
        }
        container egress-stats-scale {
          presence "Indicates a egress-stats-scale node is configured.";
          description
            "Enable Egress Stats_Scale profile counter.";
        }
        container tx-scale-enhanced {
          // NCS drop must statement
          presence "Indicates a tx-scale-enhanced node is configured.";
          description
            "Enable enhanced TX stats scale (Non L2 stats).";
          container acl-permit {
            // NCS drop must statement
            presence "Indicates a acl-permit node is configured.";
            description
              "Enable ACL permit stats.";
          }
          container qos-enhanced {
            // NCS drop must statement
            presence "Indicates a qos-enhanced node is configured.";
            description
              "Enable enhanced QoS stats.";
          }
          container ingress-sr {
            // NCS drop must statement
            presence "Indicates a ingress-sr node is configured.";
            description
              "Enable ingress SR stats profile counter.";
          }
        }
      }
      container profile-flowspec {
        description
          "Configure support for v6 flowspec";
        container v6-enable {
          presence "Indicates a v6-enable node is configured.";
          description
            "Configure support for v6 flowspec";
        }
        container v6-enable-locations {
          description
            "Location of flowspec config";
          list location {
            // NCS patched for predictable order
            ordered-by user;
            key "location-name location-name2";
            description
              "Location of flowspec config";
            leaf location-name {
              type xr:ncs_template_Node-id;
              description
                "Location of flowspec config";
            }
            leaf location-name2 {
              type xr:ncs_template_Node-id;
              description
                "Location of flowspec config";
            }
          }
        }
      }
      container profile-segment-routing {
        description
          "Segment routing options";
        container srv6 {
          presence "Indicates a srv6 node is configured.";
          description
            "Configure support for SRv6 and its paramaters";
          container mode {
            description
              "Mode of operation";
            container base {
              // NCS drop must statement
              presence "Indicates a base node is configured.";
              description
                "Base SRv6 (Format-1) support only";
              container encapsulation {
                description
                  "Configure encapsulation parameters";
                container traffic-class {
                  description
                    "Control traffic-class field on IPv6 header";
                  container propagate {
                    // NCS drop must statement
                    presence "Indicates a propagate node is configured.";
                    description
                      "Propagate traffic-class from incoming packet/frame";
                  }
                  leaf traffic-class-value {
                    type string;
                    // NCS drop must statement
                    description
                      "Traffic-class value (specified as 2 hexadecimal nibbles)";
                  }
                }
              }
            }
            container micro-segment {
              description
                "Micro-segment support only";
              container format {
                description
                  "Specify carrier format";
                container f3216 {
                  // NCS drop must statement
                  presence "Indicates a f3216 node is configured.";
                  description
                    "32-bit block and 16-bit IDs";
                  container encapsulation {
                    description
                      "Configure encapsulation parameters";
                    container traffic-class {
                      description
                        "Control traffic-class field on IPv6 header";
                      container propagate {
                        // NCS drop must statement
                        presence "Indicates a propagate node is configured.";
                        description
                          "Propagate traffic-class from incoming packet/frame";
                      }
                      leaf traffic-class-value {
                        type string;
                        // NCS drop must statement
                        description
                          "Traffic-class value (specified as 2 hexadecimal nibbles)";
                      }
                    }
                  }
                }
              }
            }
          }
        }
      }
      container profile-offload {
        description
          "Offload profile in NCS5501-SE";
        container one {
          // NCS drop must statement
          presence "Indicates a one node is configured.";
          description
            "BFDv6 and Bsync";
        }
        container two {
          // NCS drop must statement
          presence "Indicates a two node is configured.";
          description
            "BFDv6 and Route download";
        }
        container three {
          // NCS drop must statement
          presence "Indicates a three node is configured.";
          description
            "Route download and Bsync";
        }
      }
      container profile-sr-policy {
        description
          "SR Policy options";
        container v6-null-label-autopush {
          presence "Indicates a v6-null-label-autopush node is configured.";
          description
            "Configure IPV6 NULL label autopush for SR policy";
        }
      }
      leaf profile-bw-threshold {
        type xr:ncs_template_Cisco-ios-xr-string;
        description
          "Asic Fabric Link Bandwidth Availability Threshold";
      }
      container profile-oam {
        description
          "Configure oam profile";
        container sat-enable {
          presence "Indicates a sat-enable node is configured.";
          description
            "enable SAT feature";
        }
      }
      container mpls-ext-dscp-preserve {
        description
          "Preserve dscp with large label stack";
        container v4uc-enable {
          presence "Indicates a v4uc-enable node is configured.";
          description
            "Enable to preseve dscp for ipv4 unicast traffic";
        }
      }
      container profile-priority-flow-control {
        description
          "Configure priority-flow-control parameters";
        container traffic-classes {
          description
            "configure traffic-class";
          list traffic-class {
            // NCS patched for predictable order
            ordered-by user;
            key "traffic-class-id";
            description
              "configure traffic-class";
            leaf traffic-class-id {
              type string;
              description
                "configure traffic-class";
            }
            leaf pause-threshold {
              type string;
              // NCS drop mandatory statement
              description
                "configure pause-threshold";
            }
            leaf resume-threshold {
              type string;
              // NCS drop mandatory statement
              description
                "configure resume-threshold";
            }
            leaf headroom {
              type string;
              // NCS drop mandatory statement
              description
                "configure headroom";
            }
          }
        }
        container traffic-class-locations {
          description
            "Location to apply PFC configuration";
          list traffic-class-location {
            // NCS patched for predictable order
            ordered-by user;
            key "location-name location-name2 traffic-class-id";
            description
              "Location to apply PFC configuration";
            leaf location-name {
              type xr:ncs_template_Node-id;
              description
                "Location to apply PFC configuration";
            }
            leaf location-name2 {
              type xr:ncs_template_Node-id;
              description
                "Location to apply PFC configuration";
            }
            leaf traffic-class-id {
              type string;
              description
                "configure traffic-class";
            }
            leaf pause-threshold {
              type string;
              // NCS drop mandatory statement
              description
                "configure pause-threshold";
            }
            leaf resume-threshold {
              type string;
              // NCS drop mandatory statement
              description
                "configure resume-threshold";
            }
            leaf headroom {
              type string;
              // NCS drop mandatory statement
              description
                "configure headroom";
            }
          }
        }
      }
      container profile-routing {
        description
          "Configure the node's routing profile";
        leaf role {
          type string;
          description
            "Configure the node's routing role";
        }
      }
      container bundle-pindown-bum-optimization {
        description
          "To configure bundle-pindown-bum-optimization";
        container enable {
          presence "Indicates a enable node is configured.";
          description
            "Enable bundle pindown bum-optimization mode";
        }
      }
      container tcam {
        description
          "Configure profile for TCAM LC cards";
        container fib {
          description
            "Forwarding table to configure";
          container ipv4 {
            description
              "Configure ipv4 protocol";
            container scaledisable {
              presence "Indicates a scaledisable node is configured.";
              description
                "Configure scale mode for TCAM card";
            }
          }
        }
      }
      container fib {
        description
          "Forwarding table to configure";
        container ipv4 {
          description
            "Configure ipv4 protocol";
          container scale {
            description
              "Configure scale mode for no-TCAM card";
            container host-optimized-disable {
              presence "Indicates a host-optimized-disable node is configured.";
              description
                "Configure Host optimization by default";
            }
          }
        }
        container ipv6 {
          description
            "Configure ipv6 protocol";
          container scale {
            description
              "Configure scale mode for no-TCAM card";
            leaf custom-lem {
              type string;
              description
                "Customise the prefix distribution to LEM";
            }
          }
        }
        container mpls {
          description
            "Configure mpls protocol";
          container ldp {
            presence "Indicates a ldp node is configured.";
            description
              "Configure signalling protocol for MPLS";
            container lsr-optimized {
              presence "Indicates a lsr-optimized node is configured.";
              description
                "Configure optimization for LSR role";
            }
          }
          container label {
            description
              "Configure MPLS label convergence optimization for LDP/SR labels";
            container lsr-optimized {
              presence "Indicates a lsr-optimized node is configured.";
              description
                "Configure LSR optimization";
            }
            container tcam-optimized {
              presence "Indicates a tcam-optimized node is configured.";
              description
                "Configure push label in tcam optimization";
            }
          }
        }
        container recycle {
          description
            "Recycle traffic";
          container service-over-rsvpte {
            presence "Indicates a service-over-rsvpte node is configured.";
            description
              "Recycle traffic for BGP services going over RSVP TE";
          }
        }
      }
      container oversubscription {
        description
          "Configure oversubscription";
        container prioritize {
          description
            "Setting prioritization of CoS values";
          list interface {
            // NCS patched for predictable order
            ordered-by user;
            // NCS drop must statement
            key "interface-name";
            leaf interface-name {
              type xr:ncs_template_Interface-name;
              description
                "Interface name";
            }
            container cos {
              description
                "CoS values between 0-5";
              list cos-value {
                // NCS patched for predictable order
                ordered-by user;
                key "value";
                description
                  "CoS values between 0-5";
                leaf value {
                  type string;
                  description
                    "CoS values between 0-5";
                }
              }
            }
            container untagged {
              presence "Indicates a untagged node is configured.";
              description
                "Prioritize untagged packets";
            }
          }
        }
      }
      container vrrpscale {
        description
          "to scale VRRP sessions";
        container enable {
          presence "Indicates a enable node is configured.";
          description
            "enable VRRP scaling";
        }
      }
      container fib-bgp-pic {
        description
          "Prefix Independent Convergnce";
        container multipath-core {
          description
            "Multipath pic core in forwarding chain";
          container enable {
            presence "Indicates a enable node is configured.";
            description
              "Enable pic core in forwarding chain";
          }
        }
      }
      container fib-dlb {
        description
          "Destination Based Load balancing";
        container level-1 {
          description
            "DLB at level 1 of forwarding chain";
          container enable {
            presence "Indicates a enable node is configured.";
            description
              "DLB at level 1 of forwarding chain";
          }
        }
      }
    }
  }
}

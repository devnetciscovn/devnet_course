module Cisco-IOS-XR-icpe-infra-cfg {
  // Generated by yanger -t ncs
  tailf:mount-id "cisco-iosxr-nc-7.3:cisco-iosxr-nc-7.3";
  tailf:ncs-device-type "netconf";

  namespace "http://cisco.com/ns/yang/Cisco-IOS-XR-icpe-infra-cfg";
  prefix icpe-infra-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import Cisco-IOS-XR-rgmgr-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR icpe-infra package configuration.

     This module contains definitions
     for the following management objects:
       nv-satellite-global: nV Satellite Global configuration
       nv-satellites: Satellite Configuration table

     This YANG module augments the
       Cisco-IOS-XR-ifmgr-cfg,
       Cisco-IOS-XR-rgmgr-cfg,
     modules with configuration data.

     Copyright (c) 2013-2019 by Cisco Systems, Inc.
     All rights reserved.";

  revision 2019-04-05 {
    description
      "Establish semantic version baseline.";
    semver:module-version "1.0.1";
  }
  revision 2017-09-30 {
    description
      "Ensure propagation of MDA mandatory state to YANG model.";
  }
  revision 2015-11-09 {
    description
      "IOS XR 6.0 revision.";
  }

  typedef ncs_template_Icpe-sat-id {
    type string;
    description
      "Icpe sat id";
  }

  typedef ncs_template_Icpe-slot {
    type string;
    description
      "Icpe slot";
  }

  typedef ncs_template_Icpe-min-links {
    type string;
    description
      "Icpe min links";
  }

  typedef ncs_template_Icpe-subslot {
    type string;
    description
      "Icpe subslot";
  }

  typedef ncs_rpc_notif_Icpe-sat-id {
    type uint32 {
      range "100..65534";
    }
    description
      "Icpe sat id";
  }

  typedef ncs_rpc_notif_Icpe-slot {
    type uint32 {
      range "0..8";
    }
    description
      "Icpe slot";
  }

  typedef ncs_rpc_notif_Icpe-min-links {
    type uint32 {
      range "1..64";
    }
    description
      "Icpe min links";
  }

  typedef ncs_rpc_notif_Icpe-subslot {
    type uint32 {
      range "0..8";
    }
    description
      "Icpe subslot";
  }

  typedef live_ncs_Icpe-sat-id {
    type uint32 {
      range "100..65534";
    }
    description
      "Icpe sat id";
  }

  typedef live_ncs_Icpe-slot {
    type uint32 {
      range "0..8";
    }
    description
      "Icpe slot";
  }

  typedef live_ncs_Icpe-min-links {
    type uint32 {
      range "1..64";
    }
    description
      "Icpe min links";
  }

  typedef live_ncs_Icpe-subslot {
    type uint32 {
      range "0..8";
    }
    description
      "Icpe subslot";
  }

  typedef Icpe-sat-id {
    type uint32 {
      range "100..65534";
    }
    description
      "Icpe sat id";
  }

  typedef Icpe-slot {
    type uint32 {
      range "0..8";
    }
    description
      "Icpe slot";
  }

  typedef Icpe-min-links {
    type uint32 {
      range "1..64";
    }
    description
      "Icpe min links";
  }

  typedef Icpe-subslot {
    type uint32 {
      range "0..8";
    }
    description
      "Icpe subslot";
  }

  grouping ncs_template_ENABLE {
    description
      "Common node of nv-satellite-fabric-network,
       satellites";
    leaf enable {
      type empty;
      // NCS drop mandatory statement
      description
        "Enable";
    }
  }

  grouping ncs_template_REMOTE-PORTS-TABLE {
    description
      "Common node of nv-satellite-fabric-link,
       satellites";
    container remote-ports {
      description
        "Remote Ports table";
      list remote-port {
        // NCS patched for predictable order
        ordered-by user;
        key "port-type slot sub-slot";
        description
          "Remote Ports";
        leaf port-type {
          type xr:ncs_template_Cisco-ios-xr-string;
          description
            "Port type";
        }
        leaf slot {
          type ncs_template_Icpe-slot;
          description
            "Slot";
        }
        leaf sub-slot {
          type ncs_template_Icpe-subslot;
          description
            "Sub slot";
        }
        leaf port-range {
          type string;
          // NCS drop mandatory statement
          description
            "Port range";
        }
      }
    }
  }

  grouping ncs_template_REDUNDANCY {
    description
      "Common node of nv-satellite-fabric-link,
       nv-satellite-fabric-network";
    container redundancy {
      description
        "Redundancy submode";
      leaf iccp-group {
        type string;
        description
          "Links the satellite fabric to the given ICCP
           group";
      }
      leaf minimum-preferred-links {
        type ncs_template_Icpe-min-links;
        description
          "Mininum number of active links preferred";
      }
    }
  }

  grouping ncs_rpc_notif_ENABLE {
    description
      "Common node of nv-satellite-fabric-network,
       satellites";
    leaf enable {
      type empty;
      mandatory true;
      description
        "Enable";
    }
  }

  grouping ncs_rpc_notif_REMOTE-PORTS-TABLE {
    description
      "Common node of nv-satellite-fabric-link,
       satellites";
    container remote-ports {
      description
        "Remote Ports table";
      list remote-port {
        key "port-type slot sub-slot";
        description
          "Remote Ports";
        leaf port-type {
          type xr:ncs_rpc_notif_Cisco-ios-xr-string;
          description
            "Port type";
        }
        leaf slot {
          type ncs_rpc_notif_Icpe-slot;
          description
            "Slot";
        }
        leaf sub-slot {
          type ncs_rpc_notif_Icpe-subslot;
          description
            "Sub slot";
        }
        leaf port-range {
          type string;
          mandatory true;
          description
            "Port range";
        }
      }
    }
  }

  grouping ncs_rpc_notif_REDUNDANCY {
    description
      "Common node of nv-satellite-fabric-link,
       nv-satellite-fabric-network";
    container redundancy {
      description
        "Redundancy submode";
      leaf iccp-group {
        type uint32 {
          range "0..4294967295";
        }
        description
          "Links the satellite fabric to the given ICCP
           group";
      }
      leaf minimum-preferred-links {
        type ncs_rpc_notif_Icpe-min-links;
        description
          "Mininum number of active links preferred";
      }
    }
  }

  grouping live_ncs_ENABLE {
    description
      "Common node of nv-satellite-fabric-network,
       satellites";
    leaf enable {
      type empty;
      // NCS drop mandatory statement
      description
        "Enable";
    }
  }

  grouping live_ncs_REMOTE-PORTS-TABLE {
    description
      "Common node of nv-satellite-fabric-link,
       satellites";
    container remote-ports {
      description
        "Remote Ports table";
      list remote-port {
        key "port-type slot sub-slot";
        description
          "Remote Ports";
        leaf port-type {
          type xr:live_ncs_Cisco-ios-xr-string;
          description
            "Port type";
        }
        leaf slot {
          type live_ncs_Icpe-slot;
          description
            "Slot";
        }
        leaf sub-slot {
          type live_ncs_Icpe-subslot;
          description
            "Sub slot";
        }
        leaf port-range {
          type string;
          // NCS drop mandatory statement
          description
            "Port range";
        }
      }
    }
  }

  grouping live_ncs_REDUNDANCY {
    description
      "Common node of nv-satellite-fabric-link,
       nv-satellite-fabric-network";
    container redundancy {
      description
        "Redundancy submode";
      leaf iccp-group {
        type uint32 {
          range "0..4294967295";
        }
        description
          "Links the satellite fabric to the given ICCP
           group";
      }
      leaf minimum-preferred-links {
        type live_ncs_Icpe-min-links;
        description
          "Mininum number of active links preferred";
      }
    }
  }

  grouping ENABLE {
    description
      "Common node of nv-satellite-fabric-network,
       satellites";
    leaf enable {
      type empty;
      mandatory true;
      description
        "Enable";
    }
  }

  grouping REMOTE-PORTS-TABLE {
    description
      "Common node of nv-satellite-fabric-link,
       satellites";
    container remote-ports {
      description
        "Remote Ports table";
      list remote-port {
        key "port-type slot sub-slot";
        description
          "Remote Ports";
        leaf port-type {
          type xr:Cisco-ios-xr-string;
          description
            "Port type";
        }
        leaf slot {
          type Icpe-slot;
          description
            "Slot";
        }
        leaf sub-slot {
          type Icpe-subslot;
          description
            "Sub slot";
        }
        leaf port-range {
          type string;
          mandatory true;
          description
            "Port range";
        }
      }
    }
  }

  grouping REDUNDANCY {
    description
      "Common node of nv-satellite-fabric-link,
       nv-satellite-fabric-network";
    container redundancy {
      description
        "Redundancy submode";
      leaf iccp-group {
        type uint32 {
          range "0..4294967295";
        }
        description
          "Links the satellite fabric to the given ICCP
           group";
      }
      leaf minimum-preferred-links {
        type Icpe-min-links;
        description
          "Mininum number of active links preferred";
      }
    }
  }

  augment "/ncs:devices/ncs:device/ncs:config" {
    container nv-satellite-global {
      tailf:ncs-device-type "netconf";
      tailf:display-when "not(../../ncs:module) or ../../ncs:module[ncs:name='Cisco-IOS-XR-icpe-infra-cfg']";
      description
        "nV Satellite Global configuration";
      container chassis-mac {
        description
          "Chassis MAC address";
        leaf mac1 {
          type uint32 {
            range "0..2147483647";
          }
          units "byte";
          description
            "First two bytes of MAC address";
        }
        leaf mac2 {
          type uint32 {
            range "0..2147483647";
          }
          units "byte";
          description
            "Second two bytes of MAC address";
        }
        leaf mac3 {
          type uint32 {
            range "0..2147483647";
          }
          units "byte";
          description
            "Third two bytes of MAC address";
        }
      }
    }
    container nv-satellites {
      tailf:ncs-device-type "netconf";
      tailf:display-when "not(../../ncs:module) or ../../ncs:module[ncs:name='Cisco-IOS-XR-icpe-infra-cfg']";
      description
        "Satellite Configuration table";
      list nv-satellite {
        key "satellite-id";
        description
          "Satellite Configuration";
        container upgrade-on-connect {
          description
            "Satellite auto-upgrade capability";
          leaf connect-type {
            type enumeration {
              enum "on-connection" {
                value 1;
                description
                  "Satellite Upgrade on Connection";
              }
              enum "on-first-connection" {
                value 2;
                description
                  "Satellite Upgrade on First Connection after
                   configuration or host boot";
              }
            }
            description
              "When to upgrade the satellite";
          }
          leaf reference {
            type string;
            description
              "Reference name";
          }
          leaf image-reference {
            type string;
            description
              "Image Reference name";
          }
        }
        container candidate-fabric-ports {
          description
            "Enable interfaces on the satellite to be used
             as fabric ports table";
          list candidate-fabric-port {
            key "port-type slot sub-slot";
            description
              "Enable interfaces on the satellite to be used
               as fabric ports";
            leaf port-type {
              type xr:Cisco-ios-xr-string;
              description
                "Port type";
            }
            leaf slot {
              type Icpe-slot;
              description
                "Slot";
            }
            leaf sub-slot {
              type Icpe-subslot;
              description
                "Sub slot";
            }
            leaf port-range {
              type string;
              mandatory true;
              description
                "Port range";
            }
          }
        }
        container connection-info {
          description
            "Satellite User";
          leaf username {
            type string;
            description
              "Satellite Username";
          }
          leaf password {
            type xr:Md5-password;
            description
              "Encrypted password for the user";
          }
        }
        container redundancy {
          description
            "Redundancy submode";
          leaf host-priority {
            type uint32 {
              range "0..255";
            }
            description
              "Priority for this host for the given satellite";
          }
        }
        leaf vrf {
          type string;
          description
            "VRF for Satellite IP Address";
        }
        leaf timeout-warning {
          type uint32 {
            range "0..4294967295";
          }
          description
            "Discovery timeout warning for the satellite";
        }
        leaf device-name {
          type string;
          description
            "Satellite Name";
        }
        leaf description {
          type string;
          description
            "Satellite Description";
        }
        leaf type {
          type string;
          mandatory true;
          description
            "Satellite Type";
        }
        leaf enable {
          type empty;
          mandatory true;
          description
            "Enable";
        }
        leaf disc-timeout {
          type uint32 {
            range "0..4294967295";
          }
          description
            "Discovery timeout for the satellite";
        }
        leaf delayed-switchback {
          type uint32 {
            range "0..4294967295";
          }
          units "second";
          description
            "Timer (in seconds) for delaying switchback in a
             dual home setup";
        }
        leaf serial-number {
          type string;
          description
            "Satellite Serial Number";
        }
        leaf secret {
          type xr:Md5-password;
          description
            "Encrypted password for the Satellite";
        }
        leaf ip-address {
          type inet:ip-address-no-zone;
          description
            "Satellite IP Address";
        }
        leaf satellite-id {
          type Icpe-sat-id;
          description
            "Satellite ID";
        }
      }
    }
  }
  augment "/ncs:devices/ncs:device/ncs:live-status" {
    container nv-satellite-global {
      tailf:ncs-device-type "netconf";
      tailf:display-when "not(../../ncs:module) or ../../ncs:module[ncs:name='Cisco-IOS-XR-icpe-infra-cfg'] or (../../ncs:live-status-protocol[not(ncs:capability)]) or (../../ncs:live-status-protocol/ncs:capability/ncs:module[.='Cisco-IOS-XR-icpe-infra-cfg'])";
      description
        "nV Satellite Global configuration";
      container chassis-mac {
        description
          "Chassis MAC address";
        leaf mac1 {
          type uint32 {
            range "0..2147483647";
          }
          units "byte";
          description
            "First two bytes of MAC address";
        }
        leaf mac2 {
          type uint32 {
            range "0..2147483647";
          }
          units "byte";
          description
            "Second two bytes of MAC address";
        }
        leaf mac3 {
          type uint32 {
            range "0..2147483647";
          }
          units "byte";
          description
            "Third two bytes of MAC address";
        }
      }
    }
    container nv-satellites {
      tailf:ncs-device-type "netconf";
      tailf:display-when "not(../../ncs:module) or ../../ncs:module[ncs:name='Cisco-IOS-XR-icpe-infra-cfg'] or (../../ncs:live-status-protocol[not(ncs:capability)]) or (../../ncs:live-status-protocol/ncs:capability/ncs:module[.='Cisco-IOS-XR-icpe-infra-cfg'])";
      description
        "Satellite Configuration table";
      list nv-satellite {
        key "satellite-id";
        description
          "Satellite Configuration";
        container upgrade-on-connect {
          description
            "Satellite auto-upgrade capability";
          leaf connect-type {
            type enumeration {
              enum "on-connection" {
                value 1;
                description
                  "Satellite Upgrade on Connection";
              }
              enum "on-first-connection" {
                value 2;
                description
                  "Satellite Upgrade on First Connection after
                   configuration or host boot";
              }
            }
            description
              "When to upgrade the satellite";
          }
          leaf reference {
            type string;
            description
              "Reference name";
          }
          leaf image-reference {
            type string;
            description
              "Image Reference name";
          }
        }
        container candidate-fabric-ports {
          description
            "Enable interfaces on the satellite to be used
             as fabric ports table";
          list candidate-fabric-port {
            key "port-type slot sub-slot";
            description
              "Enable interfaces on the satellite to be used
               as fabric ports";
            leaf port-type {
              type xr:live_ncs_Cisco-ios-xr-string;
              description
                "Port type";
            }
            leaf slot {
              type live_ncs_Icpe-slot;
              description
                "Slot";
            }
            leaf sub-slot {
              type live_ncs_Icpe-subslot;
              description
                "Sub slot";
            }
            leaf port-range {
              type string;
              // NCS drop mandatory statement
              description
                "Port range";
            }
          }
        }
        container connection-info {
          description
            "Satellite User";
          leaf username {
            type string;
            description
              "Satellite Username";
          }
          leaf password {
            type xr:live_ncs_Md5-password;
            description
              "Encrypted password for the user";
          }
        }
        container redundancy {
          description
            "Redundancy submode";
          leaf host-priority {
            type uint32 {
              range "0..255";
            }
            description
              "Priority for this host for the given satellite";
          }
        }
        leaf vrf {
          type string;
          description
            "VRF for Satellite IP Address";
        }
        leaf timeout-warning {
          type uint32 {
            range "0..4294967295";
          }
          description
            "Discovery timeout warning for the satellite";
        }
        leaf device-name {
          type string;
          description
            "Satellite Name";
        }
        leaf description {
          type string;
          description
            "Satellite Description";
        }
        leaf type {
          type string;
          // NCS drop mandatory statement
          description
            "Satellite Type";
        }
        leaf enable {
          type empty;
          // NCS drop mandatory statement
          description
            "Enable";
        }
        leaf disc-timeout {
          type uint32 {
            range "0..4294967295";
          }
          description
            "Discovery timeout for the satellite";
        }
        leaf delayed-switchback {
          type uint32 {
            range "0..4294967295";
          }
          units "second";
          description
            "Timer (in seconds) for delaying switchback in a
             dual home setup";
        }
        leaf serial-number {
          type string;
          description
            "Satellite Serial Number";
        }
        leaf secret {
          type xr:live_ncs_Md5-password;
          description
            "Encrypted password for the Satellite";
        }
        leaf ip-address {
          type inet:ip-address-no-zone;
          description
            "Satellite IP Address";
        }
        leaf satellite-id {
          type live_ncs_Icpe-sat-id;
          description
            "Satellite ID";
        }
      }
    }
  }
  augment "/ncs:devices/ncs:template/ncs:ned-id/ncs:config" {
    container nv-satellite-global {
      description
        "nV Satellite Global configuration";
      container chassis-mac {
        description
          "Chassis MAC address";
        leaf mac1 {
          type string;
          units "byte";
          description
            "First two bytes of MAC address";
        }
        leaf mac2 {
          type string;
          units "byte";
          description
            "Second two bytes of MAC address";
        }
        leaf mac3 {
          type string;
          units "byte";
          description
            "Third two bytes of MAC address";
        }
      }
    }
    container nv-satellites {
      description
        "Satellite Configuration table";
      list nv-satellite {
        // NCS patched for predictable order
        ordered-by user;
        key "satellite-id";
        description
          "Satellite Configuration";
        container upgrade-on-connect {
          description
            "Satellite auto-upgrade capability";
          leaf connect-type {
            type string;
            description
              "When to upgrade the satellite";
          }
          leaf reference {
            type string;
            description
              "Reference name";
          }
          leaf image-reference {
            type string;
            description
              "Image Reference name";
          }
        }
        container candidate-fabric-ports {
          description
            "Enable interfaces on the satellite to be used
             as fabric ports table";
          list candidate-fabric-port {
            // NCS patched for predictable order
            ordered-by user;
            key "port-type slot sub-slot";
            description
              "Enable interfaces on the satellite to be used
               as fabric ports";
            leaf port-type {
              type xr:ncs_template_Cisco-ios-xr-string;
              description
                "Port type";
            }
            leaf slot {
              type ncs_template_Icpe-slot;
              description
                "Slot";
            }
            leaf sub-slot {
              type ncs_template_Icpe-subslot;
              description
                "Sub slot";
            }
            leaf port-range {
              type string;
              // NCS drop mandatory statement
              description
                "Port range";
            }
          }
        }
        container connection-info {
          description
            "Satellite User";
          leaf username {
            type string;
            description
              "Satellite Username";
          }
          leaf password {
            type xr:ncs_template_Md5-password;
            description
              "Encrypted password for the user";
          }
        }
        container redundancy {
          description
            "Redundancy submode";
          leaf host-priority {
            type string;
            description
              "Priority for this host for the given satellite";
          }
        }
        leaf vrf {
          type string;
          description
            "VRF for Satellite IP Address";
        }
        leaf timeout-warning {
          type string;
          description
            "Discovery timeout warning for the satellite";
        }
        leaf device-name {
          type string;
          description
            "Satellite Name";
        }
        leaf description {
          type string;
          description
            "Satellite Description";
        }
        leaf type {
          type string;
          // NCS drop mandatory statement
          description
            "Satellite Type";
        }
        leaf enable {
          type empty;
          // NCS drop mandatory statement
          description
            "Enable";
        }
        leaf disc-timeout {
          type string;
          description
            "Discovery timeout for the satellite";
        }
        leaf delayed-switchback {
          type string;
          units "second";
          description
            "Timer (in seconds) for delaying switchback in a
             dual home setup";
        }
        leaf serial-number {
          type string;
          description
            "Satellite Serial Number";
        }
        leaf secret {
          type xr:ncs_template_Md5-password;
          description
            "Encrypted password for the Satellite";
        }
        leaf ip-address {
          type string;
          description
            "Satellite IP Address";
        }
        leaf satellite-id {
          type ncs_template_Icpe-sat-id;
          description
            "Satellite ID";
        }
      }
    }
  }
  augment "/ncs:devices/ncs:template/ncs:ned-id/ncs:config/a1:interface-configurations/a1:interface-configuration" {
    description
      "This augment extends the configuration data of
       'Cisco-IOS-XR-ifmgr-cfg'";
    container nv-satellite-access {
      description
        "nV Satellite Access Link Configuration";
    }
  }
  augment "/ncs:devices/ncs:device/ncs:live-status/a1:interface-configurations/a1:interface-configuration" {
    description
      "This augment extends the configuration data of
       'Cisco-IOS-XR-ifmgr-cfg'";
    container nv-satellite-access {
      tailf:ncs-device-type "netconf";
      tailf:display-when "not(../../../../ncs:module) or ../../../../ncs:module[ncs:name='Cisco-IOS-XR-icpe-infra-cfg'] or (../../../../ncs:live-status-protocol[not(ncs:capability)]) or (../../../../ncs:live-status-protocol/ncs:capability/ncs:module[.='Cisco-IOS-XR-icpe-infra-cfg'])";
      description
        "nV Satellite Access Link Configuration";
    }
  }
  augment "/ncs:devices/ncs:device/ncs:config/a1:interface-configurations/a1:interface-configuration" {
    description
      "This augment extends the configuration data of
       'Cisco-IOS-XR-ifmgr-cfg'";
    container nv-satellite-access {
      tailf:ncs-device-type "netconf";
      tailf:display-when "not(../../../../ncs:module) or ../../../../ncs:module[ncs:name='Cisco-IOS-XR-icpe-infra-cfg']";
      description
        "nV Satellite Access Link Configuration";
    }
  }
  augment "/ncs:devices/ncs:template/ncs:ned-id/ncs:config/a1:interface-configurations/a1:interface-configuration" {
    description
      "This augment extends the configuration data of
       'Cisco-IOS-XR-ifmgr-cfg'";
    container nv-satellite-fabric-link {
      presence "Indicates a nv-satellite-fabric-link node is configured.";
      description
        "nV Satellite Fabric Link Configuration";
      leaf satellite {
        type ncs_template_Icpe-sat-id;
        // NCS drop mandatory statement
        description
          "Hub & Spoke connection to a single Satellite";
      }
      leaf minimum-required-links {
        type ncs_template_Icpe-min-links;
        description
          "Mininum number of active links required";
      }
      uses ncs_template_REDUNDANCY;
      uses ncs_template_REMOTE-PORTS-TABLE;
    }
  }
  augment "/ncs:devices/ncs:device/ncs:live-status/a1:interface-configurations/a1:interface-configuration" {
    description
      "This augment extends the configuration data of
       'Cisco-IOS-XR-ifmgr-cfg'";
    container nv-satellite-fabric-link {
      tailf:ncs-device-type "netconf";
      tailf:display-when "not(../../../../ncs:module) or ../../../../ncs:module[ncs:name='Cisco-IOS-XR-icpe-infra-cfg'] or (../../../../ncs:live-status-protocol[not(ncs:capability)]) or (../../../../ncs:live-status-protocol/ncs:capability/ncs:module[.='Cisco-IOS-XR-icpe-infra-cfg'])";
      presence "Indicates a nv-satellite-fabric-link node is configured.";
      description
        "nV Satellite Fabric Link Configuration";
      leaf satellite {
        type live_ncs_Icpe-sat-id;
        // NCS drop mandatory statement
        description
          "Hub & Spoke connection to a single Satellite";
      }
      leaf minimum-required-links {
        type live_ncs_Icpe-min-links;
        description
          "Mininum number of active links required";
      }
      uses live_ncs_REDUNDANCY;
      uses live_ncs_REMOTE-PORTS-TABLE;
    }
  }
  augment "/ncs:devices/ncs:device/ncs:config/a1:interface-configurations/a1:interface-configuration" {
    description
      "This augment extends the configuration data of
       'Cisco-IOS-XR-ifmgr-cfg'";
    container nv-satellite-fabric-link {
      tailf:ncs-device-type "netconf";
      tailf:display-when "not(../../../../ncs:module) or ../../../../ncs:module[ncs:name='Cisco-IOS-XR-icpe-infra-cfg']";
      presence "Indicates a nv-satellite-fabric-link node is configured.";
      description
        "nV Satellite Fabric Link Configuration";
      leaf satellite {
        type Icpe-sat-id;
        mandatory true;
        description
          "Hub & Spoke connection to a single Satellite";
      }
      leaf minimum-required-links {
        type Icpe-min-links;
        description
          "Mininum number of active links required";
      }
      uses REDUNDANCY;
      uses REMOTE-PORTS-TABLE;
    }
  }
  augment "/ncs:devices/ncs:template/ncs:ned-id/ncs:config/a1:interface-configurations/a1:interface-configuration" {
    description
      "This augment extends the configuration data of
       'Cisco-IOS-XR-ifmgr-cfg'";
    container nv-satellite-fabric-network {
      presence "Indicates a nv-satellite-fabric-network node is configured.";
      description
        "Complex Network connection to one or more
         Satellites";
      container satellites {
        description
          "Connected Satellite table";
        list satellite {
          // NCS patched for predictable order
          ordered-by user;
          key "satellite-id";
          description
            "Connected Satellite";
          leaf satellite-id {
            type ncs_template_Icpe-sat-id;
            description
              "Satellite ID";
          }
          uses ncs_template_REMOTE-PORTS-TABLE;
          uses ncs_template_ENABLE;
        }
      }
      uses ncs_template_REDUNDANCY;
      uses ncs_template_ENABLE;
    }
  }
  augment "/ncs:devices/ncs:device/ncs:live-status/a1:interface-configurations/a1:interface-configuration" {
    description
      "This augment extends the configuration data of
       'Cisco-IOS-XR-ifmgr-cfg'";
    container nv-satellite-fabric-network {
      tailf:ncs-device-type "netconf";
      tailf:display-when "not(../../../../ncs:module) or ../../../../ncs:module[ncs:name='Cisco-IOS-XR-icpe-infra-cfg'] or (../../../../ncs:live-status-protocol[not(ncs:capability)]) or (../../../../ncs:live-status-protocol/ncs:capability/ncs:module[.='Cisco-IOS-XR-icpe-infra-cfg'])";
      presence "Indicates a nv-satellite-fabric-network node is configured.";
      description
        "Complex Network connection to one or more
         Satellites";
      container satellites {
        description
          "Connected Satellite table";
        list satellite {
          key "satellite-id";
          description
            "Connected Satellite";
          leaf satellite-id {
            type live_ncs_Icpe-sat-id;
            description
              "Satellite ID";
          }
          uses live_ncs_REMOTE-PORTS-TABLE;
          uses live_ncs_ENABLE;
        }
      }
      uses live_ncs_REDUNDANCY;
      uses live_ncs_ENABLE;
    }
  }
  augment "/ncs:devices/ncs:device/ncs:config/a1:interface-configurations/a1:interface-configuration" {
    description
      "This augment extends the configuration data of
       'Cisco-IOS-XR-ifmgr-cfg'";
    container nv-satellite-fabric-network {
      tailf:ncs-device-type "netconf";
      tailf:display-when "not(../../../../ncs:module) or ../../../../ncs:module[ncs:name='Cisco-IOS-XR-icpe-infra-cfg']";
      presence "Indicates a nv-satellite-fabric-network node is configured.";
      description
        "Complex Network connection to one or more
         Satellites";
      container satellites {
        description
          "Connected Satellite table";
        list satellite {
          key "satellite-id";
          description
            "Connected Satellite";
          leaf satellite-id {
            type Icpe-sat-id;
            description
              "Satellite ID";
          }
          uses REMOTE-PORTS-TABLE;
          uses ENABLE;
        }
      }
      uses REDUNDANCY;
      uses ENABLE;
    }
  }
  augment "/ncs:devices/ncs:template/ncs:ned-id/ncs:config/a2:redundancy-group-manager/a2:iccp/a2:iccp-groups/a2:iccp-group" {
    description
      "This augment extends the configuration data of
       'Cisco-IOS-XR-rgmgr-cfg'";
    container nv-satellite {
      description
        "nV Satellite configuration";
      leaf system-mac {
        type string;
        description
          "Optional identifier for this system";
      }
    }
  }
  augment "/ncs:devices/ncs:device/ncs:live-status/a2:redundancy-group-manager/a2:iccp/a2:iccp-groups/a2:iccp-group" {
    description
      "This augment extends the configuration data of
       'Cisco-IOS-XR-rgmgr-cfg'";
    container nv-satellite {
      tailf:ncs-device-type "netconf";
      tailf:display-when "not(../../../../../../ncs:module) or ../../../../../../ncs:module[ncs:name='Cisco-IOS-XR-icpe-infra-cfg'] or (../../../../../../ncs:live-status-protocol[not(ncs:capability)]) or (../../../../../../ncs:live-status-protocol/ncs:capability/ncs:module[.='Cisco-IOS-XR-icpe-infra-cfg'])";
      description
        "nV Satellite configuration";
      leaf system-mac {
        type yang:mac-address;
        description
          "Optional identifier for this system";
      }
    }
  }
  augment "/ncs:devices/ncs:device/ncs:config/a2:redundancy-group-manager/a2:iccp/a2:iccp-groups/a2:iccp-group" {
    description
      "This augment extends the configuration data of
       'Cisco-IOS-XR-rgmgr-cfg'";
    container nv-satellite {
      tailf:ncs-device-type "netconf";
      tailf:display-when "not(../../../../../../ncs:module) or ../../../../../../ncs:module[ncs:name='Cisco-IOS-XR-icpe-infra-cfg']";
      description
        "nV Satellite configuration";
      leaf system-mac {
        type yang:mac-address;
        description
          "Optional identifier for this system";
      }
    }
  }
}

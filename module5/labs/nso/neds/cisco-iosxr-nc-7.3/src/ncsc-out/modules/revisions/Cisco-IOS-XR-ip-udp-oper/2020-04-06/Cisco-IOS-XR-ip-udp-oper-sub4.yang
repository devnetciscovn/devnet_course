submodule Cisco-IOS-XR-ip-udp-oper-sub4 {
  // Generated by yanger -t ncs
  tailf:mount-id "cisco-iosxr-nc-7.3:cisco-iosxr-nc-7.3";

  belongs-to Cisco-IOS-XR-ip-udp-oper {
    prefix Cisco-IOS-XR-ip-udp-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-udp package operational data.

     Copyright (c) 2013-2020 by Cisco Systems, Inc.
     All rights reserved.";

  revision 2020-04-06 {
    description
      "min_ttl_dropped field is added to PCB_DETAIL output.";
    semver:module-version "1.1.0";
  }
  revision 2019-04-05 {
    description
      "Establish semantic version baseline.";
    semver:module-version "1.0.0";
  }
  revision 2018-08-09 {
    description
      "bind_local field is added to PCB_DETAIL output";
  }
  revision 2018-03-04 {
    description
      "PCB_ID argument is passed in string format.";
  }
  revision 2017-09-07 {
    description
      "Fixed type translation error.";
  }
  revision 2016-02-26 {
    description
      "Descriptions updated.";
  }
  revision 2015-11-09 {
    description
      "IOS XR 6.0 revision.";
  }

  grouping ncs_template_IP-UDP {
    description
      "UDP Traffic Information";
    leaf udp-input-packets {
      type string;
      description
        "UDP Received";
    }
    leaf udp-checksum-error-packets {
      type string;
      description
        "UDP Checksum Errors";
    }
    leaf udp-no-port-packets {
      type string;
      description
        "UDP No Port";
    }
    leaf udp-bad-length-packets {
      type string;
      description
        "UDP bad length";
    }
    leaf udp-output-packets {
      type string;
      description
        "UDP Transmitted";
    }
    leaf udp-dropped-packets {
      type string;
      description
        "UDP drop for other reason";
    }
  }

  grouping ncs_rpc_notif_IP-UDP {
    description
      "UDP Traffic Information";
    leaf udp-input-packets {
      type uint32;
      description
        "UDP Received";
    }
    leaf udp-checksum-error-packets {
      type uint32;
      description
        "UDP Checksum Errors";
    }
    leaf udp-no-port-packets {
      type uint32;
      description
        "UDP No Port";
    }
    leaf udp-bad-length-packets {
      type uint32;
      description
        "UDP bad length";
    }
    leaf udp-output-packets {
      type uint32;
      description
        "UDP Transmitted";
    }
    leaf udp-dropped-packets {
      type uint32;
      description
        "UDP drop for other reason";
    }
  }

  grouping live_ncs_IP-UDP {
    description
      "UDP Traffic Information";
    leaf udp-input-packets {
      type uint32;
      description
        "UDP Received";
    }
    leaf udp-checksum-error-packets {
      type uint32;
      description
        "UDP Checksum Errors";
    }
    leaf udp-no-port-packets {
      type uint32;
      description
        "UDP No Port";
    }
    leaf udp-bad-length-packets {
      type uint32;
      description
        "UDP bad length";
    }
    leaf udp-output-packets {
      type uint32;
      description
        "UDP Transmitted";
    }
    leaf udp-dropped-packets {
      type uint32;
      description
        "UDP drop for other reason";
    }
  }

  grouping IP-UDP {
    description
      "UDP Traffic Information";
    leaf udp-input-packets {
      type uint32;
      description
        "UDP Received";
    }
    leaf udp-checksum-error-packets {
      type uint32;
      description
        "UDP Checksum Errors";
    }
    leaf udp-no-port-packets {
      type uint32;
      description
        "UDP No Port";
    }
    leaf udp-bad-length-packets {
      type uint32;
      description
        "UDP bad length";
    }
    leaf udp-output-packets {
      type uint32;
      description
        "UDP Transmitted";
    }
    leaf udp-dropped-packets {
      type uint32;
      description
        "UDP drop for other reason";
    }
  }
}

module Cisco-IOS-XR-sysadmin-aaa-command-accounting {
  // Generated by yanger -t ncs
  tailf:mount-id "cisco-iosxr-nc-7.3:cisco-iosxr-nc-7.3";
  tailf:ncs-device-type "netconf";

  namespace "http://www.cisco.com/ns/yang/Cisco-IOS-XR-sysadmin-aaa-command-accounting";
  prefix admin-accounting;

  import tailf-aaa {
    prefix aaa;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module is used to enable/disable the command accounting via XR
     Copyright(c) 2016 by Cisco Systems, Inc.
     All rights reserved.

     Copyright (c) 2012-2020 by Cisco Systems, Inc.
     All rights reserved.";

  revision 2019-11-15 {
    description
      "Initial revision";
    semver:module-version "1.0.0";
  }

  augment "/ncs:devices/ncs:template/ncs:ned-id/ncs:config/aaa:aaa" {
    container admin-accounting {
      leaf enable {
        type string;
        // NCS drop default statement
      }
    }
  }
  augment "/ncs:devices/ncs:device/ncs:live-status/aaa:aaa" {
    container admin-accounting {
      tailf:ncs-device-type "netconf";
      tailf:display-when "not(../../../ncs:module) or ../../../ncs:module[ncs:name='Cisco-IOS-XR-sysadmin-aaa-command-accounting'] or (../../../ncs:live-status-protocol[not(ncs:capability)]) or (../../../ncs:live-status-protocol/ncs:capability/ncs:module[.='Cisco-IOS-XR-sysadmin-aaa-command-accounting'])";
      leaf enable {
        type boolean;
        // NCS drop default statement
      }
    }
  }
  augment "/ncs:devices/ncs:device/ncs:config/aaa:aaa" {
    container admin-accounting {
      tailf:ncs-device-type "netconf";
      tailf:display-when "not(../../../ncs:module) or ../../../ncs:module[ncs:name='Cisco-IOS-XR-sysadmin-aaa-command-accounting']";
      leaf enable {
        type boolean;
        default "false";
      }
    }
  }
}

module Cisco-IOS-XR-ncs5500-qos-oper {
  // Generated by yanger -t ncs
  tailf:mount-id "cisco-iosxr-nc-7.3:cisco-iosxr-nc-7.3";
  tailf:ncs-device-type "netconf";

  namespace "http://cisco.com/ns/yang/Cisco-IOS-XR-ncs5500-qos-oper";
  prefix ncs5500-qos-oper;

  import Cisco-IOS-XR-types {
    prefix xr;
  }
  import cisco-semver {
    prefix semver;
  }
  include Cisco-IOS-XR-ncs5500-qos-oper-sub2 {
    revision-date 2019-08-24;
  }
  include Cisco-IOS-XR-ncs5500-qos-oper-sub1 {
    revision-date 2019-08-24;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs5500-qos package operational data.

     This module contains definitions
     for the following management objects:
       platform-qos: DPA QoS EA operational data

     Copyright (c) 2013-2019 by Cisco Systems, Inc.
     All rights reserved.";

  revision 2019-08-24 {
    description
      "Fixing pyang compilation error.";
    semver:module-version "2.1.0";
  }
  revision 2019-04-05 {
    description
      "Establish semantic version baseline.";
    semver:module-version "1.1.0";
  }
  revision 2015-11-09 {
    description
      "IOS XR 6.0 revision.";
  }

  grouping ncs_template_QOS-CLASS-TABLE {
    description
      "Common node of input, output";
    container qos-class-table {
      description
        "QoS list of class names";
      uses ncs_template_CLASS;
    }
  }

  grouping ncs_template_CLASS {
    description
      "Common node of class-table, qos-class-table";
    list class {
      // NCS patched for predictable order
      ordered-by user;
      key "level-one-class-name";
      description
        "QoS policy class";
      leaf level-one-class-name {
        type string;
        description
          "QoS policy class name at level 1";
      }
      leaf level-two-class-name {
        type string;
        description
          "QoS policy child class name at level 2";
      }
      uses ncs_template_DPA-QOSEA-SHOW-CLASS-ST;
    }
  }

  grouping ncs_template_POLICY-DETAILS {
    description
      "Common node of interface, bundle-interface-single
       , bundle-interface, member-interface";
    container policy-details {
      description
        "Policy Details";
      uses ncs_template_DPA-QOSEA-SHOW-IF-QOS-INFO-ST;
    }
  }

  grouping ncs_template_MEMBER-INTERFACE-TABLE {
    description
      "Common node of bundle-interface-single,
       bundle-interface";
    container member-interfaces {
      description
        "QoS list of member interfaces";
      list member-interface {
        // NCS patched for predictable order
        ordered-by user;
        key "interface-name";
        description
          "QoS interface names";
        leaf interface-name {
          type xr:ncs_template_Interface-name;
          description
            "Member interface";
        }
        uses ncs_template_POLICY-DETAILS;
        uses ncs_template_CLASS-TABLE;
      }
    }
  }

  grouping ncs_template_OUTPUT {
    description
      "Common node of qos-interfaces, interface";
    container output {
      description
        "QoS policy direction egress";
      uses ncs_template_QOS-CLASS-TABLE;
    }
  }

  grouping ncs_template_CLASS-TABLE {
    description
      "Common node of interface, bundle-interface-single
       , bundle-interface, member-interface";
    container class-table {
      description
        "QoS list of class names";
      uses ncs_template_CLASS;
    }
  }

  grouping ncs_rpc_notif_QOS-CLASS-TABLE {
    description
      "Common node of input, output";
    container qos-class-table {
      description
        "QoS list of class names";
      uses ncs_rpc_notif_CLASS;
    }
  }

  grouping ncs_rpc_notif_CLASS {
    description
      "Common node of class-table, qos-class-table";
    list class {
      key "level-one-class-name";
      description
        "QoS policy class";
      leaf level-one-class-name {
        type string;
        description
          "QoS policy class name at level 1";
      }
      leaf level-two-class-name {
        type string;
        description
          "QoS policy child class name at level 2";
      }
      uses ncs_rpc_notif_DPA-QOSEA-SHOW-CLASS-ST;
    }
  }

  grouping ncs_rpc_notif_POLICY-DETAILS {
    description
      "Common node of interface, bundle-interface-single
       , bundle-interface, member-interface";
    container policy-details {
      description
        "Policy Details";
      uses ncs_rpc_notif_DPA-QOSEA-SHOW-IF-QOS-INFO-ST;
    }
  }

  grouping ncs_rpc_notif_MEMBER-INTERFACE-TABLE {
    description
      "Common node of bundle-interface-single,
       bundle-interface";
    container member-interfaces {
      description
        "QoS list of member interfaces";
      list member-interface {
        key "interface-name";
        description
          "QoS interface names";
        leaf interface-name {
          type xr:ncs_rpc_notif_Interface-name;
          description
            "Member interface";
        }
        uses ncs_rpc_notif_POLICY-DETAILS;
        uses ncs_rpc_notif_CLASS-TABLE;
      }
    }
  }

  grouping ncs_rpc_notif_OUTPUT {
    description
      "Common node of qos-interfaces, interface";
    container output {
      description
        "QoS policy direction egress";
      uses ncs_rpc_notif_QOS-CLASS-TABLE;
    }
  }

  grouping ncs_rpc_notif_CLASS-TABLE {
    description
      "Common node of interface, bundle-interface-single
       , bundle-interface, member-interface";
    container class-table {
      description
        "QoS list of class names";
      uses ncs_rpc_notif_CLASS;
    }
  }

  grouping live_ncs_QOS-CLASS-TABLE {
    description
      "Common node of input, output";
    container qos-class-table {
      description
        "QoS list of class names";
      uses live_ncs_CLASS;
    }
  }

  grouping live_ncs_CLASS {
    description
      "Common node of class-table, qos-class-table";
    list class {
      key "level-one-class-name";
      description
        "QoS policy class";
      leaf level-one-class-name {
        type string;
        description
          "QoS policy class name at level 1";
      }
      leaf level-two-class-name {
        type string;
        description
          "QoS policy child class name at level 2";
      }
      uses live_ncs_DPA-QOSEA-SHOW-CLASS-ST;
    }
  }

  grouping live_ncs_POLICY-DETAILS {
    description
      "Common node of interface, bundle-interface-single
       , bundle-interface, member-interface";
    container policy-details {
      description
        "Policy Details";
      uses live_ncs_DPA-QOSEA-SHOW-IF-QOS-INFO-ST;
    }
  }

  grouping live_ncs_MEMBER-INTERFACE-TABLE {
    description
      "Common node of bundle-interface-single,
       bundle-interface";
    container member-interfaces {
      description
        "QoS list of member interfaces";
      list member-interface {
        key "interface-name";
        description
          "QoS interface names";
        leaf interface-name {
          type xr:live_ncs_Interface-name;
          description
            "Member interface";
        }
        uses live_ncs_POLICY-DETAILS;
        uses live_ncs_CLASS-TABLE;
      }
    }
  }

  grouping live_ncs_OUTPUT {
    description
      "Common node of qos-interfaces, interface";
    container output {
      description
        "QoS policy direction egress";
      uses live_ncs_QOS-CLASS-TABLE;
    }
  }

  grouping live_ncs_CLASS-TABLE {
    description
      "Common node of interface, bundle-interface-single
       , bundle-interface, member-interface";
    container class-table {
      description
        "QoS list of class names";
      uses live_ncs_CLASS;
    }
  }

  grouping QOS-CLASS-TABLE {
    description
      "Common node of input, output";
    container qos-class-table {
      description
        "QoS list of class names";
      uses CLASS;
    }
  }

  grouping CLASS {
    description
      "Common node of class-table, qos-class-table";
    list class {
      key "level-one-class-name";
      description
        "QoS policy class";
      leaf level-one-class-name {
        type string;
        description
          "QoS policy class name at level 1";
      }
      leaf level-two-class-name {
        type string;
        description
          "QoS policy child class name at level 2";
      }
      uses DPA-QOSEA-SHOW-CLASS-ST;
    }
  }

  grouping POLICY-DETAILS {
    description
      "Common node of interface, bundle-interface-single
       , bundle-interface, member-interface";
    container policy-details {
      description
        "Policy Details";
      uses DPA-QOSEA-SHOW-IF-QOS-INFO-ST;
    }
  }

  grouping MEMBER-INTERFACE-TABLE {
    description
      "Common node of bundle-interface-single,
       bundle-interface";
    container member-interfaces {
      description
        "QoS list of member interfaces";
      list member-interface {
        key "interface-name";
        description
          "QoS interface names";
        leaf interface-name {
          type xr:Interface-name;
          description
            "Member interface";
        }
        uses POLICY-DETAILS;
        uses CLASS-TABLE;
      }
    }
  }

  grouping OUTPUT {
    description
      "Common node of qos-interfaces, interface";
    container output {
      description
        "QoS policy direction egress";
      uses QOS-CLASS-TABLE;
    }
  }

  grouping CLASS-TABLE {
    description
      "Common node of interface, bundle-interface-single
       , bundle-interface, member-interface";
    container class-table {
      description
        "QoS list of class names";
      uses CLASS;
    }
  }

  augment "/ncs:devices/ncs:device/ncs:config" {
    // NCS drop config false container 'platform-qos'
  }
  augment "/ncs:devices/ncs:device/ncs:live-status" {
    container platform-qos {
      tailf:ncs-device-type "netconf";
      tailf:display-when "not(../../ncs:module) or ../../ncs:module[ncs:name='Cisco-IOS-XR-ncs5500-qos-oper'] or (../../ncs:live-status-protocol[not(ncs:capability)]) or (../../ncs:live-status-protocol/ncs:capability/ncs:module[.='Cisco-IOS-XR-ncs5500-qos-oper'])";
      description
        "DPA QoS EA operational data";
      container nodes {
        description
          "List of nodes with platform specific QoS
           configuration";
        list node {
          key "node-name";
          description
            "Node with platform specific QoS configuration";
          container bundle-interfaces {
            description
              "QoS list of bundle interfaces";
            list bundle-interface {
              description
                "QoS interface names";
              leaf interface-name {
                type xr:live_ncs_Interface-name;
                description
                  "Bundle interface name";
              }
              leaf npu-id {
                type uint32;
                description
                  "NPU ID";
              }
              leaf qos-direction {
                type string;
                description
                  "The interface direction on which QoS is
                   applied to.";
              }
              uses live_ncs_POLICY-DETAILS;
              uses live_ncs_MEMBER-INTERFACE-TABLE;
              uses live_ncs_CLASS-TABLE;
            }
          }
          container interfaces {
            description
              "QoS list of interfaces";
            list interface {
              description
                "QoS interface names";
              leaf interface-name {
                type xr:live_ncs_Interface-name;
                description
                  "The name of the interface";
              }
              leaf qos-direction {
                type string;
                description
                  "The interface direction on which QoS is
                   applied to.";
              }
              uses live_ncs_POLICY-DETAILS;
              uses live_ncs_OUTPUT;
              uses live_ncs_CLASS-TABLE;
            }
          }
          container qos-interfaces {
            description
              "QoS list of interfaces";
            list qos-interface {
              description
                "QoS interface names";
              container input {
                description
                  "QoS policy direction ingress";
                uses live_ncs_QOS-CLASS-TABLE;
              }
              leaf interface-name {
                type xr:live_ncs_Interface-name;
                description
                  "The name of the interface";
              }
              leaf qos-direction {
                type string;
                description
                  "The interface direction on which QoS is
                   applied to.";
              }
              uses live_ncs_OUTPUT;
            }
          }
          container bundle-interface-singles {
            description
              "QoS list of bundle interfaces";
            list bundle-interface-single {
              key "interface-name";
              description
                "QoS interface names";
              leaf interface-name {
                type xr:live_ncs_Interface-name;
                description
                  "Bundle interface name";
              }
              uses live_ncs_POLICY-DETAILS;
              uses live_ncs_MEMBER-INTERFACE-TABLE;
              uses live_ncs_CLASS-TABLE;
            }
          }
          container remote-interfaces {
            description
              "QoS list of remote interfaces";
            list remote-interface {
              key "interface-name";
              description
                "QoS remote interface names";
              leaf interface-name {
                type xr:live_ncs_Interface-name;
                description
                  "The name of the remote interface";
              }
              uses live_ncs_DPA-QOSEA-SHOW-REMOTE-IF-INFO-ST;
            }
          }
          leaf node-name {
            type xr:live_ncs_Node-id;
            description
              "Node name";
          }
        }
      }
    }
  }
  augment "/ncs:devices/ncs:template/ncs:ned-id/ncs:config" {
    // NCS drop config false container 'platform-qos'
  }
}

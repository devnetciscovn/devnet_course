module Cisco-IOS-XR-ethernet-loopback-oper {
  // Generated by yanger -t ncs
  tailf:mount-id "cisco-iosxr-nc-7.3:cisco-iosxr-nc-7.3";
  tailf:ncs-device-type "netconf";

  namespace "http://cisco.com/ns/yang/Cisco-IOS-XR-ethernet-loopback-oper";
  prefix ethernet-loopback-oper;

  import Cisco-IOS-XR-types {
    prefix xr;
  }
  import cisco-semver {
    prefix semver;
  }
  include Cisco-IOS-XR-ethernet-loopback-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-loopback package operational data.

     This module contains definitions
     for the following management objects:
       ethernet-loopback: Ethernet Loopback operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'ethernet-loopback'
  }
  augment "/ncs:devices/ncs:device/ncs:live-status" {
    container ethernet-loopback {
      tailf:ncs-device-type "netconf";
      tailf:display-when "not(../../ncs:module) or ../../ncs:module[ncs:name='Cisco-IOS-XR-ethernet-loopback-oper'] or (../../ncs:live-status-protocol[not(ncs:capability)]) or (../../ncs:live-status-protocol/ncs:capability/ncs:module[.='Cisco-IOS-XR-ethernet-loopback-oper'])";
      description
        "Ethernet Loopback operational data.";
      container messages-interfaces {
        description
          "Container for loopback messages";
        list messages-interface {
          key "interface-name";
          description
            "Loopback messages";
          leaf interface-name {
            type xr:live_ncs_Interface-name;
            description
              "InterfaceName";
          }
          uses live_ncs_EDPL-MESSAGES-BAG;
        }
      }
      container permitted-interfaces {
        description
          "Container for interfaces on which Ethernet
           Loopback is permitted.";
        list permitted-interface {
          key "interface-name";
          description
            "Data for an interface permitted to use Ethernet
             Loopback.";
          leaf interface-name {
            type xr:live_ncs_Interface-name;
            description
              "InterfaceName";
          }
          uses live_ncs_EDPL-PERMITTED-BAG;
        }
      }
      container active-interfaces {
        description
          "Container for interfaces with active Ethernet
           Loopback sessions.";
        list active-interface {
          key "interface-name";
          description
            "Data for an interface with active Ethernet
             Loopback sessions.";
          leaf interface-name {
            type xr:live_ncs_Interface-name;
            description
              "InterfaceName";
          }
          uses live_ncs_EDPL-ACTIVE-BAG;
        }
      }
    }
  }
  augment "/ncs:devices/ncs:template/ncs:ned-id/ncs:config" {
    // NCS drop config false container 'ethernet-loopback'
  }
}

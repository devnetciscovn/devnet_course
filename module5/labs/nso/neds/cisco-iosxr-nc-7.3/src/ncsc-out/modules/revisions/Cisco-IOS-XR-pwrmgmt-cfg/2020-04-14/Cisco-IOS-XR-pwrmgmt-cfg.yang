module Cisco-IOS-XR-pwrmgmt-cfg {
  // Generated by yanger -t ncs
  tailf:mount-id "cisco-iosxr-nc-7.3:cisco-iosxr-nc-7.3";
  tailf:ncs-device-type "netconf";

  namespace "http://cisco.com/ns/yang/Cisco-IOS-XR-pwrmgmt-cfg";
  prefix pwrmgmt-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pwrmgmt package configuration.

     This module contains definitions
     for the following management objects:
       power-management: EnvMon Power Management Config Data

     Copyright (c) 2013-2020 by Cisco Systems, Inc.
     All rights reserved.";

  revision 2020-04-14 {
    description
      "IOS XR 7.0.14 revision. Moved action-disable to be valid only for SF-D platforms.";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    container power-management {
      tailf:ncs-device-type "netconf";
      tailf:display-when "not(../../ncs:module) or ../../ncs:module[ncs:name='Cisco-IOS-XR-pwrmgmt-cfg']";
      description
        "EnvMon Power Management Config Data";
      leaf extended-temp {
        type boolean;
        description
          "Config for setting power budget for extended
           temp mode";
      }
      leaf single-feed-mode {
        type boolean;
        description
          "Config for suppressing alarms for missing feed
           supplies";
      }
      leaf red-num-pems {
        type uint32;
        description
          "Number of the redundant PEMS";
      }
    }
  }
  augment "/ncs:devices/ncs:device/ncs:live-status" {
    container power-management {
      tailf:ncs-device-type "netconf";
      tailf:display-when "not(../../ncs:module) or ../../ncs:module[ncs:name='Cisco-IOS-XR-pwrmgmt-cfg'] or (../../ncs:live-status-protocol[not(ncs:capability)]) or (../../ncs:live-status-protocol/ncs:capability/ncs:module[.='Cisco-IOS-XR-pwrmgmt-cfg'])";
      description
        "EnvMon Power Management Config Data";
      leaf extended-temp {
        type boolean;
        description
          "Config for setting power budget for extended
           temp mode";
      }
      leaf single-feed-mode {
        type boolean;
        description
          "Config for suppressing alarms for missing feed
           supplies";
      }
      leaf red-num-pems {
        type uint32;
        description
          "Number of the redundant PEMS";
      }
    }
  }
  augment "/ncs:devices/ncs:template/ncs:ned-id/ncs:config" {
    container power-management {
      description
        "EnvMon Power Management Config Data";
      leaf extended-temp {
        type string;
        description
          "Config for setting power budget for extended
           temp mode";
      }
      leaf single-feed-mode {
        type string;
        description
          "Config for suppressing alarms for missing feed
           supplies";
      }
      leaf red-num-pems {
        type string;
        description
          "Number of the redundant PEMS";
      }
    }
  }
}

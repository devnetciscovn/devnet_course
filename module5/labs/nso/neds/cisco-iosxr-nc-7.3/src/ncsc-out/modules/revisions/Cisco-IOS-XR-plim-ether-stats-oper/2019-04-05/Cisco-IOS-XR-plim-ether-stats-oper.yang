module Cisco-IOS-XR-plim-ether-stats-oper {
  // Generated by yanger -t ncs
  tailf:mount-id "cisco-iosxr-nc-7.3:cisco-iosxr-nc-7.3";
  tailf:ncs-device-type "netconf";

  namespace "http://cisco.com/ns/yang/Cisco-IOS-XR-plim-ether-stats-oper";
  prefix plim-ether-stats-oper;

  import Cisco-IOS-XR-types {
    prefix xr;
  }
  import cisco-semver {
    prefix semver;
  }
  include Cisco-IOS-XR-plim-ether-stats-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR plim-ether-stats package operational data.

     This module contains definitions
     for the following management objects:
       plimasic: Plim Asic Stats

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container plimasic
  }
  augment "/ncs:devices/ncs:device/ncs:live-status" {
    container plimasic {
      tailf:ncs-device-type "netconf";
      tailf:display-when "not(../../ncs:module) or ../../ncs:module[ncs:name='Cisco-IOS-XR-plim-ether-stats-oper'] or (../../ncs:live-status-protocol[not(ncs:capability)]) or (../../ncs:live-status-protocol/ncs:capability/ncs:module[.='Cisco-IOS-XR-plim-ether-stats-oper'])";
      description
        "Plim Asic Stats";
      container nodes {
        description
          "List of nodes";
        list node {
          key "node-name";
          description
            "Per node NPU data";
          container statistics {
            description
              "Plim Asic stats directory";
            container interfaces {
              description
                "Plim Interface Entry";
              list interface {
                key "interface-name";
                description
                  "Plim Asic Statistics Interface Based";
                leaf interface-name {
                  type xr:live_ncs_Cisco-ios-xr-string;
                  description
                    "Interface Name";
                }
                uses live_ncs_PLIM-ETHER-EDM-STRING;
              }
            }
            container summary {
              description
                "Plim Asic Statistics Summary";
              uses live_ncs_PLIM-ETHER-EDM-STRING;
            }
          }
          leaf node-name {
            type xr:live_ncs_Node-id;
            description
              "Node name";
          }
        }
      }
    }
  }
  augment "/ncs:devices/ncs:template/ncs:ned-id/ncs:config" {
    // NCS drop config false container plimasic
  }
}

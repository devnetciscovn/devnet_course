module Cisco-IOS-XR-fib-common-oper {
  // Generated by yanger -t ncs
  tailf:mount-id "cisco-iosxr-nc-7.3:cisco-iosxr-nc-7.3";
  tailf:ncs-device-type "netconf";

  namespace "http://cisco.com/ns/yang/Cisco-IOS-XR-fib-common-oper";
  prefix fib-common-oper;

  import ietf-inet-types {
    prefix inet;
  }
  import Cisco-IOS-XR-types {
    prefix xr;
  }
  import cisco-semver {
    prefix semver;
  }
  include Cisco-IOS-XR-fib-common-oper-sub7 {
    revision-date 2021-03-10;
  }
  include Cisco-IOS-XR-fib-common-oper-sub6 {
    revision-date 2021-03-10;
  }
  include Cisco-IOS-XR-fib-common-oper-sub5 {
    revision-date 2021-03-10;
  }
  include Cisco-IOS-XR-fib-common-oper-sub4 {
    revision-date 2021-03-10;
  }
  include Cisco-IOS-XR-fib-common-oper-sub3 {
    revision-date 2021-03-10;
  }
  include Cisco-IOS-XR-fib-common-oper-sub2 {
    revision-date 2021-03-10;
  }
  include Cisco-IOS-XR-fib-common-oper-sub1 {
    revision-date 2021-03-10;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fib-common package operational data.

     This module contains definitions
     for the following management objects:
       fib-statistics: cef interface drops operational data
       fib: FIB operational data
       oc-aft-l3: Openconfig L3 abstract forwarding table data
       mpls-forwarding: MPLS forwarding operational data

     Copyright (c) 2013-2021 by Cisco Systems, Inc.
     All rights reserved.";

  revision 2021-03-10 {
    description
      "Make FIB object Encap-ID aware.";
    semver:module-version "3.1.0";
  }
  revision 2020-10-20 {
    description
      "NBC documentation of CSCvu06764, CSCvv14573,CSCvv76648
       2020-05-26
       Update SRv6 Block Space naming convention
       2020-05-05
       changes related to treat SRv6 and SID as well-known when parsing XML for yang";
    semver:module-version "3.0.0";
  }
  revision 2020-01-16 {
    description
      "NBC documentation of CSCvs27272,CSCvs22018,CSCvs45512
       2019-10-29
       Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef ncs_template_Fib-route-source {
    type string;
    description
      "Fib route source";
  }

  typedef ncs_template_Fib-protocol {
    type string;
    description
      "Fib protocol";
  }

  typedef ncs_template_Fibipv6-flow-label {
    type string;
    description
      "Fibipv6 flow label";
  }

  typedef ncs_template_Fibafi-proto {
    type string;
    description
      "Fibafi proto";
  }

  typedef ncs_template_Fib-label {
    type string;
    description
      "Fib label";
  }

  typedef ncs_template_Fibllc-entry {
    type string;
    description
      "Fibllc entry";
  }

  typedef ncs_template_Fibnh-info-repl {
    type string;
    description
      "Fibnh info repl";
  }

  typedef ncs_template_Fibfrr {
    type string;
    description
      "Fibfrr";
  }

  typedef ncs_template_Fib-link {
    type string;
    description
      "Fib link";
  }

  typedef ncs_template_Mpls-label {
    type string;
    description
      "Mpls label";
  }

  typedef ncs_template_Mplseos {
    type string;
    description
      "Mplseos";
  }

  typedef ncs_template_Prefix-len-range {
    type string;
    description
      "Prefix len range";
  }

  typedef ncs_template_Generic-index {
    type string;
    description
      "Generic index";
  }

  typedef ncs_rpc_notif_Fib-route-source {
    type enumeration {
      enum "lsd" {
        value 5;
        description
          "LSD";
      }
      enum "rib" {
        value 7;
        description
          "RIB";
      }
      enum "mrib" {
        value 13;
        description
          "MRIB";
      }
    }
    description
      "Fib route source";
  }

  typedef ncs_rpc_notif_Fib-protocol {
    type enumeration {
      enum "ipv4" {
        value 0;
        description
          "ipv4 protocol";
      }
      enum "ipv6" {
        value 1;
        description
          "ipv6 protocol";
      }
      enum "mpls" {
        value 2;
        description
          "MPLS protocol";
      }
    }
    description
      "Fib protocol";
  }

  typedef ncs_rpc_notif_Fibipv6-flow-label {
    type uint32 {
      range "0..1048575";
    }
    description
      "Fibipv6 flow label";
  }

  typedef ncs_rpc_notif_Fibafi-proto {
    type enumeration {
      enum "ipv4" {
        value 0;
        description
          "ipv4 protocol";
      }
      enum "ipv4-mpls" {
        value 1;
        description
          "ipv4 mpls protocol";
      }
      enum "ipv6" {
        value 2;
        description
          "ipv6 protocol";
      }
      enum "ipv6-mpls" {
        value 3;
        description
          "ipv6 mpls protocol";
      }
    }
    description
      "Fibafi proto";
  }

  typedef ncs_rpc_notif_Fib-label {
    type uint32 {
      range "16..1048575";
    }
    description
      "Fib label";
  }

  typedef ncs_rpc_notif_Fibllc-entry {
    type enumeration {
      enum "xc" {
        value 1;
        description
          "LabelXconnect";
      }
      enum "pfx" {
        value 2;
        description
          "IPPrefix";
      }
    }
    description
      "Fibllc entry";
  }

  typedef ncs_rpc_notif_Fibnh-info-repl {
    type enumeration {
      enum "fib-nh-repl-none" {
        value 0;
        description
          "None Replicated NHINFO";
      }
      enum "fib-nh-repl-rsvpte" {
        value 1;
        description
          "Replicated NHINFO for TE Accounting";
      }
      enum "fib-nh-repl-sr-mpls" {
        value 2;
        description
          "Replicated NHINFO for SR MPLS Accounting";
      }
      enum "fib-nh-repl-bm" {
        value 3;
        description
          "Replicated NHINFO for Bundle member";
      }
    }
    description
      "Fibnh info repl";
  }

  typedef ncs_rpc_notif_Fibfrr {
    type enumeration {
      enum "fib-te-frr-node" {
        value 0;
        description
          "TE FRR";
      }
      enum "fib-te-frr-intf" {
        value 1;
        description
          "TE Interface FRR";
      }
      enum "fib-te-frr-protected-nh" {
        value 2;
        description
          "TE Protected FRR";
      }
      enum "fib-te-frr-backup-nh" {
        value 3;
        description
          "TE Backup FRR";
      }
      enum "fib-per-link-frr-protected-nh" {
        value 4;
        description
          "Per Link Protected FRR";
      }
      enum "fib-per-link-frr-backup-nh" {
        value 5;
        description
          "Per Link Backup FRR";
      }
      enum "fib-prefix-frr-protected-nh" {
        value 6;
        description
          "Per Prefix Protected FRR";
      }
      enum "fib-prefix-frr-backup-nh" {
        value 7;
        description
          "Per Prefix Backup FRR";
      }
      enum "fib-pic-frr-protected-nh" {
        value 8;
        description
          "BGP PIC Protected FRR";
      }
      enum "fib-pic-frr-backup-nh" {
        value 9;
        description
          "BGP PIC Backup FRR";
      }
    }
    description
      "Fibfrr";
  }

  typedef ncs_rpc_notif_Fib-link {
    type enumeration {
      enum "link-ipv4" {
        value 0;
        description
          "IPv4 link protocol";
      }
      enum "link-ipv6" {
        value 1;
        description
          "IPv6 link protocol";
      }
      enum "link-mpls" {
        value 2;
        description
          "MPLS link protocol";
      }
    }
    description
      "Fib link";
  }

  typedef ncs_rpc_notif_Mpls-label {
    type uint32 {
      range "16..1048575";
    }
    description
      "Mpls label";
  }

  typedef ncs_rpc_notif_Mplseos {
    type enumeration {
      enum "eos0" {
        value 0;
        description
          "EOS Disable";
      }
      enum "eos1" {
        value 1;
        description
          "EOS Enable";
      }
    }
    description
      "Mplseos";
  }

  typedef ncs_rpc_notif_Prefix-len-range {
    type uint32 {
      range "0..128";
    }
    description
      "Prefix len range";
  }

  typedef ncs_rpc_notif_Generic-index {
    type uint32 {
      range "0..4294967295";
    }
    description
      "Generic index";
  }

  typedef live_ncs_Fib-route-source {
    type enumeration {
      enum "lsd" {
        value 5;
        description
          "LSD";
      }
      enum "rib" {
        value 7;
        description
          "RIB";
      }
      enum "mrib" {
        value 13;
        description
          "MRIB";
      }
    }
    description
      "Fib route source";
  }

  typedef live_ncs_Fib-protocol {
    type enumeration {
      enum "ipv4" {
        value 0;
        description
          "ipv4 protocol";
      }
      enum "ipv6" {
        value 1;
        description
          "ipv6 protocol";
      }
      enum "mpls" {
        value 2;
        description
          "MPLS protocol";
      }
    }
    description
      "Fib protocol";
  }

  typedef live_ncs_Fibipv6-flow-label {
    type uint32 {
      range "0..1048575";
    }
    description
      "Fibipv6 flow label";
  }

  typedef live_ncs_Fibafi-proto {
    type enumeration {
      enum "ipv4" {
        value 0;
        description
          "ipv4 protocol";
      }
      enum "ipv4-mpls" {
        value 1;
        description
          "ipv4 mpls protocol";
      }
      enum "ipv6" {
        value 2;
        description
          "ipv6 protocol";
      }
      enum "ipv6-mpls" {
        value 3;
        description
          "ipv6 mpls protocol";
      }
    }
    description
      "Fibafi proto";
  }

  typedef live_ncs_Fib-label {
    type uint32 {
      range "16..1048575";
    }
    description
      "Fib label";
  }

  typedef live_ncs_Fibllc-entry {
    type enumeration {
      enum "xc" {
        value 1;
        description
          "LabelXconnect";
      }
      enum "pfx" {
        value 2;
        description
          "IPPrefix";
      }
    }
    description
      "Fibllc entry";
  }

  typedef live_ncs_Fibnh-info-repl {
    type enumeration {
      enum "fib-nh-repl-none" {
        value 0;
        description
          "None Replicated NHINFO";
      }
      enum "fib-nh-repl-rsvpte" {
        value 1;
        description
          "Replicated NHINFO for TE Accounting";
      }
      enum "fib-nh-repl-sr-mpls" {
        value 2;
        description
          "Replicated NHINFO for SR MPLS Accounting";
      }
      enum "fib-nh-repl-bm" {
        value 3;
        description
          "Replicated NHINFO for Bundle member";
      }
    }
    description
      "Fibnh info repl";
  }

  typedef live_ncs_Fibfrr {
    type enumeration {
      enum "fib-te-frr-node" {
        value 0;
        description
          "TE FRR";
      }
      enum "fib-te-frr-intf" {
        value 1;
        description
          "TE Interface FRR";
      }
      enum "fib-te-frr-protected-nh" {
        value 2;
        description
          "TE Protected FRR";
      }
      enum "fib-te-frr-backup-nh" {
        value 3;
        description
          "TE Backup FRR";
      }
      enum "fib-per-link-frr-protected-nh" {
        value 4;
        description
          "Per Link Protected FRR";
      }
      enum "fib-per-link-frr-backup-nh" {
        value 5;
        description
          "Per Link Backup FRR";
      }
      enum "fib-prefix-frr-protected-nh" {
        value 6;
        description
          "Per Prefix Protected FRR";
      }
      enum "fib-prefix-frr-backup-nh" {
        value 7;
        description
          "Per Prefix Backup FRR";
      }
      enum "fib-pic-frr-protected-nh" {
        value 8;
        description
          "BGP PIC Protected FRR";
      }
      enum "fib-pic-frr-backup-nh" {
        value 9;
        description
          "BGP PIC Backup FRR";
      }
    }
    description
      "Fibfrr";
  }

  typedef live_ncs_Fib-link {
    type enumeration {
      enum "link-ipv4" {
        value 0;
        description
          "IPv4 link protocol";
      }
      enum "link-ipv6" {
        value 1;
        description
          "IPv6 link protocol";
      }
      enum "link-mpls" {
        value 2;
        description
          "MPLS link protocol";
      }
    }
    description
      "Fib link";
  }

  typedef live_ncs_Mpls-label {
    type uint32 {
      range "16..1048575";
    }
    description
      "Mpls label";
  }

  typedef live_ncs_Mplseos {
    type enumeration {
      enum "eos0" {
        value 0;
        description
          "EOS Disable";
      }
      enum "eos1" {
        value 1;
        description
          "EOS Enable";
      }
    }
    description
      "Mplseos";
  }

  typedef live_ncs_Prefix-len-range {
    type uint32 {
      range "0..128";
    }
    description
      "Prefix len range";
  }

  typedef live_ncs_Generic-index {
    type uint32 {
      range "0..4294967295";
    }
    description
      "Generic index";
  }

  typedef Fib-route-source {
    type enumeration {
      enum "lsd" {
        value 5;
        description
          "LSD";
      }
      enum "rib" {
        value 7;
        description
          "RIB";
      }
      enum "mrib" {
        value 13;
        description
          "MRIB";
      }
    }
    description
      "Fib route source";
  }

  typedef Fib-protocol {
    type enumeration {
      enum "ipv4" {
        value 0;
        description
          "ipv4 protocol";
      }
      enum "ipv6" {
        value 1;
        description
          "ipv6 protocol";
      }
      enum "mpls" {
        value 2;
        description
          "MPLS protocol";
      }
    }
    description
      "Fib protocol";
  }

  typedef Fibipv6-flow-label {
    type uint32 {
      range "0..1048575";
    }
    description
      "Fibipv6 flow label";
  }

  typedef Fibafi-proto {
    type enumeration {
      enum "ipv4" {
        value 0;
        description
          "ipv4 protocol";
      }
      enum "ipv4-mpls" {
        value 1;
        description
          "ipv4 mpls protocol";
      }
      enum "ipv6" {
        value 2;
        description
          "ipv6 protocol";
      }
      enum "ipv6-mpls" {
        value 3;
        description
          "ipv6 mpls protocol";
      }
    }
    description
      "Fibafi proto";
  }

  typedef Fib-label {
    type uint32 {
      range "16..1048575";
    }
    description
      "Fib label";
  }

  typedef Fibllc-entry {
    type enumeration {
      enum "xc" {
        value 1;
        description
          "LabelXconnect";
      }
      enum "pfx" {
        value 2;
        description
          "IPPrefix";
      }
    }
    description
      "Fibllc entry";
  }

  typedef Fibnh-info-repl {
    type enumeration {
      enum "fib-nh-repl-none" {
        value 0;
        description
          "None Replicated NHINFO";
      }
      enum "fib-nh-repl-rsvpte" {
        value 1;
        description
          "Replicated NHINFO for TE Accounting";
      }
      enum "fib-nh-repl-sr-mpls" {
        value 2;
        description
          "Replicated NHINFO for SR MPLS Accounting";
      }
      enum "fib-nh-repl-bm" {
        value 3;
        description
          "Replicated NHINFO for Bundle member";
      }
    }
    description
      "Fibnh info repl";
  }

  typedef Fibfrr {
    type enumeration {
      enum "fib-te-frr-node" {
        value 0;
        description
          "TE FRR";
      }
      enum "fib-te-frr-intf" {
        value 1;
        description
          "TE Interface FRR";
      }
      enum "fib-te-frr-protected-nh" {
        value 2;
        description
          "TE Protected FRR";
      }
      enum "fib-te-frr-backup-nh" {
        value 3;
        description
          "TE Backup FRR";
      }
      enum "fib-per-link-frr-protected-nh" {
        value 4;
        description
          "Per Link Protected FRR";
      }
      enum "fib-per-link-frr-backup-nh" {
        value 5;
        description
          "Per Link Backup FRR";
      }
      enum "fib-prefix-frr-protected-nh" {
        value 6;
        description
          "Per Prefix Protected FRR";
      }
      enum "fib-prefix-frr-backup-nh" {
        value 7;
        description
          "Per Prefix Backup FRR";
      }
      enum "fib-pic-frr-protected-nh" {
        value 8;
        description
          "BGP PIC Protected FRR";
      }
      enum "fib-pic-frr-backup-nh" {
        value 9;
        description
          "BGP PIC Backup FRR";
      }
    }
    description
      "Fibfrr";
  }

  typedef Fib-link {
    type enumeration {
      enum "link-ipv4" {
        value 0;
        description
          "IPv4 link protocol";
      }
      enum "link-ipv6" {
        value 1;
        description
          "IPv6 link protocol";
      }
      enum "link-mpls" {
        value 2;
        description
          "MPLS link protocol";
      }
    }
    description
      "Fib link";
  }

  typedef Mpls-label {
    type uint32 {
      range "16..1048575";
    }
    description
      "Mpls label";
  }

  typedef Mplseos {
    type enumeration {
      enum "eos0" {
        value 0;
        description
          "EOS Disable";
      }
      enum "eos1" {
        value 1;
        description
          "EOS Enable";
      }
    }
    description
      "Mplseos";
  }

  typedef Prefix-len-range {
    type uint32 {
      range "0..128";
    }
    description
      "Prefix len range";
  }

  typedef Generic-index {
    type uint32 {
      range "0..4294967295";
    }
    description
      "Generic index";
  }

  grouping ncs_template_STATE {
    description
      "Common node of prefix, label";
    container state {
      description
        "Operational data";
      uses ncs_template_FIB-OC-AFT-PREFIX-STATE;
    }
  }

  grouping ncs_template_PREFIX-TABLE {
    description
      "Common node of ipv6-unicast, ipv4-unicast";
    container prefixes {
      description
        "Table of IP prefixes";
      list prefix {
        // NCS patched for predictable order
        ordered-by user;
        key "prefix";
        description
          "Prefix data";
        leaf prefix {
          type string;
          description
            "Prefix";
        }
        uses ncs_template_NEXT-HOP-TABLE;
        uses ncs_template_STATE;
      }
    }
  }

  grouping ncs_template_NEXT-HOP-TABLE {
    description
      "Common node of prefix, label";
    container next-hops {
      description
        "A next-hop associated with the forwarding
         instance";
      list next-hop {
        // NCS patched for predictable order
        ordered-by user;
        key "index";
        description
          "A next-hop associated with the forwarding
           instance";
        leaf index {
          type string;
          description
            "A unique index identifying the next-hop entry
             for the AFT entry";
        }
        uses ncs_template_FIB-OC-AFT-PATH;
      }
    }
  }

  grouping ncs_rpc_notif_STATE {
    description
      "Common node of prefix, label";
    container state {
      description
        "Operational data";
      uses ncs_rpc_notif_FIB-OC-AFT-PREFIX-STATE;
    }
  }

  grouping ncs_rpc_notif_PREFIX-TABLE {
    description
      "Common node of ipv6-unicast, ipv4-unicast";
    container prefixes {
      description
        "Table of IP prefixes";
      list prefix {
        key "prefix";
        description
          "Prefix data";
        leaf prefix {
          type string;
          description
            "Prefix";
        }
        uses ncs_rpc_notif_NEXT-HOP-TABLE;
        uses ncs_rpc_notif_STATE;
      }
    }
  }

  grouping ncs_rpc_notif_NEXT-HOP-TABLE {
    description
      "Common node of prefix, label";
    container next-hops {
      description
        "A next-hop associated with the forwarding
         instance";
      list next-hop {
        key "index";
        description
          "A next-hop associated with the forwarding
           instance";
        leaf index {
          type uint32;
          description
            "A unique index identifying the next-hop entry
             for the AFT entry";
        }
        uses ncs_rpc_notif_FIB-OC-AFT-PATH;
      }
    }
  }

  grouping live_ncs_STATE {
    description
      "Common node of prefix, label";
    container state {
      description
        "Operational data";
      uses live_ncs_FIB-OC-AFT-PREFIX-STATE;
    }
  }

  grouping live_ncs_PREFIX-TABLE {
    description
      "Common node of ipv6-unicast, ipv4-unicast";
    container prefixes {
      description
        "Table of IP prefixes";
      list prefix {
        key "prefix";
        description
          "Prefix data";
        leaf prefix {
          type string;
          description
            "Prefix";
        }
        uses live_ncs_NEXT-HOP-TABLE;
        uses live_ncs_STATE;
      }
    }
  }

  grouping live_ncs_NEXT-HOP-TABLE {
    description
      "Common node of prefix, label";
    container next-hops {
      description
        "A next-hop associated with the forwarding
         instance";
      list next-hop {
        key "index";
        description
          "A next-hop associated with the forwarding
           instance";
        leaf index {
          type uint32;
          description
            "A unique index identifying the next-hop entry
             for the AFT entry";
        }
        uses live_ncs_FIB-OC-AFT-PATH;
      }
    }
  }

  grouping STATE {
    description
      "Common node of prefix, label";
    container state {
      description
        "Operational data";
      uses FIB-OC-AFT-PREFIX-STATE;
    }
  }

  grouping PREFIX-TABLE {
    description
      "Common node of ipv6-unicast, ipv4-unicast";
    container prefixes {
      description
        "Table of IP prefixes";
      list prefix {
        key "prefix";
        description
          "Prefix data";
        leaf prefix {
          type string;
          description
            "Prefix";
        }
        uses NEXT-HOP-TABLE;
        uses STATE;
      }
    }
  }

  grouping NEXT-HOP-TABLE {
    description
      "Common node of prefix, label";
    container next-hops {
      description
        "A next-hop associated with the forwarding
         instance";
      list next-hop {
        key "index";
        description
          "A next-hop associated with the forwarding
           instance";
        leaf index {
          type uint32;
          description
            "A unique index identifying the next-hop entry
             for the AFT entry";
        }
        uses FIB-OC-AFT-PATH;
      }
    }
  }

  augment "/ncs:devices/ncs:device/ncs:config" {
    // NCS drop config false container 'fib-statistics'
    // NCS drop config false container fib
    // NCS drop config false container 'oc-aft-l3'
    // NCS drop config false container 'mpls-forwarding'
  }
  augment "/ncs:devices/ncs:device/ncs:live-status" {
    container fib-statistics {
      tailf:ncs-device-type "netconf";
      tailf:display-when "not(../../ncs:module) or ../../ncs:module[ncs:name='Cisco-IOS-XR-fib-common-oper'] or (../../ncs:live-status-protocol[not(ncs:capability)]) or (../../ncs:live-status-protocol/ncs:capability/ncs:module[.='Cisco-IOS-XR-fib-common-oper'])";
      description
        "cef interface drops operational data";
      container nodes {
        description
          "List of nodes";
        list node {
          key "node-name";
          description
            "Specific node operational data";
          container drops {
            description
              "Specific node drops";
            uses live_ncs_FIB-STATISTICS-BAG-DROPS;
          }
          leaf node-name {
            type xr:live_ncs_Node-id;
            description
              "Node name";
          }
        }
      }
    }
    container fib {
      tailf:ncs-device-type "netconf";
      tailf:display-when "not(../../ncs:module) or ../../ncs:module[ncs:name='Cisco-IOS-XR-fib-common-oper'] or (../../ncs:live-status-protocol[not(ncs:capability)]) or (../../ncs:live-status-protocol/ncs:capability/ncs:module[.='Cisco-IOS-XR-fib-common-oper'])";
      description
        "FIB operational data";
      container nodes {
        description
          "Table of nodes";
        list node {
          key "node-name";
          description
            "Operational data for a specific Node";
          container global {
            description
              "FIB Global info";
            container fib-cofo {
              description
                "Collapsed Forwarding";
              container fib-cofo-idb {
                description
                  "Collapsed Forwarding IDB Table";
                container fib-cofo-idb-table-entries {
                  description
                    "Collapsed Forwarding Idb Table Entries";
                  list fib-cofo-idb-table-entry {
                    description
                      "Collapsed Forwarding Idb Table Entries";
                    leaf sdr-id {
                      type uint32;
                      description
                        "SDR ID value";
                    }
                    leaf if-index {
                      type uint32;
                      description
                        "Interface Index";
                    }
                    uses live_ncs_FIB-SH-COFO-IDB-TBL-ENTRY-INFO;
                  }
                }
              }
              container fib-cofo-table-id {
                description
                  "Collapsed Forwarding Table Id Table";
                container fib-cofo-table-id-entries {
                  description
                    "Collapsed Forwarding Table Id Entries";
                  list fib-cofo-table-id-entry {
                    description
                      "Collapsed Forwarding Idb Table Entries";
                    leaf sdr-id {
                      type uint32;
                      description
                        "SDR ID value";
                    }
                    leaf protocol {
                      type live_ncs_Fib-protocol;
                      description
                        "Protocol";
                    }
                    leaf rd {
                      type xr:live_ncs_Cisco-ios-xr-string;
                      description
                        "Route Distinguisher";
                    }
                    leaf table-id {
                      type uint32;
                      description
                        "Table Id";
                    }
                    uses live_ncs_FIB-SH-COFO-TBL-ID-ENTRY-INFO;
                  }
                }
                container fib-cofo-table-id-summary {
                  description
                    "Collapsed Forwarding Table Id Entries";
                  uses live_ncs_FIB-SH-COFO-TBL-ID-DB-SUM;
                }
              }
            }
            container summary {
              description
                "Global Summary";
              container total {
                description
                  "Display total counters and common info";
                uses live_ncs_FIB-GLOBAL-SUMMARY-TOTAL;
              }
              container protos {
                description
                  "Proto Table";
                list proto {
                  key "protocol-name";
                  description
                    "Proto Table entry";
                  leaf protocol-name {
                    type live_ncs_Fibafi-proto;
                    description
                      "Protocol Name";
                  }
                  uses live_ncs_FIB-GLOBAL-SUMMARY-PROTO;
                }
              }
            }
            container object-history {
              description
                "FIB Global Object History";
              container obj-history-protos {
                description
                  "Proto Table";
                list obj-history-proto {
                  key "protocol-name";
                  description
                    "Protocol Table entry";
                  leaf protocol-name {
                    type live_ncs_Fibafi-proto;
                    description
                      "Protocol Name";
                  }
                  uses live_ncs_FIB-GLOBAL-SUMMARY-OBJ-HISTORY-PROTO;
                }
              }
            }
          }
          container protocols {
            description
              "Protocol table";
            list protocol {
              key "protocol-name";
              description
                "Protocol table entry";
              container resource-oor {
                description
                  "Resource out of resource information";
                uses live_ncs_FIB-SH-RSRC-AVAIL-OOR-STATE;
              }
              container issu-state {
                description
                  "CEF ISSU State";
                uses live_ncs_FIB-ISSU-STATE;
              }
              container cef-tables {
                description
                  "Details for cef tables db";
                list cef-table {
                  description
                    "Details for cef_db corresponding to
                     table_id";
                  leaf table-id {
                    type xr:live_ncs_Hex-integer;
                    description
                      "Table Id";
                  }
                  leaf vrf-name {
                    type string;
                    description
                      "VRF Name";
                  }
                  uses live_ncs_FIB-SH-SUM;
                }
              }
              container interfaces {
                description
                  "Interface list data details";
                list interface {
                  description
                    "Details for interface list data";
                  leaf protocol-id {
                    type live_ncs_Fib-protocol;
                    description
                      "Protocol ID";
                  }
                  leaf interface-list-id {
                    type uint32 {
                      range "0..4294967295";
                    }
                    description
                      "Interface List ID";
                  }
                  leaf interface-list-name {
                    type xr:live_ncs_Cisco-ios-xr-string;
                    description
                      "Interface List Name";
                  }
                  uses live_ncs_FIB-GENERIC-INTF-LIST-DATA;
                }
              }
              container resource {
                description
                  "Resource information";
                container resource-detail-info {
                  description
                    "Detailed info";
                  uses live_ncs_FIB-SH-RSRC-AVAIL-STATE;
                }
                container resource-hardware-ingress-info {
                  description
                    "Detailed info with ingress hardware info";
                  uses live_ncs_FIB-SH-RSRC-AVAIL-STATE;
                }
                container resource-hardware-egress-info {
                  description
                    "Detailed info with egress hardware info";
                  uses live_ncs_FIB-SH-RSRC-AVAIL-STATE;
                }
                container resource-summary-info {
                  description
                    "Summary info";
                  uses live_ncs_FIB-SH-RSRC-AVAIL-STATE;
                }
              }
              container fib-summaries {
                description
                  "Summary for FIB tables";
                list fib-summary {
                  description
                    "Summary for the requested fib table";
                  leaf vrf-name {
                    type xr:live_ncs_Cisco-ios-xr-string;
                    description
                      "VRF Name";
                  }
                  leaf table-id {
                    type xr:live_ncs_Hex-integer;
                    description
                      "FIB table id";
                  }
                  uses live_ncs_FIB-SH-SUM;
                }
              }
              container object-queues {
                description
                  "Object queue details";
                list object-queue {
                  key "object-queue-id";
                  description
                    "Details for corresponding object queue id";
                  leaf object-queue-id {
                    type uint32 {
                      range "0..255";
                    }
                    description
                      "Object Queue ID";
                  }
                  uses live_ncs_FIB-OBJECT-QUEUE-INFO;
                }
              }
              container external-summary-all {
                description
                  "Summary for all external clients";
                uses live_ncs_FIB-SH-TBL-EXT-SUM-ALL;
              }
              container frr-log {
                description
                  "Table of Fast Reroute activation logs";
                container frr-interfaces {
                  description
                    "FRR Interface Table";
                  list frr-interface {
                    key "frr-interface-name";
                    description
                      "Specify FRR Interface Name";
                    container logs {
                      description
                        "FRR log table";
                      list log {
                        key "log-index";
                        description
                          "Specify index into frr log table";
                        leaf log-index {
                          type uint32;
                          description
                            "FRR Log Index";
                        }
                        uses live_ncs_FIB-SH-FRR-LOG;
                      }
                    }
                    leaf frr-interface-name {
                      type xr:live_ncs_Interface-name;
                      description
                        "Interface Name";
                    }
                  }
                }
              }
              container retry-db-entries {
                description
                  "Details for retry db";
                list retry-db-entry {
                  description
                    "Details for retry_db corresponding to index";
                  leaf index {
                    type live_ncs_Generic-index;
                    description
                      "Index";
                  }
                  leaf frsc {
                    type live_ncs_Generic-index;
                    description
                      "Frsc";
                  }
                  leaf queue-id {
                    type live_ncs_Generic-index;
                    description
                      "Queue Id";
                  }
                  uses live_ncs_FIB-RETRY-DB-INFO;
                }
              }
              container vrfs {
                description
                  "VRF table";
                list vrf {
                  key "vrf-name";
                  description
                    "VRF table entry";
                  container ip-prefix-details {
                    description
                      "IP FIB prefix detail table";
                    list ip-prefix-detail {
                      description
                        "IP FIB prefix detail table entry";
                      leaf prefix {
                        type inet:ip-address-no-zone;
                        description
                          "Destination IP address";
                      }
                      leaf prefix-length {
                        type xr:live_ncs_Ipv6-prefix-length;
                        description
                          "IP FIB prefix length";
                      }
                      uses live_ncs_FIB-SH-TBL-FIB;
                    }
                  }
                  container summary {
                    description
                      "Operational data for FIB Tablee";
                    uses live_ncs_FIB-SH-SUM;
                  }
                  container attributes {
                    description
                      "Information on attribute data";
                    list attribute {
                      description
                        "Attribute Data";
                      leaf attribute-index {
                        type uint32 {
                          range "0..4294967295";
                        }
                        description
                          "Attribute Index";
                      }
                      leaf attribute-local-index {
                        type uint32 {
                          range "0..4294967295";
                        }
                        description
                          "Attribute Local Index";
                      }
                      uses live_ncs_FIB-ATTRIBUTE-DET;
                    }
                  }
                  container ipv6-d-var-details {
                    description
                      "IPv6 FIB prefix DVAR table";
                    list ipv6-d-var-detail {
                      description
                        "IPv6 FIB prefix dvar entry";
                      leaf table-id {
                        type xr:live_ncs_Hex-integer;
                        description
                          "Table Id";
                      }
                      leaf prefix {
                        type inet:ip-address-no-zone;
                        description
                          "IPv6 address";
                      }
                      leaf prefix-length {
                        type xr:live_ncs_Ipv6-prefix-length;
                        description
                          "IPv6 prefix length";
                      }
                      uses live_ncs_FIB-SH-TBL-FIB-DVARS;
                    }
                  }
                  container interface-infos {
                    description
                      "Table of InterfaceInfo";
                    list interface-info {
                      key "link-type";
                      description
                        "Specify link type";
                      container interfaces {
                        description
                          "Table of interfaces";
                        list interface {
                          key "interface-name";
                          description
                            "Specify Interface name";
                          leaf interface-name {
                            type xr:live_ncs_Interface-name;
                            description
                              "Interface Name";
                          }
                          uses live_ncs_FIB-SH-INT;
                        }
                      }
                      leaf link-type {
                        type live_ncs_Fib-link;
                        description
                          "Link type";
                      }
                    }
                  }
                  container recursive-nexthops {
                    description
                      "Information on Recursive Nexthop";
                    list recursive-nexthop {
                      description
                        "Route address, Prefix length";
                      leaf address {
                        type inet:ipv4-address-no-zone;
                        description
                          "Route Address ";
                      }
                      leaf prefix-length {
                        type xr:live_ncs_Ipv4-prefix-length;
                        description
                          "Prefix Length";
                      }
                      uses live_ncs_FIB-SH-REC-NH;
                    }
                  }
                  container ip-prefix-briefs {
                    description
                      "IP FIB prefix brief table";
                    list ip-prefix-brief {
                      description
                        "IP FIB prefix brief table entry";
                      leaf prefix {
                        type inet:ip-address-no-zone;
                        description
                          "Destination IP address";
                      }
                      leaf prefix-length {
                        type xr:live_ncs_Ipv6-prefix-length;
                        description
                          "IP FIB prefix length";
                      }
                      uses live_ncs_FIB-SH-TBL-FIB;
                    }
                  }
                  container ipv4-d-var-details {
                    description
                      "IPv4 FIB prefix DVAR table";
                    list ipv4-d-var-detail {
                      description
                        "IPv4 FIB prefix dvar entry";
                      leaf table-id {
                        type xr:live_ncs_Hex-integer;
                        description
                          "Table Id";
                      }
                      leaf prefix {
                        type inet:ipv4-address-no-zone;
                        description
                          "IPv4 address";
                      }
                      leaf prefix-length {
                        type xr:live_ncs_Ipv4-prefix-length;
                        description
                          "IPv4 prefix length";
                      }
                      uses live_ncs_FIB-SH-TBL-FIB-DVARS;
                    }
                  }
                  container attribute-summary {
                    description
                      "Information on attribute summary";
                    uses live_ncs_FIB-ATTRIBUTE-SUMMARY;
                  }
                  container ipv6-recursive-nexthops {
                    description
                      "Information on IPv6 Recursive Nexthop";
                    list ipv6-recursive-nexthop {
                      description
                        "IPv6 Route address, IPv6 Prefix length";
                      leaf address {
                        type inet:ip-address-no-zone;
                        description
                          "IPv6 Route Address ";
                      }
                      leaf prefix-length {
                        type xr:live_ncs_Ipv6-prefix-length;
                        description
                          "IPv6 Prefix Length";
                      }
                      uses live_ncs_FIB-SH-REC-NH;
                    }
                  }
                  container nh-info {
                    description
                      "FIB NHInfo table";
                    container nh-info-detail-hardware-egress {
                      description
                        "NHInfoTable is accessed by two keys;
                         {NHInterface,NHAddress}";
                      container nh-info-special-detail-hardware-egress {
                        description
                          "Detail hardware engress info for Special
                           nhinfo";
                        container nh-info-special-null-detail-hardware-egress {
                          description
                            "Detail hardware engress info for
                             special-null NHInfo entry";
                          uses live_ncs_FIB-SH-NHINFO;
                        }
                        container nh-info-special-punt-detail-hardware-egress {
                          description
                            "Detail hardware engress info for
                             special-punt NHInfo entry";
                          uses live_ncs_FIB-SH-NHINFO;
                        }
                        container nh-info-special-discard-detail-hardware-egress {
                          description
                            "Detail hardware engress info for
                             special-discard NHInfo entry";
                          uses live_ncs_FIB-SH-NHINFO;
                        }
                        container nh-info-special-drop-detail-hardware-egress {
                          description
                            "Detail hardware engress info for
                             special-drop NHInfo entry";
                          uses live_ncs_FIB-SH-NHINFO;
                        }
                      }
                      container nh-info-local-detail-hardware-egresses {
                        description
                          "Local (non-remote) nhinfo";
                        list nh-info-local-detail-hardware-egress {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                      container nh-info-remote-detail-hardware-egresses {
                        description
                          "Detail hardware egress info for remote
                           NHInfo table";
                        list nh-info-remote-detail-hardware-egress {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                    }
                    container nh-info-detail {
                      description
                        "NHInfoTable is accessed by two keys;
                         {NHInterface,NHAddress}";
                      container nh-info-local-details {
                        description
                          "Local (non-remote) nhinfo";
                        list nh-info-local-detail {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                      container nh-info-special-detail {
                        description
                          "Special nhinfo";
                        container nh-info-special-punt-detail {
                          description
                            "Detail special-punt NHInfo entry";
                          uses live_ncs_FIB-SH-NHINFO;
                        }
                        container nh-info-special-drop-detail {
                          description
                            "Detail special-drop NHInfo entry";
                          uses live_ncs_FIB-SH-NHINFO;
                        }
                        container nh-info-special-null-detail {
                          description
                            "Detail special-null NHInfo entry";
                          uses live_ncs_FIB-SH-NHINFO;
                        }
                        container nh-info-special-discard-detail {
                          description
                            "Detail special-discard NHInfo entry";
                          uses live_ncs_FIB-SH-NHINFO;
                        }
                      }
                      container nh-info-remote-details {
                        description
                          "Detailed Remote NHInfo table";
                        list nh-info-remote-detail {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                    }
                    container nh-info-detail-hardware-ingress {
                      description
                        "NHInfoTable is accessed by two keys;
                         {NHInterface,NHAddress}";
                      container nh-info-remote-detail-hardware-ingresses {
                        description
                          "Detailed hardware ingress info for
                           remote NHInfo table";
                        list nh-info-remote-detail-hardware-ingress {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                      container nh-info-local-detail-hardware-ingresses {
                        description
                          "Local (non-remote) nhinfo";
                        list nh-info-local-detail-hardware-ingress {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                      container nh-info-special-detail-hardware-ingress {
                        description
                          "Special nhinfo";
                        container nh-info-special-punt-detail-hardware-ingress {
                          description
                            "Detail hardware ingress info for
                             special-punt NHInfo entry";
                          uses live_ncs_FIB-SH-NHINFO;
                        }
                        container nh-info-special-null-detail-hardware-ingress {
                          description
                            "Detail hardware ingress info for
                             special-null NHInfo entry";
                          uses live_ncs_FIB-SH-NHINFO;
                        }
                        container nh-info-special-drop-detail-hardware-ingress {
                          description
                            "Detail hardware ingress info for
                             special-drop NHInfo entry";
                          uses live_ncs_FIB-SH-NHINFO;
                        }
                        container nh-info-special-discard-detail-hardware-ingress {
                          description
                            "Detail hardware ingress info for
                             special-discard NHInfo entry";
                          uses live_ncs_FIB-SH-NHINFO;
                        }
                      }
                    }
                    container nh-info-brief {
                      description
                        "NHInfoTable is accessed by two keys;
                         {NHInterface,NHAddress}";
                      container nh-info-special-brief {
                        description
                          "Special nhinfo";
                        container nh-info-special-discard-brief {
                          description
                            "Brief special-discard NHInfo entry";
                          uses live_ncs_FIB-SH-NHINFO;
                        }
                        container nh-info-special-null-brief {
                          description
                            "Brief special-null NHInfo entry";
                          uses live_ncs_FIB-SH-NHINFO;
                        }
                        container nh-info-special-punt-brief {
                          description
                            "Brief special-punt NHInfo entry";
                          uses live_ncs_FIB-SH-NHINFO;
                        }
                        container nh-info-special-drop-brief {
                          description
                            "Brief special-drop NHInfo entry";
                          uses live_ncs_FIB-SH-NHINFO;
                        }
                      }
                      container nh-info-remote-briefs {
                        description
                          "remote nhinfo";
                        list nh-info-remote-brief {
                          description
                            "Detail NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                      container nh-info-local-briefs {
                        description
                          "Local (non-remote) nhinfo";
                        list nh-info-local-brief {
                          description
                            "Brief NHinfo entry";
                          leaf nh-interface-name {
                            type xr:live_ncs_Interface-name;
                            description
                              "Interface Name";
                          }
                          leaf nh-proto {
                            type live_ncs_Fib-protocol;
                            description
                              "Next-hop proto";
                          }
                          leaf nh-pfx-length {
                            type uint32;
                            description
                              "Next-hop prefix length";
                          }
                          leaf nh-address {
                            type xr:live_ncs_Cisco-ios-xr-string;
                            description
                              "Next-hop address in string format";
                          }
                          uses live_ncs_FIB-SH-NHINFO;
                        }
                      }
                    }
                  }
                  leaf vrf-name {
                    type xr:live_ncs_Cisco-ios-xr-string;
                    description
                      "VRF Name";
                  }
                }
              }
              container exact-routes {
                description
                  "Exact Route Table";
                list exact-route {
                  description
                    "Exact route for the given source and
                     destination addresses";
                  leaf protocol-name {
                    type live_ncs_Fib-protocol;
                    description
                      "Fib Protocol Name";
                  }
                  leaf vrf-name {
                    type xr:live_ncs_Cisco-ios-xr-string;
                    description
                      "VRF Name";
                  }
                  leaf source {
                    type xr:live_ncs_Cisco-ios-xr-string;
                    description
                      "Source address";
                  }
                  leaf destination {
                    type xr:live_ncs_Cisco-ios-xr-string;
                    description
                      "Destination address";
                  }
                  leaf ipv6-flow-label {
                    type live_ncs_Fibipv6-flow-label;
                    description
                      "IPv6 flow label (applies only to and used
                       only for IPv6)";
                  }
                  uses live_ncs_FIB-SH-TBL-FIB;
                }
              }
              container protocol-global {
                description
                  "FIB ipv6 global information";
                container segment-routing {
                  description
                    "FIB ipv6 global segment routing information";
                  container srv6 {
                    description
                      "FIB ipv6 global segment routing srv6
                       information";
                    uses live_ncs_FIB-SRV6-GBL-UPD;
                  }
                }
              }
              container nh-ids {
                description
                  "NHIdTable is accessed by two keys; {NHId}
                   and/or {NHInterface,NHAddress";
                list nh-id {
                  description
                    "NextHopId table entry";
                  leaf nh-id {
                    type uint32;
                    description
                      "NexthopId Value";
                  }
                  leaf nh-interface-name {
                    type xr:live_ncs_Interface-name;
                    description
                      "Interface Name";
                  }
                  leaf nh-address {
                    type xr:live_ncs_Cisco-ios-xr-string;
                    description
                      "Next-hop address in string format (e.g., 1
                       .2.3.4)";
                  }
                  uses live_ncs_FIB-SH-NHID-ENTRY;
                }
              }
              container frr-nhinfo-pendings {
                description
                  "FIB FRR NHINFO pending information";
                list frr-nhinfo-pending {
                  description
                    "FIB FRR Nhinfo pending information";
                  leaf queue-index {
                    type live_ncs_Generic-index;
                    description
                      "FIB FRR Queue Index";
                  }
                  leaf frr-type {
                    type live_ncs_Fibfrr;
                    description
                      "FRR Type";
                  }
                  leaf link-type {
                    type live_ncs_Fib-link;
                    description
                      "Link Type";
                  }
                  leaf prefix-length {
                    type live_ncs_Prefix-len-range;
                    description
                      "Prefix Length";
                  }
                  leaf interface-name {
                    type xr:live_ncs_Interface-name;
                    description
                      "Interface Name";
                  }
                  leaf main-interface-name {
                    type xr:live_ncs_Interface-name;
                    description
                      "Main Interface Name";
                  }
                  leaf next-hop-prefix {
                    type inet:ip-address-no-zone;
                    description
                      "NextHop Address";
                  }
                  leaf replicated-nh-type {
                    type live_ncs_Fibnh-info-repl;
                    description
                      "Replicated NextHop Type";
                  }
                  uses live_ncs_FIB-SH-FRR-NHINFO;
                }
              }
              container external-client-summaries {
                description
                  "External Client Summary Table";
                list external-client-summary {
                  description
                    "Summary of the external clients";
                  leaf ecd-ver {
                    type uint32;
                    description
                      "Ecd Version";
                  }
                  leaf id {
                    type uint32;
                    description
                      "ID of the client: ECDv1 is component id,
                       ECDv2 is client id";
                  }
                  uses live_ncs_FIB-SH-TBL-EXT-CLIENT-SUM;
                }
              }
              container misc {
                description
                  "CEF misc hidden data";
                uses live_ncs_FIB-SH-MISC;
              }
              container object-queue-entries {
                description
                  "Object queue entry details";
                list object-queue-entry {
                  key "object-queue-id";
                  description
                    "Object queue id";
                  container object-queue-entry-infos {
                    description
                      "Details for corresponding object queue
                       entry";
                    list object-queue-entry-info {
                      key "item-index";
                      description
                        "Details for corresponding object queue
                         entry";
                      leaf item-index {
                        type uint32 {
                          range "0..4294967295";
                        }
                        description
                          "Item Index";
                      }
                      uses live_ncs_FIB-OBJECT-QUEUE-ITEM-INFO;
                    }
                  }
                  leaf object-queue-id {
                    type uint32 {
                      range "0..255";
                    }
                    description
                      "Object Queue ID";
                  }
                }
              }
              container local-label {
                description
                  "Fib Local label";
                container conflicts {
                  description
                    "FIB Local-label conflicts database";
                  list conflict {
                    description
                      "CEF Local-label conflicts entry";
                    leaf label {
                      type live_ncs_Fib-label;
                      description
                        "Local label";
                    }
                    leaf source {
                      type live_ncs_Fib-route-source;
                      description
                        "Route source";
                    }
                    leaf ll-ctype {
                      type live_ncs_Fibllc-entry;
                      description
                        "Type of entry";
                    }
                    leaf pfx-tbl-id {
                      type uint32;
                      description
                        "Table ID of IP prefix";
                    }
                    leaf prefix {
                      type xr:live_ncs_Cisco-ios-xr-string;
                      description
                        "IP Prefix";
                    }
                    leaf prefix-len {
                      type uint32;
                      description
                        "Length of IP Prefix";
                    }
                    uses live_ncs_FIB-MPLS-LLC;
                  }
                }
              }
              leaf protocol-name {
                type live_ncs_Fib-protocol;
                description
                  "Protocol Name ";
              }
            }
          }
          leaf node-name {
            type xr:live_ncs_Node-id;
            description
              "Node name";
          }
        }
      }
    }
    container oc-aft-l3 {
      tailf:ncs-device-type "netconf";
      tailf:display-when "not(../../ncs:module) or ../../ncs:module[ncs:name='Cisco-IOS-XR-fib-common-oper'] or (../../ncs:live-status-protocol[not(ncs:capability)]) or (../../ncs:live-status-protocol/ncs:capability/ncs:module[.='Cisco-IOS-XR-fib-common-oper'])";
      description
        "Openconfig L3 abstract forwarding table data";
      container vrfs {
        description
          "Table VRFs - openconfig network-instances";
        list vrf {
          key "vrf-name";
          description
            "VRF/network-instace table";
          container abstract-forwarding-tables {
            description
              "Abstract forwarding table per FIB protocol";
            container mpls {
              description
                "MPLS abstract forwarding table";
              container labels {
                description
                  "Table of MPLS labels";
                list label {
                  key "label";
                  description
                    "Label data";
                  leaf label {
                    type string;
                    description
                      "Label";
                  }
                  uses live_ncs_NEXT-HOP-TABLE;
                  uses live_ncs_STATE;
                }
              }
            }
            container ipv6-unicast {
              description
                "IPv6 abstract forwarding table";
              uses live_ncs_PREFIX-TABLE;
            }
            container ipv4-unicast {
              description
                "IPv4 abstract forwarding table";
              uses live_ncs_PREFIX-TABLE;
            }
          }
          leaf vrf-name {
            type xr:live_ncs_Cisco-ios-xr-string;
            description
              "Network Instance Name";
          }
        }
      }
    }
    container mpls-forwarding {
      tailf:ncs-device-type "netconf";
      tailf:display-when "not(../../ncs:module) or ../../ncs:module[ncs:name='Cisco-IOS-XR-fib-common-oper'] or (../../ncs:live-status-protocol[not(ncs:capability)]) or (../../ncs:live-status-protocol/ncs:capability/ncs:module[.='Cisco-IOS-XR-fib-common-oper'])";
      description
        "MPLS forwarding operational data";
      container nodes {
        description
          "Table of Nodes";
        list node {
          key "node-name";
          description
            "Operational data for a specific Node";
          container forwarding-summary {
            description
              "MPLS forwarding summary";
            uses live_ncs_MPLS-FWDING-SUMMARY;
          }
          container frr-logs {
            description
              "FRR Log Table";
            list frr-log {
              key "event-id";
              description
                "FRR Log information";
              leaf event-id {
                type uint32;
                description
                  "Event ID";
              }
              uses live_ncs_FIB-MPLS-FRR-EVENT;
            }
          }
          container label-fib {
            description
              "Labels For FIB";
            container forwarding-details {
              description
                "MPLS Forwarding Detail table";
              list forwarding-detail {
                description
                  "MPLS forwarding details";
                leaf label-value {
                  type live_ncs_Mpls-label;
                  description
                    "Local label value";
                }
                leaf eos {
                  type live_ncs_Mplseos;
                  description
                    "End of stack flag";
                }
                uses live_ncs_MPLS-SH-LEAF;
              }
            }
            container informations {
              description
                "Forwarding filtering details";
              list information {
                description
                  "MPLS forwarding information";
                leaf label-value {
                  type live_ncs_Mpls-label;
                  description
                    "Local label value";
                }
                leaf eos {
                  type live_ncs_Mplseos;
                  description
                    "End of stack flag";
                }
                uses live_ncs_MPLS-SH-LEAF;
              }
            }
            container label-security {
              description
                "MPLS label security";
              container interfaces {
                description
                  "MPLS label security interface table";
                list interface {
                  key "interface-name";
                  description
                    "Specify interface Name";
                  leaf interface-name {
                    type xr:live_ncs_Interface-name;
                    description
                      "Interface Name";
                  }
                  uses live_ncs_MPLS-LABEL-SECURITY-INTF;
                }
              }
              container summary {
                description
                  "MPLS label security summary";
                uses live_ncs_MPLS-LABEL-SECURITY-SUMMARY;
              }
            }
          }
          container tunnel {
            description
              "TE Tunnel information";
            container forwarding-tunnels {
              description
                "Forwarding details for TE tunnels";
              list forwarding-tunnel {
                key "interface-name";
                description
                  "Forwarding information for the TE tunnel";
                leaf interface-name {
                  type xr:live_ncs_Interface-name;
                  description
                    "Interface Name";
                }
                uses live_ncs_MPLS-SH-TEHEAD;
              }
            }
          }
          container frr-database {
            description
              "MPLS forwarding FRR Database";
            container frrdb-summary {
              description
                "MPLS forwarding FRR Database Summary";
              uses live_ncs_FIB-MPLS-FRR-DB-SUM;
            }
            container frrdb-protected-interface-table-summaries {
              description
                "MPLS forwarding FRR Database Protected
                 Interface Summary Table";
              list frrdb-protected-interface-table-summary {
                key "interface-name";
                description
                  "MPLS forwarding FRR Database Protected
                   Interface Summary";
                leaf interface-name {
                  type xr:live_ncs_Interface-name;
                  description
                    "Interface Name";
                }
                uses live_ncs_FIB-MPLS-FRR-DB-SUM;
              }
            }
            container frrdb-tunnel-midpoint-summary {
              description
                "MPLS forwarding FRR Database Tunnel Midpoint
                 Summary";
              uses live_ncs_FIB-MPLS-FRR-DB-SUM;
            }
            container frrdb-tunnel-midpoints {
              description
                "MPLS forwarding FRR Database Tunnel Midpoint
                 Table";
              list frrdb-tunnel-midpoint {
                key "local-label";
                description
                  "MPLS forwarding FRR Database Tunnel Midpoint
                   Entry";
                leaf local-label {
                  type live_ncs_Mpls-label;
                  description
                    "Local label value";
                }
                uses live_ncs_MPLS-FRR-DB-ENTRY;
              }
            }
            container frrdb-tunnel-heads {
              description
                "MPLS forwarding FRR Database Tunnel Head
                 Table";
              list frrdb-tunnel-head {
                key "interface-name";
                description
                  "MPLS forwarding FRR Database Tunnel Head
                   Entry";
                leaf interface-name {
                  type xr:live_ncs_Interface-name;
                  description
                    "Interface Name";
                }
                uses live_ncs_MPLS-FRR-DB-ENTRY;
              }
            }
            container frrdb-tunnel-head-summary {
              description
                "MPLS forwarding FRR Database Tunnel Head
                 Summary";
              uses live_ncs_FIB-MPLS-FRR-DB-SUM;
            }
            container frrdb-backup-interface-summaries {
              description
                "MPLS forwarding FRR Database Backup Interface
                 Summary Table";
              list frrdb-backup-interface-summary {
                key "interface-name";
                description
                  "MPLS forwarding FRR Database Backup
                   Interface Summary";
                leaf interface-name {
                  type xr:live_ncs_Interface-name;
                  description
                    "Interface Name";
                }
                uses live_ncs_FIB-MPLS-FRR-DB-SUM;
              }
            }
          }
          leaf node-name {
            type xr:live_ncs_Node-id;
            description
              "Node ID";
          }
        }
      }
    }
  }
  augment "/ncs:devices/ncs:template/ncs:ned-id/ncs:config" {
    // NCS drop config false container 'fib-statistics'
    // NCS drop config false container fib
    // NCS drop config false container 'oc-aft-l3'
    // NCS drop config false container 'mpls-forwarding'
  }
}

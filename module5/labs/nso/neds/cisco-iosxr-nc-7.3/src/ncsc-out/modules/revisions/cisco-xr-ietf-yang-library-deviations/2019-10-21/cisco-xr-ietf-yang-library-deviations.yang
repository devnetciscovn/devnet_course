module cisco-xr-ietf-yang-library-deviations {
  // Generated by yanger -t ncs
  tailf:mount-id "cisco-iosxr-nc-7.3:cisco-iosxr-nc-7.3";
  tailf:ncs-device-type "netconf";

  namespace "http://cisco.com/ns/yang/cisco-xr-ietf-yang-library-deviations";
  prefix cisco-xr-ietf-yanglib-devs;

  import ietf-yang-library {
    prefix yanglib;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations of IETF YANG Library data
     model set for Cisco IOS-XR.

     Copyright (c) 2019 by Cisco Systems, Inc.
     All rights reserved.";

  revision 2019-10-21 {
    description
      "Initial revision applicable to IOS-XR 7.2.1 and older releases";
  }

  deviation "/ncs:devices/ncs:device/ncs:live-status/yanglib:modules-state" {
    deviate not-supported;
  }
  deviation "/ncs:devices/ncs:device/ncs:netconf-notifications/ncs:received-notifications/ncs:notification/ncs:data/yanglib:yang-library-update" {
    deviate not-supported;
  }
  deviation "/ncs:devices/ncs:device/ncs:netconf-notifications/ncs:received-notifications/ncs:notification/ncs:data/yanglib:yang-library-change" {
    deviate not-supported;
  }
}

module Cisco-IOS-XR-infra-sla-datatypes {
  // Generated by yanger -t ncs
  tailf:mount-id "cisco-iosxr-nc-7.3:cisco-iosxr-nc-7.3";
  tailf:ncs-device-type "netconf";

  namespace "http://cisco.com/ns/yang/Cisco-IOS-XR-infra-sla-datatypes";
  prefix infra-sla-datatypes;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2020 by Cisco Systems, Inc.
     All rights reserved.";

  revision 2020-01-09 {
    description
      "Add Stateful to SLA Threshold type enumeration";
    semver:module-version "2.0.0";
  }
  revision 2019-04-05 {
    description
      "Establish semantic version baseline.";
    semver:module-version "2.0.0";
  }
  revision 2015-11-09 {
    description
      "IOS XR 6.0 revision.";
  }

  typedef ncs_template_Sla-burst-interval-units-enum {
    type string;
    description
      "Sla burst interval units enum";
  }

  typedef ncs_template_Sla-threshold-type-enum {
    type string;
    description
      "Sla threshold type enum";
  }

  typedef ncs_template_Sla-send {
    type string;
    description
      "Sla send";
  }

  typedef ncs_template_Sla-probe-interval-day-enum {
    type string;
    description
      "Sla probe interval day enum";
  }

  typedef ncs_template_Sla-packet-interval-units-enum {
    type string;
    description
      "Sla packet interval units enum";
  }

  typedef ncs_template_Sla-on-demand-repeat-interval-units-enum {
    type string;
    description
      "Sla on demand repeat interval units enum";
  }

  typedef ncs_template_Sla-probe-duration-units-enum {
    type string;
    description
      "Sla probe duration units enum";
  }

  typedef ncs_template_Sla-statistic-type-enum {
    type string;
    description
      "Sla statistic type enum";
  }

  typedef ncs_template_Sla-buckets-size-units-enum {
    type string;
    description
      "Sla buckets size units enum";
  }

  typedef ncs_template_Sla-threshold-condition-enum {
    type string;
    description
      "Sla threshold condition enum";
  }

  typedef ncs_template_Sla-probe-interval-units-enum {
    type string;
    description
      "Sla probe interval units enum";
  }

  typedef ncs_template_Sla-on-demand-start-month-enum {
    type string;
    description
      "Sla on demand start month enum";
  }

  typedef ncs_template_Sla-padding-pattern {
    type string;
    description
      "Sla padding pattern";
  }

  typedef ncs_template_Sla-on-demand-start-time-types-enum {
    type string;
    description
      "Sla on demand start time types enum";
  }

  typedef ncs_template_Sla-on-demand-probe-duration-units-enum {
    type string;
    description
      "Sla on demand probe duration units enum";
  }

  typedef ncs_template_Sla-on-demand-start-time-relative-units-enum {
    type string;
    description
      "Sla on demand start time relative units enum";
  }

  typedef ncs_template_Sla-action-type-enum-default {
    type string;
    description
      "Sla action type enum default";
  }

  typedef ncs_rpc_notif_Sla-burst-interval-units-enum {
    type enumeration {
      enum "once" {
        value 1;
        description
          "Send one burst per probe";
      }
      enum "milliseconds" {
        value 2;
        description
          "Send bursts within a probe with an interval
           unit of milliseconds";
      }
      enum "seconds" {
        value 3;
        description
          "Send bursts within a probe with an interval
           unit of seconds";
      }
      enum "minutes" {
        value 4;
        description
          "Send bursts within a probe with an interval
           unit of minutes";
      }
      enum "hours" {
        value 5;
        description
          "Send bursts within a probe with an interval
           unit of hours";
      }
    }
    description
      "Sla burst interval units enum";
  }

  typedef ncs_rpc_notif_Sla-threshold-type-enum {
    type enumeration {
      enum "stateful" {
        value 0;
        description
          "Stateful threshold";
      }
      enum "stateless" {
        value 1;
        description
          "Stateless threshold";
      }
    }
    description
      "Sla threshold type enum";
  }

  typedef ncs_rpc_notif_Sla-send {
    type enumeration {
      enum "packet" {
        value 0;
        description
          "Send individual packets";
      }
      enum "burst" {
        value 1;
        description
          "Send bursts of packets";
      }
    }
    description
      "Sla send";
  }

  typedef ncs_rpc_notif_Sla-probe-interval-day-enum {
    type enumeration {
      enum "monday" {
        value 1;
        description
          "Schedule every Monday";
      }
      enum "tuesday" {
        value 2;
        description
          "Schedule every Tuesday";
      }
      enum "wednesday" {
        value 3;
        description
          "Schedule every Wednesday";
      }
      enum "thursday" {
        value 4;
        description
          "Schedule every Thursday";
      }
      enum "friday" {
        value 5;
        description
          "Schedule every Friday";
      }
      enum "saturday" {
        value 6;
        description
          "Schedule every Saturday";
      }
      enum "sunday" {
        value 7;
        description
          "Schedule every Sunday";
      }
    }
    description
      "Sla probe interval day enum";
  }

  typedef ncs_rpc_notif_Sla-packet-interval-units-enum {
    type enumeration {
      enum "once" {
        value 1;
        description
          "Send one packet per burst";
      }
      enum "milliseconds" {
        value 2;
        description
          "Send packets with an interval unit of
           milliseconds";
      }
      enum "seconds" {
        value 3;
        description
          "Send packets with an interval unit of seconds";
      }
      enum "minutes" {
        value 4;
        description
          "Send packets with an interval unit of minutes";
      }
      enum "hours" {
        value 5;
        description
          "Send packets with an interval unit of hours";
      }
    }
    description
      "Sla packet interval units enum";
  }

  typedef ncs_rpc_notif_Sla-on-demand-repeat-interval-units-enum {
    type enumeration {
      enum "seconds" {
        value 3;
        description
          "Schedule probes to repeat with an interval unit
           of seconds";
      }
      enum "minutes" {
        value 4;
        description
          "Schedule probes to repeat with an interval unit
           of minutes";
      }
      enum "hours" {
        value 5;
        description
          "Schedule probes to repeat with an interval unit
           of hours";
      }
    }
    description
      "Sla on demand repeat interval units enum";
  }

  typedef ncs_rpc_notif_Sla-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
      enum "day" {
        value 6;
        description
          "Schedule probes to run for a duration of 1 day";
      }
      enum "week" {
        value 7;
        description
          "Schedule probes to run for a duration of 1 week";
      }
    }
    description
      "Sla probe duration units enum";
  }

  typedef ncs_rpc_notif_Sla-statistic-type-enum {
    type enumeration {
      enum "round-trip-delay" {
        value 1;
        description
          "Collect round trip delay metric data";
      }
      enum "one-way-delay-sd" {
        value 2;
        description
          "Collect one way delay source->dest metric data";
      }
      enum "one-way-delay-ds" {
        value 3;
        description
          "Collect one way delay dest->source metric data";
      }
      enum "round-trip-jitter" {
        value 4;
        description
          "Collect round trip delay metric data";
      }
      enum "one-way-jitter-sd" {
        value 5;
        description
          "Collect one way jitter source->dest metric data";
      }
      enum "one-way-jitter-ds" {
        value 6;
        description
          "Collect one way jitter dest->source metric data";
      }
      enum "one-way-loss-sd" {
        value 7;
        description
          "Collect one way loss source->dest metric data";
      }
      enum "one-way-loss-ds" {
        value 8;
        description
          "Collect one way loss dest->source metric data";
      }
    }
    description
      "Sla statistic type enum";
  }

  typedef ncs_rpc_notif_Sla-buckets-size-units-enum {
    type enumeration {
      enum "buckets-per-probe" {
        value 0;
        description
          "Store results as a number of buckets per probe
           - note that this option has been DEPRECATED";
      }
      enum "probes-per-bucket" {
        value 1;
        description
          "Store results as a number of probes per bucket";
      }
    }
    description
      "Sla buckets size units enum";
  }

  typedef ncs_rpc_notif_Sla-threshold-condition-enum {
    type enumeration {
      enum "max" {
        value 0;
        description
          "Threshold is breached when the maximum value
           crosses the configured threshold value";
      }
      enum "mean" {
        value 1;
        description
          "Threshold is breached when the mean value
           crosses the configured threshold value";
      }
      enum "sample-count" {
        value 2;
        description
          "Threshold is breached when the sample count in
           bins in and above a certain bin number crosses
           the configured sample count";
      }
    }
    description
      "Sla threshold condition enum";
  }

  typedef ncs_rpc_notif_Sla-probe-interval-units-enum {
    type enumeration {
      enum "minutes" {
        value 4;
        description
          "Schedule probes to run with an interval unit of
           minutes";
      }
      enum "hours" {
        value 5;
        description
          "Schedule probes to run with an interval unit of
           hours";
      }
      enum "day" {
        value 6;
        description
          "Schedule probes to run every day";
      }
      enum "week" {
        value 7;
        description
          "Schedule probes to run every week";
      }
    }
    description
      "Sla probe interval units enum";
  }

  typedef ncs_rpc_notif_Sla-on-demand-start-month-enum {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Sla on demand start month enum";
  }

  typedef ncs_rpc_notif_Sla-padding-pattern {
    type enumeration {
      enum "hex" {
        value 0;
        description
          "Use an optionally specified hex pattern for
           packet padding";
      }
      enum "pseudo-random" {
        value 1;
        description
          "Use a pseudo-random bit sequence for packet
           padding";
      }
    }
    description
      "Sla padding pattern";
  }

  typedef ncs_rpc_notif_Sla-on-demand-start-time-types-enum {
    type enumeration {
      enum "now" {
        value 0;
        description
          "Start immediately";
      }
      enum "absolute" {
        value 1;
        description
          "Start at a specified time";
      }
      enum "relative" {
        value 2;
        description
          "Start after a specified period";
      }
    }
    description
      "Sla on demand start time types enum";
  }

  typedef ncs_rpc_notif_Sla-on-demand-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
    }
    description
      "Sla on demand probe duration units enum";
  }

  typedef ncs_rpc_notif_Sla-on-demand-start-time-relative-units-enum {
    type enumeration {
      enum "seconds" {
        value 3;
        description
          "Schedule probe to start after a unit of seconds";
      }
      enum "minutes" {
        value 4;
        description
          "Schedule probe to start after a unit of minutes";
      }
      enum "hours" {
        value 5;
        description
          "Schedule probe to start after a unit of hours";
      }
    }
    description
      "Sla on demand start time relative units enum";
  }

  typedef ncs_rpc_notif_Sla-action-type-enum-default {
    type enumeration {
      enum "log" {
        value 0;
        description
          "Emit a syslog when the threshold is crossed";
      }
    }
    description
      "Sla action type enum default";
  }

  typedef live_ncs_Sla-burst-interval-units-enum {
    type enumeration {
      enum "once" {
        value 1;
        description
          "Send one burst per probe";
      }
      enum "milliseconds" {
        value 2;
        description
          "Send bursts within a probe with an interval
           unit of milliseconds";
      }
      enum "seconds" {
        value 3;
        description
          "Send bursts within a probe with an interval
           unit of seconds";
      }
      enum "minutes" {
        value 4;
        description
          "Send bursts within a probe with an interval
           unit of minutes";
      }
      enum "hours" {
        value 5;
        description
          "Send bursts within a probe with an interval
           unit of hours";
      }
    }
    description
      "Sla burst interval units enum";
  }

  typedef live_ncs_Sla-threshold-type-enum {
    type enumeration {
      enum "stateful" {
        value 0;
        description
          "Stateful threshold";
      }
      enum "stateless" {
        value 1;
        description
          "Stateless threshold";
      }
    }
    description
      "Sla threshold type enum";
  }

  typedef live_ncs_Sla-send {
    type enumeration {
      enum "packet" {
        value 0;
        description
          "Send individual packets";
      }
      enum "burst" {
        value 1;
        description
          "Send bursts of packets";
      }
    }
    description
      "Sla send";
  }

  typedef live_ncs_Sla-probe-interval-day-enum {
    type enumeration {
      enum "monday" {
        value 1;
        description
          "Schedule every Monday";
      }
      enum "tuesday" {
        value 2;
        description
          "Schedule every Tuesday";
      }
      enum "wednesday" {
        value 3;
        description
          "Schedule every Wednesday";
      }
      enum "thursday" {
        value 4;
        description
          "Schedule every Thursday";
      }
      enum "friday" {
        value 5;
        description
          "Schedule every Friday";
      }
      enum "saturday" {
        value 6;
        description
          "Schedule every Saturday";
      }
      enum "sunday" {
        value 7;
        description
          "Schedule every Sunday";
      }
    }
    description
      "Sla probe interval day enum";
  }

  typedef live_ncs_Sla-packet-interval-units-enum {
    type enumeration {
      enum "once" {
        value 1;
        description
          "Send one packet per burst";
      }
      enum "milliseconds" {
        value 2;
        description
          "Send packets with an interval unit of
           milliseconds";
      }
      enum "seconds" {
        value 3;
        description
          "Send packets with an interval unit of seconds";
      }
      enum "minutes" {
        value 4;
        description
          "Send packets with an interval unit of minutes";
      }
      enum "hours" {
        value 5;
        description
          "Send packets with an interval unit of hours";
      }
    }
    description
      "Sla packet interval units enum";
  }

  typedef live_ncs_Sla-on-demand-repeat-interval-units-enum {
    type enumeration {
      enum "seconds" {
        value 3;
        description
          "Schedule probes to repeat with an interval unit
           of seconds";
      }
      enum "minutes" {
        value 4;
        description
          "Schedule probes to repeat with an interval unit
           of minutes";
      }
      enum "hours" {
        value 5;
        description
          "Schedule probes to repeat with an interval unit
           of hours";
      }
    }
    description
      "Sla on demand repeat interval units enum";
  }

  typedef live_ncs_Sla-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
      enum "day" {
        value 6;
        description
          "Schedule probes to run for a duration of 1 day";
      }
      enum "week" {
        value 7;
        description
          "Schedule probes to run for a duration of 1 week";
      }
    }
    description
      "Sla probe duration units enum";
  }

  typedef live_ncs_Sla-statistic-type-enum {
    type enumeration {
      enum "round-trip-delay" {
        value 1;
        description
          "Collect round trip delay metric data";
      }
      enum "one-way-delay-sd" {
        value 2;
        description
          "Collect one way delay source->dest metric data";
      }
      enum "one-way-delay-ds" {
        value 3;
        description
          "Collect one way delay dest->source metric data";
      }
      enum "round-trip-jitter" {
        value 4;
        description
          "Collect round trip delay metric data";
      }
      enum "one-way-jitter-sd" {
        value 5;
        description
          "Collect one way jitter source->dest metric data";
      }
      enum "one-way-jitter-ds" {
        value 6;
        description
          "Collect one way jitter dest->source metric data";
      }
      enum "one-way-loss-sd" {
        value 7;
        description
          "Collect one way loss source->dest metric data";
      }
      enum "one-way-loss-ds" {
        value 8;
        description
          "Collect one way loss dest->source metric data";
      }
    }
    description
      "Sla statistic type enum";
  }

  typedef live_ncs_Sla-buckets-size-units-enum {
    type enumeration {
      enum "buckets-per-probe" {
        value 0;
        description
          "Store results as a number of buckets per probe
           - note that this option has been DEPRECATED";
      }
      enum "probes-per-bucket" {
        value 1;
        description
          "Store results as a number of probes per bucket";
      }
    }
    description
      "Sla buckets size units enum";
  }

  typedef live_ncs_Sla-threshold-condition-enum {
    type enumeration {
      enum "max" {
        value 0;
        description
          "Threshold is breached when the maximum value
           crosses the configured threshold value";
      }
      enum "mean" {
        value 1;
        description
          "Threshold is breached when the mean value
           crosses the configured threshold value";
      }
      enum "sample-count" {
        value 2;
        description
          "Threshold is breached when the sample count in
           bins in and above a certain bin number crosses
           the configured sample count";
      }
    }
    description
      "Sla threshold condition enum";
  }

  typedef live_ncs_Sla-probe-interval-units-enum {
    type enumeration {
      enum "minutes" {
        value 4;
        description
          "Schedule probes to run with an interval unit of
           minutes";
      }
      enum "hours" {
        value 5;
        description
          "Schedule probes to run with an interval unit of
           hours";
      }
      enum "day" {
        value 6;
        description
          "Schedule probes to run every day";
      }
      enum "week" {
        value 7;
        description
          "Schedule probes to run every week";
      }
    }
    description
      "Sla probe interval units enum";
  }

  typedef live_ncs_Sla-on-demand-start-month-enum {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Sla on demand start month enum";
  }

  typedef live_ncs_Sla-padding-pattern {
    type enumeration {
      enum "hex" {
        value 0;
        description
          "Use an optionally specified hex pattern for
           packet padding";
      }
      enum "pseudo-random" {
        value 1;
        description
          "Use a pseudo-random bit sequence for packet
           padding";
      }
    }
    description
      "Sla padding pattern";
  }

  typedef live_ncs_Sla-on-demand-start-time-types-enum {
    type enumeration {
      enum "now" {
        value 0;
        description
          "Start immediately";
      }
      enum "absolute" {
        value 1;
        description
          "Start at a specified time";
      }
      enum "relative" {
        value 2;
        description
          "Start after a specified period";
      }
    }
    description
      "Sla on demand start time types enum";
  }

  typedef live_ncs_Sla-on-demand-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
    }
    description
      "Sla on demand probe duration units enum";
  }

  typedef live_ncs_Sla-on-demand-start-time-relative-units-enum {
    type enumeration {
      enum "seconds" {
        value 3;
        description
          "Schedule probe to start after a unit of seconds";
      }
      enum "minutes" {
        value 4;
        description
          "Schedule probe to start after a unit of minutes";
      }
      enum "hours" {
        value 5;
        description
          "Schedule probe to start after a unit of hours";
      }
    }
    description
      "Sla on demand start time relative units enum";
  }

  typedef live_ncs_Sla-action-type-enum-default {
    type enumeration {
      enum "log" {
        value 0;
        description
          "Emit a syslog when the threshold is crossed";
      }
    }
    description
      "Sla action type enum default";
  }

  typedef Sla-burst-interval-units-enum {
    type enumeration {
      enum "once" {
        value 1;
        description
          "Send one burst per probe";
      }
      enum "milliseconds" {
        value 2;
        description
          "Send bursts within a probe with an interval
           unit of milliseconds";
      }
      enum "seconds" {
        value 3;
        description
          "Send bursts within a probe with an interval
           unit of seconds";
      }
      enum "minutes" {
        value 4;
        description
          "Send bursts within a probe with an interval
           unit of minutes";
      }
      enum "hours" {
        value 5;
        description
          "Send bursts within a probe with an interval
           unit of hours";
      }
    }
    description
      "Sla burst interval units enum";
  }

  typedef Sla-threshold-type-enum {
    type enumeration {
      enum "stateful" {
        value 0;
        description
          "Stateful threshold";
      }
      enum "stateless" {
        value 1;
        description
          "Stateless threshold";
      }
    }
    description
      "Sla threshold type enum";
  }

  typedef Sla-send {
    type enumeration {
      enum "packet" {
        value 0;
        description
          "Send individual packets";
      }
      enum "burst" {
        value 1;
        description
          "Send bursts of packets";
      }
    }
    description
      "Sla send";
  }

  typedef Sla-probe-interval-day-enum {
    type enumeration {
      enum "monday" {
        value 1;
        description
          "Schedule every Monday";
      }
      enum "tuesday" {
        value 2;
        description
          "Schedule every Tuesday";
      }
      enum "wednesday" {
        value 3;
        description
          "Schedule every Wednesday";
      }
      enum "thursday" {
        value 4;
        description
          "Schedule every Thursday";
      }
      enum "friday" {
        value 5;
        description
          "Schedule every Friday";
      }
      enum "saturday" {
        value 6;
        description
          "Schedule every Saturday";
      }
      enum "sunday" {
        value 7;
        description
          "Schedule every Sunday";
      }
    }
    description
      "Sla probe interval day enum";
  }

  typedef Sla-packet-interval-units-enum {
    type enumeration {
      enum "once" {
        value 1;
        description
          "Send one packet per burst";
      }
      enum "milliseconds" {
        value 2;
        description
          "Send packets with an interval unit of
           milliseconds";
      }
      enum "seconds" {
        value 3;
        description
          "Send packets with an interval unit of seconds";
      }
      enum "minutes" {
        value 4;
        description
          "Send packets with an interval unit of minutes";
      }
      enum "hours" {
        value 5;
        description
          "Send packets with an interval unit of hours";
      }
    }
    description
      "Sla packet interval units enum";
  }

  typedef Sla-on-demand-repeat-interval-units-enum {
    type enumeration {
      enum "seconds" {
        value 3;
        description
          "Schedule probes to repeat with an interval unit
           of seconds";
      }
      enum "minutes" {
        value 4;
        description
          "Schedule probes to repeat with an interval unit
           of minutes";
      }
      enum "hours" {
        value 5;
        description
          "Schedule probes to repeat with an interval unit
           of hours";
      }
    }
    description
      "Sla on demand repeat interval units enum";
  }

  typedef Sla-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
      enum "day" {
        value 6;
        description
          "Schedule probes to run for a duration of 1 day";
      }
      enum "week" {
        value 7;
        description
          "Schedule probes to run for a duration of 1 week";
      }
    }
    description
      "Sla probe duration units enum";
  }

  typedef Sla-statistic-type-enum {
    type enumeration {
      enum "round-trip-delay" {
        value 1;
        description
          "Collect round trip delay metric data";
      }
      enum "one-way-delay-sd" {
        value 2;
        description
          "Collect one way delay source->dest metric data";
      }
      enum "one-way-delay-ds" {
        value 3;
        description
          "Collect one way delay dest->source metric data";
      }
      enum "round-trip-jitter" {
        value 4;
        description
          "Collect round trip delay metric data";
      }
      enum "one-way-jitter-sd" {
        value 5;
        description
          "Collect one way jitter source->dest metric data";
      }
      enum "one-way-jitter-ds" {
        value 6;
        description
          "Collect one way jitter dest->source metric data";
      }
      enum "one-way-loss-sd" {
        value 7;
        description
          "Collect one way loss source->dest metric data";
      }
      enum "one-way-loss-ds" {
        value 8;
        description
          "Collect one way loss dest->source metric data";
      }
    }
    description
      "Sla statistic type enum";
  }

  typedef Sla-buckets-size-units-enum {
    type enumeration {
      enum "buckets-per-probe" {
        value 0;
        description
          "Store results as a number of buckets per probe
           - note that this option has been DEPRECATED";
      }
      enum "probes-per-bucket" {
        value 1;
        description
          "Store results as a number of probes per bucket";
      }
    }
    description
      "Sla buckets size units enum";
  }

  typedef Sla-threshold-condition-enum {
    type enumeration {
      enum "max" {
        value 0;
        description
          "Threshold is breached when the maximum value
           crosses the configured threshold value";
      }
      enum "mean" {
        value 1;
        description
          "Threshold is breached when the mean value
           crosses the configured threshold value";
      }
      enum "sample-count" {
        value 2;
        description
          "Threshold is breached when the sample count in
           bins in and above a certain bin number crosses
           the configured sample count";
      }
    }
    description
      "Sla threshold condition enum";
  }

  typedef Sla-probe-interval-units-enum {
    type enumeration {
      enum "minutes" {
        value 4;
        description
          "Schedule probes to run with an interval unit of
           minutes";
      }
      enum "hours" {
        value 5;
        description
          "Schedule probes to run with an interval unit of
           hours";
      }
      enum "day" {
        value 6;
        description
          "Schedule probes to run every day";
      }
      enum "week" {
        value 7;
        description
          "Schedule probes to run every week";
      }
    }
    description
      "Sla probe interval units enum";
  }

  typedef Sla-on-demand-start-month-enum {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Sla on demand start month enum";
  }

  typedef Sla-padding-pattern {
    type enumeration {
      enum "hex" {
        value 0;
        description
          "Use an optionally specified hex pattern for
           packet padding";
      }
      enum "pseudo-random" {
        value 1;
        description
          "Use a pseudo-random bit sequence for packet
           padding";
      }
    }
    description
      "Sla padding pattern";
  }

  typedef Sla-on-demand-start-time-types-enum {
    type enumeration {
      enum "now" {
        value 0;
        description
          "Start immediately";
      }
      enum "absolute" {
        value 1;
        description
          "Start at a specified time";
      }
      enum "relative" {
        value 2;
        description
          "Start after a specified period";
      }
    }
    description
      "Sla on demand start time types enum";
  }

  typedef Sla-on-demand-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
    }
    description
      "Sla on demand probe duration units enum";
  }

  typedef Sla-on-demand-start-time-relative-units-enum {
    type enumeration {
      enum "seconds" {
        value 3;
        description
          "Schedule probe to start after a unit of seconds";
      }
      enum "minutes" {
        value 4;
        description
          "Schedule probe to start after a unit of minutes";
      }
      enum "hours" {
        value 5;
        description
          "Schedule probe to start after a unit of hours";
      }
    }
    description
      "Sla on demand start time relative units enum";
  }

  typedef Sla-action-type-enum-default {
    type enumeration {
      enum "log" {
        value 0;
        description
          "Emit a syslog when the threshold is crossed";
      }
    }
    description
      "Sla action type enum default";
  }
}

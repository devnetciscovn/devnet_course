module Cisco-IOS-XR-mpls-ping-act {
  // Generated by yanger -t ncs
  tailf:mount-id "cisco-iosxr-nc-7.3:cisco-iosxr-nc-7.3";
  tailf:ncs-device-type "netconf";

  namespace "http://cisco.com/ns/yang/Cisco-IOS-XR-mpls-ping-act";
  prefix mpls-ping-act;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls ping action package configuration

     Copyright (c) 2020-2021 by Cisco Systems, Inc.
     All rights reserved.";

  revision 2021-04-27 {
    description
      "Added missing descriptions
       2021-04-05
         Added range values for lsp-id and pseudowire leaf values
       2021-03-25
         Added IP netmask leaf for MPLS and SR ping
       2021-02-03
         Range added for EXP leaf
       2021-01-26
         Changed Pad leaf to Hexadecimal String";
    semver:module-version "2.0.0";
  }
  revision 2020-06-13 {
    description
      "Initial revision.";
    semver:module-version "1.0.0";
  }

  typedef ncs_template_mpls-fec-type {
    type string;
    description
      "MPLS Forwarding Equivalence Class type";
  }

  typedef ncs_template_sr-fec-type {
    type string;
    description
      "SR Forwarding Equivalence Class type";
  }

  typedef ncs_template_request-reply-mode {
    type string;
    description
      "Reply mode";
  }

  typedef ncs_rpc_notif_mpls-fec-type {
    type enumeration {
      enum "bgp" {
        description
          "MPLS BGP FEC";
      }
      enum "generic" {
        description
          "MPLS Generic FEC";
      }
      enum "ldp" {
        description
          "MPLS LDP FEC";
      }
    }
    description
      "MPLS Forwarding Equivalence Class type";
  }

  typedef ncs_rpc_notif_sr-fec-type {
    type enumeration {
      enum "bgp" {
        description
          "SR IGP BGP FEC";
      }
      enum "ospf" {
        description
          "SR IGP OSPF FEC";
      }
      enum "isis" {
        description
          "SR IGP ISIS FEC";
      }
    }
    description
      "SR Forwarding Equivalence Class type";
  }

  typedef ncs_rpc_notif_request-reply-mode {
    type enumeration {
      enum "ipv4" {
        description
          "Reply Mode IPv4";
      }
      enum "no-reply" {
        description
          "Reply Mode No Reply";
      }
      enum "router-alert" {
        description
          "Reply Mode Router Alert";
      }
    }
    description
      "Reply mode";
  }

  typedef live_ncs_mpls-fec-type {
    type enumeration {
      enum "bgp" {
        description
          "MPLS BGP FEC";
      }
      enum "generic" {
        description
          "MPLS Generic FEC";
      }
      enum "ldp" {
        description
          "MPLS LDP FEC";
      }
    }
    description
      "MPLS Forwarding Equivalence Class type";
  }

  typedef live_ncs_sr-fec-type {
    type enumeration {
      enum "bgp" {
        description
          "SR IGP BGP FEC";
      }
      enum "ospf" {
        description
          "SR IGP OSPF FEC";
      }
      enum "isis" {
        description
          "SR IGP ISIS FEC";
      }
    }
    description
      "SR Forwarding Equivalence Class type";
  }

  typedef live_ncs_request-reply-mode {
    type enumeration {
      enum "ipv4" {
        description
          "Reply Mode IPv4";
      }
      enum "no-reply" {
        description
          "Reply Mode No Reply";
      }
      enum "router-alert" {
        description
          "Reply Mode Router Alert";
      }
    }
    description
      "Reply mode";
  }

  typedef mpls-fec-type {
    type enumeration {
      enum "bgp" {
        description
          "MPLS BGP FEC";
      }
      enum "generic" {
        description
          "MPLS Generic FEC";
      }
      enum "ldp" {
        description
          "MPLS LDP FEC";
      }
    }
    description
      "MPLS Forwarding Equivalence Class type";
  }

  typedef sr-fec-type {
    type enumeration {
      enum "bgp" {
        description
          "SR IGP BGP FEC";
      }
      enum "ospf" {
        description
          "SR IGP OSPF FEC";
      }
      enum "isis" {
        description
          "SR IGP ISIS FEC";
      }
    }
    description
      "SR Forwarding Equivalence Class type";
  }

  typedef request-reply-mode {
    type enumeration {
      enum "ipv4" {
        description
          "Reply Mode IPv4";
      }
      enum "no-reply" {
        description
          "Reply Mode No Reply";
      }
      enum "router-alert" {
        description
          "Reply Mode Router Alert";
      }
    }
    description
      "Reply mode";
  }

  augment "/ncs:devices/ncs:device/ncs:rpc" {
    container rpc-mpls-ping {
      tailf:ncs-device-type "netconf";
      tailf:display-when "not(../../ncs:module) or ../../ncs:module[ncs:name='Cisco-IOS-XR-mpls-ping-act']";
      tailf:action mpls-ping {
        tailf:actionpoint ncsproxy {
          tailf:internal;
        }
        description
          "Send echo messages";
        input {
          choice ping-type {
            mandatory true;
            description
              "Specify ping type";
            case type-mpls {
              container mpls {
                description
                  "MPLS ping";
                choice mpls-subtype {
                  mandatory true;
                  description
                    "Ping MPLS subtype";
                  case subtype-ipv4 {
                    container ipv4 {
                      description
                        "Ping mpls IPv4 address";
                      leaf ip {
                        type inet:ipv4-address;
                        mandatory true;
                        description
                          "destination X.X.X.X of mpls ping";
                      }
                      choice subnet {
                        mandatory true;
                        description
                          "The subnet to be specified as a prefix-length or as
                           a netmask.";
                        case prefix-length {
                          leaf prefix-length {
                            type uint8 {
                              range "0..32";
                            }
                            default "32";
                            description
                              "The length of the subnet prefix.";
                          }
                        }
                        case netmask {
                          leaf netmask {
                            type inet:ipv4-address;
                            description
                              "The subnet specified as a netmask";
                          }
                        }
                      }
                      leaf fec-type {
                        type ncs_rpc_notif_mpls-fec-type;
                        description
                          "TLV FEC type to use in request";
                      }
                    }
                  }
                  case subtype-traffic-eng {
                    container traffic-eng {
                      description
                        "MPLS-TE ping";
                      choice tunnel-identifier {
                        mandatory true;
                        description
                          "Tunnel Identifier (LSP name or tunnel-interface)";
                        case subtype-tunnel-name {
                          leaf tunnel-name {
                            type string;
                            description
                              "Next hop tunnel lsp name";
                          }
                        }
                        case subtype-tunnel-interface {
                          leaf tunnel-interface {
                            type string;
                            description
                              "Next hop Interface with form tunnel-te<number>";
                          }
                        }
                      }
                      choice te-lsp-option {
                        default "te-lsp-option-active";
                        description
                          "Specify which LSP to use";
                        case te-lsp-option-active {
                          leaf active-lsp {
                            type boolean;
                            default "true";
                            description
                              "Enforce active LSP selection for tunnel";
                          }
                        }
                        case te-lsp-option-id {
                          leaf lsp-id {
                            type uint32 {
                              range "1..10000";
                            }
                            default "1";
                            description
                              "Tunnel Label Switched Path Identifier";
                          }
                        }
                        case te-lsp-option-path-protected {
                          leaf path-protected {
                            type boolean;
                            description
                              "Test path protected LSP for tunnel";
                          }
                        }
                        case te-lsp-option-reoptimized {
                          leaf reoptimized {
                            type boolean;
                            description
                              "Test reoptimized LSP for tunnel";
                          }
                        }
                      }
                    }
                  }
                }
              }
            }
            case type-sr {
              container sr-mpls {
                description
                  "Ping sr-mpls";
                choice sr-target {
                  description
                    "Ping sr-mpls target type";
                  case target_ipv4_prefix {
                    container ipv4 {
                      description
                        "Ping sr-mpls IPv4 Prefix SID";
                      leaf ip {
                        type inet:ipv4-address;
                        mandatory true;
                        description
                          "SR LSP Egress IP";
                      }
                      choice subnet {
                        mandatory true;
                        description
                          "The subnet to be specified as a prefix-length or as
                           a netmask.";
                        case prefix-length {
                          leaf prefix-length {
                            type uint8 {
                              range "0..32";
                            }
                            default "32";
                            description
                              "The length of the subnet prefix.";
                          }
                        }
                        case netmask {
                          leaf netmask {
                            type inet:ipv4-address;
                            description
                              "The subnet specified as a netmask";
                          }
                        }
                      }
                      leaf fec-type {
                        type ncs_rpc_notif_sr-fec-type;
                        description
                          "SR OAM IGP FEC TLV type to use in request";
                      }
                    }
                  }
                  case target_labels {
                    container labels {
                      description
                        "Ping sr-mpls label stack (up to 12 labels)";
                      list label {
                        key "index";
                        description
                          "Specify label index and value";
                        leaf index {
                          type uint32 {
                            range "0..9";
                          }
                          mandatory true;
                          description
                            "Label index";
                        }
                        leaf label {
                          type uint32 {
                            range "16..1048575";
                          }
                          mandatory true;
                          description
                            "label value";
                        }
                      }
                      leaf nil-fec {
                        type boolean;
                        description
                          "Use Nil-FEC TLV and Append Explicit Null";
                      }
                      leaf lsp-endpoint {
                        type inet:ipv4-address;
                        description
                          "Specify the IP of the LSP endpoint";
                      }
                    }
                  }
                  case target_policy {
                    container policy {
                      description
                        "Ping sr-mpls policy";
                      choice sr-policy-id {
                        mandatory true;
                        description
                          "SR Policy Identifier (binding sid or policy name)";
                        case sr-policy-id-bsid {
                          leaf bsid {
                            type uint32 {
                              range "16..1048575";
                            }
                            mandatory true;
                            description
                              "SR Policy Binding SID";
                          }
                        }
                        case sr-policy-id-name {
                          leaf name {
                            type string;
                            mandatory true;
                            description
                              "SR Policy Name";
                          }
                        }
                      }
                      leaf fec-type {
                        type ncs_rpc_notif_sr-fec-type;
                        description
                          "SR OAM IGP FEC TLV type to use in request";
                      }
                      leaf nil-fec {
                        type boolean;
                        description
                          "Use Nil-FEC TLV and Append Explicit Null";
                      }
                      leaf lsp-endpoint {
                        type inet:ipv4-address;
                        description
                          "Specify the IP of the LSP endpoint";
                      }
                    }
                  }
                }
              }
            }
            case type-pseudowire {
              container pseudowire {
                description
                  "Ping mpls pseudowire";
                choice pw-type {
                  description
                    "Ping mpls pseudowire type";
                  case type-fec-128 {
                    container fec-128 {
                      description
                        "FEC 128";
                      leaf remote-pe-addr {
                        type inet:ipv4-address;
                        mandatory true;
                        description
                          "PW LSP Egress IPv4 Identifier";
                      }
                      leaf pwid {
                        type uint32 {
                          range "1..4294967295";
                        }
                        mandatory true;
                        description
                          "Pseudowire Identifier";
                      }
                      leaf deprecated-fec128 {
                        type boolean;
                        description
                          "Force the use of the Deprecated FEC128 described in RFC4379";
                      }
                      container force-control-channel {
                        description
                          "Force the use of a VCCV control channel";
                        choice force-control-channel-fec128 {
                          description
                            "Force control channel type";
                          case fcc-128-cw {
                            leaf control-word {
                              type boolean;
                              description
                                "Force Control Word";
                            }
                          }
                          case fcc-128-ralabel {
                            leaf ra-label {
                              type boolean;
                              description
                                "RA Label";
                            }
                          }
                          case fcc-128-ttl-expiry {
                            leaf ttl-expiry {
                              type boolean;
                              description
                                "VC Label TTL expiry";
                            }
                          }
                        }
                      }
                    }
                  }
                  case type-multisegment {
                    container multisegment {
                      description
                        "Ping mpls pseudowire multisegment";
                      leaf remote-pe-addr {
                        type inet:ipv4-address;
                        mandatory true;
                        description
                          "PW LSP Egress IPv4 Identifier";
                      }
                      leaf pwid {
                        type uint32 {
                          range "1..4294967295";
                        }
                        mandatory true;
                        description
                          "Pseudowire Identifier";
                      }
                      leaf deprecated-fec128 {
                        type boolean;
                        description
                          "Force the use of the Deprecated FEC128 described in RFC4379";
                      }
                      container destination-fec {
                        description
                          "Destination FEC <Sender IP Address> <Remote IP Address> <PW ID>";
                        leaf sender-ip {
                          type inet:ipv4-address;
                          mandatory true;
                          description
                            "Sender address for Destination FEC";
                        }
                        leaf remote-ip {
                          type inet:ipv4-address;
                          mandatory true;
                          description
                            "Remote address for Destination FEC";
                        }
                        leaf destination-fec-pw-id {
                          type uint32;
                          mandatory true;
                          description
                            "Destination FEC Pseudowire ID";
                        }
                      }
                      container force-control-channel {
                        description
                          "Force the use of a VCCV control channel";
                        choice force-control-channel-mspw {
                          description
                            "Force Control Channel type";
                          case fcc-mspw-cw {
                            leaf control-word {
                              type boolean;
                              description
                                "Force Control Word";
                            }
                          }
                          case fcc-mspw-ttl-expiry {
                            leaf ttl-expiry {
                              type boolean;
                              description
                                "VC Label TTL expiry";
                            }
                          }
                        }
                      }
                      leaf segment-count {
                        type uint32 {
                          range "1..255";
                        }
                        description
                          "Segement Count for Destination FEC";
                      }
                    }
                  }
                  case type-fec-129 {
                    container fec-129 {
                      description
                        "FEC 129";
                      choice fec-129-type {
                        description
                          "FEC 129 Attachement Identifier Type";
                        case fec-129-aii-type1 {
                          container aii-type1 {
                            description
                              "Type 1 Attachment Identifier";
                            container vpls-id {
                              description
                                "VPLS ID of the bridge domain";
                              choice vpls-id-type {
                                description
                                  "VPLS ID type";
                                case vpls-id-2-byte-as {
                                  container byte-as {
                                    description
                                      "Two Byte AS number";
                                    leaf byte {
                                      type uint16 {
                                        range "1..65535";
                                      }
                                      mandatory true;
                                      description
                                        "VPLS Byte ID";
                                    }
                                    leaf space {
                                      type uint32;
                                      mandatory true;
                                      description
                                        "Namespace";
                                    }
                                  }
                                }
                                case vpls-id-ip {
                                  container ip-prefix-as {
                                    description
                                      "IP address";
                                    leaf ip-prefix {
                                      type inet:ipv4-address;
                                      mandatory true;
                                      description
                                        "VPLS IP Prefix ID";
                                    }
                                    leaf space {
                                      type uint32 {
                                        range "0..32767";
                                      }
                                      mandatory true;
                                      description
                                        "Namespace";
                                    }
                                  }
                                }
                              }
                            }
                            leaf target {
                              type inet:ipv4-address;
                              mandatory true;
                              description
                                "L2VPN router-id of the target";
                            }
                          }
                        }
                        case fec-129-aii-type2 {
                          container aii-type2 {
                            description
                              "Type 2 Attachment Identifier";
                            leaf global-id {
                              type uint32 {
                                range "1..4294967295";
                              }
                              mandatory true;
                              description
                                "Global ID of the pseudowire";
                            }
                            leaf target {
                              type inet:ipv4-address;
                              mandatory true;
                              description
                                "Target end address of the pseudowire";
                            }
                            leaf circuit-id {
                              type uint32 {
                                range "1..4294967295";
                              }
                              mandatory true;
                              description
                                "Attachment Circuit ID";
                            }
                          }
                        }
                      }
                      container force-control-channel {
                        description
                          "Force the use of a VCCV control channel";
                        choice force-control-channel-fec129 {
                          description
                            "Force Control Channel type";
                          case fcc-129-cw {
                            leaf control-word {
                              type boolean;
                              description
                                "Force Control Word";
                            }
                          }
                          case fcc-129-ralabel {
                            leaf ra-label {
                              type boolean;
                              description
                                "RA Label";
                            }
                          }
                          case fcc-129-ttl-expiry {
                            leaf ttl-expiry {
                              type boolean;
                              description
                                "VC Label TTL expiry";
                            }
                          }
                        }
                      }
                    }
                  }
                }
              }
            }
          }
          container request-options-parameters {
            description
              "MPLS echo request options";
            leaf exp {
              type uint8 {
                range "0..7";
              }
              description
                "EXP Bits To Set";
            }
            leaf fec {
              type boolean;
              description
                "Force FEC TLV Checks";
            }
            leaf interval {
              type uint32 {
                range "0..3600000";
              }
              description
                "Time between echo requests in ms";
            }
            leaf ddmap {
              type boolean;
              description
                "Use DDMAP (Default is DSMAP)";
            }
            leaf force-explicit-null {
              type boolean;
              description
                "Force an explicit null label to be added";
            }
            container packet-output {
              description
                "Packet output options";
              leaf interface-name {
                type xr:ncs_rpc_notif_Interface-name;
                description
                  "Outgoing interface with form <Interface>R/S/I/P for echo packet";
              }
              leaf next-hop {
                type inet:ipv4-address;
                description
                  "Outgoing next hop IP (X.X.X.X) for echo packet";
              }
            }
            leaf pad {
              type xr:ncs_rpc_notif_Hex-integer-16;
              description
                "HEX Padding 0-ffff";
            }
            leaf repeat {
              type uint32 {
                range "1..2147483647";
              }
              default "5";
              description
                "Number of echo requests to send";
            }
            container reply {
              description
                "Echo Reply Options";
              leaf dscp {
                type uint8 {
                  range "0..63";
                }
                description
                  "Set DSCP reply value 0-63 (decimal)";
              }
              leaf reply-mode {
                type ncs_rpc_notif_request-reply-mode;
                description
                  "Echo Reply Mode";
              }
              leaf pad-tlv {
                type boolean;
                description
                  "Enable PAD TLV for the request";
              }
            }
            leaf size {
              type uint16 {
                range "100..17986";
              }
              description
                "Define Packet Size for the request";
            }
            leaf source {
              type inet:ipv4-address;
              description
                "Source IP address to use in the IP header";
            }
            leaf destination {
              type inet:ipv4-address;
              description
                "Destination IP address (127.x.y.z)";
            }
            container sweep {
              description
                "Echo request sweep options";
              leaf minimum {
                type uint32 {
                  range "100..17986";
                }
                mandatory true;
                description
                  "Sweep min value";
              }
              leaf maximum {
                type uint32 {
                  range "100..17986";
                }
                mandatory true;
                description
                  "Sweep max value";
              }
              leaf increment {
                type uint32 {
                  range "1..8993";
                }
                mandatory true;
                description
                  "Sweep incr value";
              }
            }
            leaf brief {
              type boolean;
              description
                "Brief mode. Does not include statistical data in result";
            }
            leaf timeout {
              type uint32 {
                range "0..3600";
              }
              description
                "Time in seconds before the lack of a reply invalidates a request";
            }
            leaf ttl {
              type uint32 {
                range "1..255";
              }
              description
                "Time to live (hops to until forced punt)";
            }
          }
        }
        output {
          container mpls-ping-response {
            description
              "MPLS ping Response";
            container request-options-parameters {
              description
                "Echo Request Options";
              leaf exp {
                type uint8 {
                  range "0..7";
                }
                description
                  "EXP Bits To Set";
              }
              leaf fec {
                type boolean;
                description
                  "Force FEC TLV Checks";
              }
              leaf interval {
                type uint32 {
                  range "0..3600000";
                }
                description
                  "Time between echo requests in ms";
              }
              leaf ddmap {
                type boolean;
                description
                  "Use DDMAP (Default is DSMAP)";
              }
              leaf force-explicit-null {
                type boolean;
                description
                  "Force an explicit null label to be added";
              }
              container packet-output {
                description
                  "Packet output options";
                leaf interface-name {
                  type xr:ncs_rpc_notif_Interface-name;
                  description
                    "Outgoing interface with form <Interface>R/S/I/P for echo packet";
                }
                leaf next-hop {
                  type inet:ipv4-address;
                  description
                    "Outgoing next hop IP (X.X.X.X) for echo packet";
                }
              }
              leaf pad {
                type xr:ncs_rpc_notif_Hex-integer-16;
                description
                  "HEX Padding 0-ffff";
              }
              leaf repeat {
                type uint32 {
                  range "1..2147483647";
                }
                default "5";
                description
                  "Number of echo requests to send";
              }
              container reply {
                description
                  "Reply options";
                leaf dscp {
                  type uint8 {
                    range "0..63";
                  }
                  description
                    "Set DSCP reply value 0-63 (decimal)";
                }
                leaf reply-mode {
                  type ncs_rpc_notif_request-reply-mode;
                  description
                    "Echo Reply Mode";
                }
                leaf pad-tlv {
                  type boolean;
                  description
                    "Enable PAD TLV for the request";
                }
              }
              leaf size {
                type uint16 {
                  range "100..17986";
                }
                description
                  "Define Packet Size for the request";
              }
              leaf source {
                type inet:ipv4-address;
                description
                  "Source IP address to use in the IP header";
              }
              leaf destination {
                type inet:ipv4-address;
                description
                  "Destination IP address (127.x.y.z)";
              }
              container sweep {
                description
                  "Echo request sweep options";
                leaf minimum {
                  type uint32 {
                    range "100..17986";
                  }
                  mandatory true;
                  description
                    "Sweep min value";
                }
                leaf maximum {
                  type uint32 {
                    range "100..17986";
                  }
                  mandatory true;
                  description
                    "Sweep max value";
                }
                leaf increment {
                  type uint32 {
                    range "1..8993";
                  }
                  mandatory true;
                  description
                    "Sweep incr value";
                }
              }
              leaf brief {
                type boolean;
                description
                  "Brief mode. Does not include statistical data in result";
              }
              leaf timeout {
                type uint32 {
                  range "0..3600";
                }
                description
                  "Time in seconds before the lack of a reply invalidates a request";
              }
              leaf ttl {
                type uint32 {
                  range "1..255";
                }
                description
                  "Time to live (hops to until forced punt)";
              }
            }
            container replies {
              description
                "MPLS ping replies";
              list reply {
                key "reply-index";
                description
                  "MPLS ping reply";
                leaf reply-index {
                  type uint64 {
                    range "1..2147483647";
                  }
                  description
                    "Index of the reply list";
                }
                leaf return-code {
                  type uint8;
                  description
                    "Return Code of the echo request";
                }
                leaf return-char {
                  type string;
                  description
                    "Return Char of the echo request";
                }
                leaf duration {
                  type uint32;
                  description
                    "Trip duration (msec)";
                }
                leaf reply-addr {
                  type string;
                  description
                    "Reply Address";
                }
                leaf size {
                  type uint32;
                  description
                    "Packet size";
                }
              }
            }
            container statistics {
              description
                "Statistics Response";
              leaf tmin {
                type uint32;
                description
                  "Minimum Trip Duration";
              }
              leaf tmax {
                type uint32;
                description
                  "Maximum Trip Duration";
              }
              leaf tavg {
                type uint32;
                description
                  "Average Trip Duration";
              }
              leaf hits {
                type uint32;
                description
                  "Number of successful ping requests sent";
              }
              leaf tries {
                type uint32;
                description
                  "Number of ping requests sent";
              }
            }
          }
        }
      }
    }
  }
  augment "/ncs:devices/ncs:device-group/ncs:ned-id/ncs:rpc" {
    container rpc-mpls-ping {
      tailf:ncs-device-type "netconf";
      tailf:display-when "/ncs:devices/ncs:device[ncs:name=current()/../../../ncs:member]/ncs:module[ncs:name='Cisco-IOS-XR-mpls-ping-act']";
      tailf:action mpls-ping {
        tailf:actionpoint ncsproxy {
          tailf:internal;
        }
        description
          "Send echo messages";
        input {
          choice ping-type {
            mandatory true;
            description
              "Specify ping type";
            case type-mpls {
              container mpls {
                description
                  "MPLS ping";
                choice mpls-subtype {
                  mandatory true;
                  description
                    "Ping MPLS subtype";
                  case subtype-ipv4 {
                    container ipv4 {
                      description
                        "Ping mpls IPv4 address";
                      leaf ip {
                        type inet:ipv4-address;
                        mandatory true;
                        description
                          "destination X.X.X.X of mpls ping";
                      }
                      choice subnet {
                        mandatory true;
                        description
                          "The subnet to be specified as a prefix-length or as
                           a netmask.";
                        case prefix-length {
                          leaf prefix-length {
                            type uint8 {
                              range "0..32";
                            }
                            default "32";
                            description
                              "The length of the subnet prefix.";
                          }
                        }
                        case netmask {
                          leaf netmask {
                            type inet:ipv4-address;
                            description
                              "The subnet specified as a netmask";
                          }
                        }
                      }
                      leaf fec-type {
                        type ncs_rpc_notif_mpls-fec-type;
                        description
                          "TLV FEC type to use in request";
                      }
                    }
                  }
                  case subtype-traffic-eng {
                    container traffic-eng {
                      description
                        "MPLS-TE ping";
                      choice tunnel-identifier {
                        mandatory true;
                        description
                          "Tunnel Identifier (LSP name or tunnel-interface)";
                        case subtype-tunnel-name {
                          leaf tunnel-name {
                            type string;
                            description
                              "Next hop tunnel lsp name";
                          }
                        }
                        case subtype-tunnel-interface {
                          leaf tunnel-interface {
                            type string;
                            description
                              "Next hop Interface with form tunnel-te<number>";
                          }
                        }
                      }
                      choice te-lsp-option {
                        default "te-lsp-option-active";
                        description
                          "Specify which LSP to use";
                        case te-lsp-option-active {
                          leaf active-lsp {
                            type boolean;
                            default "true";
                            description
                              "Enforce active LSP selection for tunnel";
                          }
                        }
                        case te-lsp-option-id {
                          leaf lsp-id {
                            type uint32 {
                              range "1..10000";
                            }
                            default "1";
                            description
                              "Tunnel Label Switched Path Identifier";
                          }
                        }
                        case te-lsp-option-path-protected {
                          leaf path-protected {
                            type boolean;
                            description
                              "Test path protected LSP for tunnel";
                          }
                        }
                        case te-lsp-option-reoptimized {
                          leaf reoptimized {
                            type boolean;
                            description
                              "Test reoptimized LSP for tunnel";
                          }
                        }
                      }
                    }
                  }
                }
              }
            }
            case type-sr {
              container sr-mpls {
                description
                  "Ping sr-mpls";
                choice sr-target {
                  description
                    "Ping sr-mpls target type";
                  case target_ipv4_prefix {
                    container ipv4 {
                      description
                        "Ping sr-mpls IPv4 Prefix SID";
                      leaf ip {
                        type inet:ipv4-address;
                        mandatory true;
                        description
                          "SR LSP Egress IP";
                      }
                      choice subnet {
                        mandatory true;
                        description
                          "The subnet to be specified as a prefix-length or as
                           a netmask.";
                        case prefix-length {
                          leaf prefix-length {
                            type uint8 {
                              range "0..32";
                            }
                            default "32";
                            description
                              "The length of the subnet prefix.";
                          }
                        }
                        case netmask {
                          leaf netmask {
                            type inet:ipv4-address;
                            description
                              "The subnet specified as a netmask";
                          }
                        }
                      }
                      leaf fec-type {
                        type ncs_rpc_notif_sr-fec-type;
                        description
                          "SR OAM IGP FEC TLV type to use in request";
                      }
                    }
                  }
                  case target_labels {
                    container labels {
                      description
                        "Ping sr-mpls label stack (up to 12 labels)";
                      list label {
                        key "index";
                        description
                          "Specify label index and value";
                        leaf index {
                          type uint32 {
                            range "0..9";
                          }
                          mandatory true;
                          description
                            "Label index";
                        }
                        leaf label {
                          type uint32 {
                            range "16..1048575";
                          }
                          mandatory true;
                          description
                            "label value";
                        }
                      }
                      leaf nil-fec {
                        type boolean;
                        description
                          "Use Nil-FEC TLV and Append Explicit Null";
                      }
                      leaf lsp-endpoint {
                        type inet:ipv4-address;
                        description
                          "Specify the IP of the LSP endpoint";
                      }
                    }
                  }
                  case target_policy {
                    container policy {
                      description
                        "Ping sr-mpls policy";
                      choice sr-policy-id {
                        mandatory true;
                        description
                          "SR Policy Identifier (binding sid or policy name)";
                        case sr-policy-id-bsid {
                          leaf bsid {
                            type uint32 {
                              range "16..1048575";
                            }
                            mandatory true;
                            description
                              "SR Policy Binding SID";
                          }
                        }
                        case sr-policy-id-name {
                          leaf name {
                            type string;
                            mandatory true;
                            description
                              "SR Policy Name";
                          }
                        }
                      }
                      leaf fec-type {
                        type ncs_rpc_notif_sr-fec-type;
                        description
                          "SR OAM IGP FEC TLV type to use in request";
                      }
                      leaf nil-fec {
                        type boolean;
                        description
                          "Use Nil-FEC TLV and Append Explicit Null";
                      }
                      leaf lsp-endpoint {
                        type inet:ipv4-address;
                        description
                          "Specify the IP of the LSP endpoint";
                      }
                    }
                  }
                }
              }
            }
            case type-pseudowire {
              container pseudowire {
                description
                  "Ping mpls pseudowire";
                choice pw-type {
                  description
                    "Ping mpls pseudowire type";
                  case type-fec-128 {
                    container fec-128 {
                      description
                        "FEC 128";
                      leaf remote-pe-addr {
                        type inet:ipv4-address;
                        mandatory true;
                        description
                          "PW LSP Egress IPv4 Identifier";
                      }
                      leaf pwid {
                        type uint32 {
                          range "1..4294967295";
                        }
                        mandatory true;
                        description
                          "Pseudowire Identifier";
                      }
                      leaf deprecated-fec128 {
                        type boolean;
                        description
                          "Force the use of the Deprecated FEC128 described in RFC4379";
                      }
                      container force-control-channel {
                        description
                          "Force the use of a VCCV control channel";
                        choice force-control-channel-fec128 {
                          description
                            "Force control channel type";
                          case fcc-128-cw {
                            leaf control-word {
                              type boolean;
                              description
                                "Force Control Word";
                            }
                          }
                          case fcc-128-ralabel {
                            leaf ra-label {
                              type boolean;
                              description
                                "RA Label";
                            }
                          }
                          case fcc-128-ttl-expiry {
                            leaf ttl-expiry {
                              type boolean;
                              description
                                "VC Label TTL expiry";
                            }
                          }
                        }
                      }
                    }
                  }
                  case type-multisegment {
                    container multisegment {
                      description
                        "Ping mpls pseudowire multisegment";
                      leaf remote-pe-addr {
                        type inet:ipv4-address;
                        mandatory true;
                        description
                          "PW LSP Egress IPv4 Identifier";
                      }
                      leaf pwid {
                        type uint32 {
                          range "1..4294967295";
                        }
                        mandatory true;
                        description
                          "Pseudowire Identifier";
                      }
                      leaf deprecated-fec128 {
                        type boolean;
                        description
                          "Force the use of the Deprecated FEC128 described in RFC4379";
                      }
                      container destination-fec {
                        description
                          "Destination FEC <Sender IP Address> <Remote IP Address> <PW ID>";
                        leaf sender-ip {
                          type inet:ipv4-address;
                          mandatory true;
                          description
                            "Sender address for Destination FEC";
                        }
                        leaf remote-ip {
                          type inet:ipv4-address;
                          mandatory true;
                          description
                            "Remote address for Destination FEC";
                        }
                        leaf destination-fec-pw-id {
                          type uint32;
                          mandatory true;
                          description
                            "Destination FEC Pseudowire ID";
                        }
                      }
                      container force-control-channel {
                        description
                          "Force the use of a VCCV control channel";
                        choice force-control-channel-mspw {
                          description
                            "Force Control Channel type";
                          case fcc-mspw-cw {
                            leaf control-word {
                              type boolean;
                              description
                                "Force Control Word";
                            }
                          }
                          case fcc-mspw-ttl-expiry {
                            leaf ttl-expiry {
                              type boolean;
                              description
                                "VC Label TTL expiry";
                            }
                          }
                        }
                      }
                      leaf segment-count {
                        type uint32 {
                          range "1..255";
                        }
                        description
                          "Segement Count for Destination FEC";
                      }
                    }
                  }
                  case type-fec-129 {
                    container fec-129 {
                      description
                        "FEC 129";
                      choice fec-129-type {
                        description
                          "FEC 129 Attachement Identifier Type";
                        case fec-129-aii-type1 {
                          container aii-type1 {
                            description
                              "Type 1 Attachment Identifier";
                            container vpls-id {
                              description
                                "VPLS ID of the bridge domain";
                              choice vpls-id-type {
                                description
                                  "VPLS ID type";
                                case vpls-id-2-byte-as {
                                  container byte-as {
                                    description
                                      "Two Byte AS number";
                                    leaf byte {
                                      type uint16 {
                                        range "1..65535";
                                      }
                                      mandatory true;
                                      description
                                        "VPLS Byte ID";
                                    }
                                    leaf space {
                                      type uint32;
                                      mandatory true;
                                      description
                                        "Namespace";
                                    }
                                  }
                                }
                                case vpls-id-ip {
                                  container ip-prefix-as {
                                    description
                                      "IP address";
                                    leaf ip-prefix {
                                      type inet:ipv4-address;
                                      mandatory true;
                                      description
                                        "VPLS IP Prefix ID";
                                    }
                                    leaf space {
                                      type uint32 {
                                        range "0..32767";
                                      }
                                      mandatory true;
                                      description
                                        "Namespace";
                                    }
                                  }
                                }
                              }
                            }
                            leaf target {
                              type inet:ipv4-address;
                              mandatory true;
                              description
                                "L2VPN router-id of the target";
                            }
                          }
                        }
                        case fec-129-aii-type2 {
                          container aii-type2 {
                            description
                              "Type 2 Attachment Identifier";
                            leaf global-id {
                              type uint32 {
                                range "1..4294967295";
                              }
                              mandatory true;
                              description
                                "Global ID of the pseudowire";
                            }
                            leaf target {
                              type inet:ipv4-address;
                              mandatory true;
                              description
                                "Target end address of the pseudowire";
                            }
                            leaf circuit-id {
                              type uint32 {
                                range "1..4294967295";
                              }
                              mandatory true;
                              description
                                "Attachment Circuit ID";
                            }
                          }
                        }
                      }
                      container force-control-channel {
                        description
                          "Force the use of a VCCV control channel";
                        choice force-control-channel-fec129 {
                          description
                            "Force Control Channel type";
                          case fcc-129-cw {
                            leaf control-word {
                              type boolean;
                              description
                                "Force Control Word";
                            }
                          }
                          case fcc-129-ralabel {
                            leaf ra-label {
                              type boolean;
                              description
                                "RA Label";
                            }
                          }
                          case fcc-129-ttl-expiry {
                            leaf ttl-expiry {
                              type boolean;
                              description
                                "VC Label TTL expiry";
                            }
                          }
                        }
                      }
                    }
                  }
                }
              }
            }
          }
          container request-options-parameters {
            description
              "MPLS echo request options";
            leaf exp {
              type uint8 {
                range "0..7";
              }
              description
                "EXP Bits To Set";
            }
            leaf fec {
              type boolean;
              description
                "Force FEC TLV Checks";
            }
            leaf interval {
              type uint32 {
                range "0..3600000";
              }
              description
                "Time between echo requests in ms";
            }
            leaf ddmap {
              type boolean;
              description
                "Use DDMAP (Default is DSMAP)";
            }
            leaf force-explicit-null {
              type boolean;
              description
                "Force an explicit null label to be added";
            }
            container packet-output {
              description
                "Packet output options";
              leaf interface-name {
                type xr:ncs_rpc_notif_Interface-name;
                description
                  "Outgoing interface with form <Interface>R/S/I/P for echo packet";
              }
              leaf next-hop {
                type inet:ipv4-address;
                description
                  "Outgoing next hop IP (X.X.X.X) for echo packet";
              }
            }
            leaf pad {
              type xr:ncs_rpc_notif_Hex-integer-16;
              description
                "HEX Padding 0-ffff";
            }
            leaf repeat {
              type uint32 {
                range "1..2147483647";
              }
              default "5";
              description
                "Number of echo requests to send";
            }
            container reply {
              description
                "Echo Reply Options";
              leaf dscp {
                type uint8 {
                  range "0..63";
                }
                description
                  "Set DSCP reply value 0-63 (decimal)";
              }
              leaf reply-mode {
                type ncs_rpc_notif_request-reply-mode;
                description
                  "Echo Reply Mode";
              }
              leaf pad-tlv {
                type boolean;
                description
                  "Enable PAD TLV for the request";
              }
            }
            leaf size {
              type uint16 {
                range "100..17986";
              }
              description
                "Define Packet Size for the request";
            }
            leaf source {
              type inet:ipv4-address;
              description
                "Source IP address to use in the IP header";
            }
            leaf destination {
              type inet:ipv4-address;
              description
                "Destination IP address (127.x.y.z)";
            }
            container sweep {
              description
                "Echo request sweep options";
              leaf minimum {
                type uint32 {
                  range "100..17986";
                }
                mandatory true;
                description
                  "Sweep min value";
              }
              leaf maximum {
                type uint32 {
                  range "100..17986";
                }
                mandatory true;
                description
                  "Sweep max value";
              }
              leaf increment {
                type uint32 {
                  range "1..8993";
                }
                mandatory true;
                description
                  "Sweep incr value";
              }
            }
            leaf brief {
              type boolean;
              description
                "Brief mode. Does not include statistical data in result";
            }
            leaf timeout {
              type uint32 {
                range "0..3600";
              }
              description
                "Time in seconds before the lack of a reply invalidates a request";
            }
            leaf ttl {
              type uint32 {
                range "1..255";
              }
              description
                "Time to live (hops to until forced punt)";
            }
          }
        }
        output {
          container "device" {
            leaf "name" {
              type string;
            }
            leaf "info" {
              type string;
            }
            container "result" {
              container mpls-ping-response {
                description
                  "MPLS ping Response";
                container request-options-parameters {
                  description
                    "Echo Request Options";
                  leaf exp {
                    type uint8 {
                      range "0..7";
                    }
                    description
                      "EXP Bits To Set";
                  }
                  leaf fec {
                    type boolean;
                    description
                      "Force FEC TLV Checks";
                  }
                  leaf interval {
                    type uint32 {
                      range "0..3600000";
                    }
                    description
                      "Time between echo requests in ms";
                  }
                  leaf ddmap {
                    type boolean;
                    description
                      "Use DDMAP (Default is DSMAP)";
                  }
                  leaf force-explicit-null {
                    type boolean;
                    description
                      "Force an explicit null label to be added";
                  }
                  container packet-output {
                    description
                      "Packet output options";
                    leaf interface-name {
                      type xr:ncs_rpc_notif_Interface-name;
                      description
                        "Outgoing interface with form <Interface>R/S/I/P for echo packet";
                    }
                    leaf next-hop {
                      type inet:ipv4-address;
                      description
                        "Outgoing next hop IP (X.X.X.X) for echo packet";
                    }
                  }
                  leaf pad {
                    type xr:ncs_rpc_notif_Hex-integer-16;
                    description
                      "HEX Padding 0-ffff";
                  }
                  leaf repeat {
                    type uint32 {
                      range "1..2147483647";
                    }
                    default "5";
                    description
                      "Number of echo requests to send";
                  }
                  container reply {
                    description
                      "Reply options";
                    leaf dscp {
                      type uint8 {
                        range "0..63";
                      }
                      description
                        "Set DSCP reply value 0-63 (decimal)";
                    }
                    leaf reply-mode {
                      type ncs_rpc_notif_request-reply-mode;
                      description
                        "Echo Reply Mode";
                    }
                    leaf pad-tlv {
                      type boolean;
                      description
                        "Enable PAD TLV for the request";
                    }
                  }
                  leaf size {
                    type uint16 {
                      range "100..17986";
                    }
                    description
                      "Define Packet Size for the request";
                  }
                  leaf source {
                    type inet:ipv4-address;
                    description
                      "Source IP address to use in the IP header";
                  }
                  leaf destination {
                    type inet:ipv4-address;
                    description
                      "Destination IP address (127.x.y.z)";
                  }
                  container sweep {
                    description
                      "Echo request sweep options";
                    leaf minimum {
                      type uint32 {
                        range "100..17986";
                      }
                      mandatory true;
                      description
                        "Sweep min value";
                    }
                    leaf maximum {
                      type uint32 {
                        range "100..17986";
                      }
                      mandatory true;
                      description
                        "Sweep max value";
                    }
                    leaf increment {
                      type uint32 {
                        range "1..8993";
                      }
                      mandatory true;
                      description
                        "Sweep incr value";
                    }
                  }
                  leaf brief {
                    type boolean;
                    description
                      "Brief mode. Does not include statistical data in result";
                  }
                  leaf timeout {
                    type uint32 {
                      range "0..3600";
                    }
                    description
                      "Time in seconds before the lack of a reply invalidates a request";
                  }
                  leaf ttl {
                    type uint32 {
                      range "1..255";
                    }
                    description
                      "Time to live (hops to until forced punt)";
                  }
                }
                container replies {
                  description
                    "MPLS ping replies";
                  list reply {
                    key "reply-index";
                    description
                      "MPLS ping reply";
                    leaf reply-index {
                      type uint64 {
                        range "1..2147483647";
                      }
                      description
                        "Index of the reply list";
                    }
                    leaf return-code {
                      type uint8;
                      description
                        "Return Code of the echo request";
                    }
                    leaf return-char {
                      type string;
                      description
                        "Return Char of the echo request";
                    }
                    leaf duration {
                      type uint32;
                      description
                        "Trip duration (msec)";
                    }
                    leaf reply-addr {
                      type string;
                      description
                        "Reply Address";
                    }
                    leaf size {
                      type uint32;
                      description
                        "Packet size";
                    }
                  }
                }
                container statistics {
                  description
                    "Statistics Response";
                  leaf tmin {
                    type uint32;
                    description
                      "Minimum Trip Duration";
                  }
                  leaf tmax {
                    type uint32;
                    description
                      "Maximum Trip Duration";
                  }
                  leaf tavg {
                    type uint32;
                    description
                      "Average Trip Duration";
                  }
                  leaf hits {
                    type uint32;
                    description
                      "Number of successful ping requests sent";
                  }
                  leaf tries {
                    type uint32;
                    description
                      "Number of ping requests sent";
                  }
                }
              }
            }
          }
        }
      }
    }
  }
}

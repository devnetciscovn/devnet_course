module Cisco-IOS-XR-drivers-media-eth-act {
  // Generated by yanger -t ncs
  tailf:mount-id "cisco-iosxr-nc-7.3:cisco-iosxr-nc-7.3";
  tailf:ncs-device-type "netconf";

  namespace "http://cisco.com/ns/yang/Cisco-IOS-XR-drivers-media-eth-act";
  prefix eth-drvr-act;

  import cisco-semver {
    prefix semver;
  }
  import Cisco-IOS-XR-types {
    prefix csc;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2019 by Cisco Systems, Inc.
     All rights reserved.";

  revision 2019-04-05 {
    description
      "Establish semantic version baseline.";
    semver:module-version "1.0.0";
  }
  revision 2018-02-12 {
    description
      "IOS XR 6.5.1 revision.";
  }

  augment "/ncs:devices/ncs:device/ncs:rpc" {
    container rpc-clear-controller-counters {
      tailf:ncs-device-type "netconf";
      tailf:display-when "not(../../ncs:module) or ../../ncs:module[ncs:name='Cisco-IOS-XR-drivers-media-eth-act']";
      tailf:action clear-controller-counters {
        tailf:actionpoint ncsproxy {
          tailf:internal;
        }
        description
          "Clear Ethernet MAC ASIC statistics.";
        input {
          leaf controller-name {
            type csc:ncs_rpc_notif_Interface-name;
            mandatory true;
            description
              "Controller name";
          }
        }
        csc:xr-task "interface";
        csc:cli-command "clear controller <controller-name> stats";
      }
    }
  }
  augment "/ncs:devices/ncs:device-group/ncs:ned-id/ncs:rpc" {
    container rpc-clear-controller-counters {
      tailf:ncs-device-type "netconf";
      tailf:display-when "/ncs:devices/ncs:device[ncs:name=current()/../../../ncs:member]/ncs:module[ncs:name='Cisco-IOS-XR-drivers-media-eth-act']";
      tailf:action clear-controller-counters {
        tailf:actionpoint ncsproxy {
          tailf:internal;
        }
        description
          "Clear Ethernet MAC ASIC statistics.";
        input {
          leaf controller-name {
            type csc:ncs_rpc_notif_Interface-name;
            mandatory true;
            description
              "Controller name";
          }
        }
        csc:xr-task "interface";
        csc:cli-command "clear controller <controller-name> stats";
      }
    }
  }
}

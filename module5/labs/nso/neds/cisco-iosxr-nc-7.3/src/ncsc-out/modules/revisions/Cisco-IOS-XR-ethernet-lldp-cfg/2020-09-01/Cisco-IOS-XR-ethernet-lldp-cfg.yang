module Cisco-IOS-XR-ethernet-lldp-cfg {
  // Generated by yanger -t ncs
  tailf:mount-id "cisco-iosxr-nc-7.3:cisco-iosxr-nc-7.3";
  tailf:ncs-device-type "netconf";

  namespace "http://cisco.com/ns/yang/Cisco-IOS-XR-ethernet-lldp-cfg";
  prefix ethernet-lldp-cfg;

  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-lldp package configuration.

     This module contains definitions
     for the following management objects:
       lldp: Enable LLDP, or configure global LLDP subcommands

     This YANG module augments the
       Cisco-IOS-XR-ifmgr-cfg
     module with configuration data.

     Copyright (c) 2013-2020 by Cisco Systems, Inc.
     All rights reserved.";

  revision 2020-09-01 {
    description
      "Fixing backward compatibility error in module.";
    semver:module-version "1.0.1";
  }
  revision 2019-04-05 {
    description
      "Establish semantic version baseline.";
    semver:module-version "1.0.1";
  }
  revision 2017-05-01 {
    description
      "Fixing backward compatibility error in module.";
  }
  revision 2015-11-09 {
    description
      "IOS XR 6.0 revision.";
  }

  augment "/ncs:devices/ncs:device/ncs:config" {
    container lldp {
      tailf:ncs-device-type "netconf";
      tailf:display-when "not(../../ncs:module) or ../../ncs:module[ncs:name='Cisco-IOS-XR-ethernet-lldp-cfg']";
      description
        "Enable LLDP, or configure global LLDP subcommands";
      container tlv-select {
        presence "Indicates a tlv-select node is configured.";
        description
          "Selection of LLDP TLVs to disable";
        container system-name {
          description
            "System Name TLV";
          leaf disable {
            type boolean;
            default "false";
            description
              "disable System Name TLV";
          }
        }
        container port-description {
          description
            "Port Description TLV";
          leaf disable {
            type boolean;
            default "false";
            description
              "disable Port Description TLV";
          }
        }
        container system-description {
          description
            "System Description TLV";
          leaf disable {
            type boolean;
            default "false";
            description
              "disable System Description TLV";
          }
        }
        container system-capabilities {
          description
            "System Capabilities TLV";
          leaf disable {
            type boolean;
            default "false";
            description
              "disable System Capabilities TLV";
          }
        }
        container management-address {
          description
            "Management Address TLV";
          leaf disable {
            type boolean;
            default "false";
            description
              "disable Management Address TLV";
          }
        }
        leaf tlv-select-enter {
          type boolean;
          mandatory true;
          description
            "enter lldp tlv-select submode";
        }
      }
      leaf holdtime {
        type uint32 {
          range "0..65535";
        }
        description
          "Length  of time  (in sec) that receiver must
           keep this packet";
      }
      leaf enable-priority-addr {
        type boolean;
        default "false";
        description
          "Enable or disable Priority to advertise
           Mgmt-interface Addr First";
      }
      leaf extended-show-width {
        type boolean;
        default "false";
        description
          "Enable or disable LLDP Show LLDP Neighbor
           Extended Width";
      }
      leaf enable-subintf {
        type boolean;
        default "false";
        description
          "Enable or disable LLDP on Sub-interfaces as well
           globally";
      }
      leaf enable-mgmtintf {
        type boolean;
        default "false";
        description
          "Enable or disable LLDP on Mgmt interfaces as
           well globally";
      }
      leaf timer {
        type uint32 {
          range "5..65534";
        }
        default "30";
        description
          "Specify the rate at which LLDP packets are sent
           (in sec)";
      }
      leaf reinit {
        type uint32 {
          range "2..5";
        }
        default "2";
        description
          "Delay (in sec) for LLDP initialization on any
           interface";
      }
      leaf enable {
        type boolean;
        default "false";
        description
          "Enable or disable LLDP globally";
      }
    }
  }
  augment "/ncs:devices/ncs:device/ncs:live-status" {
    container lldp {
      tailf:ncs-device-type "netconf";
      tailf:display-when "not(../../ncs:module) or ../../ncs:module[ncs:name='Cisco-IOS-XR-ethernet-lldp-cfg'] or (../../ncs:live-status-protocol[not(ncs:capability)]) or (../../ncs:live-status-protocol/ncs:capability/ncs:module[.='Cisco-IOS-XR-ethernet-lldp-cfg'])";
      description
        "Enable LLDP, or configure global LLDP subcommands";
      container tlv-select {
        presence "Indicates a tlv-select node is configured.";
        description
          "Selection of LLDP TLVs to disable";
        container system-name {
          description
            "System Name TLV";
          leaf disable {
            type boolean;
            // NCS drop default statement
            description
              "disable System Name TLV";
          }
        }
        container port-description {
          description
            "Port Description TLV";
          leaf disable {
            type boolean;
            // NCS drop default statement
            description
              "disable Port Description TLV";
          }
        }
        container system-description {
          description
            "System Description TLV";
          leaf disable {
            type boolean;
            // NCS drop default statement
            description
              "disable System Description TLV";
          }
        }
        container system-capabilities {
          description
            "System Capabilities TLV";
          leaf disable {
            type boolean;
            // NCS drop default statement
            description
              "disable System Capabilities TLV";
          }
        }
        container management-address {
          description
            "Management Address TLV";
          leaf disable {
            type boolean;
            // NCS drop default statement
            description
              "disable Management Address TLV";
          }
        }
        leaf tlv-select-enter {
          type boolean;
          // NCS drop mandatory statement
          description
            "enter lldp tlv-select submode";
        }
      }
      leaf holdtime {
        type uint32 {
          range "0..65535";
        }
        description
          "Length  of time  (in sec) that receiver must
           keep this packet";
      }
      leaf enable-priority-addr {
        type boolean;
        // NCS drop default statement
        description
          "Enable or disable Priority to advertise
           Mgmt-interface Addr First";
      }
      leaf extended-show-width {
        type boolean;
        // NCS drop default statement
        description
          "Enable or disable LLDP Show LLDP Neighbor
           Extended Width";
      }
      leaf enable-subintf {
        type boolean;
        // NCS drop default statement
        description
          "Enable or disable LLDP on Sub-interfaces as well
           globally";
      }
      leaf enable-mgmtintf {
        type boolean;
        // NCS drop default statement
        description
          "Enable or disable LLDP on Mgmt interfaces as
           well globally";
      }
      leaf timer {
        type uint32 {
          range "5..65534";
        }
        // NCS drop default statement
        description
          "Specify the rate at which LLDP packets are sent
           (in sec)";
      }
      leaf reinit {
        type uint32 {
          range "2..5";
        }
        // NCS drop default statement
        description
          "Delay (in sec) for LLDP initialization on any
           interface";
      }
      leaf enable {
        type boolean;
        // NCS drop default statement
        description
          "Enable or disable LLDP globally";
      }
    }
  }
  augment "/ncs:devices/ncs:template/ncs:ned-id/ncs:config" {
    container lldp {
      description
        "Enable LLDP, or configure global LLDP subcommands";
      container tlv-select {
        presence "Indicates a tlv-select node is configured.";
        description
          "Selection of LLDP TLVs to disable";
        container system-name {
          description
            "System Name TLV";
          leaf disable {
            type string;
            // NCS drop default statement
            description
              "disable System Name TLV";
          }
        }
        container port-description {
          description
            "Port Description TLV";
          leaf disable {
            type string;
            // NCS drop default statement
            description
              "disable Port Description TLV";
          }
        }
        container system-description {
          description
            "System Description TLV";
          leaf disable {
            type string;
            // NCS drop default statement
            description
              "disable System Description TLV";
          }
        }
        container system-capabilities {
          description
            "System Capabilities TLV";
          leaf disable {
            type string;
            // NCS drop default statement
            description
              "disable System Capabilities TLV";
          }
        }
        container management-address {
          description
            "Management Address TLV";
          leaf disable {
            type string;
            // NCS drop default statement
            description
              "disable Management Address TLV";
          }
        }
        leaf tlv-select-enter {
          type string;
          // NCS drop mandatory statement
          description
            "enter lldp tlv-select submode";
        }
      }
      leaf holdtime {
        type string;
        description
          "Length  of time  (in sec) that receiver must
           keep this packet";
      }
      leaf enable-priority-addr {
        type string;
        // NCS drop default statement
        description
          "Enable or disable Priority to advertise
           Mgmt-interface Addr First";
      }
      leaf extended-show-width {
        type string;
        // NCS drop default statement
        description
          "Enable or disable LLDP Show LLDP Neighbor
           Extended Width";
      }
      leaf enable-subintf {
        type string;
        // NCS drop default statement
        description
          "Enable or disable LLDP on Sub-interfaces as well
           globally";
      }
      leaf enable-mgmtintf {
        type string;
        // NCS drop default statement
        description
          "Enable or disable LLDP on Mgmt interfaces as
           well globally";
      }
      leaf timer {
        type string;
        // NCS drop default statement
        description
          "Specify the rate at which LLDP packets are sent
           (in sec)";
      }
      leaf reinit {
        type string;
        // NCS drop default statement
        description
          "Delay (in sec) for LLDP initialization on any
           interface";
      }
      leaf enable {
        type string;
        // NCS drop default statement
        description
          "Enable or disable LLDP globally";
      }
    }
  }
  augment "/ncs:devices/ncs:template/ncs:ned-id/ncs:config/a1:interface-configurations/a1:interface-configuration" {
    description
      "This augment extends the configuration data of
       'Cisco-IOS-XR-ifmgr-cfg'";
    container lldp {
      presence "Indicates a lldp node is configured.";
      description
        "Disable LLDP TX or RX";
      container transmit {
        description
          "Disable LLDP TX";
        leaf disable {
          type string;
          // NCS drop default statement
          description
            "disable LLDP TX";
        }
      }
      container receive {
        description
          "Disable LLDP RX";
        leaf disable {
          type string;
          // NCS drop default statement
          description
            "disable LLDP RX";
        }
      }
      leaf lldp-intf-enter {
        type string;
        // NCS drop mandatory statement
        description
          "enter LLDP interface submode";
      }
      leaf enable {
        type string;
        // NCS drop default statement
        description
          "Enable both LLDP TX and RX";
      }
    }
  }
  augment "/ncs:devices/ncs:device/ncs:live-status/a1:interface-configurations/a1:interface-configuration" {
    description
      "This augment extends the configuration data of
       'Cisco-IOS-XR-ifmgr-cfg'";
    container lldp {
      tailf:ncs-device-type "netconf";
      tailf:display-when "not(../../../../ncs:module) or ../../../../ncs:module[ncs:name='Cisco-IOS-XR-ethernet-lldp-cfg'] or (../../../../ncs:live-status-protocol[not(ncs:capability)]) or (../../../../ncs:live-status-protocol/ncs:capability/ncs:module[.='Cisco-IOS-XR-ethernet-lldp-cfg'])";
      presence "Indicates a lldp node is configured.";
      description
        "Disable LLDP TX or RX";
      container transmit {
        description
          "Disable LLDP TX";
        leaf disable {
          type boolean;
          // NCS drop default statement
          description
            "disable LLDP TX";
        }
      }
      container receive {
        description
          "Disable LLDP RX";
        leaf disable {
          type boolean;
          // NCS drop default statement
          description
            "disable LLDP RX";
        }
      }
      leaf lldp-intf-enter {
        type boolean;
        // NCS drop mandatory statement
        description
          "enter LLDP interface submode";
      }
      leaf enable {
        type boolean;
        // NCS drop default statement
        description
          "Enable both LLDP TX and RX";
      }
    }
  }
  augment "/ncs:devices/ncs:device/ncs:config/a1:interface-configurations/a1:interface-configuration" {
    description
      "This augment extends the configuration data of
       'Cisco-IOS-XR-ifmgr-cfg'";
    container lldp {
      tailf:ncs-device-type "netconf";
      tailf:display-when "not(../../../../ncs:module) or ../../../../ncs:module[ncs:name='Cisco-IOS-XR-ethernet-lldp-cfg']";
      presence "Indicates a lldp node is configured.";
      description
        "Disable LLDP TX or RX";
      container transmit {
        description
          "Disable LLDP TX";
        leaf disable {
          type boolean;
          default "false";
          description
            "disable LLDP TX";
        }
      }
      container receive {
        description
          "Disable LLDP RX";
        leaf disable {
          type boolean;
          default "false";
          description
            "disable LLDP RX";
        }
      }
      leaf lldp-intf-enter {
        type boolean;
        mandatory true;
        description
          "enter LLDP interface submode";
      }
      leaf enable {
        type boolean;
        default "false";
        description
          "Enable both LLDP TX and RX";
      }
    }
  }
}

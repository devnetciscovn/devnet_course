submodule Cisco-IOS-XR-ip-rsvp-oper-sub1 {
  // Generated by yanger -t ncs
  tailf:mount-id "cisco-iosxr-nc-7.3:cisco-iosxr-nc-7.3";

  belongs-to Cisco-IOS-XR-ip-rsvp-oper {
    prefix Cisco-IOS-XR-ip-rsvp-oper;
  }

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-rsvp package operational data.

     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef ncs_template_Igpte-lib-bw-model {
    type string;
    description
      "Bandwidth model";
  }

  typedef ncs_template_Rsvp-mgmt-restart-state {
    type string;
    description
      "RSVP GR (Graceful Restart) Restart states";
  }

  typedef ncs_template_Rsvp-mgmt-hello-down-reason {
    type string;
    description
      "Reasons why RSVP Hellos went down";
  }

  typedef ncs_template_Rsvp-mgmt-hello-instance-owner {
    type string;
    description
      "RSVP Hello instance owner";
  }

  typedef ncs_template_Rsvp-mgmt-association {
    type string;
    description
      "RSVP ASSOCIATION Types";
  }

  typedef ncs_template_Rsvp-mgmt-rro-subobj {
    type string;
    description
      "RSVP RRO Types";
  }

  typedef ncs_template_Rsi-vrf-id {
    type string;
    description
      "Rsi vrf id";
  }

  typedef ncs_template_Rsvp-mgmt-frr-state-enum {
    type string;
    description
      "RSVP FRR States";
  }

  typedef ncs_template_Rsvp-proc-nsr-not-ready-reason {
    type string;
    description
      "Rsvp proc nsr not ready reason";
  }

  typedef ncs_template_Rsvp-sync-status {
    type string;
    description
      "Rsvp sync status";
  }

  typedef ncs_template_Rsvp-mgmt-gr-app {
    type string;
    description
      "RSVP Graceful Restart application type";
  }

  typedef ncs_template_Rsvp-proc-role {
    type string;
    description
      "RSVP Process Role";
  }

  typedef ncs_template_Rsvp-mgmt-auth-challenge-status {
    type string;
    description
      "RSVP Authentication Challenge Status";
  }

  typedef ncs_template_Rsvp-mgmt-hello-instance {
    type string;
    description
      "RSVP Hello instance types";
  }

  typedef ncs_template_Rsvp-mgmt-hello-state {
    type string;
    description
      "RSVP Hello instance states";
  }

  typedef ncs_template_Rsvp-mgmt-reservation-type-enum {
    type string;
    description
      "RSVP Reservation Types";
  }

  typedef ncs_template_Rsvp-mgmt-flow-spec {
    type string;
    description
      "RSVP Generic FlowSpec Types";
  }

  typedef ncs_template_Rsvp-mgmt-qos-service-enum {
    type string;
    description
      "QOS Types";
  }

  typedef ncs_template_Rsvp-mgmt-messageid {
    type string;
    description
      "Rsvp mgmt messageid";
  }

  typedef ncs_template_Rsvp-timer-state {
    type string;
    description
      "RSVP Timer States";
  }

  typedef ncs_template_Rsvp-mgmt-ero-subobj-status {
    type string;
    description
      "RSVP ERO Status";
  }

  typedef ncs_template_Rsvp-mgmt-ero-subobj {
    type string;
    description
      "RSVP ERO Types";
  }

  typedef ncs_template_Rsvp-mgmt-generic-label {
    type string;
    description
      "RSVP Generic Label Types";
  }

  typedef ncs_template_Rsvp-mgmt-mpls-label {
    type string;
    description
      "Rsvp mgmt mpls label";
  }

  typedef ncs_template_Rsvp-mgmt-tspec {
    type string;
    description
      "RSVP Generic Sender Tspec Types";
  }

  typedef ncs_template_Rsvp-mgmt-filter {
    type string;
    description
      "RSVP Filter Types";
  }

  typedef ncs_template_Rsvp-mgmt-session {
    type string;
    description
      "RSVP Session Types";
  }

  typedef ncs_template_Rsvp-mgmt-auth-ki {
    type string;
    description
      "RSVP Authentication KeyInfo Type";
  }

  typedef ncs_template_Rsvp-mgmt-auth-direction {
    type string;
    description
      "RSVP Authentication Direction Types";
  }

  typedef ncs_template_Rsvp-mgmt-dste-modes {
    type string;
    description
      "RSVP DSTE modes";
  }

  typedef ncs_rpc_notif_Igpte-lib-bw-model {
    type enumeration {
      enum "rdm" {
        value 0;
        description
          "Russian Dolls Model";
      }
      enum "mam" {
        value 1;
        description
          "Maximum Allocation Model";
      }
      enum "not-set" {
        value 2;
        description
          "No model set";
      }
    }
    description
      "Bandwidth model";
  }

  typedef ncs_rpc_notif_Rsvp-mgmt-restart-state {
    type enumeration {
      enum "done" {
        description
          "Restart is done";
      }
      enum "recovery" {
        description
          "Neighbor is in recovery";
      }
      enum "abort" {
        description
          "Neighbor recovery aborted";
      }
    }
    description
      "RSVP GR (Graceful Restart) Restart states";
  }

  typedef ncs_rpc_notif_Rsvp-mgmt-hello-down-reason {
    type enumeration {
      enum "not-applicable" {
        description
          "Not applicable. This means RSVP Hellos are up";
      }
      enum "wrong-destination-instance" {
        description
          "Incorrect destination instance in received
           Hellos";
      }
      enum "wrong-source-instance" {
        description
          "Incorrect source instance in received Hellos";
      }
      enum "hello-missed" {
        description
          "Hellos not being received";
      }
      enum "interface-down" {
        description
          "Interface went down";
      }
      enum "neighbor-disabled-hello" {
        description
          "Neighbor disabled Hellos";
      }
      enum "control-channel-down" {
        description
          "Control channel went down";
      }
    }
    description
      "Reasons why RSVP Hellos went down";
  }

  typedef ncs_rpc_notif_Rsvp-mgmt-hello-instance-owner {
    type enumeration {
      enum "mpls-graceful-restart" {
        description
          "MPLS Graceful Restart";
      }
      enum "mpls-ouni" {
        description
          "MPLS OUNI";
      }
    }
    description
      "RSVP Hello instance owner";
  }

  typedef ncs_rpc_notif_Rsvp-mgmt-association {
    type enumeration {
      enum "none" {
        value 0;
        description
          "No ASSOCIATION Object present";
      }
      enum "ipv4" {
        value 1;
        description
          "IPv4 ASSOCIATION Type";
      }
      enum "ipv6" {
        value 2;
        description
          "IPv6 ASSOCIATION Type";
      }
      enum "extended-ipv4" {
        value 3;
        description
          "EXTENDED IPv4 ASSOCIATION Type";
      }
      enum "extended-ipv6" {
        value 4;
        description
          "EXTENDED IPv6 ASSOCIATION Type";
      }
    }
    description
      "RSVP ASSOCIATION Types";
  }

  typedef ncs_rpc_notif_Rsvp-mgmt-rro-subobj {
    type enumeration {
      enum "ipv4rro-type" {
        value 1;
        description
          "IPv4 RRO Type";
      }
      enum "label-rro-type" {
        value 3;
        description
          "Label RRO Type";
      }
      enum "unnumbered-rro-type" {
        value 4;
        description
          "Unnumbered RRO Type";
      }
      enum "srlg-rro-type" {
        value 34;
        description
          "SRLG RRO Type";
      }
    }
    description
      "RSVP RRO Types";
  }

  typedef ncs_rpc_notif_Rsi-vrf-id {
    type uint32;
    description
      "Rsi vrf id";
  }

  typedef ncs_rpc_notif_Rsvp-mgmt-frr-state-enum {
    type enumeration {
      enum "ready-state" {
        value 0;
        description
          "Ready State";
      }
      enum "pending-state" {
        value 1;
        description
          "Pending";
      }
      enum "active-state" {
        value 2;
        description
          "Active State";
      }
    }
    description
      "RSVP FRR States";
  }

  typedef ncs_rpc_notif_Rsvp-proc-nsr-not-ready-reason {
    type enumeration {
      enum "collab-time-out" {
        description
          "Collab connection time out";
      }
      enum "collab-conntection-idt" {
        description
          "Collab connection down or IDT not done";
      }
      enum "nsr-peer-not-connected" {
        description
          "NSR peer not connected";
      }
      enum "nsr-peer-not-in-sync" {
        description
          "NSR peer not in sync";
      }
    }
    description
      "Rsvp proc nsr not ready reason";
  }

  typedef ncs_rpc_notif_Rsvp-sync-status {
    type enumeration {
      enum "not-ready" {
        description
          "Not Ready";
      }
      enum "ready" {
        description
          "Ready";
      }
    }
    description
      "Rsvp sync status";
  }

  typedef ncs_rpc_notif_Rsvp-mgmt-gr-app {
    type enumeration {
      enum "ouni" {
        description
          "Application is OUNI";
      }
      enum "gmpls" {
        description
          "Application is GMPLS";
      }
    }
    description
      "RSVP Graceful Restart application type";
  }

  typedef ncs_rpc_notif_Rsvp-proc-role {
    type enumeration {
      enum "unknown" {
        description
          "Unknown";
      }
      enum "v1-active" {
        description
          "V1 Active";
      }
      enum "v1-standby" {
        description
          "V1 Standby";
      }
      enum "v2-active" {
        description
          "V2 Active";
      }
      enum "v2-standby" {
        description
          "V2 Standby";
      }
      enum "v1-active-post-big-bang" {
        description
          "V1 Active post big-bang";
      }
      enum "v1-standby-post-big-bang" {
        description
          "V1 Standbyi post big-bang";
      }
      enum "count" {
        description
          "Count";
      }
    }
    description
      "RSVP Process Role";
  }

  typedef ncs_rpc_notif_Rsvp-mgmt-auth-challenge-status {
    type enumeration {
      enum "rsvp-mgmt-auth-cs-not-cfg" {
        description
          "Not configured";
      }
      enum "rsvp-mgmt-auth-cs-completed" {
        description
          "Complete";
      }
      enum "rsvp-mgmt-auth-cs-in-progress" {
        description
          "In Progress";
      }
      enum "rsvp-mgmt-auth-cs-failure" {
        description
          "Failed";
      }
      enum "rsvp-mgmt-auth-cs-not-supported" {
        description
          "Not supported";
      }
    }
    description
      "RSVP Authentication Challenge Status";
  }

  typedef ncs_rpc_notif_Rsvp-mgmt-hello-instance {
    type enumeration {
      enum "active" {
        description
          "Hello requests and ACKs are sent";
      }
      enum "passive" {
        description
          "Hello ACKs only are sent";
      }
    }
    description
      "RSVP Hello instance types";
  }

  typedef ncs_rpc_notif_Rsvp-mgmt-hello-state {
    type enumeration {
      enum "hello-state-init" {
        description
          "No Hello messages ever received from neighbor";
      }
      enum "hello-state-up" {
        description
          "Receiving expected Hello messages from neighbor";
      }
      enum "hello-state-down" {
        description
          "Stopped receiving expected Hello messages from
           neighbor";
      }
    }
    description
      "RSVP Hello instance states";
  }

  typedef ncs_rpc_notif_Rsvp-mgmt-reservation-type-enum {
    type enumeration {
      enum "rsvp-mgmt-ff-option" {
        value 10;
        description
          "Single Reservation";
      }
      enum "rsvp-mgmt-wf-option" {
        value 17;
        description
          "Shared Reservation, Unlimited Scope";
      }
      enum "rsvp-mgmt-se-option" {
        value 18;
        description
          "Shared Reservation, Limited Scope";
      }
    }
    description
      "RSVP Reservation Types";
  }

  typedef ncs_rpc_notif_Rsvp-mgmt-flow-spec {
    type enumeration {
      enum "g709otn" {
        value 5;
        description
          "G709 OTN FlowSpec Type";
      }
    }
    description
      "RSVP Generic FlowSpec Types";
  }

  typedef ncs_rpc_notif_Rsvp-mgmt-qos-service-enum {
    type enumeration {
      enum "rsvp-mgmt-qos-unknown" {
        value 0;
        description
          "QOS Unknown";
      }
      enum "rsvp-mgmt-qos-guaranteed" {
        value 3;
        description
          "QOS Guaranteed";
      }
      enum "rsvp-mgmt-qos-controlled-load" {
        value 5;
        description
          "QOS Controlled Load";
      }
      enum "rsvp-mgmt-qos-qualitative" {
        value 6;
        description
          "QOS Qualitative";
      }
    }
    description
      "QOS Types";
  }

  typedef ncs_rpc_notif_Rsvp-mgmt-messageid {
    type uint32;
    description
      "Rsvp mgmt messageid";
  }

  typedef ncs_rpc_notif_Rsvp-timer-state {
    type enumeration {
      enum "rsvp-timer-running-and-sleeping" {
        value 1;
        description
          "RSVP timer running and sleeping";
      }
      enum "rsvp-timer-running" {
        value 2;
        description
          "RSVP timer running";
      }
      enum "rsvp-timer-not-running" {
        value 3;
        description
          "RSVP timer not running";
      }
    }
    description
      "RSVP Timer States";
  }

  typedef ncs_rpc_notif_Rsvp-mgmt-ero-subobj-status {
    type enumeration {
      enum "rsvp-mgmt-ero-status-not-available" {
        value 0;
        description
          "ERO is not available in topology";
      }
      enum "rsvp-mgmt-ero-status-available" {
        value 1;
        description
          "ERO is available in topology";
      }
      enum "rsvp-mgmt-ero-status-bw-not-available" {
        value 2;
        description
          "ERO doesn't have bw available in topology";
      }
    }
    description
      "RSVP ERO Status";
  }

  typedef ncs_rpc_notif_Rsvp-mgmt-ero-subobj {
    type enumeration {
      enum "rsvp-mgmt-ero-type-ipv4" {
        value 1;
        description
          "IPv4 ERO Type";
      }
      enum "rsvp-mgmt-ero-type-un-num" {
        value 4;
        description
          "Unnumbered ERO Type";
      }
    }
    description
      "RSVP ERO Types";
  }

  typedef ncs_rpc_notif_Rsvp-mgmt-generic-label {
    type enumeration {
      enum "rsvp-mgmt-label-type-gmpls" {
        value 2;
        description
          "Generalized Label Type";
      }
    }
    description
      "RSVP Generic Label Types";
  }

  typedef ncs_rpc_notif_Rsvp-mgmt-mpls-label {
    type uint32;
    description
      "Rsvp mgmt mpls label";
  }

  typedef ncs_rpc_notif_Rsvp-mgmt-tspec {
    type enumeration {
      enum "g709otn" {
        value 5;
        description
          "G709 OTN Sender Tspec Type";
      }
      enum "intsrv" {
        value 12;
        description
          "Int-Serv Sender Tspec Type";
      }
    }
    description
      "RSVP Generic Sender Tspec Types";
  }

  typedef ncs_rpc_notif_Rsvp-mgmt-filter {
    type enumeration {
      enum "rsvp-mgmt-filter-type-ipv4" {
        value 1;
        description
          "IPv4 FilterSpec Type";
      }
      enum "rsvp-mgmt-filter-type-p2mp-lsp-ipv4" {
        value 12;
        description
          "P2MP LSP IPv4 FilterSpec Type";
      }
    }
    description
      "RSVP Filter Types";
  }

  typedef ncs_rpc_notif_Rsvp-mgmt-session {
    type enumeration {
      enum "rsvp-mgmt-session-type-udp-ipv4" {
        value 1;
        description
          "UDP IPv4 Session Type";
      }
      enum "rsvp-mgmt-session-type-lsp-ipv4" {
        value 7;
        description
          "LSP IPv4 Session Type";
      }
      enum "rsvp-mgmt-session-type-uni-ipv4" {
        value 9;
        description
          "UNI IPv4 Session Type";
      }
      enum "rsvp-mgmt-session-type-p2mp-lsp-ipv4" {
        value 13;
        description
          "P2MP LSP IPv4 Session Type";
      }
    }
    description
      "RSVP Session Types";
  }

  typedef ncs_rpc_notif_Rsvp-mgmt-auth-ki {
    type enumeration {
      enum "rsvp-mgmt-auth-ki-type-none" {
        description
          "None";
      }
      enum "rsvp-mgmt-auth-ki-type-global" {
        description
          "Global";
      }
      enum "rsvp-mgmt-auth-ki-type-interface" {
        description
          "Interface";
      }
      enum "rsvp-mgmt-auth-ki-type-neighbor" {
        description
          "Neighbor";
      }
    }
    description
      "RSVP Authentication KeyInfo Type";
  }

  typedef ncs_rpc_notif_Rsvp-mgmt-auth-direction {
    type enumeration {
      enum "rsvp-mgmt-auth-direction-send" {
        description
          "Send";
      }
      enum "rsvp-mgmt-auth-direction-recv" {
        description
          "Receive";
      }
    }
    description
      "RSVP Authentication Direction Types";
  }

  typedef ncs_rpc_notif_Rsvp-mgmt-dste-modes {
    type enumeration {
      enum "pre-standard" {
        value 1;
        description
          "pre standard";
      }
      enum "standard" {
        value 3;
        description
          "standard";
      }
    }
    description
      "RSVP DSTE modes";
  }

  typedef live_ncs_Igpte-lib-bw-model {
    type enumeration {
      enum "rdm" {
        value 0;
        description
          "Russian Dolls Model";
      }
      enum "mam" {
        value 1;
        description
          "Maximum Allocation Model";
      }
      enum "not-set" {
        value 2;
        description
          "No model set";
      }
    }
    description
      "Bandwidth model";
  }

  typedef live_ncs_Rsvp-mgmt-restart-state {
    type enumeration {
      enum "done" {
        description
          "Restart is done";
      }
      enum "recovery" {
        description
          "Neighbor is in recovery";
      }
      enum "abort" {
        description
          "Neighbor recovery aborted";
      }
    }
    description
      "RSVP GR (Graceful Restart) Restart states";
  }

  typedef live_ncs_Rsvp-mgmt-hello-down-reason {
    type enumeration {
      enum "not-applicable" {
        description
          "Not applicable. This means RSVP Hellos are up";
      }
      enum "wrong-destination-instance" {
        description
          "Incorrect destination instance in received
           Hellos";
      }
      enum "wrong-source-instance" {
        description
          "Incorrect source instance in received Hellos";
      }
      enum "hello-missed" {
        description
          "Hellos not being received";
      }
      enum "interface-down" {
        description
          "Interface went down";
      }
      enum "neighbor-disabled-hello" {
        description
          "Neighbor disabled Hellos";
      }
      enum "control-channel-down" {
        description
          "Control channel went down";
      }
    }
    description
      "Reasons why RSVP Hellos went down";
  }

  typedef live_ncs_Rsvp-mgmt-hello-instance-owner {
    type enumeration {
      enum "mpls-graceful-restart" {
        description
          "MPLS Graceful Restart";
      }
      enum "mpls-ouni" {
        description
          "MPLS OUNI";
      }
    }
    description
      "RSVP Hello instance owner";
  }

  typedef live_ncs_Rsvp-mgmt-association {
    type enumeration {
      enum "none" {
        value 0;
        description
          "No ASSOCIATION Object present";
      }
      enum "ipv4" {
        value 1;
        description
          "IPv4 ASSOCIATION Type";
      }
      enum "ipv6" {
        value 2;
        description
          "IPv6 ASSOCIATION Type";
      }
      enum "extended-ipv4" {
        value 3;
        description
          "EXTENDED IPv4 ASSOCIATION Type";
      }
      enum "extended-ipv6" {
        value 4;
        description
          "EXTENDED IPv6 ASSOCIATION Type";
      }
    }
    description
      "RSVP ASSOCIATION Types";
  }

  typedef live_ncs_Rsvp-mgmt-rro-subobj {
    type enumeration {
      enum "ipv4rro-type" {
        value 1;
        description
          "IPv4 RRO Type";
      }
      enum "label-rro-type" {
        value 3;
        description
          "Label RRO Type";
      }
      enum "unnumbered-rro-type" {
        value 4;
        description
          "Unnumbered RRO Type";
      }
      enum "srlg-rro-type" {
        value 34;
        description
          "SRLG RRO Type";
      }
    }
    description
      "RSVP RRO Types";
  }

  typedef live_ncs_Rsi-vrf-id {
    type uint32;
    description
      "Rsi vrf id";
  }

  typedef live_ncs_Rsvp-mgmt-frr-state-enum {
    type enumeration {
      enum "ready-state" {
        value 0;
        description
          "Ready State";
      }
      enum "pending-state" {
        value 1;
        description
          "Pending";
      }
      enum "active-state" {
        value 2;
        description
          "Active State";
      }
    }
    description
      "RSVP FRR States";
  }

  typedef live_ncs_Rsvp-proc-nsr-not-ready-reason {
    type enumeration {
      enum "collab-time-out" {
        description
          "Collab connection time out";
      }
      enum "collab-conntection-idt" {
        description
          "Collab connection down or IDT not done";
      }
      enum "nsr-peer-not-connected" {
        description
          "NSR peer not connected";
      }
      enum "nsr-peer-not-in-sync" {
        description
          "NSR peer not in sync";
      }
    }
    description
      "Rsvp proc nsr not ready reason";
  }

  typedef live_ncs_Rsvp-sync-status {
    type enumeration {
      enum "not-ready" {
        description
          "Not Ready";
      }
      enum "ready" {
        description
          "Ready";
      }
    }
    description
      "Rsvp sync status";
  }

  typedef live_ncs_Rsvp-mgmt-gr-app {
    type enumeration {
      enum "ouni" {
        description
          "Application is OUNI";
      }
      enum "gmpls" {
        description
          "Application is GMPLS";
      }
    }
    description
      "RSVP Graceful Restart application type";
  }

  typedef live_ncs_Rsvp-proc-role {
    type enumeration {
      enum "unknown" {
        description
          "Unknown";
      }
      enum "v1-active" {
        description
          "V1 Active";
      }
      enum "v1-standby" {
        description
          "V1 Standby";
      }
      enum "v2-active" {
        description
          "V2 Active";
      }
      enum "v2-standby" {
        description
          "V2 Standby";
      }
      enum "v1-active-post-big-bang" {
        description
          "V1 Active post big-bang";
      }
      enum "v1-standby-post-big-bang" {
        description
          "V1 Standbyi post big-bang";
      }
      enum "count" {
        description
          "Count";
      }
    }
    description
      "RSVP Process Role";
  }

  typedef live_ncs_Rsvp-mgmt-auth-challenge-status {
    type enumeration {
      enum "rsvp-mgmt-auth-cs-not-cfg" {
        description
          "Not configured";
      }
      enum "rsvp-mgmt-auth-cs-completed" {
        description
          "Complete";
      }
      enum "rsvp-mgmt-auth-cs-in-progress" {
        description
          "In Progress";
      }
      enum "rsvp-mgmt-auth-cs-failure" {
        description
          "Failed";
      }
      enum "rsvp-mgmt-auth-cs-not-supported" {
        description
          "Not supported";
      }
    }
    description
      "RSVP Authentication Challenge Status";
  }

  typedef live_ncs_Rsvp-mgmt-hello-instance {
    type enumeration {
      enum "active" {
        description
          "Hello requests and ACKs are sent";
      }
      enum "passive" {
        description
          "Hello ACKs only are sent";
      }
    }
    description
      "RSVP Hello instance types";
  }

  typedef live_ncs_Rsvp-mgmt-hello-state {
    type enumeration {
      enum "hello-state-init" {
        description
          "No Hello messages ever received from neighbor";
      }
      enum "hello-state-up" {
        description
          "Receiving expected Hello messages from neighbor";
      }
      enum "hello-state-down" {
        description
          "Stopped receiving expected Hello messages from
           neighbor";
      }
    }
    description
      "RSVP Hello instance states";
  }

  typedef live_ncs_Rsvp-mgmt-reservation-type-enum {
    type enumeration {
      enum "rsvp-mgmt-ff-option" {
        value 10;
        description
          "Single Reservation";
      }
      enum "rsvp-mgmt-wf-option" {
        value 17;
        description
          "Shared Reservation, Unlimited Scope";
      }
      enum "rsvp-mgmt-se-option" {
        value 18;
        description
          "Shared Reservation, Limited Scope";
      }
    }
    description
      "RSVP Reservation Types";
  }

  typedef live_ncs_Rsvp-mgmt-flow-spec {
    type enumeration {
      enum "g709otn" {
        value 5;
        description
          "G709 OTN FlowSpec Type";
      }
    }
    description
      "RSVP Generic FlowSpec Types";
  }

  typedef live_ncs_Rsvp-mgmt-qos-service-enum {
    type enumeration {
      enum "rsvp-mgmt-qos-unknown" {
        value 0;
        description
          "QOS Unknown";
      }
      enum "rsvp-mgmt-qos-guaranteed" {
        value 3;
        description
          "QOS Guaranteed";
      }
      enum "rsvp-mgmt-qos-controlled-load" {
        value 5;
        description
          "QOS Controlled Load";
      }
      enum "rsvp-mgmt-qos-qualitative" {
        value 6;
        description
          "QOS Qualitative";
      }
    }
    description
      "QOS Types";
  }

  typedef live_ncs_Rsvp-mgmt-messageid {
    type uint32;
    description
      "Rsvp mgmt messageid";
  }

  typedef live_ncs_Rsvp-timer-state {
    type enumeration {
      enum "rsvp-timer-running-and-sleeping" {
        value 1;
        description
          "RSVP timer running and sleeping";
      }
      enum "rsvp-timer-running" {
        value 2;
        description
          "RSVP timer running";
      }
      enum "rsvp-timer-not-running" {
        value 3;
        description
          "RSVP timer not running";
      }
    }
    description
      "RSVP Timer States";
  }

  typedef live_ncs_Rsvp-mgmt-ero-subobj-status {
    type enumeration {
      enum "rsvp-mgmt-ero-status-not-available" {
        value 0;
        description
          "ERO is not available in topology";
      }
      enum "rsvp-mgmt-ero-status-available" {
        value 1;
        description
          "ERO is available in topology";
      }
      enum "rsvp-mgmt-ero-status-bw-not-available" {
        value 2;
        description
          "ERO doesn't have bw available in topology";
      }
    }
    description
      "RSVP ERO Status";
  }

  typedef live_ncs_Rsvp-mgmt-ero-subobj {
    type enumeration {
      enum "rsvp-mgmt-ero-type-ipv4" {
        value 1;
        description
          "IPv4 ERO Type";
      }
      enum "rsvp-mgmt-ero-type-un-num" {
        value 4;
        description
          "Unnumbered ERO Type";
      }
    }
    description
      "RSVP ERO Types";
  }

  typedef live_ncs_Rsvp-mgmt-generic-label {
    type enumeration {
      enum "rsvp-mgmt-label-type-gmpls" {
        value 2;
        description
          "Generalized Label Type";
      }
    }
    description
      "RSVP Generic Label Types";
  }

  typedef live_ncs_Rsvp-mgmt-mpls-label {
    type uint32;
    description
      "Rsvp mgmt mpls label";
  }

  typedef live_ncs_Rsvp-mgmt-tspec {
    type enumeration {
      enum "g709otn" {
        value 5;
        description
          "G709 OTN Sender Tspec Type";
      }
      enum "intsrv" {
        value 12;
        description
          "Int-Serv Sender Tspec Type";
      }
    }
    description
      "RSVP Generic Sender Tspec Types";
  }

  typedef live_ncs_Rsvp-mgmt-filter {
    type enumeration {
      enum "rsvp-mgmt-filter-type-ipv4" {
        value 1;
        description
          "IPv4 FilterSpec Type";
      }
      enum "rsvp-mgmt-filter-type-p2mp-lsp-ipv4" {
        value 12;
        description
          "P2MP LSP IPv4 FilterSpec Type";
      }
    }
    description
      "RSVP Filter Types";
  }

  typedef live_ncs_Rsvp-mgmt-session {
    type enumeration {
      enum "rsvp-mgmt-session-type-udp-ipv4" {
        value 1;
        description
          "UDP IPv4 Session Type";
      }
      enum "rsvp-mgmt-session-type-lsp-ipv4" {
        value 7;
        description
          "LSP IPv4 Session Type";
      }
      enum "rsvp-mgmt-session-type-uni-ipv4" {
        value 9;
        description
          "UNI IPv4 Session Type";
      }
      enum "rsvp-mgmt-session-type-p2mp-lsp-ipv4" {
        value 13;
        description
          "P2MP LSP IPv4 Session Type";
      }
    }
    description
      "RSVP Session Types";
  }

  typedef live_ncs_Rsvp-mgmt-auth-ki {
    type enumeration {
      enum "rsvp-mgmt-auth-ki-type-none" {
        description
          "None";
      }
      enum "rsvp-mgmt-auth-ki-type-global" {
        description
          "Global";
      }
      enum "rsvp-mgmt-auth-ki-type-interface" {
        description
          "Interface";
      }
      enum "rsvp-mgmt-auth-ki-type-neighbor" {
        description
          "Neighbor";
      }
    }
    description
      "RSVP Authentication KeyInfo Type";
  }

  typedef live_ncs_Rsvp-mgmt-auth-direction {
    type enumeration {
      enum "rsvp-mgmt-auth-direction-send" {
        description
          "Send";
      }
      enum "rsvp-mgmt-auth-direction-recv" {
        description
          "Receive";
      }
    }
    description
      "RSVP Authentication Direction Types";
  }

  typedef live_ncs_Rsvp-mgmt-dste-modes {
    type enumeration {
      enum "pre-standard" {
        value 1;
        description
          "pre standard";
      }
      enum "standard" {
        value 3;
        description
          "standard";
      }
    }
    description
      "RSVP DSTE modes";
  }

  typedef Igpte-lib-bw-model {
    type enumeration {
      enum "rdm" {
        value 0;
        description
          "Russian Dolls Model";
      }
      enum "mam" {
        value 1;
        description
          "Maximum Allocation Model";
      }
      enum "not-set" {
        value 2;
        description
          "No model set";
      }
    }
    description
      "Bandwidth model";
  }

  typedef Rsvp-mgmt-restart-state {
    type enumeration {
      enum "done" {
        description
          "Restart is done";
      }
      enum "recovery" {
        description
          "Neighbor is in recovery";
      }
      enum "abort" {
        description
          "Neighbor recovery aborted";
      }
    }
    description
      "RSVP GR (Graceful Restart) Restart states";
  }

  typedef Rsvp-mgmt-hello-down-reason {
    type enumeration {
      enum "not-applicable" {
        description
          "Not applicable. This means RSVP Hellos are up";
      }
      enum "wrong-destination-instance" {
        description
          "Incorrect destination instance in received
           Hellos";
      }
      enum "wrong-source-instance" {
        description
          "Incorrect source instance in received Hellos";
      }
      enum "hello-missed" {
        description
          "Hellos not being received";
      }
      enum "interface-down" {
        description
          "Interface went down";
      }
      enum "neighbor-disabled-hello" {
        description
          "Neighbor disabled Hellos";
      }
      enum "control-channel-down" {
        description
          "Control channel went down";
      }
    }
    description
      "Reasons why RSVP Hellos went down";
  }

  typedef Rsvp-mgmt-hello-instance-owner {
    type enumeration {
      enum "mpls-graceful-restart" {
        description
          "MPLS Graceful Restart";
      }
      enum "mpls-ouni" {
        description
          "MPLS OUNI";
      }
    }
    description
      "RSVP Hello instance owner";
  }

  typedef Rsvp-mgmt-association {
    type enumeration {
      enum "none" {
        value 0;
        description
          "No ASSOCIATION Object present";
      }
      enum "ipv4" {
        value 1;
        description
          "IPv4 ASSOCIATION Type";
      }
      enum "ipv6" {
        value 2;
        description
          "IPv6 ASSOCIATION Type";
      }
      enum "extended-ipv4" {
        value 3;
        description
          "EXTENDED IPv4 ASSOCIATION Type";
      }
      enum "extended-ipv6" {
        value 4;
        description
          "EXTENDED IPv6 ASSOCIATION Type";
      }
    }
    description
      "RSVP ASSOCIATION Types";
  }

  typedef Rsvp-mgmt-rro-subobj {
    type enumeration {
      enum "ipv4rro-type" {
        value 1;
        description
          "IPv4 RRO Type";
      }
      enum "label-rro-type" {
        value 3;
        description
          "Label RRO Type";
      }
      enum "unnumbered-rro-type" {
        value 4;
        description
          "Unnumbered RRO Type";
      }
      enum "srlg-rro-type" {
        value 34;
        description
          "SRLG RRO Type";
      }
    }
    description
      "RSVP RRO Types";
  }

  typedef Rsi-vrf-id {
    type uint32;
    description
      "Rsi vrf id";
  }

  typedef Rsvp-mgmt-frr-state-enum {
    type enumeration {
      enum "ready-state" {
        value 0;
        description
          "Ready State";
      }
      enum "pending-state" {
        value 1;
        description
          "Pending";
      }
      enum "active-state" {
        value 2;
        description
          "Active State";
      }
    }
    description
      "RSVP FRR States";
  }

  typedef Rsvp-proc-nsr-not-ready-reason {
    type enumeration {
      enum "collab-time-out" {
        description
          "Collab connection time out";
      }
      enum "collab-conntection-idt" {
        description
          "Collab connection down or IDT not done";
      }
      enum "nsr-peer-not-connected" {
        description
          "NSR peer not connected";
      }
      enum "nsr-peer-not-in-sync" {
        description
          "NSR peer not in sync";
      }
    }
    description
      "Rsvp proc nsr not ready reason";
  }

  typedef Rsvp-sync-status {
    type enumeration {
      enum "not-ready" {
        description
          "Not Ready";
      }
      enum "ready" {
        description
          "Ready";
      }
    }
    description
      "Rsvp sync status";
  }

  typedef Rsvp-mgmt-gr-app {
    type enumeration {
      enum "ouni" {
        description
          "Application is OUNI";
      }
      enum "gmpls" {
        description
          "Application is GMPLS";
      }
    }
    description
      "RSVP Graceful Restart application type";
  }

  typedef Rsvp-proc-role {
    type enumeration {
      enum "unknown" {
        description
          "Unknown";
      }
      enum "v1-active" {
        description
          "V1 Active";
      }
      enum "v1-standby" {
        description
          "V1 Standby";
      }
      enum "v2-active" {
        description
          "V2 Active";
      }
      enum "v2-standby" {
        description
          "V2 Standby";
      }
      enum "v1-active-post-big-bang" {
        description
          "V1 Active post big-bang";
      }
      enum "v1-standby-post-big-bang" {
        description
          "V1 Standbyi post big-bang";
      }
      enum "count" {
        description
          "Count";
      }
    }
    description
      "RSVP Process Role";
  }

  typedef Rsvp-mgmt-auth-challenge-status {
    type enumeration {
      enum "rsvp-mgmt-auth-cs-not-cfg" {
        description
          "Not configured";
      }
      enum "rsvp-mgmt-auth-cs-completed" {
        description
          "Complete";
      }
      enum "rsvp-mgmt-auth-cs-in-progress" {
        description
          "In Progress";
      }
      enum "rsvp-mgmt-auth-cs-failure" {
        description
          "Failed";
      }
      enum "rsvp-mgmt-auth-cs-not-supported" {
        description
          "Not supported";
      }
    }
    description
      "RSVP Authentication Challenge Status";
  }

  typedef Rsvp-mgmt-hello-instance {
    type enumeration {
      enum "active" {
        description
          "Hello requests and ACKs are sent";
      }
      enum "passive" {
        description
          "Hello ACKs only are sent";
      }
    }
    description
      "RSVP Hello instance types";
  }

  typedef Rsvp-mgmt-hello-state {
    type enumeration {
      enum "hello-state-init" {
        description
          "No Hello messages ever received from neighbor";
      }
      enum "hello-state-up" {
        description
          "Receiving expected Hello messages from neighbor";
      }
      enum "hello-state-down" {
        description
          "Stopped receiving expected Hello messages from
           neighbor";
      }
    }
    description
      "RSVP Hello instance states";
  }

  typedef Rsvp-mgmt-reservation-type-enum {
    type enumeration {
      enum "rsvp-mgmt-ff-option" {
        value 10;
        description
          "Single Reservation";
      }
      enum "rsvp-mgmt-wf-option" {
        value 17;
        description
          "Shared Reservation, Unlimited Scope";
      }
      enum "rsvp-mgmt-se-option" {
        value 18;
        description
          "Shared Reservation, Limited Scope";
      }
    }
    description
      "RSVP Reservation Types";
  }

  typedef Rsvp-mgmt-flow-spec {
    type enumeration {
      enum "g709otn" {
        value 5;
        description
          "G709 OTN FlowSpec Type";
      }
    }
    description
      "RSVP Generic FlowSpec Types";
  }

  typedef Rsvp-mgmt-qos-service-enum {
    type enumeration {
      enum "rsvp-mgmt-qos-unknown" {
        value 0;
        description
          "QOS Unknown";
      }
      enum "rsvp-mgmt-qos-guaranteed" {
        value 3;
        description
          "QOS Guaranteed";
      }
      enum "rsvp-mgmt-qos-controlled-load" {
        value 5;
        description
          "QOS Controlled Load";
      }
      enum "rsvp-mgmt-qos-qualitative" {
        value 6;
        description
          "QOS Qualitative";
      }
    }
    description
      "QOS Types";
  }

  typedef Rsvp-mgmt-messageid {
    type uint32;
    description
      "Rsvp mgmt messageid";
  }

  typedef Rsvp-timer-state {
    type enumeration {
      enum "rsvp-timer-running-and-sleeping" {
        value 1;
        description
          "RSVP timer running and sleeping";
      }
      enum "rsvp-timer-running" {
        value 2;
        description
          "RSVP timer running";
      }
      enum "rsvp-timer-not-running" {
        value 3;
        description
          "RSVP timer not running";
      }
    }
    description
      "RSVP Timer States";
  }

  typedef Rsvp-mgmt-ero-subobj-status {
    type enumeration {
      enum "rsvp-mgmt-ero-status-not-available" {
        value 0;
        description
          "ERO is not available in topology";
      }
      enum "rsvp-mgmt-ero-status-available" {
        value 1;
        description
          "ERO is available in topology";
      }
      enum "rsvp-mgmt-ero-status-bw-not-available" {
        value 2;
        description
          "ERO doesn't have bw available in topology";
      }
    }
    description
      "RSVP ERO Status";
  }

  typedef Rsvp-mgmt-ero-subobj {
    type enumeration {
      enum "rsvp-mgmt-ero-type-ipv4" {
        value 1;
        description
          "IPv4 ERO Type";
      }
      enum "rsvp-mgmt-ero-type-un-num" {
        value 4;
        description
          "Unnumbered ERO Type";
      }
    }
    description
      "RSVP ERO Types";
  }

  typedef Rsvp-mgmt-generic-label {
    type enumeration {
      enum "rsvp-mgmt-label-type-gmpls" {
        value 2;
        description
          "Generalized Label Type";
      }
    }
    description
      "RSVP Generic Label Types";
  }

  typedef Rsvp-mgmt-mpls-label {
    type uint32;
    description
      "Rsvp mgmt mpls label";
  }

  typedef Rsvp-mgmt-tspec {
    type enumeration {
      enum "g709otn" {
        value 5;
        description
          "G709 OTN Sender Tspec Type";
      }
      enum "intsrv" {
        value 12;
        description
          "Int-Serv Sender Tspec Type";
      }
    }
    description
      "RSVP Generic Sender Tspec Types";
  }

  typedef Rsvp-mgmt-filter {
    type enumeration {
      enum "rsvp-mgmt-filter-type-ipv4" {
        value 1;
        description
          "IPv4 FilterSpec Type";
      }
      enum "rsvp-mgmt-filter-type-p2mp-lsp-ipv4" {
        value 12;
        description
          "P2MP LSP IPv4 FilterSpec Type";
      }
    }
    description
      "RSVP Filter Types";
  }

  typedef Rsvp-mgmt-session {
    type enumeration {
      enum "rsvp-mgmt-session-type-udp-ipv4" {
        value 1;
        description
          "UDP IPv4 Session Type";
      }
      enum "rsvp-mgmt-session-type-lsp-ipv4" {
        value 7;
        description
          "LSP IPv4 Session Type";
      }
      enum "rsvp-mgmt-session-type-uni-ipv4" {
        value 9;
        description
          "UNI IPv4 Session Type";
      }
      enum "rsvp-mgmt-session-type-p2mp-lsp-ipv4" {
        value 13;
        description
          "P2MP LSP IPv4 Session Type";
      }
    }
    description
      "RSVP Session Types";
  }

  typedef Rsvp-mgmt-auth-ki {
    type enumeration {
      enum "rsvp-mgmt-auth-ki-type-none" {
        description
          "None";
      }
      enum "rsvp-mgmt-auth-ki-type-global" {
        description
          "Global";
      }
      enum "rsvp-mgmt-auth-ki-type-interface" {
        description
          "Interface";
      }
      enum "rsvp-mgmt-auth-ki-type-neighbor" {
        description
          "Neighbor";
      }
    }
    description
      "RSVP Authentication KeyInfo Type";
  }

  typedef Rsvp-mgmt-auth-direction {
    type enumeration {
      enum "rsvp-mgmt-auth-direction-send" {
        description
          "Send";
      }
      enum "rsvp-mgmt-auth-direction-recv" {
        description
          "Receive";
      }
    }
    description
      "RSVP Authentication Direction Types";
  }

  typedef Rsvp-mgmt-dste-modes {
    type enumeration {
      enum "pre-standard" {
        value 1;
        description
          "pre standard";
      }
      enum "standard" {
        value 3;
        description
          "standard";
      }
    }
    description
      "RSVP DSTE modes";
  }

  grouping ncs_template_RSVP-MGMT-RXSB-DETAIL {
    description
      "Detailed Form of RSVP Proxy Reservation";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container style {
      description
        "RSVP Style";
      uses ncs_template_RSVP-MGMT-STYLE;
    }
    container filter {
      description
        "RSVP Filter";
      uses ncs_template_RSVP-MGMT-FILTER-INFO;
    }
    container flow-spec {
      description
        "Flow Spec Information";
      uses ncs_template_RSVP-MGMT-FLOW-SPEC;
    }
    container generic-flow-spec {
      description
        "Generic Flow Spec Information";
      uses ncs_template_RSVP-MGMT-GEN-FLOW-SPEC;
    }
    container hop {
      description
        "Path Hop Info";
      uses ncs_template_RSVP-MGMT-HOP-INFO;
    }
    container rsvp-header {
      description
        "RSVP Header";
      uses ncs_template_RSVP-MGMT-HEADER-INFO;
    }
    leaf input-interface {
      type string;
      description
        "Path Input Interface";
    }
    leaf dynamic-state {
      type string;
      description
        "Dynamic State Handle";
    }
  }

  grouping ncs_template_RSVP-MGMT-PXSB-DETAIL {
    description
      "Detailed Form of RSVP Proxy Path";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container template {
      description
        "RSVP Template";
      uses ncs_template_RSVP-MGMT-FILTER-INFO;
    }
    container traffic-spec {
      description
        "RSVP Traffic Spec Info";
      uses ncs_template_RSVP-MGMT-TRAFFIC-SPEC;
    }
    container generic-traffic-spec {
      description
        "RSVP Generic Traffic Spec Info";
      uses ncs_template_RSVP-MGMT-GEN-TRAFFIC-SPEC;
    }
    container hop {
      description
        "Path Hop Info";
      uses ncs_template_RSVP-MGMT-HOP-INFO;
    }
    container rsvp-header {
      description
        "RSVP Header";
      uses ncs_template_RSVP-MGMT-HEADER-INFO;
    }
    leaf input-interface {
      type string;
      description
        "Path Input Interface";
    }
    leaf dynamic-state {
      type string;
      description
        "Dynamic State Handle";
    }
  }

  grouping ncs_template_RSVP-MGMT-GLBL-BW-POOL-INFO {
    description
      "Global B/W pool information";
    leaf max-res-pool-percent {
      type string;
      units "percentage";
      description
        "Maxium reservable I/F percent B/W";
    }
    leaf bc0-percent {
      type string;
      units "percentage";
      description
        "BC0 I/F percent B/W";
    }
    leaf bc1-percent {
      type string;
      units "percentage";
      description
        "BC1 I/F percent B/W";
    }
    leaf is-max-res-pool-percent-configured {
      type string;
      description
        "Is maximum reservable default I/F percent
         configured";
    }
    leaf is-bc0-percent-configured {
      type string;
      description
        "Is BC0 default I/F percent configured";
    }
    leaf is-bc1-percent-configured {
      type string;
      description
        "Is BC1 default I/F percent configured";
    }
    leaf bandwidth-configuration-model {
      type ncs_template_Igpte-lib-bw-model;
      description
        "Bandwith configuration model currently in use
         (MAM/RDM)";
    }
  }

  grouping ncs_template_RSVP-MGMT-GLBL-NBR-COMPACT {
    description
      "Compact Info for RSVP Global Neighbor";
    container global-neighbor-flags {
      description
        "Global Neighbor Flags";
      uses ncs_template_RSVP-MGMT-GLBL-NBR-FLAGS;
    }
    leaf is-gr-enabled {
      type string;
      description
        "Is GR enabled";
    }
    leaf node-address {
      type string;
      description
        "Neighbor node address";
    }
    leaf restart-state {
      type ncs_template_Rsvp-mgmt-restart-state;
      description
        "Restart state";
    }
    list local-node-address {
      // NCS patched for predictable order
      ordered-by user;
      description
        "Local node address";
      leaf entry {
        type string;
        description
          "Local node address";
      }
    }
    list neighbor-hello-state {
      // NCS patched for predictable order
      ordered-by user;
      description
        "Neighbor Hello state";
      leaf entry {
        type ncs_template_Rsvp-mgmt-hello-state;
        description
          "Neighbor Hello state";
      }
    }
    list lost-communication-reason {
      // NCS patched for predictable order
      ordered-by user;
      description
        "Reason why communication was lost";
      leaf entry {
        type ncs_template_Rsvp-mgmt-hello-down-reason;
        description
          "Reason why communication was lost";
      }
    }
    list lost-communication-total {
      // NCS patched for predictable order
      ordered-by user;
      description
        "Total number of times communication got lost";
      leaf entry {
        type string;
        description
          "Total number of times communication got lost";
      }
    }
    list up-time {
      // NCS patched for predictable order
      ordered-by user;
      description
        "Time hellos have been up";
      uses ncs_template_RSVP-MGMT-TIMESPEC;
    }
    list lost-communication-time {
      // NCS patched for predictable order
      ordered-by user;
      description
        "Time when communication was lost";
      uses ncs_template_RSVP-MGMT-TIMESPEC;
    }
  }

  grouping ncs_template_RSVP-MGMT-PATH-COMPACT {
    description
      "Compact Form of RSVP Path Info";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container template {
      description
        "RSVP Template";
      uses ncs_template_RSVP-MGMT-FILTER-INFO;
    }
    container session-attribute {
      description
        "RSVP Session Attribute";
      uses ncs_template_RSVP-MGMT-SESSION-ATTRIBUTE;
    }
    container traffic-spec {
      description
        "RSVP Traffic Spec Info";
      uses ncs_template_RSVP-MGMT-TRAFFIC-SPEC;
    }
    container generic-traffic-spec {
      description
        "RSVP Generic Traffic Spec Info";
      uses ncs_template_RSVP-MGMT-GEN-TRAFFIC-SPEC;
    }
    leaf input-interface {
      type string;
      description
        "Path Input Interface";
    }
  }

  grouping ncs_template_RSVP-MGMT-GLBL-NBR-FLAGS {
    description
      "Global Neighbor Flags";
    leaf is-application-ouni {
      type string;
      description
        "OUNI Application";
    }
    leaf is-application-mpls {
      type string;
      description
        "MPLS Application";
    }
  }

  grouping ncs_template_RSVP-MGMT-GLBL-NBR-DETAIL {
    description
      "Detail Info for RSVP Global Neighbor";
    container global-neighbor-flags {
      description
        "Global Neighbor Flags";
      uses ncs_template_RSVP-MGMT-GLBL-NBR-FLAGS;
    }
    container restart-time-left {
      description
        "How much restart time remains";
      uses ncs_template_RSVP-MGMT-TIMESPEC;
    }
    container restart-timer-expiry-time {
      description
        "When will restart timer expire";
      uses ncs_template_RSVP-MGMT-TIMESPEC;
    }
    container recovery-time-left {
      description
        "How much recovery timer remains";
      uses ncs_template_RSVP-MGMT-TIMESPEC;
    }
    container recovery-timer-exp-time {
      description
        "Time at which recovery timer will expire";
      uses ncs_template_RSVP-MGMT-TIMESPEC;
    }
    leaf is-gr-enabled {
      type string;
      description
        "Is GR enabled";
    }
    leaf node-address {
      type string;
      description
        "Neighbor node address";
    }
    leaf restart-state {
      type ncs_template_Rsvp-mgmt-restart-state;
      description
        "Current restart state";
    }
    leaf restart-time {
      type string;
      units "millisecond";
      description
        "GR Restart Time (milliseconds)";
    }
    leaf is-restart-timer-running {
      type string;
      description
        "Is GR restart timer running";
    }
    leaf recovery-time {
      type string;
      units "millisecond";
      description
        "GR Recovery Time (milliseconds)";
    }
    leaf is-recovery-timer-running {
      type string;
      description
        "Is RSVP recovery timer running";
    }
    leaf hello-interval {
      type string;
      units "millisecond";
      description
        "Hello Interval (milliseconds)";
    }
    leaf missed-hellos {
      type string;
      description
        "Hello missed count";
    }
    leaf pending-states {
      type string;
      description
        "Number of pending states for this neighbor";
    }
    list local-node-address {
      // NCS patched for predictable order
      ordered-by user;
      description
        "Local node address";
      leaf entry {
        type string;
        description
          "Local node address";
      }
    }
    list interface-neighbor {
      // NCS patched for predictable order
      ordered-by user;
      description
        "Interface Neighbor List";
      leaf entry {
        type string;
        description
          "Interface Neighbor List";
      }
    }
    list neighbor-hello-state {
      // NCS patched for predictable order
      ordered-by user;
      description
        "Neighbor's hello state";
      leaf entry {
        type ncs_template_Rsvp-mgmt-hello-state;
        description
          "Neighbor's hello state";
      }
    }
    list lost-communication-reason {
      // NCS patched for predictable order
      ordered-by user;
      description
        "Reason why communication was lost";
      leaf entry {
        type ncs_template_Rsvp-mgmt-hello-down-reason;
        description
          "Reason why communication was lost";
      }
    }
    list lost-communication-total {
      // NCS patched for predictable order
      ordered-by user;
      description
        "Total number of times communication got lost";
      leaf entry {
        type string;
        description
          "Total number of times communication got lost";
      }
    }
    list up-time {
      // NCS patched for predictable order
      ordered-by user;
      description
        "Hello up time";
      uses ncs_template_RSVP-MGMT-TIMESPEC;
    }
    list lost-communication-time {
      // NCS patched for predictable order
      ordered-by user;
      description
        "Time when communication was lost";
      uses ncs_template_RSVP-MGMT-TIMESPEC;
    }
  }

  grouping ncs_template_RSVP-MGMT-HELLO-INSTANCE-DETAIL {
    description
      "Detail Info for RSVP Hello Instance";
    container up-time {
      description
        "Hello up time";
      uses ncs_template_RSVP-MGMT-TIMESPEC;
    }
    container communication-lost-time {
      description
        "Time when communication was lost";
      uses ncs_template_RSVP-MGMT-TIMESPEC;
    }
    leaf source-address-xr {
      type string;
      description
        "Source address";
    }
    leaf destination-address-xr {
      type string;
      description
        "Destination address";
    }
    leaf hello-instance-owner {
      type ncs_template_Rsvp-mgmt-hello-instance-owner;
      description
        "Hello instance owner";
    }
    leaf neighbor-hello-state {
      type ncs_template_Rsvp-mgmt-hello-state;
      description
        "Neighbor Hello state";
    }
    leaf instance-type {
      type ncs_template_Rsvp-mgmt-hello-instance;
      description
        "Hello instance type";
    }
    leaf hello-interface {
      type xr:ncs_template_Interface-name;
      description
        "Interface to use";
    }
    leaf hello-interval {
      type string;
      description
        "Hello Interval";
    }
    leaf missed-acks-allowed {
      type string;
      description
        "Number of missed Hello allowed";
    }
    leaf source-instance {
      type string;
      description
        "Source Instance";
    }
    leaf destination-instance {
      type string;
      description
        "Destination Instance";
    }
    leaf communication-lost-reason {
      type ncs_template_Rsvp-mgmt-hello-down-reason;
      description
        "Reason why communication was lost";
    }
    leaf total-communication-lost {
      type string;
      description
        "Total number of times communication got lost";
    }
    leaf communication-lost-hello-missed {
      type string;
      description
        "Lost Comm. Hello missed count";
    }
    leaf communication-lost-wrong-source-inst {
      type string;
      description
        "Count of lost comm. due to wrong Source Inst";
    }
    leaf communication-lost-wrong-destination-inst {
      type string;
      description
        "Count of lost comm. due to wrong Destination
         Inst";
    }
    leaf communication-lost-interface-down {
      type string;
      description
        "Count of lost comm. due to interface down";
    }
    leaf communication-lost-neighbor-disabled-hello {
      type string;
      description
        "Count of lost comm. due to nbor disabling Hellos";
    }
    leaf hello-messages-sent {
      type string;
      description
        "Number of hello messages sent";
    }
    leaf hello-messages-received {
      type string;
      description
        "Number of hello messages received";
    }
    leaf hello-request-suppressed {
      type string;
      description
        "Count of Hello Requests suppessed";
    }
  }

  grouping ncs_template_RSVP-SESSION-RSB-DETAIL {
    description
      "RSVP Detail Session Reservation Info";
    container generic-out-label {
      description
        "Generic Label for outbound traffic";
      uses ncs_template_RSVP-MGMT-GENERIC-LABEL;
    }
    container flow-spec {
      description
        "Flow spec object";
      uses ncs_template_RSVP-MGMT-FLOW-SPEC;
    }
    container generic-flow-spec {
      description
        "Generic Flow Spec object";
      uses ncs_template_RSVP-MGMT-GEN-FLOW-SPEC;
    }
    leaf is-valid {
      type string;
      description
        "Entry validity";
    }
    leaf destination-address {
      type string;
      description
        "Destination address";
    }
    leaf out-interface {
      type xr:ncs_template_Interface-name;
      description
        "Interface on which outbound message was sent";
    }
    leaf out-label {
      type ncs_template_Rsvp-mgmt-mpls-label;
      description
        "Label for outbound traffic";
    }
    leaf backup-interface {
      type xr:ncs_template_Interface-name;
      description
        "Backup tunnel interface";
    }
    leaf backup-label {
      type ncs_template_Rsvp-mgmt-mpls-label;
      description
        "Backup label";
    }
    leaf is-rro-valid {
      type string;
      description
        "RRO validity";
    }
    leaf is-flow-spec-valid {
      type string;
      description
        "FlowSpec validity";
    }
    list rro {
      // NCS patched for predictable order
      ordered-by user;
      description
        "Record route object";
      uses ncs_template_RSVP-MGMT-RRO-SUBOBJ;
    }
  }

  grouping ncs_template_RSVP-MGMT-REV-LSP-UNSUPPORTED-SUBOBJ {
    description
      "RSVP MGMT REV LSP UNSUPPORTED SUBOBJ";
    list rsvp-mgmt-rev-lsp-unsupported-subobj {
      // NCS patched for predictable order
      ordered-by user;
      description
        "rsvp mgmt rev lsp unsupported subobj";
      leaf entry {
        type string;
        description
          "rsvp mgmt rev lsp unsupported subobj";
      }
    }
  }

  grouping ncs_template_RSVP-MGMT-REVERSE-LSP {
    description
      "RSVP REVERSE_LSP Object";
    container generic-traffic-spec {
      description
        "Generic Traffic Spec object";
      uses ncs_template_RSVP-MGMT-GEN-TRAFFIC-SPEC;
    }
    list ero {
      // NCS patched for predictable order
      ordered-by user;
      description
        "Explicit Route Sub Objects";
      uses ncs_template_RSVP-MGMT-ERO-SUBOBJ;
    }
    list unsup-sub-object {
      // NCS patched for predictable order
      ordered-by user;
      description
        "Unsupported REVERSE_LSP Sub Objects";
      uses ncs_template_RSVP-MGMT-REV-LSP-UNSUPPORTED-SUBOBJ;
    }
  }

  grouping ncs_template_RSVP-MGMT-PROTECTION-LINK-FLAGS {
    description
      "RSVP PROTECTION Object Link Flags";
    leaf enhanced {
      type string;
      description
        "Indicates Enhanced Protection Scheme";
    }
    leaf ded1-plus1 {
      type string;
      description
        "Dedicated 1+1 Protection";
    }
    leaf ded1-to1 {
      type string;
      description
        "Dedicated 1:1 Protection";
    }
    leaf shared {
      type string;
      description
        "Shared Link Layer Protection";
    }
    leaf unprotected {
      type string;
      description
        "LSP should not use any Link Layer Protection";
    }
    leaf extra-traffic {
      type string;
      description
        "LSP should use Links that are protecting other
         (primary) traffic";
    }
    leaf reserved-bit1 {
      type string;
      description
        "Reserved Bit 1";
    }
    leaf reserved-bit2 {
      type string;
      description
        "Reserved Bit 2";
    }
  }

  grouping ncs_template_RSVP-MGMT-PROTECTION-LSP-FLAGS {
    description
      "RSVP PROTECTION Object LSP Flags";
    leaf rerouting {
      type string;
      description
        "Full Rerouting";
    }
    leaf rerouting-no-et {
      type string;
      description
        "Rerouting Without Extra-Traffic";
    }
    leaf one-to-n-protection-et {
      type string;
      description
        "1:N Protection with Extra-Traffic";
    }
    leaf one-plus-one-uni {
      type string;
      description
        "1+1 Unidirectional Protection";
    }
    leaf one-plus-one-bi {
      type string;
      description
        "1+1 Bidirectional Protection";
    }
  }

  grouping ncs_template_RSVP-MGMT-PROTECTION {
    description
      "RSVP PROTECTION Object Info";
    container lsp-flags {
      description
        "PROTECTION Object LSP Flags";
      uses ncs_template_RSVP-MGMT-PROTECTION-LSP-FLAGS;
    }
    container link-flags {
      description
        "PROTECTION Object Link Flags";
      uses ncs_template_RSVP-MGMT-PROTECTION-LINK-FLAGS;
    }
    leaf s {
      type string;
      description
        "Secondary Bit";
    }
    leaf p {
      type string;
      description
        "Protecting Bit";
    }
    leaf n {
      type string;
      description
        "Notification Bit";
    }
    leaf o {
      type string;
      description
        "Operational Bit";
    }
  }

  grouping ncs_template_RSVP-MGMT-ASSOCIATION-IPV6-EXT {
    description
      "RSVP EXTENDED ASSOCIATION IPv6 Object Info";
    leaf type {
      type string;
      description
        "Association Type (RFC 4872)";
    }
    leaf id {
      type string;
      description
        "Association ID";
    }
    leaf source {
      type string;
      description
        "Association IPV6 Source Address";
    }
    leaf global-source {
      type string;
      description
        "Global Association Source";
    }
    list extended-id {
      // NCS patched for predictable order
      ordered-by user;
      description
        "Extended Association ID";
      leaf entry {
        type string;
        description
          "Extended Association ID";
      }
    }
  }

  grouping ncs_template_RSVP-MGMT-ASSOCIATION-IPV4-EXT {
    description
      "RSVP EXTENDED ASSOCIATION IPv4 Object Info";
    leaf type {
      type string;
      description
        "Association Type (RFC 4872)";
    }
    leaf id {
      type string;
      description
        "Association ID";
    }
    leaf source {
      type string;
      description
        "Association IPV4 Source Address";
    }
    leaf global-source {
      type string;
      description
        "Global Association Source";
    }
    list extended-id {
      // NCS patched for predictable order
      ordered-by user;
      description
        "Extended Association ID";
      leaf entry {
        type string;
        description
          "Extended Association ID";
      }
    }
  }

  grouping ncs_template_RSVP-MGMT-ASSOCIATION-IPV6 {
    description
      "RSVP ASSOCIATION IPv6 Object Info";
    leaf type {
      type string;
      description
        "Association Type (RFC 4872)";
    }
    leaf id {
      type string;
      description
        "Association ID";
    }
    leaf source {
      type string;
      description
        "Association IPV6 Source Address";
    }
  }

  grouping ncs_template_RSVP-MGMT-ASSOCIATION-IPV4 {
    description
      "RSVP ASSOCIATION IPv4 Object Info";
    leaf type {
      type string;
      description
        "Association Type (RFC 4872)";
    }
    leaf id {
      type string;
      description
        "Association ID";
    }
    leaf source {
      type string;
      description
        "Association IPV4 Source Address";
    }
  }

  grouping ncs_template_RSVP-MGMT-ASSOCIATION {
    description
      "Union of the different ASSOCIATION types";
    container ipv4 {
      // NCS drop when statement
      description
        "IPV4 ASSOCIATION Object";
      uses ncs_template_RSVP-MGMT-ASSOCIATION-IPV4;
    }
    container ipv6 {
      // NCS drop when statement
      description
        "IPV6 ASSOCIATION Object";
      uses ncs_template_RSVP-MGMT-ASSOCIATION-IPV6;
    }
    container extended-ipv4 {
      // NCS drop when statement
      description
        "EXTENDED IPV4 ASSOCIATION Object";
      uses ncs_template_RSVP-MGMT-ASSOCIATION-IPV4-EXT;
    }
    container extended-ipv6 {
      // NCS drop when statement
      description
        "EXTENDED IPV6 ASSOCIATION Object";
      uses ncs_template_RSVP-MGMT-ASSOCIATION-IPV6-EXT;
    }
    leaf association-type {
      type ncs_template_Rsvp-mgmt-association;
      description
        "AssociationType";
    }
  }

  grouping ncs_template_RSVP-MGMT-RRO-SRLG-SUBOBJ {
    description
      "RSVP RRO SRLG subobject";
    list srl-gs {
      // NCS patched for predictable order
      ordered-by user;
      description
        "The RRO Subobject SRLGs";
      leaf entry {
        type string;
        description
          "The RRO Subobject SRLGs";
      }
    }
  }

  grouping ncs_template_RSVP-MGMT-RRO-UNNUMBERED-SUBOBJ-FLAGS {
    description
      "RSVP RRO UNNUMBERED Subobject Flags";
    leaf is-protection-available {
      type string;
      description
        "Local Protection Available";
    }
    leaf is-protection-in-use {
      type string;
      description
        "Local Protection In Use";
    }
    leaf is-bandwidth-protected {
      type string;
      description
        "Bandwidth Protection Available";
    }
    leaf is-node-protection-available {
      type string;
      description
        "Node Protection Available";
    }
    leaf is-node-id {
      type string;
      description
        "Node ID In Use";
    }
  }

  grouping ncs_template_RSVP-MGMT-RRO-UNNUMBERED-SUBOBJ {
    description
      "RSVP RRO Unnumbered subobject";
    container flags {
      description
        "The RRO Subobject Unnumbered Flags";
      uses ncs_template_RSVP-MGMT-RRO-UNNUMBERED-SUBOBJ-FLAGS;
    }
    leaf interface-address {
      type string;
      description
        "The RRO Interface Address";
    }
    leaf interface-id {
      type string;
      description
        "The RRO Interface ID";
    }
  }

  grouping ncs_template_RSVP-MGMT-RRO-LABEL-SUBOBJ-FLAGS {
    description
      "RSVP RRO Label Subobject Flags";
    leaf is-global-label {
      type string;
      description
        "Label is Global across all interfaces";
    }
  }

  grouping ncs_template_RSVP-MGMT-RRO-LABEL-SUBOBJ {
    description
      "RSVP RRO Label subobject";
    container flags {
      description
        "The RRO Subobject Label Flags";
      uses ncs_template_RSVP-MGMT-RRO-LABEL-SUBOBJ-FLAGS;
    }
    leaf label {
      type string;
      description
        "The RRO Subobject Label Value";
    }
    leaf is-label-variable-length {
      type string;
      description
        "Is the RRO Subobject Label Variable Length";
    }
    list variable-length-label {
      // NCS patched for predictable order
      ordered-by user;
      description
        "The RRO Subobject Variable Length Label";
      leaf entry {
        type string;
        description
          "The RRO Subobject Variable Length Label";
      }
    }
  }

  grouping ncs_template_RSVP-MGMT-RRO-IPV4-SUBOBJ-FLAGS {
    description
      "RSVP RRO IPV4 Subobject Flags";
    leaf is-protection-available {
      type string;
      description
        "Local Protection Available";
    }
    leaf is-protection-in-use {
      type string;
      description
        "Local Protection In Use";
    }
    leaf is-bandwidth-protected {
      type string;
      description
        "Bandwidth Protection Available";
    }
    leaf is-node-protection-available {
      type string;
      description
        "Node Protection Available";
    }
    leaf is-node-id {
      type string;
      description
        "Node ID In Use";
    }
  }

  grouping ncs_template_RSVP-MGMT-RRO-IPV4-SUBOBJ {
    description
      "RSVP RRO IPV4 subobject";
    container flags {
      description
        "The RRO IPV4 Subobject Flags";
      uses ncs_template_RSVP-MGMT-RRO-IPV4-SUBOBJ-FLAGS;
    }
    leaf rro-address {
      type string;
      description
        "The RRO IPV4 Address";
    }
  }

  grouping ncs_template_RSVP-MGMT-RRO-SUBOBJ {
    description
      "Union of the different RSVP RRO types";
    container ipv4rro-sub-object {
      // NCS drop when statement
      description
        "IPV4 RRO Sub Object";
      uses ncs_template_RSVP-MGMT-RRO-IPV4-SUBOBJ;
    }
    container label-rro-sub-object {
      // NCS drop when statement
      description
        "Label RRO Sub Object";
      uses ncs_template_RSVP-MGMT-RRO-LABEL-SUBOBJ;
    }
    container unnumbered-rro-sub-object {
      // NCS drop when statement
      description
        "Unnumbered RRO Sub Object";
      uses ncs_template_RSVP-MGMT-RRO-UNNUMBERED-SUBOBJ;
    }
    container srlg-rro-sub-object {
      // NCS drop when statement
      description
        "SRLG RRO Sub Object";
      uses ncs_template_RSVP-MGMT-RRO-SRLG-SUBOBJ;
    }
    leaf rro-type {
      type ncs_template_Rsvp-mgmt-rro-subobj;
      description
        "RROType";
    }
  }

  grouping ncs_template_RSVP-SESSION-PSB-DETAIL {
    description
      "RSVP Detail Session Path Info";
    container generic-in-label {
      description
        "Generic Label for inbound traffic";
      uses ncs_template_RSVP-MGMT-GENERIC-LABEL;
    }
    container traffic-spec {
      description
        "Traffic Spec object";
      uses ncs_template_RSVP-MGMT-TRAFFIC-SPEC;
    }
    container generic-traffic-spec {
      description
        "Generic Traffic Spec object";
      uses ncs_template_RSVP-MGMT-GEN-TRAFFIC-SPEC;
    }
    container association {
      description
        "Association object";
      uses ncs_template_RSVP-MGMT-ASSOCIATION;
    }
    container protection {
      description
        "Protection object";
      uses ncs_template_RSVP-MGMT-PROTECTION;
    }
    container reverse-lsp {
      description
        "Reverse LSP object";
      uses ncs_template_RSVP-MGMT-REVERSE-LSP;
    }
    leaf is-valid {
      type string;
      description
        "Entry validity";
    }
    leaf destination-address {
      type string;
      description
        "Destination address";
    }
    leaf lsp-id {
      type string;
      description
        "LSP ID";
    }
    leaf p2mp-sub-group-origin {
      type string;
      description
        "Point to Multipoint SubGroup Origin";
    }
    leaf sub-group-id {
      type string;
      description
        "Point to Multipoint Subgroup ID";
    }
    leaf in-interface {
      type xr:ncs_template_Interface-name;
      description
        "Interface on which inbound message was received";
    }
    leaf in-label {
      type ncs_template_Rsvp-mgmt-mpls-label;
      description
        "Label for inbound traffic";
    }
    leaf lsp-wrap-label {
      type ncs_template_Rsvp-mgmt-mpls-label;
      description
        "LSP Wrap Label";
    }
    leaf is-bad-address {
      type string;
      description
        "Address validity";
    }
    leaf incoming-interface-address {
      type string;
      description
        "IP address of Path's incoming interface";
    }
    leaf is-ero-valid {
      type string;
      description
        "ERO validity";
    }
    leaf is-rro-valid {
      type string;
      description
        "RRO validity";
    }
    leaf is-traffic-spec-valid {
      type string;
      description
        "Traffic Spec validity";
    }
    leaf tunnel-name {
      type string;
      description
        "Tunnel name";
    }
    list ero {
      // NCS patched for predictable order
      ordered-by user;
      description
        "Explicit Route Sub Objects";
      uses ncs_template_RSVP-MGMT-ERO-SUBOBJ;
    }
    list rro {
      // NCS patched for predictable order
      ordered-by user;
      description
        "Record Route Sub Objects";
      uses ncs_template_RSVP-MGMT-RRO-SUBOBJ;
    }
  }

  grouping ncs_template_RSVP-SESSION-PSB-RSB-DETAIL {
    description
      "List of Path and Reservation Info";
    list psb-info {
      // NCS patched for predictable order
      ordered-by user;
      description
        "Path Info";
      uses ncs_template_RSVP-SESSION-PSB-DETAIL;
    }
    list rsb-info {
      // NCS patched for predictable order
      ordered-by user;
      description
        "Reservation Info";
      uses ncs_template_RSVP-SESSION-RSB-DETAIL;
    }
  }

  grouping ncs_template_RSVP-MGMT-SESSION-DETAIL {
    description
      "RSVP Detail Session Info";
    container compact {
      description
        "Compact session data";
      uses ncs_template_RSVP-MGMT-SESSION-COMPACT;
    }
    container s2l-sub-lsp {
      description
        "RSVP S2L Sub-LSP information";
      uses ncs_template_RSVP-MGMT-S2L-SUB-LSP-IPV4;
    }
    list psb-rsb-info {
      // NCS patched for predictable order
      ordered-by user;
      description
        "Path and Reservation Info";
      uses ncs_template_RSVP-SESSION-PSB-RSB-DETAIL;
    }
  }

  grouping ncs_template_RSVP-MGMT-KEY {
    description
      "Key to uniquely identify some RSVP records";
    leaf p2mp-id {
      type string;
      description
        "Point-to-multipoint ID";
    }
    leaf destination-address {
      type string;
      description
        "Destination address";
    }
    leaf destination-port-or-tunnel-id {
      type string;
      description
        "Destination Port or Tunnel ID. For the LSP and
         OUNI session types this represents the Tunnel ID
         whereas for the UDP session type this represents
         the Destination Port";
    }
    leaf protocol {
      type string;
      description
        "Protocol. UDP session type this represents the
         Protocol (UDP not supported at present)";
    }
    leaf extended-tunnel-id {
      type string;
      description
        "Protocol or Extended Tunnel ID. For the LSP and
         OUNI sesion types this represents the Extended
         Tunnel ID";
    }
    leaf session-type {
      type ncs_template_Rsvp-mgmt-session;
      description
        "Session Type (e.g. LSP, OUNI or UDP)";
    }
    leaf source-address {
      type string;
      description
        "Source Address";
    }
    leaf source-port-or-lsp-id {
      type string;
      description
        "Source Port or LSP_ID. For the LSP and OUNI
         session types this represents the LSP_ID whereas
         for the UDP session type this represents the
         SourcePort";
    }
    leaf p2mp-sub-group-origin {
      type string;
      description
        "Point to Multipoint SubGroup Origin";
    }
    leaf sub-group-id {
      type string;
      description
        "Point to Multipoint Subgroup ID";
    }
    leaf vrfid {
      type ncs_template_Rsi-vrf-id;
      description
        "Signalling VRF ID";
    }
  }

  grouping ncs_template_RSVP-MGMT-REQUEST-FLAGS {
    description
      "Request state flags";
    leaf is-local-receiver {
      type string;
      description
        "Local Receiver";
    }
    leaf is-refreshing {
      type string;
      description
        "Is neighbor refreshing";
    }
    leaf is-send-confirm {
      type string;
      description
        "Send Confirm message";
    }
    leaf is-ack-outstanding {
      type string;
      description
        "Is ACK message outstanding";
    }
    leaf is-message-id-allocated {
      type string;
      description
        "Is MessageID allocated";
    }
    leaf is-nack-received {
      type string;
      description
        "A NACK message was received";
    }
    leaf is-retransmit {
      type string;
      description
        "Retransmit the message";
    }
    leaf is-paced {
      type string;
      description
        "Message is paced";
    }
    leaf is-label-request-in-path {
      type string;
      description
        "The Path message contains Label Request";
    }
    leaf is-rro-in-path {
      type string;
      description
        "The Path message contains RRO";
    }
    leaf is-record-label-in-path {
      type string;
      description
        "Path has Session-Attr object with Record Labels
         set";
    }
    leaf is-merge-point {
      type string;
      description
        "Is node a Merge Point";
    }
  }

  grouping ncs_template_RSVP-MGMT-REQUEST-DETAIL {
    description
      "Detailed Form of RSVP Request Info";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container flow-spec {
      description
        "Flow Spec Information";
      uses ncs_template_RSVP-MGMT-FLOW-SPEC;
    }
    container generic-flow-spec {
      description
        "Generic Flow Spec Information";
      uses ncs_template_RSVP-MGMT-GEN-FLOW-SPEC;
    }
    container filter {
      description
        "RSVP Filter";
      uses ncs_template_RSVP-MGMT-FILTER-INFO;
    }
    container style {
      description
        "RSVP Style";
      uses ncs_template_RSVP-MGMT-STYLE;
    }
    container req-flags {
      description
        "Request flags";
      uses ncs_template_RSVP-MGMT-REQUEST-FLAGS;
    }
    container hop {
      description
        "Hop Infomation";
      uses ncs_template_RSVP-MGMT-HOP-INFO;
    }
    container header {
      description
        "RSVP Header Information";
      uses ncs_template_RSVP-MGMT-HEADER-INFO;
    }
    container policy-sources {
      description
        "RSVP Policy Sources";
      uses ncs_template_RSVP-MGMT-POLICY-SOURCES;
    }
    container policy-flags {
      description
        "RSVP Policy Flags";
      uses ncs_template_RSVP-MGMT-POLICY-FLAGS;
    }
    container policy-query-flags {
      description
        "RSVP Query Flags";
      uses ncs_template_RSVP-MGMT-POLICY-QUERY-FLAGS;
    }
    leaf output-interface {
      type string;
      description
        "output Interface";
    }
    list psb-key {
      // NCS patched for predictable order
      ordered-by user;
      description
        "List of RSB keys";
      uses ncs_template_RSVP-MGMT-KEY;
    }
    list rsb-key {
      // NCS patched for predictable order
      ordered-by user;
      description
        "List of RSB keys";
      uses ncs_template_RSVP-MGMT-KEY;
    }
  }

  grouping ncs_template_RSVP-MGMT-REQUEST-COMPACT {
    description
      "Compact Form of RSVP Request Info";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container flow-spec {
      description
        "Flow Spec Information";
      uses ncs_template_RSVP-MGMT-FLOW-SPEC;
    }
    container generic-flow-spec {
      description
        "Generic Flow Spec Information";
      uses ncs_template_RSVP-MGMT-GEN-FLOW-SPEC;
    }
    container filter {
      description
        "RSVP Filter";
      uses ncs_template_RSVP-MGMT-FILTER-INFO;
    }
    container style {
      description
        "RSVP Style";
      uses ncs_template_RSVP-MGMT-STYLE;
    }
    leaf output-interface {
      type string;
      description
        "Output Interface";
    }
  }

  grouping ncs_template_RSVP-MGMT-FRR-STATES-DETAIL {
    description
      "RSVP states for one FRR LSP";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    leaf path-status {
      type ncs_template_Rsvp-mgmt-frr-state-enum;
      description
        "RSVP FRR Path States";
    }
    leaf reservation-status {
      type ncs_template_Rsvp-mgmt-frr-state-enum;
      description
        "RSVP FRR Reservation States";
    }
  }

  grouping ncs_template_RSVP-GLOBAL-INFO {
    description
      "RSVP global information";
    container issu-status {
      description
        "Issu status";
      uses ncs_template_RSVP-NSR-ISSU-STATUS-INFO;
    }
    container nsr-status {
      description
        "NSR status";
      uses ncs_template_RSVP-NSR-ISSU-STATUS-INFO;
    }
    container database-counters {
      description
        "All database counters";
      uses ncs_template_RSVP-MGMT-ALL-DB-COUNTERS;
    }
    leaf interfaces {
      type string;
      description
        "Total interfaces";
    }
    leaf ls-ps {
      type string;
      description
        "Total LSPs";
    }
  }

  grouping ncs_template_RSVP-IDT-STATUS {
    description
      "IDT status information";
    leaf sync-status {
      type ncs_template_Rsvp-sync-status;
      description
        "Sync status";
    }
    leaf not-ready-reason {
      type ncs_template_Rsvp-proc-nsr-not-ready-reason;
      description
        "Not ready reason";
    }
    leaf idt-start-time {
      type string;
      units "second";
      description
        "IDT start timestamp in seconds";
    }
    leaf idt-end-time {
      type string;
      units "second";
      description
        "IDT end timestamp in seconds";
    }
    leaf declare-time {
      type string;
      units "second";
      description
        "Declare ready timestamp in seconds";
    }
    leaf withdraw-time {
      type string;
      units "second";
      description
        "Withdraw ready timestamp in seconds";
    }
  }

  grouping ncs_template_RSVP-NSR-ISSU-STATUS-INFO {
    description
      "NSR/ISSU status information";
    container idt-status {
      description
        "IDT status";
      uses ncs_template_RSVP-IDT-STATUS;
    }
    container previous-idt-status {
      description
        "Previous IDT status";
      uses ncs_template_RSVP-IDT-STATUS;
    }
    leaf role {
      type ncs_template_Rsvp-proc-role;
      description
        "Process role";
    }
  }

  grouping ncs_template_RSVP-MGMT-IF-NBR-DETAIL {
    description
      "Detail Info for RSVP Interface Neighbor";
    leaf interface-neighbor-address {
      type string;
      description
        "Interface Neighbor address";
    }
    leaf neighbor-interface-name {
      type xr:ncs_template_Interface-name;
      description
        "Neighbor's Interface handle";
    }
    leaf is-rr-enabled {
      type string;
      description
        "Is Neighbor's RR enable";
    }
    leaf neighbor-epoch {
      type string;
      description
        "Neighbor's epoch value";
    }
    leaf out-of-order-messages {
      type string;
      description
        "Number of out of order msgs";
    }
    leaf retransmitted-messages {
      type string;
      description
        "Number of retransmitted msgs";
    }
  }

  grouping ncs_template_RSVP-MGMT-NBR-DETAIL {
    description
      "Detail Info for RSVP Neighbor";
    leaf node-address {
      type string;
      description
        "Neighbor node address";
    }
    list interface-neighbor-list-detail {
      // NCS patched for predictable order
      ordered-by user;
      description
        "Detail list of I/F Neighbors";
      uses ncs_template_RSVP-MGMT-IF-NBR-DETAIL;
    }
  }

  grouping ncs_template_RSVP-MGMT-HELLO-IF-INSTANCE-DETAIL {
    description
      "Detail Info for IF-based RSVP Hello Instance";
    container last-message-sent-time {
      description
        "Last Ack/msg sent time";
      uses ncs_template_RSVP-MGMT-TIMESPEC;
    }
    leaf source-address-xr {
      type string;
      description
        "Source address";
    }
    leaf destination-address-xr {
      type string;
      description
        "Destination address";
    }
    leaf hello-global-neighbor-id {
      type string;
      description
        "Global Neighbor ID";
    }
    leaf instance-type {
      type ncs_template_Rsvp-mgmt-hello-instance;
      description
        "Hello instance type";
    }
    leaf hello-interface {
      type xr:ncs_template_Interface-name;
      description
        "Interface to use";
    }
    leaf source-instance {
      type string;
      description
        "Source Instance";
    }
    leaf destination-instance {
      type string;
      description
        "Destination Instance";
    }
    leaf hello-messages-sent {
      type string;
      description
        "Number of hello messages sent";
    }
    leaf hello-messages-received {
      type string;
      description
        "Number of hello messages received";
    }
  }

  grouping ncs_template_RSVP-MGMT-HELLO-IF-INSTANCE-COMPACT {
    description
      "Compact Info for IF-based RSVP Hello Instance";
    leaf source-address-xr {
      type string;
      description
        "Source address";
    }
    leaf destination-address-xr {
      type string;
      description
        "Destination address";
    }
    leaf instance-type {
      type ncs_template_Rsvp-mgmt-hello-instance;
      description
        "Hello instance type";
    }
    leaf hello-interface {
      type xr:ncs_template_Interface-name;
      description
        "Interface to use";
    }
  }

  grouping ncs_template_RSVP-MGMT-LOCAL-NODE-ID-IPV4 {
    description
      "Local Node-id";
    leaf local-node-ip-address {
      type string;
      description
        "Local node address";
    }
    leaf application-type {
      type ncs_template_Rsvp-mgmt-gr-app;
      description
        "GR local node-id app type";
    }
  }

  grouping ncs_template_RSVP-MGMT-GRACEFUL-RESTART {
    description
      "RSVP Graceful Restart Info";
    container recovery-time-left {
      description
        "How much recovery timer remains";
      uses ncs_template_RSVP-MGMT-TIMESPEC;
    }
    container recovery-timer-exp-time {
      description
        "Time at which recovery timer will expire";
      uses ncs_template_RSVP-MGMT-TIMESPEC;
    }
    leaf is-gr-enabled {
      type string;
      description
        "Whether GR is enabled";
    }
    leaf global-neighbors {
      type string;
      description
        "Global neighbor count";
    }
    leaf restart-time {
      type string;
      units "millisecond";
      description
        "Restart time (milliseconds)";
    }
    leaf recovery-time {
      type string;
      units "millisecond";
      description
        "Recovery time (milliseconds)";
    }
    leaf is-recovery-timer-running {
      type string;
      description
        "Whether recovery timer is running";
    }
    leaf hello-interval {
      type string;
      description
        "Interval at which hello messages are sent";
    }
    leaf missed-hellos {
      type string;
      description
        "Max number of hellos missed before hellos
         declared down";
    }
    leaf pending-states {
      type string;
      description
        "Total number of pending states";
    }
    list local-node-address {
      // NCS patched for predictable order
      ordered-by user;
      description
        "Local node address";
      uses ncs_template_RSVP-MGMT-LOCAL-NODE-ID-IPV4;
    }
  }

  grouping ncs_template_RSVP-MGMT-INTERFACE-COMPACT {
    description
      "Compact Form of RSVP interface Info";
    container bandwidth-information {
      description
        "Interface bandwidth information";
      uses ncs_template_RSVP-MGMT-DSTE-MODE-INTERFACE-BW;
    }
    leaf interface-name-xr {
      type string;
      description
        "Interface Name";
    }
  }

  grouping ncs_template_RSVP-MGMT-ALL-DB-COUNTERS {
    description
      "All database counters";
    leaf sessions {
      type string;
      description
        "Number of sessions";
    }
    leaf incoming-paths {
      type string;
      description
        "Number of locally created and incoming path
         states";
    }
    leaf outgoing-paths {
      type string;
      description
        "Number of outgoing path states";
    }
    leaf incoming-reservations {
      type string;
      description
        "Number of locally created and incoming
         reservation states";
    }
    leaf outgoing-reservations {
      type string;
      description
        "Number of outgoing reservation states";
    }
    leaf interfaces {
      type string;
      description
        "Number of Interfaces";
    }
  }

  grouping ncs_template_RSVP-SYNC-COUNT-INFO {
    description
      "RSVP sync sent and received counters information";
    leaf last-cleared-timestamp {
      type string;
      units "second";
      description
        "The timestamp, in seconds, when these statistics
         are cleared              since 00:00:00 UTC,
         January 1, 1970";
    }
    leaf rsvp-process-role {
      type ncs_template_Rsvp-proc-role;
      description
        "Process role";
    }
    leaf last-idt-states {
      type string;
      description
        "Last IDT number of states";
    }
    leaf total-states {
      type string;
      description
        "Total number of states";
    }
    leaf total-deletions {
      type string;
      description
        "Total number of deletions";
    }
    leaf total-nacks {
      type string;
      description
        "Total number of NACKs";
    }
    leaf total-id-ts {
      type string;
      description
        "Total number of IDTs";
    }
  }

  grouping ncs_template_RSVP-MGMT-EVENT-COUNT-INFO {
    description
      "Count of events";
    leaf expired-paths {
      type string;
      description
        "Counter for Expired Path states";
    }
    leaf expired-reservations {
      type string;
      description
        "Counter for Expired Reservation states";
    }
    leaf nac-ks {
      type string;
      description
        "Counter for NACKs received";
    }
  }

  grouping ncs_template_RSVP-MGMT-COUNTERS-OOR {
    description
      "Counters for all messages dropped in OOR
       condition";
    leaf dropped-path-messages {
      type string;
      description
        "Count of Path messages dropped due to an out of
         resource condition";
    }
  }

  grouping ncs_template_RSVP-MGMT-COUNT-PREFIX-INTERFACE-INFO {
    description
      "Prefix filtering interface counters";
    container forwarded {
      description
        "Count of messages which got forwarded";
      uses ncs_template_RSVP-MGMT-COUNT-PREFIX-MSG;
    }
    container locally-destined {
      description
        "Count of locally destined messages";
      uses ncs_template_RSVP-MGMT-COUNT-PREFIX-MSG;
    }
    container dropped {
      description
        "Count of messages dropped";
      uses ncs_template_RSVP-MGMT-COUNT-PREFIX-MSG;
    }
    container default-action-dropped {
      description
        "Count of messages which got dropped due to
         default ACL action";
      uses ncs_template_RSVP-MGMT-COUNT-PREFIX-MSG;
    }
    container default-action-processed {
      description
        "Count of messages which were processed due to
         default ACL action";
      uses ncs_template_RSVP-MGMT-COUNT-PREFIX-MSG;
    }
    container total {
      description
        "Count of total messages";
      uses ncs_template_RSVP-MGMT-COUNT-PREFIX-MSG;
    }
  }

  grouping ncs_template_RSVP-MGMT-COUNT-PREFIX-MSG {
    description
      "Message types for prefix filtering";
    leaf path {
      type string;
      description
        "Count of Path messages";
    }
    leaf path-tear {
      type string;
      description
        "Count of PathTear messages";
    }
    leaf reservation-confirm {
      type string;
      description
        "Count of ReservationConfirm messages";
    }
    leaf total {
      type string;
      description
        "Total count of messages";
    }
  }

  grouping ncs_template_RSVP-MGMT-COUNT-PREFIX-ACL-INFO {
    description
      "Prefix filtering ACL counters";
    container forwarded {
      description
        "Count of messages which got forwarded";
      uses ncs_template_RSVP-MGMT-COUNT-PREFIX-MSG;
    }
    container locally-destined {
      description
        "Count of locally destined messages";
      uses ncs_template_RSVP-MGMT-COUNT-PREFIX-MSG;
    }
    container dropped {
      description
        "Count of messages dropped";
      uses ncs_template_RSVP-MGMT-COUNT-PREFIX-MSG;
    }
    container total {
      description
        "Count of total messages";
      uses ncs_template_RSVP-MGMT-COUNT-PREFIX-MSG;
    }
  }

  grouping ncs_template_RSVP-MGMT-COUNTS {
    description
      "Counters for all known RSVP message types";
    leaf path {
      type string;
      description
        "Count of Path messages";
    }
    leaf reservation {
      type string;
      description
        "Count of Reservation messages";
    }
    leaf path-error {
      type string;
      description
        "Count of PathError messages";
    }
    leaf reservation-error {
      type string;
      description
        "Count of ReservationError messages";
    }
    leaf path-tear {
      type string;
      description
        "Count of PathTear messages";
    }
    leaf reservation-tear {
      type string;
      description
        "Count of ReservationTear messages";
    }
    leaf reservation-confirm {
      type string;
      description
        "Count of ReservationConfirm messages";
    }
    leaf bundle {
      type string;
      description
        "Count of Bundle messages";
    }
    leaf ack {
      type string;
      description
        "Count of ACK messages";
    }
    leaf srefresh {
      type string;
      description
        "Count of Srefresh messages";
    }
    leaf hello {
      type string;
      description
        "Count of Hello messages";
    }
    leaf challenge {
      type string;
      description
        "Count of Integrity Challenge messages";
    }
    leaf response {
      type string;
      description
        "Count of Integrity Response messages";
    }
  }

  grouping ncs_template_RSVP-MGMT-COUNT-MESSAGE {
    description
      "Counters for all messages";
    container received-messages {
      description
        "Count of messages received";
      uses ncs_template_RSVP-MGMT-COUNTS;
    }
    container transmitted-messages {
      description
        "Count of messages transmitted";
      uses ncs_template_RSVP-MGMT-COUNTS;
    }
    container bundle-received-messages {
      description
        "Count of Bundle messages received";
      uses ncs_template_RSVP-MGMT-COUNTS;
    }
    container bundle-transmitted-messages {
      description
        "Count of Bundle messages transmitted";
      uses ncs_template_RSVP-MGMT-COUNTS;
    }
    leaf retransmitted-messages {
      type string;
      description
        "Count of messages retransmitted";
    }
    leaf out-of-order-messages {
      type string;
      description
        "Count of Out of Order messages";
    }
    leaf rate-limited-messages {
      type string;
      description
        "Count of Rate Limited messages";
    }
  }

  grouping ncs_template_RSVP-MGMT-RESERVATION-COMPACT {
    description
      "Compact Form of RSVP Reservation Info";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container flow-spec {
      description
        "Flow Spec Information";
      uses ncs_template_RSVP-MGMT-FLOW-SPEC;
    }
    container generic-flow-spec {
      description
        "Generic Flow Spec Info";
      uses ncs_template_RSVP-MGMT-GEN-FLOW-SPEC;
    }
    container style {
      description
        "RSVP Style";
      uses ncs_template_RSVP-MGMT-STYLE;
    }
    container filter {
      description
        "RSVP Filter";
      uses ncs_template_RSVP-MGMT-FILTER-INFO;
    }
    leaf input-interface {
      type string;
      description
        "Reservation Input Interface";
    }
  }

  grouping ncs_template_RSVP-MGMT-AUTH-RECV-TYPE-COUNTERS {
    description
      "RSVP Authentication Receive Type Counters";
    leaf authentication-received-valid-messages {
      type string;
      description
        "Valid messages";
    }
    leaf authentication-received-challenges-sent {
      type string;
      description
        "Challenges sent";
    }
    leaf authentication-received-challenge-response {
      type string;
      description
        "Challenge responses received";
    }
    leaf authentication-received-challenges-resent {
      type string;
      description
        "Challenges resent";
    }
    leaf authentication-received-challenge-timeouts {
      type string;
      description
        "Challenge timeouts";
    }
    leaf authentication-received-during-challenge {
      type string;
      description
        "Authentication received during challenge";
    }
    leaf authentication-received-incomplete {
      type string;
      description
        "Authentication received incomplete";
    }
    leaf authentication-received-no-integrity {
      type string;
      description
        "Authentication received with no integrity";
    }
    leaf authentication-received-bad-digest {
      type string;
      description
        "Authentication received with bad digest";
    }
    leaf authentication-received-wrong-digest-type {
      type string;
      description
        "Authentication received with wrong digest type";
    }
    leaf authentication-received-sequence-number-duplicate {
      type string;
      description
        "Authentication received with duplicate sequence
         number";
    }
    leaf authentication-received-sequence-number-outof-range {
      type string;
      description
        "Authentication received with sequence number out
         of range";
    }
    leaf authentication-received-wrong-challenges-response {
      type string;
      description
        "Incorect challenge responses received";
    }
    leaf authentication-received-challenges-response-duplicate {
      type string;
      description
        "Duplicate challenge responses received";
    }
    leaf authentication-received-response-late {
      type string;
      description
        "Challenge responses received late";
    }
    leaf authentication-received-bad-message-format {
      type string;
      description
        "Authentication received with bad mesage format";
    }
  }

  grouping ncs_template_RSVP-MGMT-AUTH-DIRECTION-RECV {
    description
      "RSVP Authentication Recieve Type Information";
    container counters {
      description
        "Counters";
      uses ncs_template_RSVP-MGMT-AUTH-RECV-TYPE-COUNTERS;
    }
    leaf sequence {
      type string;
      description
        "Sequence number";
    }
    leaf sequence-window-size {
      type string;
      description
        "Sequence window size";
    }
    leaf sequence-window-count {
      type string;
      description
        "Sequence window count";
    }
    list sequence-window {
      // NCS patched for predictable order
      ordered-by user;
      // NCS drop max-elements statement
      description
        "Sequence window";
      leaf entry {
        type string;
        description
          "Sequence window";
      }
    }
  }

  grouping ncs_template_RSVP-MGMT-AUTH-SEND-TYPE-COUNTERS {
    description
      "RSVP Authentication Send Type Counters";
    leaf authentication-sent {
      type string;
      description
        "Messages sent";
    }
    leaf authentication-failures {
      type string;
      description
        "Failures";
    }
    leaf authentication-send-challenges-received {
      type string;
      description
        "Challenges received";
    }
    leaf authentication-challenge-responses-sent {
      type string;
      description
        "Challenge responses sent";
    }
  }

  grouping ncs_template_RSVP-MGMT-AUTH-DIRECTION-SEND {
    description
      "RSVP Authentication Send Type Information";
    container counters {
      description
        "Counters";
      uses ncs_template_RSVP-MGMT-AUTH-SEND-TYPE-COUNTERS;
    }
    leaf sequence {
      type string;
      description
        "Sequence number";
    }
  }

  grouping ncs_template_RSVP-MGMT-AUTH-DIRECTION {
    description
      "Union of the different RSVP Authentication
       Direction types";
    container send-info {
      // NCS drop when statement
      description
        "send info";
      uses ncs_template_RSVP-MGMT-AUTH-DIRECTION-SEND;
    }
    container receive-info {
      // NCS drop when statement
      description
        "receive info";
      uses ncs_template_RSVP-MGMT-AUTH-DIRECTION-RECV;
    }
    leaf auth-direction {
      type ncs_template_Rsvp-mgmt-auth-direction;
      description
        "AuthDirection";
    }
  }

  grouping ncs_template_RSVP-MGMT-AUTHENTICATION-DETAIL {
    description
      "Authentication Detail Information";
    container auth-compact {
      description
        "Basic authentication data";
      uses ncs_template_RSVP-MGMT-AUTHENTICATION-COMPACT;
    }
    container direction-info {
      description
        "direction info";
      uses ncs_template_RSVP-MGMT-AUTH-DIRECTION;
    }
    leaf key-status {
      type string;
      description
        "Key status";
    }
    leaf key-digest-info {
      type string;
      description
        "Direction";
    }
    leaf lifetime {
      type string;
      units "second";
      description
        "Lifetime (seconds)";
    }
    leaf lifetime-left {
      type string;
      units "second";
      description
        "Remaining lifetime (seconds)";
    }
    leaf challenge-status {
      type ncs_template_Rsvp-mgmt-auth-challenge-status;
      description
        "Challenge status";
    }
  }

  grouping ncs_template_RSVP-MGMT-HELLO-INSTANCE-COMPACT {
    description
      "Compact Info for RSVP Hello Instance";
    leaf source-address-xr {
      type string;
      description
        "Source address";
    }
    leaf destination-address-xr {
      type string;
      description
        "Destination address";
    }
    leaf neighbor-hello-state {
      type ncs_template_Rsvp-mgmt-hello-state;
      description
        "Neighbor Hello state";
    }
    leaf instance-type {
      type ncs_template_Rsvp-mgmt-hello-instance;
      description
        "Hello instance type";
    }
    leaf hello-interface {
      type xr:ncs_template_Interface-name;
      description
        "Interface to use";
    }
    leaf lost-communication-total {
      type string;
      description
        "Total number of times communication got lost";
    }
  }

  grouping ncs_template_RSVP-MGMT-RSB-FLAGS {
    description
      "Reservation State Block Flags";
    leaf is-local-receiver {
      type string;
      description
        "Local Receiver";
    }
    leaf is-message-id-valid {
      type string;
      description
        "MessageID Valid";
    }
    leaf is-local-repair {
      type string;
      description
        "Rerouted";
    }
    leaf is-merge-point {
      type string;
      description
        "Is node a Merge Point";
    }
    leaf is-lockout {
      type string;
      description
        "Locked Out";
    }
  }

  grouping ncs_template_RSVP-MGMT-STYLE {
    description
      "RSVP Reservation Style";
    leaf reservation-type {
      type ncs_template_Rsvp-mgmt-reservation-type-enum;
      description
        "The Reservation Type: WF, SE or FF";
    }
  }

  grouping ncs_template_RSVP-MGMT-FLOW-SPEC-G709-OTN {
    description
      "RSVP G709 OTN FlowSpec Info";
    leaf flow-signal-type {
      type string;
      description
        "G709 OTN Flow Signal Type (Refer G709 v3)";
    }
    leaf flow-nvc {
      type string;
      description
        "G709 OTN Flow NVC";
    }
    leaf flow-multiplier {
      type string;
      description
        "G709 OTN Flow Multiplier";
    }
    leaf flow-bit-rate {
      type string;
      description
        "G709 OTN Flow Bit Rate";
    }
  }

  grouping ncs_template_RSVP-MGMT-GEN-FLOW-SPEC {
    description
      "Union of different RSVP Generic FlowSpec types";
    container g709otn-flow-spec {
      // NCS drop when statement
      description
        "G709 OTN FlowSpec";
      uses ncs_template_RSVP-MGMT-FLOW-SPEC-G709-OTN;
    }
    leaf flow-spec-type {
      type ncs_template_Rsvp-mgmt-flow-spec;
      description
        "FlowSpecType";
    }
  }

  grouping ncs_template_RSVP-MGMT-FLOW-SPEC {
    description
      "RSVP Flow Spec";
    leaf flow-average-rate {
      type string;
      units "byte/s";
      description
        "The Flow Average Rate in bytes per second";
    }
    leaf flow-max-burst {
      type string;
      description
        "The Flow Maximum Burst";
    }
    leaf flow-peak-rate {
      type string;
      units "byte/s";
      description
        "The Flow Peak Rate in bytes per second";
    }
    leaf flow-min-unit {
      type string;
      description
        "The Flow Minimum Unit";
    }
    leaf flow-max-unit {
      type string;
      description
        "The Flow Maximum Unit";
    }
    leaf flow-requested-rate {
      type string;
      units "byte/s";
      description
        "The Flow Requested Rate in bytes per second";
    }
    leaf flow-slack {
      type string;
      description
        "The Flow Slack";
    }
    leaf flow-qos {
      type ncs_template_Rsvp-mgmt-qos-service-enum;
      description
        "The Flow Quality of Service";
    }
  }

  grouping ncs_template_RSVP-MGMT-RESERVATION-DETAIL {
    description
      "Detailed Form of RSVP Reservation Info";
    container flow-spec {
      description
        "Flow Spec Information";
      uses ncs_template_RSVP-MGMT-FLOW-SPEC;
    }
    container generic-flow-spec {
      description
        "Generic Flow Spec Information";
      uses ncs_template_RSVP-MGMT-GEN-FLOW-SPEC;
    }
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container style {
      description
        "RSVP Style";
      uses ncs_template_RSVP-MGMT-STYLE;
    }
    container filter {
      description
        "RSVP Filter";
      uses ncs_template_RSVP-MGMT-FILTER-INFO;
    }
    container rsb-flags {
      description
        "Reservation State Block Flags";
      uses ncs_template_RSVP-MGMT-RSB-FLAGS;
    }
    container hop {
      description
        "Hop Infomation";
      uses ncs_template_RSVP-MGMT-HOP-INFO;
    }
    container policy-sources {
      description
        "RSVP Policy Sources";
      uses ncs_template_RSVP-MGMT-POLICY-SOURCES;
    }
    container header {
      description
        "RSVP Header Information";
      uses ncs_template_RSVP-MGMT-HEADER-INFO;
    }
    container policy-flags {
      description
        "RSVP Policy Flags";
      uses ncs_template_RSVP-MGMT-POLICY-FLAGS;
    }
    container expiry-time {
      description
        "Expiry Time";
      uses ncs_template_RSVP-MGMT-TIMESPEC;
    }
    container policy-query-flags {
      description
        "RSVP Query Flags";
      uses ncs_template_RSVP-MGMT-POLICY-QUERY-FLAGS;
    }
    container label-info {
      description
        "Label Information";
      uses ncs_template_RSVP-MGMT-LABEL-INFO;
    }
    leaf input-adjusted-interface {
      type string;
      description
        "Input Adjusted Interface";
    }
    leaf input-physical-interface {
      type string;
      description
        "Input Physical Interface";
    }
  }

  grouping ncs_template_RSVP-MGMT-FRR-STATE-STATUS-COUNTERS {
    description
      "FRR state counters";
    leaf total {
      type string;
      description
        "Total number of instances of this state";
    }
    leaf active-instances {
      type string;
      description
        "Number of active instances of this state";
    }
    leaf ready-instances {
      type string;
      description
        "Number of ready instances of this state";
    }
    leaf active-wait-instances {
      type string;
      description
        "Number of instances of this state awaiting Path
         messages to be sent out or Resv messages to be
         received";
    }
  }

  grouping ncs_template_RSVP-MGMT-FRR-STATES-COMPACT {
    description
      "Count of RSVP FRR States";
    container path-states {
      description
        "Path state counters";
      uses ncs_template_RSVP-MGMT-FRR-STATE-STATUS-COUNTERS;
    }
    container reservation-states {
      description
        "Rerservation state counters";
      uses ncs_template_RSVP-MGMT-FRR-STATE-STATUS-COUNTERS;
    }
  }

  grouping ncs_template_RSVP-MGMT-MESSAGEID {
    description
      "RSVP Message ID";
    leaf message-id {
      type ncs_template_Rsvp-mgmt-messageid;
      description
        "Message ID";
    }
  }

  grouping ncs_template_RSVP-MGMT-NBOR {
    description
      "Neighbor";
    container expiry-time {
      description
        "Expiry time";
      uses ncs_template_RSVP-MGMT-TIMESPEC;
    }
    leaf is-neighbor-refresh-reduction-capable {
      type string;
      description
        "Is neighbor capable of Refresh Reduction";
    }
    leaf neighbor-address {
      type string;
      description
        "IP address of the neighbor";
    }
    leaf message-ids {
      type string;
      description
        "Number of MessageIDs";
    }
    leaf outgoing-states {
      type string;
      description
        "Number of outgoing states to the neighbour";
    }
    list neighbor-message-id {
      // NCS patched for predictable order
      ordered-by user;
      // NCS drop max-elements statement
      description
        "List of Neighbor MessageIDs";
      uses ncs_template_RSVP-MGMT-MESSAGEID;
    }
  }

  grouping ncs_template_RSVP-MGMT-INTERFACE-FLAGS {
    description
      "Interface related flags";
    leaf is-mpls-enabled {
      type string;
      description
        "MPLS enabled on interface";
    }
    leaf is-refresh-reduction-enabled {
      type string;
      description
        "Refresh Reduction enabled";
    }
    leaf is-pacing-enabled {
      type string;
      description
        "Message pacing enabled";
    }
    leaf is-refresh-enabled {
      type string;
      description
        "Refresh enabled";
    }
    leaf is-s-refresh-enabled {
      type string;
      description
        "Summary Refresh enabled";
    }
    leaf is-interface-down {
      type string;
      description
        "Interface is DOWN";
    }
    leaf is-interface-created {
      type string;
      description
        "Interface is created";
    }
    leaf is-rel-s-refresh-enabled {
      type string;
      description
        "Use reliable xmt for SRefresh";
    }
    leaf is-backup-tunnel {
      type string;
      description
        "This is backup tunnel";
    }
    leaf is-rsvp-configured {
      type string;
      description
        "RSVP explicitly configured";
    }
    leaf is-non-default-vrf {
      type string;
      description
        "Interface is defined in non-Default VRF";
    }
    leaf is-message-bundling-enabled {
      type string;
      description
        "Use bundling for outgoing RSVP messages.";
    }
  }

  grouping ncs_template_RSVP-MGMT-INTERFACE-DETAIL {
    description
      "Detail Form of RSVP interface Info";
    container bandwidth-information {
      description
        "Interface bandwidth information";
      uses ncs_template_RSVP-MGMT-DSTE-MODE-INTERFACE-BW;
    }
    container flags {
      description
        "Interface flags";
      uses ncs_template_RSVP-MGMT-INTERFACE-FLAGS;
    }
    leaf interface-name-xr {
      type string;
      description
        "Interface Name";
    }
    leaf signalling-ip-tos {
      type string;
      description
        "IP TOS (precedence/DSCP) to use in signalling
         messages";
    }
    leaf integrity-send-password {
      type string;
      description
        "Integrity send password";
    }
    leaf integrity-receive-password {
      type string;
      description
        "Integrity receive password";
    }
    leaf integrity-receive-password-optional {
      type string;
      description
        "Integrity recv password optional";
    }
    leaf refresh-timer-state {
      type ncs_template_Rsvp-timer-state;
      description
        "Refresh timer state";
    }
    leaf summary-refresh-timer-state {
      type ncs_template_Rsvp-timer-state;
      description
        "Summary refresh timer state";
    }
    leaf refresh-interval {
      type string;
      units "millisecond";
      description
        "Refresh interval in msecs";
    }
    leaf out-of-band-refresh-interval {
      type string;
      units "millisecond";
      description
        "Out-of-band Refresh interval in msecs";
    }
    leaf summary-refresh-max-size {
      type string;
      units "byte";
      description
        "Max size in bytes of a single SRefresh";
    }
    leaf bundle-message-max-size {
      type string;
      units "byte";
      description
        "Max size in bytes of a single Bundle message";
    }
    leaf expiry-timer-state {
      type ncs_template_Rsvp-timer-state;
      description
        "Expiry timer state";
    }
    leaf expiry-states {
      type string;
      description
        "Number of states for expiry check";
    }
    leaf expiry-interval {
      type string;
      units "millisecond";
      description
        "Expiry interval in msecs";
    }
    leaf expiry-drops-tolerated {
      type string;
      description
        "Number of missed messages tolerated";
    }
    leaf out-of-band-expiry-drops-tolerated {
      type string;
      description
        "Number of out-of-band missed messages tolerated";
    }
    leaf ack-hold-time {
      type string;
      description
        "ACK hold time in msec";
    }
    leaf ack-max-size {
      type string;
      description
        "Max size for ACK message";
    }
    leaf retransmit-time {
      type string;
      description
        "Retransmit time in msec";
    }
    leaf pacing-interval {
      type string;
      units "millisecond";
      description
        "Pacing interval in msecs";
    }
    leaf pacing-message-rate {
      type string;
      description
        "No. of messages per interval";
    }
    leaf pacing-timer-state {
      type ncs_template_Rsvp-timer-state;
      description
        "State of pacing timer";
    }
    leaf pacing-messages {
      type string;
      description
        "Number of messages deferred for pacing";
    }
    list neighbor-array {
      // NCS patched for predictable order
      ordered-by user;
      // NCS drop max-elements statement
      description
        "Neighbor array";
      uses ncs_template_RSVP-MGMT-NBOR;
    }
  }

  grouping ncs_template_RSVP-MGMT-ERO-UNNUM-SUBOBJ {
    description
      "RSVP ERO UNNUM subobject";
    leaf is-strict-route {
      type string;
      description
        "ERO Entry Is Strict";
    }
    leaf ero-interface-id {
      type string;
      description
        "The Interface ID in ERO";
    }
    leaf ero-router-id {
      type string;
      description
        "The Router ID in ERO";
    }
    leaf status {
      type ncs_template_Rsvp-mgmt-ero-subobj-status;
      description
        "Status of ERO";
    }
  }

  grouping ncs_template_RSVP-MGMT-ERO-IPV4-SUBOBJ {
    description
      "RSVP ERO IPV4 subobject";
    leaf is-strict-route {
      type string;
      description
        "ERO Entry Is Strict";
    }
    leaf ero-address {
      type string;
      description
        "The ERO IPV4 Address";
    }
    leaf prefix-length {
      type string;
      description
        "ERO Prefix Length";
    }
  }

  grouping ncs_template_RSVP-MGMT-ERO-SUBOBJ {
    description
      "Union of the different RSVP ERO types";
    container ipv4ero-sub-object {
      // NCS drop when statement
      description
        "IPV4 ERO Sub Object";
      uses ncs_template_RSVP-MGMT-ERO-IPV4-SUBOBJ;
    }
    container unnumbered-ero-sub-object {
      // NCS drop when statement
      description
        "Unnumbered ERO Sub Object";
      uses ncs_template_RSVP-MGMT-ERO-UNNUM-SUBOBJ;
    }
    leaf ero-type {
      type ncs_template_Rsvp-mgmt-ero-subobj;
      description
        "EROType";
    }
  }

  grouping ncs_template_RSVP-MGMT-CT-INFO {
    description
      "Class-Type Information";
    leaf is-class-type-info-valid {
      type string;
      description
        "Is the Class-Type information valid";
    }
    leaf class-type {
      type string;
      description
        "DS-TE Class-Type";
    }
  }

  grouping ncs_template_RSVP-MGMT-GENERALIZED-LABEL {
    description
      "RSVP Generalized Label";
    list value {
      // NCS patched for predictable order
      ordered-by user;
      description
        "Generalized Label Value";
      leaf entry {
        type string;
        description
          "Generalized Label Value";
      }
    }
  }

  grouping ncs_template_RSVP-MGMT-GENERIC-LABEL {
    description
      "Union of different RSVP Generic Label types";
    container generalized-label {
      // NCS drop when statement
      description
        "Generalized Label";
      uses ncs_template_RSVP-MGMT-GENERALIZED-LABEL;
    }
    leaf generic-label-type {
      type ncs_template_Rsvp-mgmt-generic-label;
      description
        "GenericLabelType";
    }
  }

  grouping ncs_template_RSVP-MGMT-LABEL-INFO {
    description
      "Label Information";
    container generic-local-downstream-label {
      description
        "Generic Local Downstream Label";
      uses ncs_template_RSVP-MGMT-GENERIC-LABEL;
    }
    container generic-outgoing-downstream-label {
      description
        "Generic Outgoing Downstream Label";
      uses ncs_template_RSVP-MGMT-GENERIC-LABEL;
    }
    container generic-merge-point-label {
      description
        "Generic MergePoint Label";
      uses ncs_template_RSVP-MGMT-GENERIC-LABEL;
    }
    container generic-outgoing-upstream-label {
      description
        "Generic Outgoing Upstream Label";
      uses ncs_template_RSVP-MGMT-GENERIC-LABEL;
    }
    container generic-local-upstream-label {
      description
        "Generic Local Upstream Label";
      uses ncs_template_RSVP-MGMT-GENERIC-LABEL;
    }
    container generic-recovery-label {
      description
        "Generic Recovery Label";
      uses ncs_template_RSVP-MGMT-GENERIC-LABEL;
    }
    leaf is-valid {
      type string;
      description
        "Is the label information valid";
    }
    leaf local-downstream-label {
      type ncs_template_Rsvp-mgmt-mpls-label;
      description
        "Local Downstream Label";
    }
    leaf outgoing-downstream-label {
      type ncs_template_Rsvp-mgmt-mpls-label;
      description
        "Outgoing Downstream Label";
    }
    leaf merge-point-label {
      type ncs_template_Rsvp-mgmt-mpls-label;
      description
        "MergePoint Label";
    }
    leaf outgoing-upstream-label {
      type ncs_template_Rsvp-mgmt-mpls-label;
      description
        "Outgoing Upstream Label";
    }
    leaf local-upstream-label {
      type ncs_template_Rsvp-mgmt-mpls-label;
      description
        "Local Upstream Label";
    }
    leaf recovery-label {
      type ncs_template_Rsvp-mgmt-mpls-label;
      description
        "Recovery Label";
    }
    leaf lsp-wrap-label {
      type ncs_template_Rsvp-mgmt-mpls-label;
      description
        "LSP Wrap Label";
    }
  }

  grouping ncs_template_RSVP-PATH-FORWARDING-CONTEXT {
    description
      "RSVP Path Forwarding Context";
    container policy-flags {
      description
        "Policy Flags";
      uses ncs_template_RSVP-MGMT-POLICY-FLAGS;
    }
    container policy-query-flags {
      description
        "Policy Query Flags";
      uses ncs_template_RSVP-MGMT-POLICY-QUERY-FLAGS;
    }
    leaf output-interface {
      type string;
      description
        "Output interface";
    }
  }

  grouping ncs_template_RSVP-MGMT-POLICY-QUERY-FLAGS {
    description
      "RSVP Policy Query Flags";
    leaf is-needed {
      type string;
      description
        "Needed";
    }
    leaf is-report-required {
      type string;
      description
        "Report Required";
    }
    leaf is-resync {
      type string;
      description
        "Resynchronization";
    }
    leaf is-bypass {
      type string;
      description
        "Bypass";
    }
  }

  grouping ncs_template_RSVP-MGMT-POLICY-FLAGS {
    description
      "RSVP Policy Flags";
    leaf is-accepted {
      type string;
      description
        "Accepted";
    }
    leaf is-installed {
      type string;
      description
        "Installed";
    }
    leaf is-forwarding {
      type string;
      description
        "Forwarding";
    }
  }

  grouping ncs_template_RSVP-MGMT-TIMESPEC {
    description
      "RSVP Time Spec";
    leaf seconds {
      type string;
      units "second";
      description
        "Time Value in Seconds";
    }
    leaf nanoseconds {
      type string;
      units "nanosecond";
      description
        "Time Value in Nano-seconds";
    }
  }

  grouping ncs_template_RSVP-MGMT-HEADER-INFO {
    description
      "RSVP/IP Header Info";
    leaf rsvp-version {
      type string;
      description
        "RSVP Version";
    }
    leaf rsvp-header-flags {
      type string;
      description
        "RSVP Header Flags (defined in RFC2205 Section 3
         .1.1)";
    }
    leaf rsvp-ttl {
      type string;
      description
        "RSVP TTL";
    }
    leaf rsvp-message-type {
      type string;
      description
        "RSVP Message Type";
    }
    leaf ip-tos {
      type string;
      description
        "IP Type of Service";
    }
    leaf ip-ttl {
      type string;
      description
        "IP TTL";
    }
    leaf ip-source-address {
      type string;
      description
        "IP Source Address";
    }
  }

  grouping ncs_template_RSVP-MGMT-POLICY-SOURCES {
    description
      "RSVP Policy Sources";
    leaf is-te-link {
      type string;
      description
        "Policy Source is TE Link";
    }
    leaf is-local {
      type string;
      description
        "Policy Source is Local";
    }
    leaf is-cops {
      type string;
      description
        "Policy Source is COPS";
    }
    leaf is-default {
      type string;
      description
        "Policy Source is Default";
    }
    leaf is-cable {
      type string;
      description
        "Policy Source is Cable";
    }
  }

  grouping ncs_template_RSVP-MGMT-HOP-INFO {
    description
      "Hop Info";
    leaf neighbor-address {
      type string;
      description
        "IP address of the neighbor";
    }
    leaf neighbor-logical-interface-handle {
      type string;
      description
        "Neighbor Logical Interface Handle";
    }
  }

  grouping ncs_template_RSVP-MGMT-PATH-FLAGS {
    description
      "RSVP Path Flags";
    leaf is-non-rsvp-hop-upstream {
      type string;
      description
        "Non-RSVP Hop Upstream";
    }
    leaf is-local-sender {
      type string;
      description
        "Local Sender";
    }
    leaf is-message-id-valid {
      type string;
      description
        "MessageID Valid";
    }
    leaf is-local-repair {
      type string;
      description
        "Rerouted";
    }
    leaf is-bidirectional {
      type string;
      description
        "Bidirectional";
    }
    leaf is-lockout {
      type string;
      description
        "Locked Out";
    }
  }

  grouping ncs_template_RSVP-MGMT-TSPEC-G709-OTN {
    description
      "RSVP G709 OTN Sender Tspec Info";
    leaf traffic-signal-type {
      type string;
      description
        "G709 OTN Traffic Signal Type (Refer G709 v3)";
    }
    leaf traffic-nvc {
      type string;
      description
        "G709 OTN Traffic NVC";
    }
    leaf traffic-multiplier {
      type string;
      description
        "G709 OTN Traffic Multiplier";
    }
    leaf traffic-bit-rate {
      type string;
      description
        "G709 OTN Traffic Bit Rate";
    }
  }

  grouping ncs_template_RSVP-MGMT-GEN-TRAFFIC-SPEC {
    description
      "Union of different RSVP Generic Sender Tspec
       types";
    container g709otn-tspec {
      // NCS drop when statement
      description
        "G709 OTN Sender Tspec";
      uses ncs_template_RSVP-MGMT-TSPEC-G709-OTN;
    }
    container intsrv-tspec {
      // NCS drop when statement
      description
        "Integrated Services Sender Tspec";
      uses ncs_template_RSVP-MGMT-TRAFFIC-SPEC;
    }
    leaf tspec-type {
      type ncs_template_Rsvp-mgmt-tspec;
      description
        "TspecType";
    }
  }

  grouping ncs_template_RSVP-MGMT-TRAFFIC-SPEC {
    description
      "RSVP Traffic Spec Info";
    leaf traffic-average-rate {
      type string;
      units "byte/s";
      description
        "Traffic Average Rate in bytes per second";
    }
    leaf traffic-max-burst {
      type string;
      description
        "Traffic Maximum Burst";
    }
    leaf traffic-peak-rate {
      type string;
      units "byte/s";
      description
        "Traffic Peak Rate in bytes per second";
    }
    leaf traffic-min-unit {
      type string;
      description
        "Traffic Minimum Unit";
    }
    leaf traffic-max-unit {
      type string;
      description
        "Traffic Maximum Unit";
    }
  }

  grouping ncs_template_RSVP-MGMT-SESSION-ATTRIBUTE-FLAGS {
    description
      "RSVP Session Attribute Flags";
    leaf is-local-protect {
      type string;
      description
        "Local Protection";
    }
    leaf is-node-protect {
      type string;
      description
        "Node Protection";
    }
    leaf is-bandwidth-protect {
      type string;
      description
        "Bandwidth Protection";
    }
    leaf is-record-labels {
      type string;
      description
        "Records Labels";
    }
    leaf is-shared-explicit-requested {
      type string;
      description
        "Shared Explicit Requested";
    }
  }

  grouping ncs_template_RSVP-MGMT-SESSION-ATTRIBUTE {
    description
      "RSVP Session Attributes";
    container sess-attribute-flags {
      description
        "Session Attributes";
      uses ncs_template_RSVP-MGMT-SESSION-ATTRIBUTE-FLAGS;
    }
    leaf setup-priority {
      type string;
      description
        "Setup Priority";
    }
    leaf reservation-priority {
      type string;
      description
        "Reservation Priority";
    }
  }

  grouping ncs_template_RSVP-MGMT-FILTER-P2MP-IPV4 {
    description
      "RSVP P2MP IPv4 FilterSpec";
    leaf source-address {
      type string;
      description
        "Source Address";
    }
    leaf source-port {
      type string;
      description
        "Source Port";
    }
    leaf p2mp-sub-group-origin {
      type string;
      description
        "Point to Multipoint SubGroup Origin";
    }
    leaf sub-group-id {
      type string;
      description
        "Point to Multipoint Subgroup ID";
    }
  }

  grouping ncs_template_RSVP-MGMT-FILTER-IPV4 {
    description
      "RSVP Filter";
    leaf source-address {
      type string;
      description
        "Source Address";
    }
    leaf source-port {
      type string;
      description
        "Source Port";
    }
  }

  grouping ncs_template_RSVP-FILTER-UNION {
    description
      "Union of the different RSVP filterspec types";
    container udp-ipv4-session {
      // NCS drop when statement
      description
        "UDP IPV4 FilterSpec";
      uses ncs_template_RSVP-MGMT-FILTER-IPV4;
    }
    container p2mp-ipv4-session {
      // NCS drop when statement
      description
        "IPv4 P2MP LSP FilterSpec";
      uses ncs_template_RSVP-MGMT-FILTER-P2MP-IPV4;
    }
    leaf filter-type {
      type ncs_template_Rsvp-mgmt-filter;
      description
        "FilterType";
    }
  }

  grouping ncs_template_RSVP-MGMT-FILTER-INFO {
    description
      "RSVP FilterSpec Info";
    container rsvp-filter {
      description
        "RSVP Filter";
      uses ncs_template_RSVP-FILTER-UNION;
    }
  }

  grouping ncs_template_RSVP-MGMT-S2L-SUB-LSP-IPV4 {
    description
      "RSVP S2L Sub-LSP";
    leaf s2l-destination-address {
      type string;
      description
        "S2L Sub-LSP Destination Address";
    }
  }

  grouping ncs_template_RSVP-MGMT-PATH-DETAIL {
    description
      "Detailed Form of RSVP Path Info";
    container session {
      description
        "RSVP Session Information";
      uses ncs_template_RSVP-MGMT-SESSION-INFO;
    }
    container s2l-sub-lsp {
      description
        "RSVP S2L Sub-LSP information";
      uses ncs_template_RSVP-MGMT-S2L-SUB-LSP-IPV4;
    }
    container template {
      description
        "RSVP Template";
      uses ncs_template_RSVP-MGMT-FILTER-INFO;
    }
    container session-attribute {
      description
        "RSVP Session Attribute";
      uses ncs_template_RSVP-MGMT-SESSION-ATTRIBUTE;
    }
    container traffic-spec {
      description
        "RSVP Traffic Spec Info";
      uses ncs_template_RSVP-MGMT-TRAFFIC-SPEC;
    }
    container generic-traffic-spec {
      description
        "RSVP Generic Traffic Spec Info";
      uses ncs_template_RSVP-MGMT-GEN-TRAFFIC-SPEC;
    }
    container path-flags {
      description
        "Path Flags";
      uses ncs_template_RSVP-MGMT-PATH-FLAGS;
    }
    container hop {
      description
        "Path Hop Info";
      uses ncs_template_RSVP-MGMT-HOP-INFO;
    }
    container policy-source-info {
      description
        "Policy Sources Info";
      uses ncs_template_RSVP-MGMT-POLICY-SOURCES;
    }
    container header {
      description
        "RSVP Header Info";
      uses ncs_template_RSVP-MGMT-HEADER-INFO;
    }
    container expiry-time {
      description
        "Expiry Time";
      uses ncs_template_RSVP-MGMT-TIMESPEC;
    }
    container policy-flags {
      description
        "Policy Flags";
      uses ncs_template_RSVP-MGMT-POLICY-FLAGS;
    }
    container policy-query-flags {
      description
        "Policy Query Flags";
      uses ncs_template_RSVP-MGMT-POLICY-QUERY-FLAGS;
    }
    container label-info {
      description
        "Label Information";
      uses ncs_template_RSVP-MGMT-LABEL-INFO;
    }
    container class-type {
      description
        "DS-TE Class-Type";
      uses ncs_template_RSVP-MGMT-CT-INFO;
    }
    leaf input-interface {
      type string;
      description
        "Path Input Interface";
    }
    leaf backup-tunnel-name {
      type string;
      description
        "Path Backup Tunnel";
    }
    leaf is-in-ero-valid {
      type string;
      description
        "Incoming ERO validity";
    }
    leaf is-out-ero-valid {
      type string;
      description
        "Outgoing ERO validity";
    }
    list pfc {
      // NCS patched for predictable order
      ordered-by user;
      description
        "Path Forwarding Contexts";
      uses ncs_template_RSVP-PATH-FORWARDING-CONTEXT;
    }
    list in-ero {
      // NCS patched for predictable order
      ordered-by user;
      description
        "Incoming Explicit Route Sub Objects";
      uses ncs_template_RSVP-MGMT-ERO-SUBOBJ;
    }
    list out-ero {
      // NCS patched for predictable order
      ordered-by user;
      description
        "Outgoing Explicit Route Sub Objects";
      uses ncs_template_RSVP-MGMT-ERO-SUBOBJ;
    }
  }

  grouping ncs_template_RSVP-MGMT-SESSION-P2MP-LSP-TUNNEL-IPV4 {
    description
      "RSVP P2MP-LSP-Tunnel-IPv4 Session";
    leaf p2mp-id {
      type string;
      description
        "The Point to Multipoint ID";
    }
    leaf tunnel-id {
      type string;
      description
        "The Session Tunnel ID";
    }
    leaf extended-tunnel-id {
      type string;
      description
        "The Session Extended Tunnel ID";
    }
  }

  grouping ncs_template_RSVP-MGMT-SESSION-UNI-IPV4 {
    description
      "RSVP UNI IPv4 Session";
    leaf destination-address {
      type string;
      description
        "Destination address";
    }
    leaf tunnel-id {
      type string;
      description
        "The Session Tunnel ID";
    }
    leaf extended-address {
      type string;
      description
        "The Session Extended Address";
    }
  }

  grouping ncs_template_RSVP-MGMT-SESSION-LSP-TUNNEL-IPV4 {
    description
      "RSVP LSP-Tunnel-IPv4 Session";
    leaf destination-address {
      type string;
      description
        "Destination address";
    }
    leaf tunnel-id {
      type string;
      description
        "The Session Tunnel ID";
    }
    leaf extended-tunnel-id {
      type string;
      description
        "The Session Extended Tunnel ID";
    }
  }

  grouping ncs_template_RSVP-MGMT-SESSION-UDP-IPV4 {
    description
      "RSVP UDP IPv4 Session";
    leaf destination-address {
      type string;
      description
        "Destination address";
    }
    leaf protocol {
      type string;
      description
        "Protocol type (originally defined in RFC 790,
         further values in subsequent RFCs)";
    }
    leaf destination-port {
      type string;
      description
        "The Session Destination Port";
    }
  }

  grouping ncs_template_RSVP-SESSION-UNION {
    description
      "Union of the different RSVP session types";
    container ipv4 {
      // NCS drop when statement
      description
        "UDP IPv4 session";
      uses ncs_template_RSVP-MGMT-SESSION-UDP-IPV4;
    }
    container ipv4-lsp-session {
      // NCS drop when statement
      description
        "IPv4 LSP session";
      uses ncs_template_RSVP-MGMT-SESSION-LSP-TUNNEL-IPV4;
    }
    container ipv4-uni-session {
      // NCS drop when statement
      description
        "IPv4 UNI session";
      uses ncs_template_RSVP-MGMT-SESSION-UNI-IPV4;
    }
    container ipv4-p2mp-lsp-session {
      // NCS drop when statement
      description
        "IPv4 P2MP LSP session";
      uses ncs_template_RSVP-MGMT-SESSION-P2MP-LSP-TUNNEL-IPV4;
    }
    leaf session-type {
      type ncs_template_Rsvp-mgmt-session;
      description
        "SessionType";
    }
  }

  grouping ncs_template_RSVP-MGMT-SESSION-INFO {
    description
      "RSVP Session Info";
    container rsvp-session {
      description
        "RSVP Session";
      uses ncs_template_RSVP-SESSION-UNION;
    }
  }

  grouping ncs_template_RSVP-MGMT-SESSION-COMPACT {
    description
      "RSVP Compact Session Info";
    container session {
      description
        "RSVP Session Information";
      uses ncs_template_RSVP-MGMT-SESSION-INFO;
    }
    leaf ps-bs {
      type string;
      description
        "Number of path state block states";
    }
    leaf rs-bs {
      type string;
      description
        "Number of reservation state block states";
    }
    leaf requests {
      type string;
      description
        "Number of request states";
    }
    leaf detail-list-size {
      type string;
      description
        "Number of elements in detail list";
    }
  }

  grouping ncs_template_RSVP-MGMT-AUTHENTICATION-COMPACT {
    description
      "Authentication Compact Information";
    leaf source-address-xr {
      type string;
      description
        "Source address";
    }
    leaf destination-address-xr {
      type string;
      description
        "Destination address";
    }
    leaf neighbor-address {
      type string;
      description
        "Neighbor address";
    }
    leaf direction {
      type ncs_template_Rsvp-mgmt-auth-direction;
      description
        "Direction";
    }
    leaf key-type {
      type ncs_template_Rsvp-mgmt-auth-ki;
      description
        "Key type";
    }
    leaf key-source {
      type string;
      description
        "Key source";
    }
    leaf key-id {
      type string;
      description
        "Key ID";
    }
    leaf key-id-valid {
      type string;
      description
        "Key validity";
    }
  }

  grouping ncs_template_RSVP-MGMT-INTERFACE-BW-STD-DSTE {
    description
      "RSVP interface bandwidth info with standard based
       DSTE enabled";
    leaf allocated-bit-rate {
      type string;
      units "bit/s";
      description
        "Bandwidth (bits per second) now allocated";
    }
    leaf max-flow-bandwidth {
      type string;
      units "bit/s";
      description
        "Max bandwidth (bits per second) allowed per flow";
    }
    leaf max-bandwidth {
      type string;
      units "bit/s";
      description
        "Max bandwidth (bits per second) allowed";
    }
    leaf max-pool0-bandwidth {
      type string;
      units "bit/s";
      description
        "Max bandwidth (bits per second) allowed in BC0
         pool";
    }
    leaf max-pool1-bandwidth {
      type string;
      units "bit/s";
      description
        "Max bandwidth (bits per second) allowed in BC1
         pool";
    }
    leaf is-max-bandwidth-absolute {
      type string;
      description
        "True if the Max B/W is an absolute value and
         false if its a percentage";
    }
    leaf is-max-bc0-bandwidth-absolute {
      type string;
      description
        "True if the Max BC0 B/W is an absolute value and
         false if its a percentage";
    }
    leaf is-max-bc1-bandwidth-absolute {
      type string;
      description
        "True if the Max BC1 sub-pool B/W is an absolute
         value and false if its a percentage";
    }
  }

  grouping ncs_template_RSVP-MGMT-INTERFACE-BW-PRESTD-DSTE {
    description
      "Prestandard DSTE interface bandwidth information";
    leaf allocated-bit-rate {
      type string;
      units "bit/s";
      description
        "Bandwidth (bits per second) now allocated";
    }
    leaf max-flow-bandwidth {
      type string;
      units "bit/s";
      description
        "Max bandwidth (bits per second) allowed per flow";
    }
    leaf max-bandwidth {
      type string;
      units "bit/s";
      description
        "Max bandwidth (bits per second) allowed";
    }
    leaf max-subpool-bandwidth {
      type string;
      units "bit/s";
      description
        "Max bandwidth (bits per second) allowed in
         subpool";
    }
    leaf is-max-bandwidth-absolute {
      type string;
      description
        "True if the Max B/W is an absolute value and
         false if its a percentage";
    }
    leaf is-max-subpool-bandwidth-absolute {
      type string;
      description
        "True if the Max sub-pool B/W is an absolute
         value and false if its a percentage";
    }
  }

  grouping ncs_template_RSVP-MGMT-DSTE-MODE-INTERFACE-BW {
    description
      "Union of the different RSVP interface bandwidth
       types";
    container pre-standard-dste-interface {
      // NCS drop when statement
      description
        "Prestandard DSTE interface information";
      uses ncs_template_RSVP-MGMT-INTERFACE-BW-PRESTD-DSTE;
    }
    container standard-dste-interface {
      // NCS drop when statement
      description
        "Standard DSTE interface information";
      uses ncs_template_RSVP-MGMT-INTERFACE-BW-STD-DSTE;
    }
    leaf dste-mode {
      type ncs_template_Rsvp-mgmt-dste-modes;
      description
        "DSTEMode";
    }
  }

  grouping ncs_template_RSVP-MGMT-INTERFACE-SUMMARY {
    description
      "Summary Form of RSVP interface Info";
    container bandwidth-information {
      description
        "Interface bandwidth information";
      uses ncs_template_RSVP-MGMT-DSTE-MODE-INTERFACE-BW;
    }
    leaf interface-name-xr {
      type string;
      description
        "Interface Name";
    }
    leaf paths-in {
      type string;
      description
        "Number of locally created and incoming path
         states";
    }
    leaf paths-out {
      type string;
      description
        "Number of outgoing path states";
    }
    leaf reservations-in {
      type string;
      description
        "Number of locally created and incoming
         reservation states";
    }
    leaf reservations-out {
      type string;
      description
        "Number of outgoing reservation states";
    }
  }

  grouping ncs_template_RSVP-MGMT-IF-NBR-COMPACT {
    description
      "Compact Info for RSVP Interface Neighbor";
    leaf interface-neighbor-address {
      type string;
      description
        "Interface Neighbor address";
    }
    leaf neighbor-interface-name {
      type xr:ncs_template_Interface-name;
      description
        "Neighbor's Interface handle";
    }
  }

  grouping ncs_template_RSVP-MGMT-NBR-COMPACT {
    description
      "Compact Info for RSVP Neighbor";
    leaf node-address {
      type string;
      description
        "Neighbor node address";
    }
    list interface-neighbor-list-compact {
      // NCS patched for predictable order
      ordered-by user;
      description
        "Compact list of I/F Neighbors";
      uses ncs_template_RSVP-MGMT-IF-NBR-COMPACT;
    }
  }

  grouping ncs_rpc_notif_RSVP-MGMT-RXSB-DETAIL {
    description
      "Detailed Form of RSVP Proxy Reservation";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container style {
      description
        "RSVP Style";
      uses ncs_rpc_notif_RSVP-MGMT-STYLE;
    }
    container filter {
      description
        "RSVP Filter";
      uses ncs_rpc_notif_RSVP-MGMT-FILTER-INFO;
    }
    container flow-spec {
      description
        "Flow Spec Information";
      uses ncs_rpc_notif_RSVP-MGMT-FLOW-SPEC;
    }
    container generic-flow-spec {
      description
        "Generic Flow Spec Information";
      uses ncs_rpc_notif_RSVP-MGMT-GEN-FLOW-SPEC;
    }
    container hop {
      description
        "Path Hop Info";
      uses ncs_rpc_notif_RSVP-MGMT-HOP-INFO;
    }
    container rsvp-header {
      description
        "RSVP Header";
      uses ncs_rpc_notif_RSVP-MGMT-HEADER-INFO;
    }
    leaf input-interface {
      type string;
      description
        "Path Input Interface";
    }
    leaf dynamic-state {
      type uint32;
      description
        "Dynamic State Handle";
    }
  }

  grouping ncs_rpc_notif_RSVP-MGMT-PXSB-DETAIL {
    description
      "Detailed Form of RSVP Proxy Path";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container template {
      description
        "RSVP Template";
      uses ncs_rpc_notif_RSVP-MGMT-FILTER-INFO;
    }
    container traffic-spec {
      description
        "RSVP Traffic Spec Info";
      uses ncs_rpc_notif_RSVP-MGMT-TRAFFIC-SPEC;
    }
    container generic-traffic-spec {
      description
        "RSVP Generic Traffic Spec Info";
      uses ncs_rpc_notif_RSVP-MGMT-GEN-TRAFFIC-SPEC;
    }
    container hop {
      description
        "Path Hop Info";
      uses ncs_rpc_notif_RSVP-MGMT-HOP-INFO;
    }
    container rsvp-header {
      description
        "RSVP Header";
      uses ncs_rpc_notif_RSVP-MGMT-HEADER-INFO;
    }
    leaf input-interface {
      type string;
      description
        "Path Input Interface";
    }
    leaf dynamic-state {
      type uint32;
      description
        "Dynamic State Handle";
    }
  }

  grouping ncs_rpc_notif_RSVP-MGMT-GLBL-BW-POOL-INFO {
    description
      "Global B/W pool information";
    leaf max-res-pool-percent {
      type uint32;
      units "percentage";
      description
        "Maxium reservable I/F percent B/W";
    }
    leaf bc0-percent {
      type uint32;
      units "percentage";
      description
        "BC0 I/F percent B/W";
    }
    leaf bc1-percent {
      type uint32;
      units "percentage";
      description
        "BC1 I/F percent B/W";
    }
    leaf is-max-res-pool-percent-configured {
      type boolean;
      description
        "Is maximum reservable default I/F percent
         configured";
    }
    leaf is-bc0-percent-configured {
      type boolean;
      description
        "Is BC0 default I/F percent configured";
    }
    leaf is-bc1-percent-configured {
      type boolean;
      description
        "Is BC1 default I/F percent configured";
    }
    leaf bandwidth-configuration-model {
      type ncs_rpc_notif_Igpte-lib-bw-model;
      description
        "Bandwith configuration model currently in use
         (MAM/RDM)";
    }
  }

  grouping ncs_rpc_notif_RSVP-MGMT-GLBL-NBR-COMPACT {
    description
      "Compact Info for RSVP Global Neighbor";
    container global-neighbor-flags {
      description
        "Global Neighbor Flags";
      uses ncs_rpc_notif_RSVP-MGMT-GLBL-NBR-FLAGS;
    }
    leaf is-gr-enabled {
      type boolean;
      description
        "Is GR enabled";
    }
    leaf node-address {
      type inet:ipv4-address;
      description
        "Neighbor node address";
    }
    leaf restart-state {
      type ncs_rpc_notif_Rsvp-mgmt-restart-state;
      description
        "Restart state";
    }
    list local-node-address {
      description
        "Local node address";
      leaf entry {
        type inet:ipv4-address;
        description
          "Local node address";
      }
    }
    list neighbor-hello-state {
      description
        "Neighbor Hello state";
      leaf entry {
        type ncs_rpc_notif_Rsvp-mgmt-hello-state;
        description
          "Neighbor Hello state";
      }
    }
    list lost-communication-reason {
      description
        "Reason why communication was lost";
      leaf entry {
        type ncs_rpc_notif_Rsvp-mgmt-hello-down-reason;
        description
          "Reason why communication was lost";
      }
    }
    list lost-communication-total {
      description
        "Total number of times communication got lost";
      leaf entry {
        type uint16;
        description
          "Total number of times communication got lost";
      }
    }
    list up-time {
      description
        "Time hellos have been up";
      uses ncs_rpc_notif_RSVP-MGMT-TIMESPEC;
    }
    list lost-communication-time {
      description
        "Time when communication was lost";
      uses ncs_rpc_notif_RSVP-MGMT-TIMESPEC;
    }
  }

  grouping ncs_rpc_notif_RSVP-MGMT-PATH-COMPACT {
    description
      "Compact Form of RSVP Path Info";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container template {
      description
        "RSVP Template";
      uses ncs_rpc_notif_RSVP-MGMT-FILTER-INFO;
    }
    container session-attribute {
      description
        "RSVP Session Attribute";
      uses ncs_rpc_notif_RSVP-MGMT-SESSION-ATTRIBUTE;
    }
    container traffic-spec {
      description
        "RSVP Traffic Spec Info";
      uses ncs_rpc_notif_RSVP-MGMT-TRAFFIC-SPEC;
    }
    container generic-traffic-spec {
      description
        "RSVP Generic Traffic Spec Info";
      uses ncs_rpc_notif_RSVP-MGMT-GEN-TRAFFIC-SPEC;
    }
    leaf input-interface {
      type string;
      description
        "Path Input Interface";
    }
  }

  grouping ncs_rpc_notif_RSVP-MGMT-GLBL-NBR-FLAGS {
    description
      "Global Neighbor Flags";
    leaf is-application-ouni {
      type boolean;
      description
        "OUNI Application";
    }
    leaf is-application-mpls {
      type boolean;
      description
        "MPLS Application";
    }
  }

  grouping ncs_rpc_notif_RSVP-MGMT-GLBL-NBR-DETAIL {
    description
      "Detail Info for RSVP Global Neighbor";
    container global-neighbor-flags {
      description
        "Global Neighbor Flags";
      uses ncs_rpc_notif_RSVP-MGMT-GLBL-NBR-FLAGS;
    }
    container restart-time-left {
      description
        "How much restart time remains";
      uses ncs_rpc_notif_RSVP-MGMT-TIMESPEC;
    }
    container restart-timer-expiry-time {
      description
        "When will restart timer expire";
      uses ncs_rpc_notif_RSVP-MGMT-TIMESPEC;
    }
    container recovery-time-left {
      description
        "How much recovery timer remains";
      uses ncs_rpc_notif_RSVP-MGMT-TIMESPEC;
    }
    container recovery-timer-exp-time {
      description
        "Time at which recovery timer will expire";
      uses ncs_rpc_notif_RSVP-MGMT-TIMESPEC;
    }
    leaf is-gr-enabled {
      type boolean;
      description
        "Is GR enabled";
    }
    leaf node-address {
      type inet:ipv4-address;
      description
        "Neighbor node address";
    }
    leaf restart-state {
      type ncs_rpc_notif_Rsvp-mgmt-restart-state;
      description
        "Current restart state";
    }
    leaf restart-time {
      type uint32;
      units "millisecond";
      description
        "GR Restart Time (milliseconds)";
    }
    leaf is-restart-timer-running {
      type boolean;
      description
        "Is GR restart timer running";
    }
    leaf recovery-time {
      type uint32;
      units "millisecond";
      description
        "GR Recovery Time (milliseconds)";
    }
    leaf is-recovery-timer-running {
      type boolean;
      description
        "Is RSVP recovery timer running";
    }
    leaf hello-interval {
      type uint32;
      units "millisecond";
      description
        "Hello Interval (milliseconds)";
    }
    leaf missed-hellos {
      type uint8;
      description
        "Hello missed count";
    }
    leaf pending-states {
      type uint32;
      description
        "Number of pending states for this neighbor";
    }
    list local-node-address {
      description
        "Local node address";
      leaf entry {
        type inet:ipv4-address;
        description
          "Local node address";
      }
    }
    list interface-neighbor {
      description
        "Interface Neighbor List";
      leaf entry {
        type inet:ipv4-address;
        description
          "Interface Neighbor List";
      }
    }
    list neighbor-hello-state {
      description
        "Neighbor's hello state";
      leaf entry {
        type ncs_rpc_notif_Rsvp-mgmt-hello-state;
        description
          "Neighbor's hello state";
      }
    }
    list lost-communication-reason {
      description
        "Reason why communication was lost";
      leaf entry {
        type ncs_rpc_notif_Rsvp-mgmt-hello-down-reason;
        description
          "Reason why communication was lost";
      }
    }
    list lost-communication-total {
      description
        "Total number of times communication got lost";
      leaf entry {
        type uint16;
        description
          "Total number of times communication got lost";
      }
    }
    list up-time {
      description
        "Hello up time";
      uses ncs_rpc_notif_RSVP-MGMT-TIMESPEC;
    }
    list lost-communication-time {
      description
        "Time when communication was lost";
      uses ncs_rpc_notif_RSVP-MGMT-TIMESPEC;
    }
  }

  grouping ncs_rpc_notif_RSVP-MGMT-HELLO-INSTANCE-DETAIL {
    description
      "Detail Info for RSVP Hello Instance";
    container up-time {
      description
        "Hello up time";
      uses ncs_rpc_notif_RSVP-MGMT-TIMESPEC;
    }
    container communication-lost-time {
      description
        "Time when communication was lost";
      uses ncs_rpc_notif_RSVP-MGMT-TIMESPEC;
    }
    leaf source-address-xr {
      type inet:ipv4-address;
      description
        "Source address";
    }
    leaf destination-address-xr {
      type inet:ipv4-address;
      description
        "Destination address";
    }
    leaf hello-instance-owner {
      type ncs_rpc_notif_Rsvp-mgmt-hello-instance-owner;
      description
        "Hello instance owner";
    }
    leaf neighbor-hello-state {
      type ncs_rpc_notif_Rsvp-mgmt-hello-state;
      description
        "Neighbor Hello state";
    }
    leaf instance-type {
      type ncs_rpc_notif_Rsvp-mgmt-hello-instance;
      description
        "Hello instance type";
    }
    leaf hello-interface {
      type xr:ncs_rpc_notif_Interface-name;
      description
        "Interface to use";
    }
    leaf hello-interval {
      type uint32;
      description
        "Hello Interval";
    }
    leaf missed-acks-allowed {
      type uint32;
      description
        "Number of missed Hello allowed";
    }
    leaf source-instance {
      type uint32;
      description
        "Source Instance";
    }
    leaf destination-instance {
      type uint32;
      description
        "Destination Instance";
    }
    leaf communication-lost-reason {
      type ncs_rpc_notif_Rsvp-mgmt-hello-down-reason;
      description
        "Reason why communication was lost";
    }
    leaf total-communication-lost {
      type uint16;
      description
        "Total number of times communication got lost";
    }
    leaf communication-lost-hello-missed {
      type uint16;
      description
        "Lost Comm. Hello missed count";
    }
    leaf communication-lost-wrong-source-inst {
      type uint16;
      description
        "Count of lost comm. due to wrong Source Inst";
    }
    leaf communication-lost-wrong-destination-inst {
      type uint16;
      description
        "Count of lost comm. due to wrong Destination
         Inst";
    }
    leaf communication-lost-interface-down {
      type uint16;
      description
        "Count of lost comm. due to interface down";
    }
    leaf communication-lost-neighbor-disabled-hello {
      type uint16;
      description
        "Count of lost comm. due to nbor disabling Hellos";
    }
    leaf hello-messages-sent {
      type uint64;
      description
        "Number of hello messages sent";
    }
    leaf hello-messages-received {
      type uint64;
      description
        "Number of hello messages received";
    }
    leaf hello-request-suppressed {
      type uint64;
      description
        "Count of Hello Requests suppessed";
    }
  }

  grouping ncs_rpc_notif_RSVP-SESSION-RSB-DETAIL {
    description
      "RSVP Detail Session Reservation Info";
    container generic-out-label {
      description
        "Generic Label for outbound traffic";
      uses ncs_rpc_notif_RSVP-MGMT-GENERIC-LABEL;
    }
    container flow-spec {
      description
        "Flow spec object";
      uses ncs_rpc_notif_RSVP-MGMT-FLOW-SPEC;
    }
    container generic-flow-spec {
      description
        "Generic Flow Spec object";
      uses ncs_rpc_notif_RSVP-MGMT-GEN-FLOW-SPEC;
    }
    leaf is-valid {
      type boolean;
      description
        "Entry validity";
    }
    leaf destination-address {
      type inet:ipv4-address;
      description
        "Destination address";
    }
    leaf out-interface {
      type xr:ncs_rpc_notif_Interface-name;
      description
        "Interface on which outbound message was sent";
    }
    leaf out-label {
      type ncs_rpc_notif_Rsvp-mgmt-mpls-label;
      description
        "Label for outbound traffic";
    }
    leaf backup-interface {
      type xr:ncs_rpc_notif_Interface-name;
      description
        "Backup tunnel interface";
    }
    leaf backup-label {
      type ncs_rpc_notif_Rsvp-mgmt-mpls-label;
      description
        "Backup label";
    }
    leaf is-rro-valid {
      type boolean;
      description
        "RRO validity";
    }
    leaf is-flow-spec-valid {
      type boolean;
      description
        "FlowSpec validity";
    }
    list rro {
      description
        "Record route object";
      uses ncs_rpc_notif_RSVP-MGMT-RRO-SUBOBJ;
    }
  }

  grouping ncs_rpc_notif_RSVP-MGMT-REV-LSP-UNSUPPORTED-SUBOBJ {
    description
      "RSVP MGMT REV LSP UNSUPPORTED SUBOBJ";
    list rsvp-mgmt-rev-lsp-unsupported-subobj {
      description
        "rsvp mgmt rev lsp unsupported subobj";
      leaf entry {
        type uint8;
        description
          "rsvp mgmt rev lsp unsupported subobj";
      }
    }
  }

  grouping ncs_rpc_notif_RSVP-MGMT-REVERSE-LSP {
    description
      "RSVP REVERSE_LSP Object";
    container generic-traffic-spec {
      description
        "Generic Traffic Spec object";
      uses ncs_rpc_notif_RSVP-MGMT-GEN-TRAFFIC-SPEC;
    }
    list ero {
      description
        "Explicit Route Sub Objects";
      uses ncs_rpc_notif_RSVP-MGMT-ERO-SUBOBJ;
    }
    list unsup-sub-object {
      description
        "Unsupported REVERSE_LSP Sub Objects";
      uses ncs_rpc_notif_RSVP-MGMT-REV-LSP-UNSUPPORTED-SUBOBJ;
    }
  }

  grouping ncs_rpc_notif_RSVP-MGMT-PROTECTION-LINK-FLAGS {
    description
      "RSVP PROTECTION Object Link Flags";
    leaf enhanced {
      type boolean;
      description
        "Indicates Enhanced Protection Scheme";
    }
    leaf ded1-plus1 {
      type boolean;
      description
        "Dedicated 1+1 Protection";
    }
    leaf ded1-to1 {
      type boolean;
      description
        "Dedicated 1:1 Protection";
    }
    leaf shared {
      type boolean;
      description
        "Shared Link Layer Protection";
    }
    leaf unprotected {
      type boolean;
      description
        "LSP should not use any Link Layer Protection";
    }
    leaf extra-traffic {
      type boolean;
      description
        "LSP should use Links that are protecting other
         (primary) traffic";
    }
    leaf reserved-bit1 {
      type boolean;
      description
        "Reserved Bit 1";
    }
    leaf reserved-bit2 {
      type boolean;
      description
        "Reserved Bit 2";
    }
  }

  grouping ncs_rpc_notif_RSVP-MGMT-PROTECTION-LSP-FLAGS {
    description
      "RSVP PROTECTION Object LSP Flags";
    leaf rerouting {
      type boolean;
      description
        "Full Rerouting";
    }
    leaf rerouting-no-et {
      type boolean;
      description
        "Rerouting Without Extra-Traffic";
    }
    leaf one-to-n-protection-et {
      type boolean;
      description
        "1:N Protection with Extra-Traffic";
    }
    leaf one-plus-one-uni {
      type boolean;
      description
        "1+1 Unidirectional Protection";
    }
    leaf one-plus-one-bi {
      type boolean;
      description
        "1+1 Bidirectional Protection";
    }
  }

  grouping ncs_rpc_notif_RSVP-MGMT-PROTECTION {
    description
      "RSVP PROTECTION Object Info";
    container lsp-flags {
      description
        "PROTECTION Object LSP Flags";
      uses ncs_rpc_notif_RSVP-MGMT-PROTECTION-LSP-FLAGS;
    }
    container link-flags {
      description
        "PROTECTION Object Link Flags";
      uses ncs_rpc_notif_RSVP-MGMT-PROTECTION-LINK-FLAGS;
    }
    leaf s {
      type boolean;
      description
        "Secondary Bit";
    }
    leaf p {
      type boolean;
      description
        "Protecting Bit";
    }
    leaf n {
      type boolean;
      description
        "Notification Bit";
    }
    leaf o {
      type boolean;
      description
        "Operational Bit";
    }
  }

  grouping ncs_rpc_notif_RSVP-MGMT-ASSOCIATION-IPV6-EXT {
    description
      "RSVP EXTENDED ASSOCIATION IPv6 Object Info";
    leaf type {
      type uint16;
      description
        "Association Type (RFC 4872)";
    }
    leaf id {
      type uint16;
      description
        "Association ID";
    }
    leaf source {
      type inet:ipv6-address;
      description
        "Association IPV6 Source Address";
    }
    leaf global-source {
      type uint32;
      description
        "Global Association Source";
    }
    list extended-id {
      description
        "Extended Association ID";
      leaf entry {
        type uint32;
        description
          "Extended Association ID";
      }
    }
  }

  grouping ncs_rpc_notif_RSVP-MGMT-ASSOCIATION-IPV4-EXT {
    description
      "RSVP EXTENDED ASSOCIATION IPv4 Object Info";
    leaf type {
      type uint16;
      description
        "Association Type (RFC 4872)";
    }
    leaf id {
      type uint16;
      description
        "Association ID";
    }
    leaf source {
      type inet:ipv4-address;
      description
        "Association IPV4 Source Address";
    }
    leaf global-source {
      type uint32;
      description
        "Global Association Source";
    }
    list extended-id {
      description
        "Extended Association ID";
      leaf entry {
        type uint32;
        description
          "Extended Association ID";
      }
    }
  }

  grouping ncs_rpc_notif_RSVP-MGMT-ASSOCIATION-IPV6 {
    description
      "RSVP ASSOCIATION IPv6 Object Info";
    leaf type {
      type uint16;
      description
        "Association Type (RFC 4872)";
    }
    leaf id {
      type uint16;
      description
        "Association ID";
    }
    leaf source {
      type inet:ipv6-address;
      description
        "Association IPV6 Source Address";
    }
  }

  grouping ncs_rpc_notif_RSVP-MGMT-ASSOCIATION-IPV4 {
    description
      "RSVP ASSOCIATION IPv4 Object Info";
    leaf type {
      type uint16;
      description
        "Association Type (RFC 4872)";
    }
    leaf id {
      type uint16;
      description
        "Association ID";
    }
    leaf source {
      type inet:ipv4-address;
      description
        "Association IPV4 Source Address";
    }
  }

  grouping ncs_rpc_notif_RSVP-MGMT-ASSOCIATION {
    description
      "Union of the different ASSOCIATION types";
    container ipv4 {
      when "../association-type = 'ipv4'" {
        tailf:xpath-root 3;
        description
          "../AssociationType = 'IPv4'";
      }
      description
        "IPV4 ASSOCIATION Object";
      uses ncs_rpc_notif_RSVP-MGMT-ASSOCIATION-IPV4;
    }
    container ipv6 {
      when "../association-type = 'ipv6'" {
        tailf:xpath-root 3;
        description
          "../AssociationType = 'IPv6'";
      }
      description
        "IPV6 ASSOCIATION Object";
      uses ncs_rpc_notif_RSVP-MGMT-ASSOCIATION-IPV6;
    }
    container extended-ipv4 {
      when "../association-type = 'extended-ipv4'" {
        tailf:xpath-root 3;
        description
          "../AssociationType = 'ExtendedIPv4'";
      }
      description
        "EXTENDED IPV4 ASSOCIATION Object";
      uses ncs_rpc_notif_RSVP-MGMT-ASSOCIATION-IPV4-EXT;
    }
    container extended-ipv6 {
      when "../association-type = 'extended-ipv6'" {
        tailf:xpath-root 3;
        description
          "../AssociationType = 'ExtendedIPv6'";
      }
      description
        "EXTENDED IPV6 ASSOCIATION Object";
      uses ncs_rpc_notif_RSVP-MGMT-ASSOCIATION-IPV6-EXT;
    }
    leaf association-type {
      type ncs_rpc_notif_Rsvp-mgmt-association;
      description
        "AssociationType";
    }
  }

  grouping ncs_rpc_notif_RSVP-MGMT-RRO-SRLG-SUBOBJ {
    description
      "RSVP RRO SRLG subobject";
    list srl-gs {
      description
        "The RRO Subobject SRLGs";
      leaf entry {
        type uint32;
        description
          "The RRO Subobject SRLGs";
      }
    }
  }

  grouping ncs_rpc_notif_RSVP-MGMT-RRO-UNNUMBERED-SUBOBJ-FLAGS {
    description
      "RSVP RRO UNNUMBERED Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping ncs_rpc_notif_RSVP-MGMT-RRO-UNNUMBERED-SUBOBJ {
    description
      "RSVP RRO Unnumbered subobject";
    container flags {
      description
        "The RRO Subobject Unnumbered Flags";
      uses ncs_rpc_notif_RSVP-MGMT-RRO-UNNUMBERED-SUBOBJ-FLAGS;
    }
    leaf interface-address {
      type inet:ipv4-address;
      description
        "The RRO Interface Address";
    }
    leaf interface-id {
      type uint32;
      description
        "The RRO Interface ID";
    }
  }

  grouping ncs_rpc_notif_RSVP-MGMT-RRO-LABEL-SUBOBJ-FLAGS {
    description
      "RSVP RRO Label Subobject Flags";
    leaf is-global-label {
      type boolean;
      description
        "Label is Global across all interfaces";
    }
  }

  grouping ncs_rpc_notif_RSVP-MGMT-RRO-LABEL-SUBOBJ {
    description
      "RSVP RRO Label subobject";
    container flags {
      description
        "The RRO Subobject Label Flags";
      uses ncs_rpc_notif_RSVP-MGMT-RRO-LABEL-SUBOBJ-FLAGS;
    }
    leaf label {
      type uint32;
      description
        "The RRO Subobject Label Value";
    }
    leaf is-label-variable-length {
      type boolean;
      description
        "Is the RRO Subobject Label Variable Length";
    }
    list variable-length-label {
      description
        "The RRO Subobject Variable Length Label";
      leaf entry {
        type uint32;
        description
          "The RRO Subobject Variable Length Label";
      }
    }
  }

  grouping ncs_rpc_notif_RSVP-MGMT-RRO-IPV4-SUBOBJ-FLAGS {
    description
      "RSVP RRO IPV4 Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping ncs_rpc_notif_RSVP-MGMT-RRO-IPV4-SUBOBJ {
    description
      "RSVP RRO IPV4 subobject";
    container flags {
      description
        "The RRO IPV4 Subobject Flags";
      uses ncs_rpc_notif_RSVP-MGMT-RRO-IPV4-SUBOBJ-FLAGS;
    }
    leaf rro-address {
      type inet:ipv4-address;
      description
        "The RRO IPV4 Address";
    }
  }

  grouping ncs_rpc_notif_RSVP-MGMT-RRO-SUBOBJ {
    description
      "Union of the different RSVP RRO types";
    container ipv4rro-sub-object {
      when "../rro-type = 'ipv4rro-type'" {
        tailf:xpath-root 3;
        description
          "../RROType = 'IPv4RROType'";
      }
      description
        "IPV4 RRO Sub Object";
      uses ncs_rpc_notif_RSVP-MGMT-RRO-IPV4-SUBOBJ;
    }
    container label-rro-sub-object {
      when "../rro-type = 'label-rro-type'" {
        tailf:xpath-root 3;
        description
          "../RROType = 'LabelRROType'";
      }
      description
        "Label RRO Sub Object";
      uses ncs_rpc_notif_RSVP-MGMT-RRO-LABEL-SUBOBJ;
    }
    container unnumbered-rro-sub-object {
      when "../rro-type = 'unnumbered-rro-type'" {
        tailf:xpath-root 3;
        description
          "../RROType = 'UnnumberedRROType'";
      }
      description
        "Unnumbered RRO Sub Object";
      uses ncs_rpc_notif_RSVP-MGMT-RRO-UNNUMBERED-SUBOBJ;
    }
    container srlg-rro-sub-object {
      when "../rro-type = 'srlg-rro-type'" {
        tailf:xpath-root 3;
        description
          "../RROType = 'SRLG_RROType'";
      }
      description
        "SRLG RRO Sub Object";
      uses ncs_rpc_notif_RSVP-MGMT-RRO-SRLG-SUBOBJ;
    }
    leaf rro-type {
      type ncs_rpc_notif_Rsvp-mgmt-rro-subobj;
      description
        "RROType";
    }
  }

  grouping ncs_rpc_notif_RSVP-SESSION-PSB-DETAIL {
    description
      "RSVP Detail Session Path Info";
    container generic-in-label {
      description
        "Generic Label for inbound traffic";
      uses ncs_rpc_notif_RSVP-MGMT-GENERIC-LABEL;
    }
    container traffic-spec {
      description
        "Traffic Spec object";
      uses ncs_rpc_notif_RSVP-MGMT-TRAFFIC-SPEC;
    }
    container generic-traffic-spec {
      description
        "Generic Traffic Spec object";
      uses ncs_rpc_notif_RSVP-MGMT-GEN-TRAFFIC-SPEC;
    }
    container association {
      description
        "Association object";
      uses ncs_rpc_notif_RSVP-MGMT-ASSOCIATION;
    }
    container protection {
      description
        "Protection object";
      uses ncs_rpc_notif_RSVP-MGMT-PROTECTION;
    }
    container reverse-lsp {
      description
        "Reverse LSP object";
      uses ncs_rpc_notif_RSVP-MGMT-REVERSE-LSP;
    }
    leaf is-valid {
      type boolean;
      description
        "Entry validity";
    }
    leaf destination-address {
      type inet:ipv4-address;
      description
        "Destination address";
    }
    leaf lsp-id {
      type uint32;
      description
        "LSP ID";
    }
    leaf p2mp-sub-group-origin {
      type inet:ipv4-address;
      description
        "Point to Multipoint SubGroup Origin";
    }
    leaf sub-group-id {
      type uint16;
      description
        "Point to Multipoint Subgroup ID";
    }
    leaf in-interface {
      type xr:ncs_rpc_notif_Interface-name;
      description
        "Interface on which inbound message was received";
    }
    leaf in-label {
      type ncs_rpc_notif_Rsvp-mgmt-mpls-label;
      description
        "Label for inbound traffic";
    }
    leaf lsp-wrap-label {
      type ncs_rpc_notif_Rsvp-mgmt-mpls-label;
      description
        "LSP Wrap Label";
    }
    leaf is-bad-address {
      type boolean;
      description
        "Address validity";
    }
    leaf incoming-interface-address {
      type inet:ipv4-address;
      description
        "IP address of Path's incoming interface";
    }
    leaf is-ero-valid {
      type boolean;
      description
        "ERO validity";
    }
    leaf is-rro-valid {
      type boolean;
      description
        "RRO validity";
    }
    leaf is-traffic-spec-valid {
      type boolean;
      description
        "Traffic Spec validity";
    }
    leaf tunnel-name {
      type string;
      description
        "Tunnel name";
    }
    list ero {
      description
        "Explicit Route Sub Objects";
      uses ncs_rpc_notif_RSVP-MGMT-ERO-SUBOBJ;
    }
    list rro {
      description
        "Record Route Sub Objects";
      uses ncs_rpc_notif_RSVP-MGMT-RRO-SUBOBJ;
    }
  }

  grouping ncs_rpc_notif_RSVP-SESSION-PSB-RSB-DETAIL {
    description
      "List of Path and Reservation Info";
    list psb-info {
      description
        "Path Info";
      uses ncs_rpc_notif_RSVP-SESSION-PSB-DETAIL;
    }
    list rsb-info {
      description
        "Reservation Info";
      uses ncs_rpc_notif_RSVP-SESSION-RSB-DETAIL;
    }
  }

  grouping ncs_rpc_notif_RSVP-MGMT-SESSION-DETAIL {
    description
      "RSVP Detail Session Info";
    container compact {
      description
        "Compact session data";
      uses ncs_rpc_notif_RSVP-MGMT-SESSION-COMPACT;
    }
    container s2l-sub-lsp {
      description
        "RSVP S2L Sub-LSP information";
      uses ncs_rpc_notif_RSVP-MGMT-S2L-SUB-LSP-IPV4;
    }
    list psb-rsb-info {
      description
        "Path and Reservation Info";
      uses ncs_rpc_notif_RSVP-SESSION-PSB-RSB-DETAIL;
    }
  }

  grouping ncs_rpc_notif_RSVP-MGMT-KEY {
    description
      "Key to uniquely identify some RSVP records";
    leaf p2mp-id {
      type uint32;
      description
        "Point-to-multipoint ID";
    }
    leaf destination-address {
      type inet:ipv4-address;
      description
        "Destination address";
    }
    leaf destination-port-or-tunnel-id {
      type uint32;
      description
        "Destination Port or Tunnel ID. For the LSP and
         OUNI session types this represents the Tunnel ID
         whereas for the UDP session type this represents
         the Destination Port";
    }
    leaf protocol {
      type uint32;
      description
        "Protocol. UDP session type this represents the
         Protocol (UDP not supported at present)";
    }
    leaf extended-tunnel-id {
      type inet:ipv4-address;
      description
        "Protocol or Extended Tunnel ID. For the LSP and
         OUNI sesion types this represents the Extended
         Tunnel ID";
    }
    leaf session-type {
      type ncs_rpc_notif_Rsvp-mgmt-session;
      description
        "Session Type (e.g. LSP, OUNI or UDP)";
    }
    leaf source-address {
      type inet:ipv4-address;
      description
        "Source Address";
    }
    leaf source-port-or-lsp-id {
      type uint32;
      description
        "Source Port or LSP_ID. For the LSP and OUNI
         session types this represents the LSP_ID whereas
         for the UDP session type this represents the
         SourcePort";
    }
    leaf p2mp-sub-group-origin {
      type inet:ipv4-address;
      description
        "Point to Multipoint SubGroup Origin";
    }
    leaf sub-group-id {
      type uint16;
      description
        "Point to Multipoint Subgroup ID";
    }
    leaf vrfid {
      type ncs_rpc_notif_Rsi-vrf-id;
      description
        "Signalling VRF ID";
    }
  }

  grouping ncs_rpc_notif_RSVP-MGMT-REQUEST-FLAGS {
    description
      "Request state flags";
    leaf is-local-receiver {
      type boolean;
      description
        "Local Receiver";
    }
    leaf is-refreshing {
      type boolean;
      description
        "Is neighbor refreshing";
    }
    leaf is-send-confirm {
      type boolean;
      description
        "Send Confirm message";
    }
    leaf is-ack-outstanding {
      type boolean;
      description
        "Is ACK message outstanding";
    }
    leaf is-message-id-allocated {
      type boolean;
      description
        "Is MessageID allocated";
    }
    leaf is-nack-received {
      type boolean;
      description
        "A NACK message was received";
    }
    leaf is-retransmit {
      type boolean;
      description
        "Retransmit the message";
    }
    leaf is-paced {
      type boolean;
      description
        "Message is paced";
    }
    leaf is-label-request-in-path {
      type boolean;
      description
        "The Path message contains Label Request";
    }
    leaf is-rro-in-path {
      type boolean;
      description
        "The Path message contains RRO";
    }
    leaf is-record-label-in-path {
      type boolean;
      description
        "Path has Session-Attr object with Record Labels
         set";
    }
    leaf is-merge-point {
      type boolean;
      description
        "Is node a Merge Point";
    }
  }

  grouping ncs_rpc_notif_RSVP-MGMT-REQUEST-DETAIL {
    description
      "Detailed Form of RSVP Request Info";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container flow-spec {
      description
        "Flow Spec Information";
      uses ncs_rpc_notif_RSVP-MGMT-FLOW-SPEC;
    }
    container generic-flow-spec {
      description
        "Generic Flow Spec Information";
      uses ncs_rpc_notif_RSVP-MGMT-GEN-FLOW-SPEC;
    }
    container filter {
      description
        "RSVP Filter";
      uses ncs_rpc_notif_RSVP-MGMT-FILTER-INFO;
    }
    container style {
      description
        "RSVP Style";
      uses ncs_rpc_notif_RSVP-MGMT-STYLE;
    }
    container req-flags {
      description
        "Request flags";
      uses ncs_rpc_notif_RSVP-MGMT-REQUEST-FLAGS;
    }
    container hop {
      description
        "Hop Infomation";
      uses ncs_rpc_notif_RSVP-MGMT-HOP-INFO;
    }
    container header {
      description
        "RSVP Header Information";
      uses ncs_rpc_notif_RSVP-MGMT-HEADER-INFO;
    }
    container policy-sources {
      description
        "RSVP Policy Sources";
      uses ncs_rpc_notif_RSVP-MGMT-POLICY-SOURCES;
    }
    container policy-flags {
      description
        "RSVP Policy Flags";
      uses ncs_rpc_notif_RSVP-MGMT-POLICY-FLAGS;
    }
    container policy-query-flags {
      description
        "RSVP Query Flags";
      uses ncs_rpc_notif_RSVP-MGMT-POLICY-QUERY-FLAGS;
    }
    leaf output-interface {
      type string;
      description
        "output Interface";
    }
    list psb-key {
      description
        "List of RSB keys";
      uses ncs_rpc_notif_RSVP-MGMT-KEY;
    }
    list rsb-key {
      description
        "List of RSB keys";
      uses ncs_rpc_notif_RSVP-MGMT-KEY;
    }
  }

  grouping ncs_rpc_notif_RSVP-MGMT-REQUEST-COMPACT {
    description
      "Compact Form of RSVP Request Info";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container flow-spec {
      description
        "Flow Spec Information";
      uses ncs_rpc_notif_RSVP-MGMT-FLOW-SPEC;
    }
    container generic-flow-spec {
      description
        "Generic Flow Spec Information";
      uses ncs_rpc_notif_RSVP-MGMT-GEN-FLOW-SPEC;
    }
    container filter {
      description
        "RSVP Filter";
      uses ncs_rpc_notif_RSVP-MGMT-FILTER-INFO;
    }
    container style {
      description
        "RSVP Style";
      uses ncs_rpc_notif_RSVP-MGMT-STYLE;
    }
    leaf output-interface {
      type string;
      description
        "Output Interface";
    }
  }

  grouping ncs_rpc_notif_RSVP-MGMT-FRR-STATES-DETAIL {
    description
      "RSVP states for one FRR LSP";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    leaf path-status {
      type ncs_rpc_notif_Rsvp-mgmt-frr-state-enum;
      description
        "RSVP FRR Path States";
    }
    leaf reservation-status {
      type ncs_rpc_notif_Rsvp-mgmt-frr-state-enum;
      description
        "RSVP FRR Reservation States";
    }
  }

  grouping ncs_rpc_notif_RSVP-GLOBAL-INFO {
    description
      "RSVP global information";
    container issu-status {
      description
        "Issu status";
      uses ncs_rpc_notif_RSVP-NSR-ISSU-STATUS-INFO;
    }
    container nsr-status {
      description
        "NSR status";
      uses ncs_rpc_notif_RSVP-NSR-ISSU-STATUS-INFO;
    }
    container database-counters {
      description
        "All database counters";
      uses ncs_rpc_notif_RSVP-MGMT-ALL-DB-COUNTERS;
    }
    leaf interfaces {
      type uint32;
      description
        "Total interfaces";
    }
    leaf ls-ps {
      type uint32;
      description
        "Total LSPs";
    }
  }

  grouping ncs_rpc_notif_RSVP-IDT-STATUS {
    description
      "IDT status information";
    leaf sync-status {
      type ncs_rpc_notif_Rsvp-sync-status;
      description
        "Sync status";
    }
    leaf not-ready-reason {
      type ncs_rpc_notif_Rsvp-proc-nsr-not-ready-reason;
      description
        "Not ready reason";
    }
    leaf idt-start-time {
      type uint32;
      units "second";
      description
        "IDT start timestamp in seconds";
    }
    leaf idt-end-time {
      type uint32;
      units "second";
      description
        "IDT end timestamp in seconds";
    }
    leaf declare-time {
      type uint32;
      units "second";
      description
        "Declare ready timestamp in seconds";
    }
    leaf withdraw-time {
      type uint32;
      units "second";
      description
        "Withdraw ready timestamp in seconds";
    }
  }

  grouping ncs_rpc_notif_RSVP-NSR-ISSU-STATUS-INFO {
    description
      "NSR/ISSU status information";
    container idt-status {
      description
        "IDT status";
      uses ncs_rpc_notif_RSVP-IDT-STATUS;
    }
    container previous-idt-status {
      description
        "Previous IDT status";
      uses ncs_rpc_notif_RSVP-IDT-STATUS;
    }
    leaf role {
      type ncs_rpc_notif_Rsvp-proc-role;
      description
        "Process role";
    }
  }

  grouping ncs_rpc_notif_RSVP-MGMT-IF-NBR-DETAIL {
    description
      "Detail Info for RSVP Interface Neighbor";
    leaf interface-neighbor-address {
      type inet:ipv4-address;
      description
        "Interface Neighbor address";
    }
    leaf neighbor-interface-name {
      type xr:ncs_rpc_notif_Interface-name;
      description
        "Neighbor's Interface handle";
    }
    leaf is-rr-enabled {
      type boolean;
      description
        "Is Neighbor's RR enable";
    }
    leaf neighbor-epoch {
      type uint32;
      description
        "Neighbor's epoch value";
    }
    leaf out-of-order-messages {
      type uint32;
      description
        "Number of out of order msgs";
    }
    leaf retransmitted-messages {
      type uint32;
      description
        "Number of retransmitted msgs";
    }
  }

  grouping ncs_rpc_notif_RSVP-MGMT-NBR-DETAIL {
    description
      "Detail Info for RSVP Neighbor";
    leaf node-address {
      type inet:ipv4-address;
      description
        "Neighbor node address";
    }
    list interface-neighbor-list-detail {
      description
        "Detail list of I/F Neighbors";
      uses ncs_rpc_notif_RSVP-MGMT-IF-NBR-DETAIL;
    }
  }

  grouping ncs_rpc_notif_RSVP-MGMT-HELLO-IF-INSTANCE-DETAIL {
    description
      "Detail Info for IF-based RSVP Hello Instance";
    container last-message-sent-time {
      description
        "Last Ack/msg sent time";
      uses ncs_rpc_notif_RSVP-MGMT-TIMESPEC;
    }
    leaf source-address-xr {
      type inet:ipv4-address;
      description
        "Source address";
    }
    leaf destination-address-xr {
      type inet:ipv4-address;
      description
        "Destination address";
    }
    leaf hello-global-neighbor-id {
      type inet:ipv4-address;
      description
        "Global Neighbor ID";
    }
    leaf instance-type {
      type ncs_rpc_notif_Rsvp-mgmt-hello-instance;
      description
        "Hello instance type";
    }
    leaf hello-interface {
      type xr:ncs_rpc_notif_Interface-name;
      description
        "Interface to use";
    }
    leaf source-instance {
      type uint32;
      description
        "Source Instance";
    }
    leaf destination-instance {
      type uint32;
      description
        "Destination Instance";
    }
    leaf hello-messages-sent {
      type uint64;
      description
        "Number of hello messages sent";
    }
    leaf hello-messages-received {
      type uint64;
      description
        "Number of hello messages received";
    }
  }

  grouping ncs_rpc_notif_RSVP-MGMT-HELLO-IF-INSTANCE-COMPACT {
    description
      "Compact Info for IF-based RSVP Hello Instance";
    leaf source-address-xr {
      type inet:ipv4-address;
      description
        "Source address";
    }
    leaf destination-address-xr {
      type inet:ipv4-address;
      description
        "Destination address";
    }
    leaf instance-type {
      type ncs_rpc_notif_Rsvp-mgmt-hello-instance;
      description
        "Hello instance type";
    }
    leaf hello-interface {
      type xr:ncs_rpc_notif_Interface-name;
      description
        "Interface to use";
    }
  }

  grouping ncs_rpc_notif_RSVP-MGMT-LOCAL-NODE-ID-IPV4 {
    description
      "Local Node-id";
    leaf local-node-ip-address {
      type inet:ipv4-address;
      description
        "Local node address";
    }
    leaf application-type {
      type ncs_rpc_notif_Rsvp-mgmt-gr-app;
      description
        "GR local node-id app type";
    }
  }

  grouping ncs_rpc_notif_RSVP-MGMT-GRACEFUL-RESTART {
    description
      "RSVP Graceful Restart Info";
    container recovery-time-left {
      description
        "How much recovery timer remains";
      uses ncs_rpc_notif_RSVP-MGMT-TIMESPEC;
    }
    container recovery-timer-exp-time {
      description
        "Time at which recovery timer will expire";
      uses ncs_rpc_notif_RSVP-MGMT-TIMESPEC;
    }
    leaf is-gr-enabled {
      type boolean;
      description
        "Whether GR is enabled";
    }
    leaf global-neighbors {
      type uint32;
      description
        "Global neighbor count";
    }
    leaf restart-time {
      type uint32;
      units "millisecond";
      description
        "Restart time (milliseconds)";
    }
    leaf recovery-time {
      type uint32;
      units "millisecond";
      description
        "Recovery time (milliseconds)";
    }
    leaf is-recovery-timer-running {
      type boolean;
      description
        "Whether recovery timer is running";
    }
    leaf hello-interval {
      type uint32;
      description
        "Interval at which hello messages are sent";
    }
    leaf missed-hellos {
      type uint8;
      description
        "Max number of hellos missed before hellos
         declared down";
    }
    leaf pending-states {
      type uint32;
      description
        "Total number of pending states";
    }
    list local-node-address {
      description
        "Local node address";
      uses ncs_rpc_notif_RSVP-MGMT-LOCAL-NODE-ID-IPV4;
    }
  }

  grouping ncs_rpc_notif_RSVP-MGMT-INTERFACE-COMPACT {
    description
      "Compact Form of RSVP interface Info";
    container bandwidth-information {
      description
        "Interface bandwidth information";
      uses ncs_rpc_notif_RSVP-MGMT-DSTE-MODE-INTERFACE-BW;
    }
    leaf interface-name-xr {
      type string;
      description
        "Interface Name";
    }
  }

  grouping ncs_rpc_notif_RSVP-MGMT-ALL-DB-COUNTERS {
    description
      "All database counters";
    leaf sessions {
      type uint32;
      description
        "Number of sessions";
    }
    leaf incoming-paths {
      type uint32;
      description
        "Number of locally created and incoming path
         states";
    }
    leaf outgoing-paths {
      type uint32;
      description
        "Number of outgoing path states";
    }
    leaf incoming-reservations {
      type uint32;
      description
        "Number of locally created and incoming
         reservation states";
    }
    leaf outgoing-reservations {
      type uint32;
      description
        "Number of outgoing reservation states";
    }
    leaf interfaces {
      type uint32;
      description
        "Number of Interfaces";
    }
  }

  grouping ncs_rpc_notif_RSVP-SYNC-COUNT-INFO {
    description
      "RSVP sync sent and received counters information";
    leaf last-cleared-timestamp {
      type uint32;
      units "second";
      description
        "The timestamp, in seconds, when these statistics
         are cleared              since 00:00:00 UTC,
         January 1, 1970";
    }
    leaf rsvp-process-role {
      type ncs_rpc_notif_Rsvp-proc-role;
      description
        "Process role";
    }
    leaf last-idt-states {
      type uint32;
      description
        "Last IDT number of states";
    }
    leaf total-states {
      type uint32;
      description
        "Total number of states";
    }
    leaf total-deletions {
      type uint32;
      description
        "Total number of deletions";
    }
    leaf total-nacks {
      type uint64;
      description
        "Total number of NACKs";
    }
    leaf total-id-ts {
      type uint32;
      description
        "Total number of IDTs";
    }
  }

  grouping ncs_rpc_notif_RSVP-MGMT-EVENT-COUNT-INFO {
    description
      "Count of events";
    leaf expired-paths {
      type uint32;
      description
        "Counter for Expired Path states";
    }
    leaf expired-reservations {
      type uint32;
      description
        "Counter for Expired Reservation states";
    }
    leaf nac-ks {
      type uint32;
      description
        "Counter for NACKs received";
    }
  }

  grouping ncs_rpc_notif_RSVP-MGMT-COUNTERS-OOR {
    description
      "Counters for all messages dropped in OOR
       condition";
    leaf dropped-path-messages {
      type uint32;
      description
        "Count of Path messages dropped due to an out of
         resource condition";
    }
  }

  grouping ncs_rpc_notif_RSVP-MGMT-COUNT-PREFIX-INTERFACE-INFO {
    description
      "Prefix filtering interface counters";
    container forwarded {
      description
        "Count of messages which got forwarded";
      uses ncs_rpc_notif_RSVP-MGMT-COUNT-PREFIX-MSG;
    }
    container locally-destined {
      description
        "Count of locally destined messages";
      uses ncs_rpc_notif_RSVP-MGMT-COUNT-PREFIX-MSG;
    }
    container dropped {
      description
        "Count of messages dropped";
      uses ncs_rpc_notif_RSVP-MGMT-COUNT-PREFIX-MSG;
    }
    container default-action-dropped {
      description
        "Count of messages which got dropped due to
         default ACL action";
      uses ncs_rpc_notif_RSVP-MGMT-COUNT-PREFIX-MSG;
    }
    container default-action-processed {
      description
        "Count of messages which were processed due to
         default ACL action";
      uses ncs_rpc_notif_RSVP-MGMT-COUNT-PREFIX-MSG;
    }
    container total {
      description
        "Count of total messages";
      uses ncs_rpc_notif_RSVP-MGMT-COUNT-PREFIX-MSG;
    }
  }

  grouping ncs_rpc_notif_RSVP-MGMT-COUNT-PREFIX-MSG {
    description
      "Message types for prefix filtering";
    leaf path {
      type uint32;
      description
        "Count of Path messages";
    }
    leaf path-tear {
      type uint32;
      description
        "Count of PathTear messages";
    }
    leaf reservation-confirm {
      type uint32;
      description
        "Count of ReservationConfirm messages";
    }
    leaf total {
      type uint32;
      description
        "Total count of messages";
    }
  }

  grouping ncs_rpc_notif_RSVP-MGMT-COUNT-PREFIX-ACL-INFO {
    description
      "Prefix filtering ACL counters";
    container forwarded {
      description
        "Count of messages which got forwarded";
      uses ncs_rpc_notif_RSVP-MGMT-COUNT-PREFIX-MSG;
    }
    container locally-destined {
      description
        "Count of locally destined messages";
      uses ncs_rpc_notif_RSVP-MGMT-COUNT-PREFIX-MSG;
    }
    container dropped {
      description
        "Count of messages dropped";
      uses ncs_rpc_notif_RSVP-MGMT-COUNT-PREFIX-MSG;
    }
    container total {
      description
        "Count of total messages";
      uses ncs_rpc_notif_RSVP-MGMT-COUNT-PREFIX-MSG;
    }
  }

  grouping ncs_rpc_notif_RSVP-MGMT-COUNTS {
    description
      "Counters for all known RSVP message types";
    leaf path {
      type uint32;
      description
        "Count of Path messages";
    }
    leaf reservation {
      type uint32;
      description
        "Count of Reservation messages";
    }
    leaf path-error {
      type uint32;
      description
        "Count of PathError messages";
    }
    leaf reservation-error {
      type uint32;
      description
        "Count of ReservationError messages";
    }
    leaf path-tear {
      type uint32;
      description
        "Count of PathTear messages";
    }
    leaf reservation-tear {
      type uint32;
      description
        "Count of ReservationTear messages";
    }
    leaf reservation-confirm {
      type uint32;
      description
        "Count of ReservationConfirm messages";
    }
    leaf bundle {
      type uint32;
      description
        "Count of Bundle messages";
    }
    leaf ack {
      type uint32;
      description
        "Count of ACK messages";
    }
    leaf srefresh {
      type uint32;
      description
        "Count of Srefresh messages";
    }
    leaf hello {
      type uint32;
      description
        "Count of Hello messages";
    }
    leaf challenge {
      type uint32;
      description
        "Count of Integrity Challenge messages";
    }
    leaf response {
      type uint32;
      description
        "Count of Integrity Response messages";
    }
  }

  grouping ncs_rpc_notif_RSVP-MGMT-COUNT-MESSAGE {
    description
      "Counters for all messages";
    container received-messages {
      description
        "Count of messages received";
      uses ncs_rpc_notif_RSVP-MGMT-COUNTS;
    }
    container transmitted-messages {
      description
        "Count of messages transmitted";
      uses ncs_rpc_notif_RSVP-MGMT-COUNTS;
    }
    container bundle-received-messages {
      description
        "Count of Bundle messages received";
      uses ncs_rpc_notif_RSVP-MGMT-COUNTS;
    }
    container bundle-transmitted-messages {
      description
        "Count of Bundle messages transmitted";
      uses ncs_rpc_notif_RSVP-MGMT-COUNTS;
    }
    leaf retransmitted-messages {
      type uint32;
      description
        "Count of messages retransmitted";
    }
    leaf out-of-order-messages {
      type uint32;
      description
        "Count of Out of Order messages";
    }
    leaf rate-limited-messages {
      type uint32;
      description
        "Count of Rate Limited messages";
    }
  }

  grouping ncs_rpc_notif_RSVP-MGMT-RESERVATION-COMPACT {
    description
      "Compact Form of RSVP Reservation Info";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container flow-spec {
      description
        "Flow Spec Information";
      uses ncs_rpc_notif_RSVP-MGMT-FLOW-SPEC;
    }
    container generic-flow-spec {
      description
        "Generic Flow Spec Info";
      uses ncs_rpc_notif_RSVP-MGMT-GEN-FLOW-SPEC;
    }
    container style {
      description
        "RSVP Style";
      uses ncs_rpc_notif_RSVP-MGMT-STYLE;
    }
    container filter {
      description
        "RSVP Filter";
      uses ncs_rpc_notif_RSVP-MGMT-FILTER-INFO;
    }
    leaf input-interface {
      type string;
      description
        "Reservation Input Interface";
    }
  }

  grouping ncs_rpc_notif_RSVP-MGMT-AUTH-RECV-TYPE-COUNTERS {
    description
      "RSVP Authentication Receive Type Counters";
    leaf authentication-received-valid-messages {
      type uint32;
      description
        "Valid messages";
    }
    leaf authentication-received-challenges-sent {
      type uint32;
      description
        "Challenges sent";
    }
    leaf authentication-received-challenge-response {
      type uint32;
      description
        "Challenge responses received";
    }
    leaf authentication-received-challenges-resent {
      type uint32;
      description
        "Challenges resent";
    }
    leaf authentication-received-challenge-timeouts {
      type uint32;
      description
        "Challenge timeouts";
    }
    leaf authentication-received-during-challenge {
      type uint32;
      description
        "Authentication received during challenge";
    }
    leaf authentication-received-incomplete {
      type uint32;
      description
        "Authentication received incomplete";
    }
    leaf authentication-received-no-integrity {
      type uint32;
      description
        "Authentication received with no integrity";
    }
    leaf authentication-received-bad-digest {
      type uint32;
      description
        "Authentication received with bad digest";
    }
    leaf authentication-received-wrong-digest-type {
      type uint32;
      description
        "Authentication received with wrong digest type";
    }
    leaf authentication-received-sequence-number-duplicate {
      type uint32;
      description
        "Authentication received with duplicate sequence
         number";
    }
    leaf authentication-received-sequence-number-outof-range {
      type uint32;
      description
        "Authentication received with sequence number out
         of range";
    }
    leaf authentication-received-wrong-challenges-response {
      type uint32;
      description
        "Incorect challenge responses received";
    }
    leaf authentication-received-challenges-response-duplicate {
      type uint32;
      description
        "Duplicate challenge responses received";
    }
    leaf authentication-received-response-late {
      type uint32;
      description
        "Challenge responses received late";
    }
    leaf authentication-received-bad-message-format {
      type uint32;
      description
        "Authentication received with bad mesage format";
    }
  }

  grouping ncs_rpc_notif_RSVP-MGMT-AUTH-DIRECTION-RECV {
    description
      "RSVP Authentication Recieve Type Information";
    container counters {
      description
        "Counters";
      uses ncs_rpc_notif_RSVP-MGMT-AUTH-RECV-TYPE-COUNTERS;
    }
    leaf sequence {
      type uint64;
      description
        "Sequence number";
    }
    leaf sequence-window-size {
      type uint32;
      description
        "Sequence window size";
    }
    leaf sequence-window-count {
      type uint32;
      description
        "Sequence window count";
    }
    list sequence-window {
      max-elements 64;
      description
        "Sequence window";
      leaf entry {
        type uint64;
        description
          "Sequence window";
      }
    }
  }

  grouping ncs_rpc_notif_RSVP-MGMT-AUTH-SEND-TYPE-COUNTERS {
    description
      "RSVP Authentication Send Type Counters";
    leaf authentication-sent {
      type uint32;
      description
        "Messages sent";
    }
    leaf authentication-failures {
      type uint32;
      description
        "Failures";
    }
    leaf authentication-send-challenges-received {
      type uint32;
      description
        "Challenges received";
    }
    leaf authentication-challenge-responses-sent {
      type uint32;
      description
        "Challenge responses sent";
    }
  }

  grouping ncs_rpc_notif_RSVP-MGMT-AUTH-DIRECTION-SEND {
    description
      "RSVP Authentication Send Type Information";
    container counters {
      description
        "Counters";
      uses ncs_rpc_notif_RSVP-MGMT-AUTH-SEND-TYPE-COUNTERS;
    }
    leaf sequence {
      type uint64;
      description
        "Sequence number";
    }
  }

  grouping ncs_rpc_notif_RSVP-MGMT-AUTH-DIRECTION {
    description
      "Union of the different RSVP Authentication
       Direction types";
    container send-info {
      when "../auth-direction = 'rsvp-mgmt-auth-direction-send'" {
        tailf:xpath-root 3;
        description
          "../AuthDirection = 'RSVPMgmtAuthDirectionSend'";
      }
      description
        "send info";
      uses ncs_rpc_notif_RSVP-MGMT-AUTH-DIRECTION-SEND;
    }
    container receive-info {
      when "../auth-direction = 'rsvp-mgmt-auth-direction-recv'" {
        tailf:xpath-root 3;
        description
          "../AuthDirection = 'RSVPMgmtAuthDirectionRecv'";
      }
      description
        "receive info";
      uses ncs_rpc_notif_RSVP-MGMT-AUTH-DIRECTION-RECV;
    }
    leaf auth-direction {
      type ncs_rpc_notif_Rsvp-mgmt-auth-direction;
      description
        "AuthDirection";
    }
  }

  grouping ncs_rpc_notif_RSVP-MGMT-AUTHENTICATION-DETAIL {
    description
      "Authentication Detail Information";
    container auth-compact {
      description
        "Basic authentication data";
      uses ncs_rpc_notif_RSVP-MGMT-AUTHENTICATION-COMPACT;
    }
    container direction-info {
      description
        "direction info";
      uses ncs_rpc_notif_RSVP-MGMT-AUTH-DIRECTION;
    }
    leaf key-status {
      type uint32;
      description
        "Key status";
    }
    leaf key-digest-info {
      type uint32;
      description
        "Direction";
    }
    leaf lifetime {
      type uint32;
      units "second";
      description
        "Lifetime (seconds)";
    }
    leaf lifetime-left {
      type uint32;
      units "second";
      description
        "Remaining lifetime (seconds)";
    }
    leaf challenge-status {
      type ncs_rpc_notif_Rsvp-mgmt-auth-challenge-status;
      description
        "Challenge status";
    }
  }

  grouping ncs_rpc_notif_RSVP-MGMT-HELLO-INSTANCE-COMPACT {
    description
      "Compact Info for RSVP Hello Instance";
    leaf source-address-xr {
      type inet:ipv4-address;
      description
        "Source address";
    }
    leaf destination-address-xr {
      type inet:ipv4-address;
      description
        "Destination address";
    }
    leaf neighbor-hello-state {
      type ncs_rpc_notif_Rsvp-mgmt-hello-state;
      description
        "Neighbor Hello state";
    }
    leaf instance-type {
      type ncs_rpc_notif_Rsvp-mgmt-hello-instance;
      description
        "Hello instance type";
    }
    leaf hello-interface {
      type xr:ncs_rpc_notif_Interface-name;
      description
        "Interface to use";
    }
    leaf lost-communication-total {
      type uint16;
      description
        "Total number of times communication got lost";
    }
  }

  grouping ncs_rpc_notif_RSVP-MGMT-RSB-FLAGS {
    description
      "Reservation State Block Flags";
    leaf is-local-receiver {
      type boolean;
      description
        "Local Receiver";
    }
    leaf is-message-id-valid {
      type boolean;
      description
        "MessageID Valid";
    }
    leaf is-local-repair {
      type boolean;
      description
        "Rerouted";
    }
    leaf is-merge-point {
      type boolean;
      description
        "Is node a Merge Point";
    }
    leaf is-lockout {
      type boolean;
      description
        "Locked Out";
    }
  }

  grouping ncs_rpc_notif_RSVP-MGMT-STYLE {
    description
      "RSVP Reservation Style";
    leaf reservation-type {
      type ncs_rpc_notif_Rsvp-mgmt-reservation-type-enum;
      description
        "The Reservation Type: WF, SE or FF";
    }
  }

  grouping ncs_rpc_notif_RSVP-MGMT-FLOW-SPEC-G709-OTN {
    description
      "RSVP G709 OTN FlowSpec Info";
    leaf flow-signal-type {
      type uint8;
      description
        "G709 OTN Flow Signal Type (Refer G709 v3)";
    }
    leaf flow-nvc {
      type uint16;
      description
        "G709 OTN Flow NVC";
    }
    leaf flow-multiplier {
      type uint16;
      description
        "G709 OTN Flow Multiplier";
    }
    leaf flow-bit-rate {
      type uint64;
      description
        "G709 OTN Flow Bit Rate";
    }
  }

  grouping ncs_rpc_notif_RSVP-MGMT-GEN-FLOW-SPEC {
    description
      "Union of different RSVP Generic FlowSpec types";
    container g709otn-flow-spec {
      when "../flow-spec-type = 'g709otn'" {
        tailf:xpath-root 3;
        description
          "../FlowSpecType = 'G709OTN'";
      }
      description
        "G709 OTN FlowSpec";
      uses ncs_rpc_notif_RSVP-MGMT-FLOW-SPEC-G709-OTN;
    }
    leaf flow-spec-type {
      type ncs_rpc_notif_Rsvp-mgmt-flow-spec;
      description
        "FlowSpecType";
    }
  }

  grouping ncs_rpc_notif_RSVP-MGMT-FLOW-SPEC {
    description
      "RSVP Flow Spec";
    leaf flow-average-rate {
      type uint64;
      units "byte/s";
      description
        "The Flow Average Rate in bytes per second";
    }
    leaf flow-max-burst {
      type uint64;
      description
        "The Flow Maximum Burst";
    }
    leaf flow-peak-rate {
      type uint64;
      units "byte/s";
      description
        "The Flow Peak Rate in bytes per second";
    }
    leaf flow-min-unit {
      type uint32;
      description
        "The Flow Minimum Unit";
    }
    leaf flow-max-unit {
      type uint32;
      description
        "The Flow Maximum Unit";
    }
    leaf flow-requested-rate {
      type uint64;
      units "byte/s";
      description
        "The Flow Requested Rate in bytes per second";
    }
    leaf flow-slack {
      type uint32;
      description
        "The Flow Slack";
    }
    leaf flow-qos {
      type ncs_rpc_notif_Rsvp-mgmt-qos-service-enum;
      description
        "The Flow Quality of Service";
    }
  }

  grouping ncs_rpc_notif_RSVP-MGMT-RESERVATION-DETAIL {
    description
      "Detailed Form of RSVP Reservation Info";
    container flow-spec {
      description
        "Flow Spec Information";
      uses ncs_rpc_notif_RSVP-MGMT-FLOW-SPEC;
    }
    container generic-flow-spec {
      description
        "Generic Flow Spec Information";
      uses ncs_rpc_notif_RSVP-MGMT-GEN-FLOW-SPEC;
    }
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container style {
      description
        "RSVP Style";
      uses ncs_rpc_notif_RSVP-MGMT-STYLE;
    }
    container filter {
      description
        "RSVP Filter";
      uses ncs_rpc_notif_RSVP-MGMT-FILTER-INFO;
    }
    container rsb-flags {
      description
        "Reservation State Block Flags";
      uses ncs_rpc_notif_RSVP-MGMT-RSB-FLAGS;
    }
    container hop {
      description
        "Hop Infomation";
      uses ncs_rpc_notif_RSVP-MGMT-HOP-INFO;
    }
    container policy-sources {
      description
        "RSVP Policy Sources";
      uses ncs_rpc_notif_RSVP-MGMT-POLICY-SOURCES;
    }
    container header {
      description
        "RSVP Header Information";
      uses ncs_rpc_notif_RSVP-MGMT-HEADER-INFO;
    }
    container policy-flags {
      description
        "RSVP Policy Flags";
      uses ncs_rpc_notif_RSVP-MGMT-POLICY-FLAGS;
    }
    container expiry-time {
      description
        "Expiry Time";
      uses ncs_rpc_notif_RSVP-MGMT-TIMESPEC;
    }
    container policy-query-flags {
      description
        "RSVP Query Flags";
      uses ncs_rpc_notif_RSVP-MGMT-POLICY-QUERY-FLAGS;
    }
    container label-info {
      description
        "Label Information";
      uses ncs_rpc_notif_RSVP-MGMT-LABEL-INFO;
    }
    leaf input-adjusted-interface {
      type string;
      description
        "Input Adjusted Interface";
    }
    leaf input-physical-interface {
      type string;
      description
        "Input Physical Interface";
    }
  }

  grouping ncs_rpc_notif_RSVP-MGMT-FRR-STATE-STATUS-COUNTERS {
    description
      "FRR state counters";
    leaf total {
      type uint32;
      description
        "Total number of instances of this state";
    }
    leaf active-instances {
      type uint32;
      description
        "Number of active instances of this state";
    }
    leaf ready-instances {
      type uint32;
      description
        "Number of ready instances of this state";
    }
    leaf active-wait-instances {
      type uint32;
      description
        "Number of instances of this state awaiting Path
         messages to be sent out or Resv messages to be
         received";
    }
  }

  grouping ncs_rpc_notif_RSVP-MGMT-FRR-STATES-COMPACT {
    description
      "Count of RSVP FRR States";
    container path-states {
      description
        "Path state counters";
      uses ncs_rpc_notif_RSVP-MGMT-FRR-STATE-STATUS-COUNTERS;
    }
    container reservation-states {
      description
        "Rerservation state counters";
      uses ncs_rpc_notif_RSVP-MGMT-FRR-STATE-STATUS-COUNTERS;
    }
  }

  grouping ncs_rpc_notif_RSVP-MGMT-MESSAGEID {
    description
      "RSVP Message ID";
    leaf message-id {
      type ncs_rpc_notif_Rsvp-mgmt-messageid;
      description
        "Message ID";
    }
  }

  grouping ncs_rpc_notif_RSVP-MGMT-NBOR {
    description
      "Neighbor";
    container expiry-time {
      description
        "Expiry time";
      uses ncs_rpc_notif_RSVP-MGMT-TIMESPEC;
    }
    leaf is-neighbor-refresh-reduction-capable {
      type boolean;
      description
        "Is neighbor capable of Refresh Reduction";
    }
    leaf neighbor-address {
      type inet:ipv4-address;
      description
        "IP address of the neighbor";
    }
    leaf message-ids {
      type uint32;
      description
        "Number of MessageIDs";
    }
    leaf outgoing-states {
      type int32;
      description
        "Number of outgoing states to the neighbour";
    }
    list neighbor-message-id {
      max-elements 6;
      description
        "List of Neighbor MessageIDs";
      uses ncs_rpc_notif_RSVP-MGMT-MESSAGEID;
    }
  }

  grouping ncs_rpc_notif_RSVP-MGMT-INTERFACE-FLAGS {
    description
      "Interface related flags";
    leaf is-mpls-enabled {
      type boolean;
      description
        "MPLS enabled on interface";
    }
    leaf is-refresh-reduction-enabled {
      type boolean;
      description
        "Refresh Reduction enabled";
    }
    leaf is-pacing-enabled {
      type boolean;
      description
        "Message pacing enabled";
    }
    leaf is-refresh-enabled {
      type boolean;
      description
        "Refresh enabled";
    }
    leaf is-s-refresh-enabled {
      type boolean;
      description
        "Summary Refresh enabled";
    }
    leaf is-interface-down {
      type boolean;
      description
        "Interface is DOWN";
    }
    leaf is-interface-created {
      type boolean;
      description
        "Interface is created";
    }
    leaf is-rel-s-refresh-enabled {
      type boolean;
      description
        "Use reliable xmt for SRefresh";
    }
    leaf is-backup-tunnel {
      type boolean;
      description
        "This is backup tunnel";
    }
    leaf is-rsvp-configured {
      type boolean;
      description
        "RSVP explicitly configured";
    }
    leaf is-non-default-vrf {
      type boolean;
      description
        "Interface is defined in non-Default VRF";
    }
    leaf is-message-bundling-enabled {
      type boolean;
      description
        "Use bundling for outgoing RSVP messages.";
    }
  }

  grouping ncs_rpc_notif_RSVP-MGMT-INTERFACE-DETAIL {
    description
      "Detail Form of RSVP interface Info";
    container bandwidth-information {
      description
        "Interface bandwidth information";
      uses ncs_rpc_notif_RSVP-MGMT-DSTE-MODE-INTERFACE-BW;
    }
    container flags {
      description
        "Interface flags";
      uses ncs_rpc_notif_RSVP-MGMT-INTERFACE-FLAGS;
    }
    leaf interface-name-xr {
      type string;
      description
        "Interface Name";
    }
    leaf signalling-ip-tos {
      type uint8;
      description
        "IP TOS (precedence/DSCP) to use in signalling
         messages";
    }
    leaf integrity-send-password {
      type string {
        length "0..40";
      }
      description
        "Integrity send password";
    }
    leaf integrity-receive-password {
      type string {
        length "0..40";
      }
      description
        "Integrity receive password";
    }
    leaf integrity-receive-password-optional {
      type uint8;
      description
        "Integrity recv password optional";
    }
    leaf refresh-timer-state {
      type ncs_rpc_notif_Rsvp-timer-state;
      description
        "Refresh timer state";
    }
    leaf summary-refresh-timer-state {
      type ncs_rpc_notif_Rsvp-timer-state;
      description
        "Summary refresh timer state";
    }
    leaf refresh-interval {
      type int32;
      units "millisecond";
      description
        "Refresh interval in msecs";
    }
    leaf out-of-band-refresh-interval {
      type uint32;
      units "millisecond";
      description
        "Out-of-band Refresh interval in msecs";
    }
    leaf summary-refresh-max-size {
      type uint32;
      units "byte";
      description
        "Max size in bytes of a single SRefresh";
    }
    leaf bundle-message-max-size {
      type uint32;
      units "byte";
      description
        "Max size in bytes of a single Bundle message";
    }
    leaf expiry-timer-state {
      type ncs_rpc_notif_Rsvp-timer-state;
      description
        "Expiry timer state";
    }
    leaf expiry-states {
      type int32;
      description
        "Number of states for expiry check";
    }
    leaf expiry-interval {
      type int32;
      units "millisecond";
      description
        "Expiry interval in msecs";
    }
    leaf expiry-drops-tolerated {
      type int32;
      description
        "Number of missed messages tolerated";
    }
    leaf out-of-band-expiry-drops-tolerated {
      type uint32;
      description
        "Number of out-of-band missed messages tolerated";
    }
    leaf ack-hold-time {
      type uint32;
      description
        "ACK hold time in msec";
    }
    leaf ack-max-size {
      type uint32;
      description
        "Max size for ACK message";
    }
    leaf retransmit-time {
      type uint32;
      description
        "Retransmit time in msec";
    }
    leaf pacing-interval {
      type uint32;
      units "millisecond";
      description
        "Pacing interval in msecs";
    }
    leaf pacing-message-rate {
      type uint32;
      description
        "No. of messages per interval";
    }
    leaf pacing-timer-state {
      type ncs_rpc_notif_Rsvp-timer-state;
      description
        "State of pacing timer";
    }
    leaf pacing-messages {
      type int32;
      description
        "Number of messages deferred for pacing";
    }
    list neighbor-array {
      max-elements 6;
      description
        "Neighbor array";
      uses ncs_rpc_notif_RSVP-MGMT-NBOR;
    }
  }

  grouping ncs_rpc_notif_RSVP-MGMT-ERO-UNNUM-SUBOBJ {
    description
      "RSVP ERO UNNUM subobject";
    leaf is-strict-route {
      type boolean;
      description
        "ERO Entry Is Strict";
    }
    leaf ero-interface-id {
      type uint32;
      description
        "The Interface ID in ERO";
    }
    leaf ero-router-id {
      type inet:ipv4-address;
      description
        "The Router ID in ERO";
    }
    leaf status {
      type ncs_rpc_notif_Rsvp-mgmt-ero-subobj-status;
      description
        "Status of ERO";
    }
  }

  grouping ncs_rpc_notif_RSVP-MGMT-ERO-IPV4-SUBOBJ {
    description
      "RSVP ERO IPV4 subobject";
    leaf is-strict-route {
      type boolean;
      description
        "ERO Entry Is Strict";
    }
    leaf ero-address {
      type inet:ipv4-address;
      description
        "The ERO IPV4 Address";
    }
    leaf prefix-length {
      type uint8;
      description
        "ERO Prefix Length";
    }
  }

  grouping ncs_rpc_notif_RSVP-MGMT-ERO-SUBOBJ {
    description
      "Union of the different RSVP ERO types";
    container ipv4ero-sub-object {
      when "../ero-type = 'rsvp-mgmt-ero-type-ipv4'" {
        tailf:xpath-root 3;
        description
          "../EROType = 'RSVP_MGMT_ERO_TYPE_IPv4'";
      }
      description
        "IPV4 ERO Sub Object";
      uses ncs_rpc_notif_RSVP-MGMT-ERO-IPV4-SUBOBJ;
    }
    container unnumbered-ero-sub-object {
      when "../ero-type = 'rsvp-mgmt-ero-type-un-num'" {
        tailf:xpath-root 3;
        description
          "../EROType = 'RSVP_MGMT_ERO_TYPE_UNNUM'";
      }
      description
        "Unnumbered ERO Sub Object";
      uses ncs_rpc_notif_RSVP-MGMT-ERO-UNNUM-SUBOBJ;
    }
    leaf ero-type {
      type ncs_rpc_notif_Rsvp-mgmt-ero-subobj;
      description
        "EROType";
    }
  }

  grouping ncs_rpc_notif_RSVP-MGMT-CT-INFO {
    description
      "Class-Type Information";
    leaf is-class-type-info-valid {
      type boolean;
      description
        "Is the Class-Type information valid";
    }
    leaf class-type {
      type uint8;
      description
        "DS-TE Class-Type";
    }
  }

  grouping ncs_rpc_notif_RSVP-MGMT-GENERALIZED-LABEL {
    description
      "RSVP Generalized Label";
    list value {
      description
        "Generalized Label Value";
      leaf entry {
        type uint32;
        description
          "Generalized Label Value";
      }
    }
  }

  grouping ncs_rpc_notif_RSVP-MGMT-GENERIC-LABEL {
    description
      "Union of different RSVP Generic Label types";
    container generalized-label {
      when "../generic-label-type = 'rsvp-mgmt-label-type-gmpls'" {
        tailf:xpath-root 3;
        description
          "../GenericLabelType =
           'RSVP_MGMT_LABEL_TYPE_GMPLS'";
      }
      description
        "Generalized Label";
      uses ncs_rpc_notif_RSVP-MGMT-GENERALIZED-LABEL;
    }
    leaf generic-label-type {
      type ncs_rpc_notif_Rsvp-mgmt-generic-label;
      description
        "GenericLabelType";
    }
  }

  grouping ncs_rpc_notif_RSVP-MGMT-LABEL-INFO {
    description
      "Label Information";
    container generic-local-downstream-label {
      description
        "Generic Local Downstream Label";
      uses ncs_rpc_notif_RSVP-MGMT-GENERIC-LABEL;
    }
    container generic-outgoing-downstream-label {
      description
        "Generic Outgoing Downstream Label";
      uses ncs_rpc_notif_RSVP-MGMT-GENERIC-LABEL;
    }
    container generic-merge-point-label {
      description
        "Generic MergePoint Label";
      uses ncs_rpc_notif_RSVP-MGMT-GENERIC-LABEL;
    }
    container generic-outgoing-upstream-label {
      description
        "Generic Outgoing Upstream Label";
      uses ncs_rpc_notif_RSVP-MGMT-GENERIC-LABEL;
    }
    container generic-local-upstream-label {
      description
        "Generic Local Upstream Label";
      uses ncs_rpc_notif_RSVP-MGMT-GENERIC-LABEL;
    }
    container generic-recovery-label {
      description
        "Generic Recovery Label";
      uses ncs_rpc_notif_RSVP-MGMT-GENERIC-LABEL;
    }
    leaf is-valid {
      type boolean;
      description
        "Is the label information valid";
    }
    leaf local-downstream-label {
      type ncs_rpc_notif_Rsvp-mgmt-mpls-label;
      description
        "Local Downstream Label";
    }
    leaf outgoing-downstream-label {
      type ncs_rpc_notif_Rsvp-mgmt-mpls-label;
      description
        "Outgoing Downstream Label";
    }
    leaf merge-point-label {
      type ncs_rpc_notif_Rsvp-mgmt-mpls-label;
      description
        "MergePoint Label";
    }
    leaf outgoing-upstream-label {
      type ncs_rpc_notif_Rsvp-mgmt-mpls-label;
      description
        "Outgoing Upstream Label";
    }
    leaf local-upstream-label {
      type ncs_rpc_notif_Rsvp-mgmt-mpls-label;
      description
        "Local Upstream Label";
    }
    leaf recovery-label {
      type ncs_rpc_notif_Rsvp-mgmt-mpls-label;
      description
        "Recovery Label";
    }
    leaf lsp-wrap-label {
      type ncs_rpc_notif_Rsvp-mgmt-mpls-label;
      description
        "LSP Wrap Label";
    }
  }

  grouping ncs_rpc_notif_RSVP-PATH-FORWARDING-CONTEXT {
    description
      "RSVP Path Forwarding Context";
    container policy-flags {
      description
        "Policy Flags";
      uses ncs_rpc_notif_RSVP-MGMT-POLICY-FLAGS;
    }
    container policy-query-flags {
      description
        "Policy Query Flags";
      uses ncs_rpc_notif_RSVP-MGMT-POLICY-QUERY-FLAGS;
    }
    leaf output-interface {
      type string;
      description
        "Output interface";
    }
  }

  grouping ncs_rpc_notif_RSVP-MGMT-POLICY-QUERY-FLAGS {
    description
      "RSVP Policy Query Flags";
    leaf is-needed {
      type boolean;
      description
        "Needed";
    }
    leaf is-report-required {
      type boolean;
      description
        "Report Required";
    }
    leaf is-resync {
      type boolean;
      description
        "Resynchronization";
    }
    leaf is-bypass {
      type boolean;
      description
        "Bypass";
    }
  }

  grouping ncs_rpc_notif_RSVP-MGMT-POLICY-FLAGS {
    description
      "RSVP Policy Flags";
    leaf is-accepted {
      type boolean;
      description
        "Accepted";
    }
    leaf is-installed {
      type boolean;
      description
        "Installed";
    }
    leaf is-forwarding {
      type boolean;
      description
        "Forwarding";
    }
  }

  grouping ncs_rpc_notif_RSVP-MGMT-TIMESPEC {
    description
      "RSVP Time Spec";
    leaf seconds {
      type int32;
      units "second";
      description
        "Time Value in Seconds";
    }
    leaf nanoseconds {
      type int32;
      units "nanosecond";
      description
        "Time Value in Nano-seconds";
    }
  }

  grouping ncs_rpc_notif_RSVP-MGMT-HEADER-INFO {
    description
      "RSVP/IP Header Info";
    leaf rsvp-version {
      type uint8;
      description
        "RSVP Version";
    }
    leaf rsvp-header-flags {
      type uint8;
      description
        "RSVP Header Flags (defined in RFC2205 Section 3
         .1.1)";
    }
    leaf rsvp-ttl {
      type uint8;
      description
        "RSVP TTL";
    }
    leaf rsvp-message-type {
      type uint8;
      description
        "RSVP Message Type";
    }
    leaf ip-tos {
      type uint8;
      description
        "IP Type of Service";
    }
    leaf ip-ttl {
      type uint8;
      description
        "IP TTL";
    }
    leaf ip-source-address {
      type inet:ipv4-address;
      description
        "IP Source Address";
    }
  }

  grouping ncs_rpc_notif_RSVP-MGMT-POLICY-SOURCES {
    description
      "RSVP Policy Sources";
    leaf is-te-link {
      type boolean;
      description
        "Policy Source is TE Link";
    }
    leaf is-local {
      type boolean;
      description
        "Policy Source is Local";
    }
    leaf is-cops {
      type boolean;
      description
        "Policy Source is COPS";
    }
    leaf is-default {
      type boolean;
      description
        "Policy Source is Default";
    }
    leaf is-cable {
      type boolean;
      description
        "Policy Source is Cable";
    }
  }

  grouping ncs_rpc_notif_RSVP-MGMT-HOP-INFO {
    description
      "Hop Info";
    leaf neighbor-address {
      type inet:ipv4-address;
      description
        "IP address of the neighbor";
    }
    leaf neighbor-logical-interface-handle {
      type uint32;
      description
        "Neighbor Logical Interface Handle";
    }
  }

  grouping ncs_rpc_notif_RSVP-MGMT-PATH-FLAGS {
    description
      "RSVP Path Flags";
    leaf is-non-rsvp-hop-upstream {
      type boolean;
      description
        "Non-RSVP Hop Upstream";
    }
    leaf is-local-sender {
      type boolean;
      description
        "Local Sender";
    }
    leaf is-message-id-valid {
      type boolean;
      description
        "MessageID Valid";
    }
    leaf is-local-repair {
      type boolean;
      description
        "Rerouted";
    }
    leaf is-bidirectional {
      type boolean;
      description
        "Bidirectional";
    }
    leaf is-lockout {
      type boolean;
      description
        "Locked Out";
    }
  }

  grouping ncs_rpc_notif_RSVP-MGMT-TSPEC-G709-OTN {
    description
      "RSVP G709 OTN Sender Tspec Info";
    leaf traffic-signal-type {
      type uint8;
      description
        "G709 OTN Traffic Signal Type (Refer G709 v3)";
    }
    leaf traffic-nvc {
      type uint16;
      description
        "G709 OTN Traffic NVC";
    }
    leaf traffic-multiplier {
      type uint16;
      description
        "G709 OTN Traffic Multiplier";
    }
    leaf traffic-bit-rate {
      type uint64;
      description
        "G709 OTN Traffic Bit Rate";
    }
  }

  grouping ncs_rpc_notif_RSVP-MGMT-GEN-TRAFFIC-SPEC {
    description
      "Union of different RSVP Generic Sender Tspec
       types";
    container g709otn-tspec {
      when "../tspec-type = 'g709otn'" {
        tailf:xpath-root 3;
        description
          "../TspecType = 'G709OTN'";
      }
      description
        "G709 OTN Sender Tspec";
      uses ncs_rpc_notif_RSVP-MGMT-TSPEC-G709-OTN;
    }
    container intsrv-tspec {
      when "../tspec-type = 'intsrv'" {
        tailf:xpath-root 3;
        description
          "../TspecType = 'INTSRV'";
      }
      description
        "Integrated Services Sender Tspec";
      uses ncs_rpc_notif_RSVP-MGMT-TRAFFIC-SPEC;
    }
    leaf tspec-type {
      type ncs_rpc_notif_Rsvp-mgmt-tspec;
      description
        "TspecType";
    }
  }

  grouping ncs_rpc_notif_RSVP-MGMT-TRAFFIC-SPEC {
    description
      "RSVP Traffic Spec Info";
    leaf traffic-average-rate {
      type uint64;
      units "byte/s";
      description
        "Traffic Average Rate in bytes per second";
    }
    leaf traffic-max-burst {
      type uint64;
      description
        "Traffic Maximum Burst";
    }
    leaf traffic-peak-rate {
      type uint64;
      units "byte/s";
      description
        "Traffic Peak Rate in bytes per second";
    }
    leaf traffic-min-unit {
      type uint32;
      description
        "Traffic Minimum Unit";
    }
    leaf traffic-max-unit {
      type uint32;
      description
        "Traffic Maximum Unit";
    }
  }

  grouping ncs_rpc_notif_RSVP-MGMT-SESSION-ATTRIBUTE-FLAGS {
    description
      "RSVP Session Attribute Flags";
    leaf is-local-protect {
      type boolean;
      description
        "Local Protection";
    }
    leaf is-node-protect {
      type boolean;
      description
        "Node Protection";
    }
    leaf is-bandwidth-protect {
      type boolean;
      description
        "Bandwidth Protection";
    }
    leaf is-record-labels {
      type boolean;
      description
        "Records Labels";
    }
    leaf is-shared-explicit-requested {
      type boolean;
      description
        "Shared Explicit Requested";
    }
  }

  grouping ncs_rpc_notif_RSVP-MGMT-SESSION-ATTRIBUTE {
    description
      "RSVP Session Attributes";
    container sess-attribute-flags {
      description
        "Session Attributes";
      uses ncs_rpc_notif_RSVP-MGMT-SESSION-ATTRIBUTE-FLAGS;
    }
    leaf setup-priority {
      type uint8;
      description
        "Setup Priority";
    }
    leaf reservation-priority {
      type uint8;
      description
        "Reservation Priority";
    }
  }

  grouping ncs_rpc_notif_RSVP-MGMT-FILTER-P2MP-IPV4 {
    description
      "RSVP P2MP IPv4 FilterSpec";
    leaf source-address {
      type inet:ipv4-address;
      description
        "Source Address";
    }
    leaf source-port {
      type uint16;
      description
        "Source Port";
    }
    leaf p2mp-sub-group-origin {
      type inet:ipv4-address;
      description
        "Point to Multipoint SubGroup Origin";
    }
    leaf sub-group-id {
      type uint16;
      description
        "Point to Multipoint Subgroup ID";
    }
  }

  grouping ncs_rpc_notif_RSVP-MGMT-FILTER-IPV4 {
    description
      "RSVP Filter";
    leaf source-address {
      type inet:ipv4-address;
      description
        "Source Address";
    }
    leaf source-port {
      type uint16;
      description
        "Source Port";
    }
  }

  grouping ncs_rpc_notif_RSVP-FILTER-UNION {
    description
      "Union of the different RSVP filterspec types";
    container udp-ipv4-session {
      when "../filter-type = 'rsvp-mgmt-filter-type-ipv4'" {
        tailf:xpath-root 3;
        description
          "../FilterType = 'RSVPMgmtFilterTypeIPv4'";
      }
      description
        "UDP IPV4 FilterSpec";
      uses ncs_rpc_notif_RSVP-MGMT-FILTER-IPV4;
    }
    container p2mp-ipv4-session {
      when "../filter-type = 'rsvp-mgmt-filter-type-p2mp-lsp-ipv4'" {
        tailf:xpath-root 3;
        description
          "../FilterType =
           'RSVPMgmtFilterTypeP2MP_LSP_IPv4'";
      }
      description
        "IPv4 P2MP LSP FilterSpec";
      uses ncs_rpc_notif_RSVP-MGMT-FILTER-P2MP-IPV4;
    }
    leaf filter-type {
      type ncs_rpc_notif_Rsvp-mgmt-filter;
      description
        "FilterType";
    }
  }

  grouping ncs_rpc_notif_RSVP-MGMT-FILTER-INFO {
    description
      "RSVP FilterSpec Info";
    container rsvp-filter {
      description
        "RSVP Filter";
      uses ncs_rpc_notif_RSVP-FILTER-UNION;
    }
  }

  grouping ncs_rpc_notif_RSVP-MGMT-S2L-SUB-LSP-IPV4 {
    description
      "RSVP S2L Sub-LSP";
    leaf s2l-destination-address {
      type inet:ipv4-address;
      description
        "S2L Sub-LSP Destination Address";
    }
  }

  grouping ncs_rpc_notif_RSVP-MGMT-PATH-DETAIL {
    description
      "Detailed Form of RSVP Path Info";
    container session {
      description
        "RSVP Session Information";
      uses ncs_rpc_notif_RSVP-MGMT-SESSION-INFO;
    }
    container s2l-sub-lsp {
      description
        "RSVP S2L Sub-LSP information";
      uses ncs_rpc_notif_RSVP-MGMT-S2L-SUB-LSP-IPV4;
    }
    container template {
      description
        "RSVP Template";
      uses ncs_rpc_notif_RSVP-MGMT-FILTER-INFO;
    }
    container session-attribute {
      description
        "RSVP Session Attribute";
      uses ncs_rpc_notif_RSVP-MGMT-SESSION-ATTRIBUTE;
    }
    container traffic-spec {
      description
        "RSVP Traffic Spec Info";
      uses ncs_rpc_notif_RSVP-MGMT-TRAFFIC-SPEC;
    }
    container generic-traffic-spec {
      description
        "RSVP Generic Traffic Spec Info";
      uses ncs_rpc_notif_RSVP-MGMT-GEN-TRAFFIC-SPEC;
    }
    container path-flags {
      description
        "Path Flags";
      uses ncs_rpc_notif_RSVP-MGMT-PATH-FLAGS;
    }
    container hop {
      description
        "Path Hop Info";
      uses ncs_rpc_notif_RSVP-MGMT-HOP-INFO;
    }
    container policy-source-info {
      description
        "Policy Sources Info";
      uses ncs_rpc_notif_RSVP-MGMT-POLICY-SOURCES;
    }
    container header {
      description
        "RSVP Header Info";
      uses ncs_rpc_notif_RSVP-MGMT-HEADER-INFO;
    }
    container expiry-time {
      description
        "Expiry Time";
      uses ncs_rpc_notif_RSVP-MGMT-TIMESPEC;
    }
    container policy-flags {
      description
        "Policy Flags";
      uses ncs_rpc_notif_RSVP-MGMT-POLICY-FLAGS;
    }
    container policy-query-flags {
      description
        "Policy Query Flags";
      uses ncs_rpc_notif_RSVP-MGMT-POLICY-QUERY-FLAGS;
    }
    container label-info {
      description
        "Label Information";
      uses ncs_rpc_notif_RSVP-MGMT-LABEL-INFO;
    }
    container class-type {
      description
        "DS-TE Class-Type";
      uses ncs_rpc_notif_RSVP-MGMT-CT-INFO;
    }
    leaf input-interface {
      type string;
      description
        "Path Input Interface";
    }
    leaf backup-tunnel-name {
      type string;
      description
        "Path Backup Tunnel";
    }
    leaf is-in-ero-valid {
      type boolean;
      description
        "Incoming ERO validity";
    }
    leaf is-out-ero-valid {
      type boolean;
      description
        "Outgoing ERO validity";
    }
    list pfc {
      description
        "Path Forwarding Contexts";
      uses ncs_rpc_notif_RSVP-PATH-FORWARDING-CONTEXT;
    }
    list in-ero {
      description
        "Incoming Explicit Route Sub Objects";
      uses ncs_rpc_notif_RSVP-MGMT-ERO-SUBOBJ;
    }
    list out-ero {
      description
        "Outgoing Explicit Route Sub Objects";
      uses ncs_rpc_notif_RSVP-MGMT-ERO-SUBOBJ;
    }
  }

  grouping ncs_rpc_notif_RSVP-MGMT-SESSION-P2MP-LSP-TUNNEL-IPV4 {
    description
      "RSVP P2MP-LSP-Tunnel-IPv4 Session";
    leaf p2mp-id {
      type uint32;
      description
        "The Point to Multipoint ID";
    }
    leaf tunnel-id {
      type uint16;
      description
        "The Session Tunnel ID";
    }
    leaf extended-tunnel-id {
      type inet:ipv4-address;
      description
        "The Session Extended Tunnel ID";
    }
  }

  grouping ncs_rpc_notif_RSVP-MGMT-SESSION-UNI-IPV4 {
    description
      "RSVP UNI IPv4 Session";
    leaf destination-address {
      type inet:ipv4-address;
      description
        "Destination address";
    }
    leaf tunnel-id {
      type uint16;
      description
        "The Session Tunnel ID";
    }
    leaf extended-address {
      type inet:ipv4-address;
      description
        "The Session Extended Address";
    }
  }

  grouping ncs_rpc_notif_RSVP-MGMT-SESSION-LSP-TUNNEL-IPV4 {
    description
      "RSVP LSP-Tunnel-IPv4 Session";
    leaf destination-address {
      type inet:ipv4-address;
      description
        "Destination address";
    }
    leaf tunnel-id {
      type uint16;
      description
        "The Session Tunnel ID";
    }
    leaf extended-tunnel-id {
      type inet:ipv4-address;
      description
        "The Session Extended Tunnel ID";
    }
  }

  grouping ncs_rpc_notif_RSVP-MGMT-SESSION-UDP-IPV4 {
    description
      "RSVP UDP IPv4 Session";
    leaf destination-address {
      type inet:ipv4-address;
      description
        "Destination address";
    }
    leaf protocol {
      type uint8;
      description
        "Protocol type (originally defined in RFC 790,
         further values in subsequent RFCs)";
    }
    leaf destination-port {
      type uint16;
      description
        "The Session Destination Port";
    }
  }

  grouping ncs_rpc_notif_RSVP-SESSION-UNION {
    description
      "Union of the different RSVP session types";
    container ipv4 {
      when "../session-type = 'rsvp-mgmt-session-type-udp-ipv4'" {
        tailf:xpath-root 3;
        description
          "../SessionType = 'RSVPMgmtSessionTypeUDP_IPv4'";
      }
      description
        "UDP IPv4 session";
      uses ncs_rpc_notif_RSVP-MGMT-SESSION-UDP-IPV4;
    }
    container ipv4-lsp-session {
      when "../session-type = 'rsvp-mgmt-session-type-lsp-ipv4'" {
        tailf:xpath-root 3;
        description
          "../SessionType = 'RSVPMgmtSessionTypeLSP_IPv4'";
      }
      description
        "IPv4 LSP session";
      uses ncs_rpc_notif_RSVP-MGMT-SESSION-LSP-TUNNEL-IPV4;
    }
    container ipv4-uni-session {
      when "../session-type = 'rsvp-mgmt-session-type-uni-ipv4'" {
        tailf:xpath-root 3;
        description
          "../SessionType = 'RSVPMgmtSessionTypeUNI_IPv4'";
      }
      description
        "IPv4 UNI session";
      uses ncs_rpc_notif_RSVP-MGMT-SESSION-UNI-IPV4;
    }
    container ipv4-p2mp-lsp-session {
      when "../session-type = 'rsvp-mgmt-session-type-p2mp-lsp-ipv4'" {
        tailf:xpath-root 3;
        description
          "../SessionType =
           'RSVPMgmtSessionTypeP2MP_LSP_IPv4'";
      }
      description
        "IPv4 P2MP LSP session";
      uses ncs_rpc_notif_RSVP-MGMT-SESSION-P2MP-LSP-TUNNEL-IPV4;
    }
    leaf session-type {
      type ncs_rpc_notif_Rsvp-mgmt-session;
      description
        "SessionType";
    }
  }

  grouping ncs_rpc_notif_RSVP-MGMT-SESSION-INFO {
    description
      "RSVP Session Info";
    container rsvp-session {
      description
        "RSVP Session";
      uses ncs_rpc_notif_RSVP-SESSION-UNION;
    }
  }

  grouping ncs_rpc_notif_RSVP-MGMT-SESSION-COMPACT {
    description
      "RSVP Compact Session Info";
    container session {
      description
        "RSVP Session Information";
      uses ncs_rpc_notif_RSVP-MGMT-SESSION-INFO;
    }
    leaf ps-bs {
      type uint32;
      description
        "Number of path state block states";
    }
    leaf rs-bs {
      type uint32;
      description
        "Number of reservation state block states";
    }
    leaf requests {
      type uint32;
      description
        "Number of request states";
    }
    leaf detail-list-size {
      type uint32;
      description
        "Number of elements in detail list";
    }
  }

  grouping ncs_rpc_notif_RSVP-MGMT-AUTHENTICATION-COMPACT {
    description
      "Authentication Compact Information";
    leaf source-address-xr {
      type inet:ipv4-address;
      description
        "Source address";
    }
    leaf destination-address-xr {
      type inet:ipv4-address;
      description
        "Destination address";
    }
    leaf neighbor-address {
      type inet:ipv4-address;
      description
        "Neighbor address";
    }
    leaf direction {
      type ncs_rpc_notif_Rsvp-mgmt-auth-direction;
      description
        "Direction";
    }
    leaf key-type {
      type ncs_rpc_notif_Rsvp-mgmt-auth-ki;
      description
        "Key type";
    }
    leaf key-source {
      type string;
      description
        "Key source";
    }
    leaf key-id {
      type uint64;
      description
        "Key ID";
    }
    leaf key-id-valid {
      type uint32;
      description
        "Key validity";
    }
  }

  grouping ncs_rpc_notif_RSVP-MGMT-INTERFACE-BW-STD-DSTE {
    description
      "RSVP interface bandwidth info with standard based
       DSTE enabled";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-pool0-bandwidth {
      type uint64;
      units "bit/s";
      description
        "Max bandwidth (bits per second) allowed in BC0
         pool";
    }
    leaf max-pool1-bandwidth {
      type uint64;
      units "bit/s";
      description
        "Max bandwidth (bits per second) allowed in BC1
         pool";
    }
    leaf is-max-bandwidth-absolute {
      type boolean;
      description
        "True if the Max B/W is an absolute value and
         false if its a percentage";
    }
    leaf is-max-bc0-bandwidth-absolute {
      type boolean;
      description
        "True if the Max BC0 B/W is an absolute value and
         false if its a percentage";
    }
    leaf is-max-bc1-bandwidth-absolute {
      type boolean;
      description
        "True if the Max BC1 sub-pool B/W is an absolute
         value and false if its a percentage";
    }
  }

  grouping ncs_rpc_notif_RSVP-MGMT-INTERFACE-BW-PRESTD-DSTE {
    description
      "Prestandard DSTE interface bandwidth information";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-subpool-bandwidth {
      type uint64;
      units "bit/s";
      description
        "Max bandwidth (bits per second) allowed in
         subpool";
    }
    leaf is-max-bandwidth-absolute {
      type boolean;
      description
        "True if the Max B/W is an absolute value and
         false if its a percentage";
    }
    leaf is-max-subpool-bandwidth-absolute {
      type boolean;
      description
        "True if the Max sub-pool B/W is an absolute
         value and false if its a percentage";
    }
  }

  grouping ncs_rpc_notif_RSVP-MGMT-DSTE-MODE-INTERFACE-BW {
    description
      "Union of the different RSVP interface bandwidth
       types";
    container pre-standard-dste-interface {
      when "../dste-mode = 'pre-standard'" {
        tailf:xpath-root 3;
        description
          "../DSTEMode = 'PreStandard'";
      }
      description
        "Prestandard DSTE interface information";
      uses ncs_rpc_notif_RSVP-MGMT-INTERFACE-BW-PRESTD-DSTE;
    }
    container standard-dste-interface {
      when "../dste-mode = 'standard'" {
        tailf:xpath-root 3;
        description
          "../DSTEMode = 'Standard'";
      }
      description
        "Standard DSTE interface information";
      uses ncs_rpc_notif_RSVP-MGMT-INTERFACE-BW-STD-DSTE;
    }
    leaf dste-mode {
      type ncs_rpc_notif_Rsvp-mgmt-dste-modes;
      description
        "DSTEMode";
    }
  }

  grouping ncs_rpc_notif_RSVP-MGMT-INTERFACE-SUMMARY {
    description
      "Summary Form of RSVP interface Info";
    container bandwidth-information {
      description
        "Interface bandwidth information";
      uses ncs_rpc_notif_RSVP-MGMT-DSTE-MODE-INTERFACE-BW;
    }
    leaf interface-name-xr {
      type string;
      description
        "Interface Name";
    }
    leaf paths-in {
      type uint32;
      description
        "Number of locally created and incoming path
         states";
    }
    leaf paths-out {
      type uint32;
      description
        "Number of outgoing path states";
    }
    leaf reservations-in {
      type uint32;
      description
        "Number of locally created and incoming
         reservation states";
    }
    leaf reservations-out {
      type uint32;
      description
        "Number of outgoing reservation states";
    }
  }

  grouping ncs_rpc_notif_RSVP-MGMT-IF-NBR-COMPACT {
    description
      "Compact Info for RSVP Interface Neighbor";
    leaf interface-neighbor-address {
      type inet:ipv4-address;
      description
        "Interface Neighbor address";
    }
    leaf neighbor-interface-name {
      type xr:ncs_rpc_notif_Interface-name;
      description
        "Neighbor's Interface handle";
    }
  }

  grouping ncs_rpc_notif_RSVP-MGMT-NBR-COMPACT {
    description
      "Compact Info for RSVP Neighbor";
    leaf node-address {
      type inet:ipv4-address;
      description
        "Neighbor node address";
    }
    list interface-neighbor-list-compact {
      description
        "Compact list of I/F Neighbors";
      uses ncs_rpc_notif_RSVP-MGMT-IF-NBR-COMPACT;
    }
  }

  grouping live_ncs_RSVP-MGMT-RXSB-DETAIL {
    description
      "Detailed Form of RSVP Proxy Reservation";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container style {
      description
        "RSVP Style";
      uses live_ncs_RSVP-MGMT-STYLE;
    }
    container filter {
      description
        "RSVP Filter";
      uses live_ncs_RSVP-MGMT-FILTER-INFO;
    }
    container flow-spec {
      description
        "Flow Spec Information";
      uses live_ncs_RSVP-MGMT-FLOW-SPEC;
    }
    container generic-flow-spec {
      description
        "Generic Flow Spec Information";
      uses live_ncs_RSVP-MGMT-GEN-FLOW-SPEC;
    }
    container hop {
      description
        "Path Hop Info";
      uses live_ncs_RSVP-MGMT-HOP-INFO;
    }
    container rsvp-header {
      description
        "RSVP Header";
      uses live_ncs_RSVP-MGMT-HEADER-INFO;
    }
    leaf input-interface {
      type string;
      description
        "Path Input Interface";
    }
    leaf dynamic-state {
      type uint32;
      description
        "Dynamic State Handle";
    }
  }

  grouping live_ncs_RSVP-MGMT-PXSB-DETAIL {
    description
      "Detailed Form of RSVP Proxy Path";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container template {
      description
        "RSVP Template";
      uses live_ncs_RSVP-MGMT-FILTER-INFO;
    }
    container traffic-spec {
      description
        "RSVP Traffic Spec Info";
      uses live_ncs_RSVP-MGMT-TRAFFIC-SPEC;
    }
    container generic-traffic-spec {
      description
        "RSVP Generic Traffic Spec Info";
      uses live_ncs_RSVP-MGMT-GEN-TRAFFIC-SPEC;
    }
    container hop {
      description
        "Path Hop Info";
      uses live_ncs_RSVP-MGMT-HOP-INFO;
    }
    container rsvp-header {
      description
        "RSVP Header";
      uses live_ncs_RSVP-MGMT-HEADER-INFO;
    }
    leaf input-interface {
      type string;
      description
        "Path Input Interface";
    }
    leaf dynamic-state {
      type uint32;
      description
        "Dynamic State Handle";
    }
  }

  grouping live_ncs_RSVP-MGMT-GLBL-BW-POOL-INFO {
    description
      "Global B/W pool information";
    leaf max-res-pool-percent {
      type uint32;
      units "percentage";
      description
        "Maxium reservable I/F percent B/W";
    }
    leaf bc0-percent {
      type uint32;
      units "percentage";
      description
        "BC0 I/F percent B/W";
    }
    leaf bc1-percent {
      type uint32;
      units "percentage";
      description
        "BC1 I/F percent B/W";
    }
    leaf is-max-res-pool-percent-configured {
      type boolean;
      description
        "Is maximum reservable default I/F percent
         configured";
    }
    leaf is-bc0-percent-configured {
      type boolean;
      description
        "Is BC0 default I/F percent configured";
    }
    leaf is-bc1-percent-configured {
      type boolean;
      description
        "Is BC1 default I/F percent configured";
    }
    leaf bandwidth-configuration-model {
      type live_ncs_Igpte-lib-bw-model;
      description
        "Bandwith configuration model currently in use
         (MAM/RDM)";
    }
  }

  grouping live_ncs_RSVP-MGMT-GLBL-NBR-COMPACT {
    description
      "Compact Info for RSVP Global Neighbor";
    container global-neighbor-flags {
      description
        "Global Neighbor Flags";
      uses live_ncs_RSVP-MGMT-GLBL-NBR-FLAGS;
    }
    leaf is-gr-enabled {
      type boolean;
      description
        "Is GR enabled";
    }
    leaf node-address {
      type inet:ipv4-address;
      description
        "Neighbor node address";
    }
    leaf restart-state {
      type live_ncs_Rsvp-mgmt-restart-state;
      description
        "Restart state";
    }
    list local-node-address {
      description
        "Local node address";
      leaf entry {
        type inet:ipv4-address;
        description
          "Local node address";
      }
    }
    list neighbor-hello-state {
      description
        "Neighbor Hello state";
      leaf entry {
        type live_ncs_Rsvp-mgmt-hello-state;
        description
          "Neighbor Hello state";
      }
    }
    list lost-communication-reason {
      description
        "Reason why communication was lost";
      leaf entry {
        type live_ncs_Rsvp-mgmt-hello-down-reason;
        description
          "Reason why communication was lost";
      }
    }
    list lost-communication-total {
      description
        "Total number of times communication got lost";
      leaf entry {
        type uint16;
        description
          "Total number of times communication got lost";
      }
    }
    list up-time {
      description
        "Time hellos have been up";
      uses live_ncs_RSVP-MGMT-TIMESPEC;
    }
    list lost-communication-time {
      description
        "Time when communication was lost";
      uses live_ncs_RSVP-MGMT-TIMESPEC;
    }
  }

  grouping live_ncs_RSVP-MGMT-PATH-COMPACT {
    description
      "Compact Form of RSVP Path Info";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container template {
      description
        "RSVP Template";
      uses live_ncs_RSVP-MGMT-FILTER-INFO;
    }
    container session-attribute {
      description
        "RSVP Session Attribute";
      uses live_ncs_RSVP-MGMT-SESSION-ATTRIBUTE;
    }
    container traffic-spec {
      description
        "RSVP Traffic Spec Info";
      uses live_ncs_RSVP-MGMT-TRAFFIC-SPEC;
    }
    container generic-traffic-spec {
      description
        "RSVP Generic Traffic Spec Info";
      uses live_ncs_RSVP-MGMT-GEN-TRAFFIC-SPEC;
    }
    leaf input-interface {
      type string;
      description
        "Path Input Interface";
    }
  }

  grouping live_ncs_RSVP-MGMT-GLBL-NBR-FLAGS {
    description
      "Global Neighbor Flags";
    leaf is-application-ouni {
      type boolean;
      description
        "OUNI Application";
    }
    leaf is-application-mpls {
      type boolean;
      description
        "MPLS Application";
    }
  }

  grouping live_ncs_RSVP-MGMT-GLBL-NBR-DETAIL {
    description
      "Detail Info for RSVP Global Neighbor";
    container global-neighbor-flags {
      description
        "Global Neighbor Flags";
      uses live_ncs_RSVP-MGMT-GLBL-NBR-FLAGS;
    }
    container restart-time-left {
      description
        "How much restart time remains";
      uses live_ncs_RSVP-MGMT-TIMESPEC;
    }
    container restart-timer-expiry-time {
      description
        "When will restart timer expire";
      uses live_ncs_RSVP-MGMT-TIMESPEC;
    }
    container recovery-time-left {
      description
        "How much recovery timer remains";
      uses live_ncs_RSVP-MGMT-TIMESPEC;
    }
    container recovery-timer-exp-time {
      description
        "Time at which recovery timer will expire";
      uses live_ncs_RSVP-MGMT-TIMESPEC;
    }
    leaf is-gr-enabled {
      type boolean;
      description
        "Is GR enabled";
    }
    leaf node-address {
      type inet:ipv4-address;
      description
        "Neighbor node address";
    }
    leaf restart-state {
      type live_ncs_Rsvp-mgmt-restart-state;
      description
        "Current restart state";
    }
    leaf restart-time {
      type uint32;
      units "millisecond";
      description
        "GR Restart Time (milliseconds)";
    }
    leaf is-restart-timer-running {
      type boolean;
      description
        "Is GR restart timer running";
    }
    leaf recovery-time {
      type uint32;
      units "millisecond";
      description
        "GR Recovery Time (milliseconds)";
    }
    leaf is-recovery-timer-running {
      type boolean;
      description
        "Is RSVP recovery timer running";
    }
    leaf hello-interval {
      type uint32;
      units "millisecond";
      description
        "Hello Interval (milliseconds)";
    }
    leaf missed-hellos {
      type uint8;
      description
        "Hello missed count";
    }
    leaf pending-states {
      type uint32;
      description
        "Number of pending states for this neighbor";
    }
    list local-node-address {
      description
        "Local node address";
      leaf entry {
        type inet:ipv4-address;
        description
          "Local node address";
      }
    }
    list interface-neighbor {
      description
        "Interface Neighbor List";
      leaf entry {
        type inet:ipv4-address;
        description
          "Interface Neighbor List";
      }
    }
    list neighbor-hello-state {
      description
        "Neighbor's hello state";
      leaf entry {
        type live_ncs_Rsvp-mgmt-hello-state;
        description
          "Neighbor's hello state";
      }
    }
    list lost-communication-reason {
      description
        "Reason why communication was lost";
      leaf entry {
        type live_ncs_Rsvp-mgmt-hello-down-reason;
        description
          "Reason why communication was lost";
      }
    }
    list lost-communication-total {
      description
        "Total number of times communication got lost";
      leaf entry {
        type uint16;
        description
          "Total number of times communication got lost";
      }
    }
    list up-time {
      description
        "Hello up time";
      uses live_ncs_RSVP-MGMT-TIMESPEC;
    }
    list lost-communication-time {
      description
        "Time when communication was lost";
      uses live_ncs_RSVP-MGMT-TIMESPEC;
    }
  }

  grouping live_ncs_RSVP-MGMT-HELLO-INSTANCE-DETAIL {
    description
      "Detail Info for RSVP Hello Instance";
    container up-time {
      description
        "Hello up time";
      uses live_ncs_RSVP-MGMT-TIMESPEC;
    }
    container communication-lost-time {
      description
        "Time when communication was lost";
      uses live_ncs_RSVP-MGMT-TIMESPEC;
    }
    leaf source-address-xr {
      type inet:ipv4-address;
      description
        "Source address";
    }
    leaf destination-address-xr {
      type inet:ipv4-address;
      description
        "Destination address";
    }
    leaf hello-instance-owner {
      type live_ncs_Rsvp-mgmt-hello-instance-owner;
      description
        "Hello instance owner";
    }
    leaf neighbor-hello-state {
      type live_ncs_Rsvp-mgmt-hello-state;
      description
        "Neighbor Hello state";
    }
    leaf instance-type {
      type live_ncs_Rsvp-mgmt-hello-instance;
      description
        "Hello instance type";
    }
    leaf hello-interface {
      type xr:live_ncs_Interface-name;
      description
        "Interface to use";
    }
    leaf hello-interval {
      type uint32;
      description
        "Hello Interval";
    }
    leaf missed-acks-allowed {
      type uint32;
      description
        "Number of missed Hello allowed";
    }
    leaf source-instance {
      type uint32;
      description
        "Source Instance";
    }
    leaf destination-instance {
      type uint32;
      description
        "Destination Instance";
    }
    leaf communication-lost-reason {
      type live_ncs_Rsvp-mgmt-hello-down-reason;
      description
        "Reason why communication was lost";
    }
    leaf total-communication-lost {
      type uint16;
      description
        "Total number of times communication got lost";
    }
    leaf communication-lost-hello-missed {
      type uint16;
      description
        "Lost Comm. Hello missed count";
    }
    leaf communication-lost-wrong-source-inst {
      type uint16;
      description
        "Count of lost comm. due to wrong Source Inst";
    }
    leaf communication-lost-wrong-destination-inst {
      type uint16;
      description
        "Count of lost comm. due to wrong Destination
         Inst";
    }
    leaf communication-lost-interface-down {
      type uint16;
      description
        "Count of lost comm. due to interface down";
    }
    leaf communication-lost-neighbor-disabled-hello {
      type uint16;
      description
        "Count of lost comm. due to nbor disabling Hellos";
    }
    leaf hello-messages-sent {
      type uint64;
      description
        "Number of hello messages sent";
    }
    leaf hello-messages-received {
      type uint64;
      description
        "Number of hello messages received";
    }
    leaf hello-request-suppressed {
      type uint64;
      description
        "Count of Hello Requests suppessed";
    }
  }

  grouping live_ncs_RSVP-SESSION-RSB-DETAIL {
    description
      "RSVP Detail Session Reservation Info";
    container generic-out-label {
      description
        "Generic Label for outbound traffic";
      uses live_ncs_RSVP-MGMT-GENERIC-LABEL;
    }
    container flow-spec {
      description
        "Flow spec object";
      uses live_ncs_RSVP-MGMT-FLOW-SPEC;
    }
    container generic-flow-spec {
      description
        "Generic Flow Spec object";
      uses live_ncs_RSVP-MGMT-GEN-FLOW-SPEC;
    }
    leaf is-valid {
      type boolean;
      description
        "Entry validity";
    }
    leaf destination-address {
      type inet:ipv4-address;
      description
        "Destination address";
    }
    leaf out-interface {
      type xr:live_ncs_Interface-name;
      description
        "Interface on which outbound message was sent";
    }
    leaf out-label {
      type live_ncs_Rsvp-mgmt-mpls-label;
      description
        "Label for outbound traffic";
    }
    leaf backup-interface {
      type xr:live_ncs_Interface-name;
      description
        "Backup tunnel interface";
    }
    leaf backup-label {
      type live_ncs_Rsvp-mgmt-mpls-label;
      description
        "Backup label";
    }
    leaf is-rro-valid {
      type boolean;
      description
        "RRO validity";
    }
    leaf is-flow-spec-valid {
      type boolean;
      description
        "FlowSpec validity";
    }
    list rro {
      description
        "Record route object";
      uses live_ncs_RSVP-MGMT-RRO-SUBOBJ;
    }
  }

  grouping live_ncs_RSVP-MGMT-REV-LSP-UNSUPPORTED-SUBOBJ {
    description
      "RSVP MGMT REV LSP UNSUPPORTED SUBOBJ";
    list rsvp-mgmt-rev-lsp-unsupported-subobj {
      description
        "rsvp mgmt rev lsp unsupported subobj";
      leaf entry {
        type uint8;
        description
          "rsvp mgmt rev lsp unsupported subobj";
      }
    }
  }

  grouping live_ncs_RSVP-MGMT-REVERSE-LSP {
    description
      "RSVP REVERSE_LSP Object";
    container generic-traffic-spec {
      description
        "Generic Traffic Spec object";
      uses live_ncs_RSVP-MGMT-GEN-TRAFFIC-SPEC;
    }
    list ero {
      description
        "Explicit Route Sub Objects";
      uses live_ncs_RSVP-MGMT-ERO-SUBOBJ;
    }
    list unsup-sub-object {
      description
        "Unsupported REVERSE_LSP Sub Objects";
      uses live_ncs_RSVP-MGMT-REV-LSP-UNSUPPORTED-SUBOBJ;
    }
  }

  grouping live_ncs_RSVP-MGMT-PROTECTION-LINK-FLAGS {
    description
      "RSVP PROTECTION Object Link Flags";
    leaf enhanced {
      type boolean;
      description
        "Indicates Enhanced Protection Scheme";
    }
    leaf ded1-plus1 {
      type boolean;
      description
        "Dedicated 1+1 Protection";
    }
    leaf ded1-to1 {
      type boolean;
      description
        "Dedicated 1:1 Protection";
    }
    leaf shared {
      type boolean;
      description
        "Shared Link Layer Protection";
    }
    leaf unprotected {
      type boolean;
      description
        "LSP should not use any Link Layer Protection";
    }
    leaf extra-traffic {
      type boolean;
      description
        "LSP should use Links that are protecting other
         (primary) traffic";
    }
    leaf reserved-bit1 {
      type boolean;
      description
        "Reserved Bit 1";
    }
    leaf reserved-bit2 {
      type boolean;
      description
        "Reserved Bit 2";
    }
  }

  grouping live_ncs_RSVP-MGMT-PROTECTION-LSP-FLAGS {
    description
      "RSVP PROTECTION Object LSP Flags";
    leaf rerouting {
      type boolean;
      description
        "Full Rerouting";
    }
    leaf rerouting-no-et {
      type boolean;
      description
        "Rerouting Without Extra-Traffic";
    }
    leaf one-to-n-protection-et {
      type boolean;
      description
        "1:N Protection with Extra-Traffic";
    }
    leaf one-plus-one-uni {
      type boolean;
      description
        "1+1 Unidirectional Protection";
    }
    leaf one-plus-one-bi {
      type boolean;
      description
        "1+1 Bidirectional Protection";
    }
  }

  grouping live_ncs_RSVP-MGMT-PROTECTION {
    description
      "RSVP PROTECTION Object Info";
    container lsp-flags {
      description
        "PROTECTION Object LSP Flags";
      uses live_ncs_RSVP-MGMT-PROTECTION-LSP-FLAGS;
    }
    container link-flags {
      description
        "PROTECTION Object Link Flags";
      uses live_ncs_RSVP-MGMT-PROTECTION-LINK-FLAGS;
    }
    leaf s {
      type boolean;
      description
        "Secondary Bit";
    }
    leaf p {
      type boolean;
      description
        "Protecting Bit";
    }
    leaf n {
      type boolean;
      description
        "Notification Bit";
    }
    leaf o {
      type boolean;
      description
        "Operational Bit";
    }
  }

  grouping live_ncs_RSVP-MGMT-ASSOCIATION-IPV6-EXT {
    description
      "RSVP EXTENDED ASSOCIATION IPv6 Object Info";
    leaf type {
      type uint16;
      description
        "Association Type (RFC 4872)";
    }
    leaf id {
      type uint16;
      description
        "Association ID";
    }
    leaf source {
      type inet:ipv6-address;
      description
        "Association IPV6 Source Address";
    }
    leaf global-source {
      type uint32;
      description
        "Global Association Source";
    }
    list extended-id {
      description
        "Extended Association ID";
      leaf entry {
        type uint32;
        description
          "Extended Association ID";
      }
    }
  }

  grouping live_ncs_RSVP-MGMT-ASSOCIATION-IPV4-EXT {
    description
      "RSVP EXTENDED ASSOCIATION IPv4 Object Info";
    leaf type {
      type uint16;
      description
        "Association Type (RFC 4872)";
    }
    leaf id {
      type uint16;
      description
        "Association ID";
    }
    leaf source {
      type inet:ipv4-address;
      description
        "Association IPV4 Source Address";
    }
    leaf global-source {
      type uint32;
      description
        "Global Association Source";
    }
    list extended-id {
      description
        "Extended Association ID";
      leaf entry {
        type uint32;
        description
          "Extended Association ID";
      }
    }
  }

  grouping live_ncs_RSVP-MGMT-ASSOCIATION-IPV6 {
    description
      "RSVP ASSOCIATION IPv6 Object Info";
    leaf type {
      type uint16;
      description
        "Association Type (RFC 4872)";
    }
    leaf id {
      type uint16;
      description
        "Association ID";
    }
    leaf source {
      type inet:ipv6-address;
      description
        "Association IPV6 Source Address";
    }
  }

  grouping live_ncs_RSVP-MGMT-ASSOCIATION-IPV4 {
    description
      "RSVP ASSOCIATION IPv4 Object Info";
    leaf type {
      type uint16;
      description
        "Association Type (RFC 4872)";
    }
    leaf id {
      type uint16;
      description
        "Association ID";
    }
    leaf source {
      type inet:ipv4-address;
      description
        "Association IPV4 Source Address";
    }
  }

  grouping live_ncs_RSVP-MGMT-ASSOCIATION {
    description
      "Union of the different ASSOCIATION types";
    container ipv4 {
      // NCS drop when statement
      description
        "IPV4 ASSOCIATION Object";
      uses live_ncs_RSVP-MGMT-ASSOCIATION-IPV4;
    }
    container ipv6 {
      // NCS drop when statement
      description
        "IPV6 ASSOCIATION Object";
      uses live_ncs_RSVP-MGMT-ASSOCIATION-IPV6;
    }
    container extended-ipv4 {
      // NCS drop when statement
      description
        "EXTENDED IPV4 ASSOCIATION Object";
      uses live_ncs_RSVP-MGMT-ASSOCIATION-IPV4-EXT;
    }
    container extended-ipv6 {
      // NCS drop when statement
      description
        "EXTENDED IPV6 ASSOCIATION Object";
      uses live_ncs_RSVP-MGMT-ASSOCIATION-IPV6-EXT;
    }
    leaf association-type {
      type live_ncs_Rsvp-mgmt-association;
      description
        "AssociationType";
    }
  }

  grouping live_ncs_RSVP-MGMT-RRO-SRLG-SUBOBJ {
    description
      "RSVP RRO SRLG subobject";
    list srl-gs {
      description
        "The RRO Subobject SRLGs";
      leaf entry {
        type uint32;
        description
          "The RRO Subobject SRLGs";
      }
    }
  }

  grouping live_ncs_RSVP-MGMT-RRO-UNNUMBERED-SUBOBJ-FLAGS {
    description
      "RSVP RRO UNNUMBERED Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping live_ncs_RSVP-MGMT-RRO-UNNUMBERED-SUBOBJ {
    description
      "RSVP RRO Unnumbered subobject";
    container flags {
      description
        "The RRO Subobject Unnumbered Flags";
      uses live_ncs_RSVP-MGMT-RRO-UNNUMBERED-SUBOBJ-FLAGS;
    }
    leaf interface-address {
      type inet:ipv4-address;
      description
        "The RRO Interface Address";
    }
    leaf interface-id {
      type uint32;
      description
        "The RRO Interface ID";
    }
  }

  grouping live_ncs_RSVP-MGMT-RRO-LABEL-SUBOBJ-FLAGS {
    description
      "RSVP RRO Label Subobject Flags";
    leaf is-global-label {
      type boolean;
      description
        "Label is Global across all interfaces";
    }
  }

  grouping live_ncs_RSVP-MGMT-RRO-LABEL-SUBOBJ {
    description
      "RSVP RRO Label subobject";
    container flags {
      description
        "The RRO Subobject Label Flags";
      uses live_ncs_RSVP-MGMT-RRO-LABEL-SUBOBJ-FLAGS;
    }
    leaf label {
      type uint32;
      description
        "The RRO Subobject Label Value";
    }
    leaf is-label-variable-length {
      type boolean;
      description
        "Is the RRO Subobject Label Variable Length";
    }
    list variable-length-label {
      description
        "The RRO Subobject Variable Length Label";
      leaf entry {
        type uint32;
        description
          "The RRO Subobject Variable Length Label";
      }
    }
  }

  grouping live_ncs_RSVP-MGMT-RRO-IPV4-SUBOBJ-FLAGS {
    description
      "RSVP RRO IPV4 Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping live_ncs_RSVP-MGMT-RRO-IPV4-SUBOBJ {
    description
      "RSVP RRO IPV4 subobject";
    container flags {
      description
        "The RRO IPV4 Subobject Flags";
      uses live_ncs_RSVP-MGMT-RRO-IPV4-SUBOBJ-FLAGS;
    }
    leaf rro-address {
      type inet:ipv4-address;
      description
        "The RRO IPV4 Address";
    }
  }

  grouping live_ncs_RSVP-MGMT-RRO-SUBOBJ {
    description
      "Union of the different RSVP RRO types";
    container ipv4rro-sub-object {
      // NCS drop when statement
      description
        "IPV4 RRO Sub Object";
      uses live_ncs_RSVP-MGMT-RRO-IPV4-SUBOBJ;
    }
    container label-rro-sub-object {
      // NCS drop when statement
      description
        "Label RRO Sub Object";
      uses live_ncs_RSVP-MGMT-RRO-LABEL-SUBOBJ;
    }
    container unnumbered-rro-sub-object {
      // NCS drop when statement
      description
        "Unnumbered RRO Sub Object";
      uses live_ncs_RSVP-MGMT-RRO-UNNUMBERED-SUBOBJ;
    }
    container srlg-rro-sub-object {
      // NCS drop when statement
      description
        "SRLG RRO Sub Object";
      uses live_ncs_RSVP-MGMT-RRO-SRLG-SUBOBJ;
    }
    leaf rro-type {
      type live_ncs_Rsvp-mgmt-rro-subobj;
      description
        "RROType";
    }
  }

  grouping live_ncs_RSVP-SESSION-PSB-DETAIL {
    description
      "RSVP Detail Session Path Info";
    container generic-in-label {
      description
        "Generic Label for inbound traffic";
      uses live_ncs_RSVP-MGMT-GENERIC-LABEL;
    }
    container traffic-spec {
      description
        "Traffic Spec object";
      uses live_ncs_RSVP-MGMT-TRAFFIC-SPEC;
    }
    container generic-traffic-spec {
      description
        "Generic Traffic Spec object";
      uses live_ncs_RSVP-MGMT-GEN-TRAFFIC-SPEC;
    }
    container association {
      description
        "Association object";
      uses live_ncs_RSVP-MGMT-ASSOCIATION;
    }
    container protection {
      description
        "Protection object";
      uses live_ncs_RSVP-MGMT-PROTECTION;
    }
    container reverse-lsp {
      description
        "Reverse LSP object";
      uses live_ncs_RSVP-MGMT-REVERSE-LSP;
    }
    leaf is-valid {
      type boolean;
      description
        "Entry validity";
    }
    leaf destination-address {
      type inet:ipv4-address;
      description
        "Destination address";
    }
    leaf lsp-id {
      type uint32;
      description
        "LSP ID";
    }
    leaf p2mp-sub-group-origin {
      type inet:ipv4-address;
      description
        "Point to Multipoint SubGroup Origin";
    }
    leaf sub-group-id {
      type uint16;
      description
        "Point to Multipoint Subgroup ID";
    }
    leaf in-interface {
      type xr:live_ncs_Interface-name;
      description
        "Interface on which inbound message was received";
    }
    leaf in-label {
      type live_ncs_Rsvp-mgmt-mpls-label;
      description
        "Label for inbound traffic";
    }
    leaf lsp-wrap-label {
      type live_ncs_Rsvp-mgmt-mpls-label;
      description
        "LSP Wrap Label";
    }
    leaf is-bad-address {
      type boolean;
      description
        "Address validity";
    }
    leaf incoming-interface-address {
      type inet:ipv4-address;
      description
        "IP address of Path's incoming interface";
    }
    leaf is-ero-valid {
      type boolean;
      description
        "ERO validity";
    }
    leaf is-rro-valid {
      type boolean;
      description
        "RRO validity";
    }
    leaf is-traffic-spec-valid {
      type boolean;
      description
        "Traffic Spec validity";
    }
    leaf tunnel-name {
      type string;
      description
        "Tunnel name";
    }
    list ero {
      description
        "Explicit Route Sub Objects";
      uses live_ncs_RSVP-MGMT-ERO-SUBOBJ;
    }
    list rro {
      description
        "Record Route Sub Objects";
      uses live_ncs_RSVP-MGMT-RRO-SUBOBJ;
    }
  }

  grouping live_ncs_RSVP-SESSION-PSB-RSB-DETAIL {
    description
      "List of Path and Reservation Info";
    list psb-info {
      description
        "Path Info";
      uses live_ncs_RSVP-SESSION-PSB-DETAIL;
    }
    list rsb-info {
      description
        "Reservation Info";
      uses live_ncs_RSVP-SESSION-RSB-DETAIL;
    }
  }

  grouping live_ncs_RSVP-MGMT-SESSION-DETAIL {
    description
      "RSVP Detail Session Info";
    container compact {
      description
        "Compact session data";
      uses live_ncs_RSVP-MGMT-SESSION-COMPACT;
    }
    container s2l-sub-lsp {
      description
        "RSVP S2L Sub-LSP information";
      uses live_ncs_RSVP-MGMT-S2L-SUB-LSP-IPV4;
    }
    list psb-rsb-info {
      description
        "Path and Reservation Info";
      uses live_ncs_RSVP-SESSION-PSB-RSB-DETAIL;
    }
  }

  grouping live_ncs_RSVP-MGMT-KEY {
    description
      "Key to uniquely identify some RSVP records";
    leaf p2mp-id {
      type uint32;
      description
        "Point-to-multipoint ID";
    }
    leaf destination-address {
      type inet:ipv4-address;
      description
        "Destination address";
    }
    leaf destination-port-or-tunnel-id {
      type uint32;
      description
        "Destination Port or Tunnel ID. For the LSP and
         OUNI session types this represents the Tunnel ID
         whereas for the UDP session type this represents
         the Destination Port";
    }
    leaf protocol {
      type uint32;
      description
        "Protocol. UDP session type this represents the
         Protocol (UDP not supported at present)";
    }
    leaf extended-tunnel-id {
      type inet:ipv4-address;
      description
        "Protocol or Extended Tunnel ID. For the LSP and
         OUNI sesion types this represents the Extended
         Tunnel ID";
    }
    leaf session-type {
      type live_ncs_Rsvp-mgmt-session;
      description
        "Session Type (e.g. LSP, OUNI or UDP)";
    }
    leaf source-address {
      type inet:ipv4-address;
      description
        "Source Address";
    }
    leaf source-port-or-lsp-id {
      type uint32;
      description
        "Source Port or LSP_ID. For the LSP and OUNI
         session types this represents the LSP_ID whereas
         for the UDP session type this represents the
         SourcePort";
    }
    leaf p2mp-sub-group-origin {
      type inet:ipv4-address;
      description
        "Point to Multipoint SubGroup Origin";
    }
    leaf sub-group-id {
      type uint16;
      description
        "Point to Multipoint Subgroup ID";
    }
    leaf vrfid {
      type live_ncs_Rsi-vrf-id;
      description
        "Signalling VRF ID";
    }
  }

  grouping live_ncs_RSVP-MGMT-REQUEST-FLAGS {
    description
      "Request state flags";
    leaf is-local-receiver {
      type boolean;
      description
        "Local Receiver";
    }
    leaf is-refreshing {
      type boolean;
      description
        "Is neighbor refreshing";
    }
    leaf is-send-confirm {
      type boolean;
      description
        "Send Confirm message";
    }
    leaf is-ack-outstanding {
      type boolean;
      description
        "Is ACK message outstanding";
    }
    leaf is-message-id-allocated {
      type boolean;
      description
        "Is MessageID allocated";
    }
    leaf is-nack-received {
      type boolean;
      description
        "A NACK message was received";
    }
    leaf is-retransmit {
      type boolean;
      description
        "Retransmit the message";
    }
    leaf is-paced {
      type boolean;
      description
        "Message is paced";
    }
    leaf is-label-request-in-path {
      type boolean;
      description
        "The Path message contains Label Request";
    }
    leaf is-rro-in-path {
      type boolean;
      description
        "The Path message contains RRO";
    }
    leaf is-record-label-in-path {
      type boolean;
      description
        "Path has Session-Attr object with Record Labels
         set";
    }
    leaf is-merge-point {
      type boolean;
      description
        "Is node a Merge Point";
    }
  }

  grouping live_ncs_RSVP-MGMT-REQUEST-DETAIL {
    description
      "Detailed Form of RSVP Request Info";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container flow-spec {
      description
        "Flow Spec Information";
      uses live_ncs_RSVP-MGMT-FLOW-SPEC;
    }
    container generic-flow-spec {
      description
        "Generic Flow Spec Information";
      uses live_ncs_RSVP-MGMT-GEN-FLOW-SPEC;
    }
    container filter {
      description
        "RSVP Filter";
      uses live_ncs_RSVP-MGMT-FILTER-INFO;
    }
    container style {
      description
        "RSVP Style";
      uses live_ncs_RSVP-MGMT-STYLE;
    }
    container req-flags {
      description
        "Request flags";
      uses live_ncs_RSVP-MGMT-REQUEST-FLAGS;
    }
    container hop {
      description
        "Hop Infomation";
      uses live_ncs_RSVP-MGMT-HOP-INFO;
    }
    container header {
      description
        "RSVP Header Information";
      uses live_ncs_RSVP-MGMT-HEADER-INFO;
    }
    container policy-sources {
      description
        "RSVP Policy Sources";
      uses live_ncs_RSVP-MGMT-POLICY-SOURCES;
    }
    container policy-flags {
      description
        "RSVP Policy Flags";
      uses live_ncs_RSVP-MGMT-POLICY-FLAGS;
    }
    container policy-query-flags {
      description
        "RSVP Query Flags";
      uses live_ncs_RSVP-MGMT-POLICY-QUERY-FLAGS;
    }
    leaf output-interface {
      type string;
      description
        "output Interface";
    }
    list psb-key {
      description
        "List of RSB keys";
      uses live_ncs_RSVP-MGMT-KEY;
    }
    list rsb-key {
      description
        "List of RSB keys";
      uses live_ncs_RSVP-MGMT-KEY;
    }
  }

  grouping live_ncs_RSVP-MGMT-REQUEST-COMPACT {
    description
      "Compact Form of RSVP Request Info";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container flow-spec {
      description
        "Flow Spec Information";
      uses live_ncs_RSVP-MGMT-FLOW-SPEC;
    }
    container generic-flow-spec {
      description
        "Generic Flow Spec Information";
      uses live_ncs_RSVP-MGMT-GEN-FLOW-SPEC;
    }
    container filter {
      description
        "RSVP Filter";
      uses live_ncs_RSVP-MGMT-FILTER-INFO;
    }
    container style {
      description
        "RSVP Style";
      uses live_ncs_RSVP-MGMT-STYLE;
    }
    leaf output-interface {
      type string;
      description
        "Output Interface";
    }
  }

  grouping live_ncs_RSVP-MGMT-FRR-STATES-DETAIL {
    description
      "RSVP states for one FRR LSP";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    leaf path-status {
      type live_ncs_Rsvp-mgmt-frr-state-enum;
      description
        "RSVP FRR Path States";
    }
    leaf reservation-status {
      type live_ncs_Rsvp-mgmt-frr-state-enum;
      description
        "RSVP FRR Reservation States";
    }
  }

  grouping live_ncs_RSVP-GLOBAL-INFO {
    description
      "RSVP global information";
    container issu-status {
      description
        "Issu status";
      uses live_ncs_RSVP-NSR-ISSU-STATUS-INFO;
    }
    container nsr-status {
      description
        "NSR status";
      uses live_ncs_RSVP-NSR-ISSU-STATUS-INFO;
    }
    container database-counters {
      description
        "All database counters";
      uses live_ncs_RSVP-MGMT-ALL-DB-COUNTERS;
    }
    leaf interfaces {
      type uint32;
      description
        "Total interfaces";
    }
    leaf ls-ps {
      type uint32;
      description
        "Total LSPs";
    }
  }

  grouping live_ncs_RSVP-IDT-STATUS {
    description
      "IDT status information";
    leaf sync-status {
      type live_ncs_Rsvp-sync-status;
      description
        "Sync status";
    }
    leaf not-ready-reason {
      type live_ncs_Rsvp-proc-nsr-not-ready-reason;
      description
        "Not ready reason";
    }
    leaf idt-start-time {
      type uint32;
      units "second";
      description
        "IDT start timestamp in seconds";
    }
    leaf idt-end-time {
      type uint32;
      units "second";
      description
        "IDT end timestamp in seconds";
    }
    leaf declare-time {
      type uint32;
      units "second";
      description
        "Declare ready timestamp in seconds";
    }
    leaf withdraw-time {
      type uint32;
      units "second";
      description
        "Withdraw ready timestamp in seconds";
    }
  }

  grouping live_ncs_RSVP-NSR-ISSU-STATUS-INFO {
    description
      "NSR/ISSU status information";
    container idt-status {
      description
        "IDT status";
      uses live_ncs_RSVP-IDT-STATUS;
    }
    container previous-idt-status {
      description
        "Previous IDT status";
      uses live_ncs_RSVP-IDT-STATUS;
    }
    leaf role {
      type live_ncs_Rsvp-proc-role;
      description
        "Process role";
    }
  }

  grouping live_ncs_RSVP-MGMT-IF-NBR-DETAIL {
    description
      "Detail Info for RSVP Interface Neighbor";
    leaf interface-neighbor-address {
      type inet:ipv4-address;
      description
        "Interface Neighbor address";
    }
    leaf neighbor-interface-name {
      type xr:live_ncs_Interface-name;
      description
        "Neighbor's Interface handle";
    }
    leaf is-rr-enabled {
      type boolean;
      description
        "Is Neighbor's RR enable";
    }
    leaf neighbor-epoch {
      type uint32;
      description
        "Neighbor's epoch value";
    }
    leaf out-of-order-messages {
      type uint32;
      description
        "Number of out of order msgs";
    }
    leaf retransmitted-messages {
      type uint32;
      description
        "Number of retransmitted msgs";
    }
  }

  grouping live_ncs_RSVP-MGMT-NBR-DETAIL {
    description
      "Detail Info for RSVP Neighbor";
    leaf node-address {
      type inet:ipv4-address;
      description
        "Neighbor node address";
    }
    list interface-neighbor-list-detail {
      description
        "Detail list of I/F Neighbors";
      uses live_ncs_RSVP-MGMT-IF-NBR-DETAIL;
    }
  }

  grouping live_ncs_RSVP-MGMT-HELLO-IF-INSTANCE-DETAIL {
    description
      "Detail Info for IF-based RSVP Hello Instance";
    container last-message-sent-time {
      description
        "Last Ack/msg sent time";
      uses live_ncs_RSVP-MGMT-TIMESPEC;
    }
    leaf source-address-xr {
      type inet:ipv4-address;
      description
        "Source address";
    }
    leaf destination-address-xr {
      type inet:ipv4-address;
      description
        "Destination address";
    }
    leaf hello-global-neighbor-id {
      type inet:ipv4-address;
      description
        "Global Neighbor ID";
    }
    leaf instance-type {
      type live_ncs_Rsvp-mgmt-hello-instance;
      description
        "Hello instance type";
    }
    leaf hello-interface {
      type xr:live_ncs_Interface-name;
      description
        "Interface to use";
    }
    leaf source-instance {
      type uint32;
      description
        "Source Instance";
    }
    leaf destination-instance {
      type uint32;
      description
        "Destination Instance";
    }
    leaf hello-messages-sent {
      type uint64;
      description
        "Number of hello messages sent";
    }
    leaf hello-messages-received {
      type uint64;
      description
        "Number of hello messages received";
    }
  }

  grouping live_ncs_RSVP-MGMT-HELLO-IF-INSTANCE-COMPACT {
    description
      "Compact Info for IF-based RSVP Hello Instance";
    leaf source-address-xr {
      type inet:ipv4-address;
      description
        "Source address";
    }
    leaf destination-address-xr {
      type inet:ipv4-address;
      description
        "Destination address";
    }
    leaf instance-type {
      type live_ncs_Rsvp-mgmt-hello-instance;
      description
        "Hello instance type";
    }
    leaf hello-interface {
      type xr:live_ncs_Interface-name;
      description
        "Interface to use";
    }
  }

  grouping live_ncs_RSVP-MGMT-LOCAL-NODE-ID-IPV4 {
    description
      "Local Node-id";
    leaf local-node-ip-address {
      type inet:ipv4-address;
      description
        "Local node address";
    }
    leaf application-type {
      type live_ncs_Rsvp-mgmt-gr-app;
      description
        "GR local node-id app type";
    }
  }

  grouping live_ncs_RSVP-MGMT-GRACEFUL-RESTART {
    description
      "RSVP Graceful Restart Info";
    container recovery-time-left {
      description
        "How much recovery timer remains";
      uses live_ncs_RSVP-MGMT-TIMESPEC;
    }
    container recovery-timer-exp-time {
      description
        "Time at which recovery timer will expire";
      uses live_ncs_RSVP-MGMT-TIMESPEC;
    }
    leaf is-gr-enabled {
      type boolean;
      description
        "Whether GR is enabled";
    }
    leaf global-neighbors {
      type uint32;
      description
        "Global neighbor count";
    }
    leaf restart-time {
      type uint32;
      units "millisecond";
      description
        "Restart time (milliseconds)";
    }
    leaf recovery-time {
      type uint32;
      units "millisecond";
      description
        "Recovery time (milliseconds)";
    }
    leaf is-recovery-timer-running {
      type boolean;
      description
        "Whether recovery timer is running";
    }
    leaf hello-interval {
      type uint32;
      description
        "Interval at which hello messages are sent";
    }
    leaf missed-hellos {
      type uint8;
      description
        "Max number of hellos missed before hellos
         declared down";
    }
    leaf pending-states {
      type uint32;
      description
        "Total number of pending states";
    }
    list local-node-address {
      description
        "Local node address";
      uses live_ncs_RSVP-MGMT-LOCAL-NODE-ID-IPV4;
    }
  }

  grouping live_ncs_RSVP-MGMT-INTERFACE-COMPACT {
    description
      "Compact Form of RSVP interface Info";
    container bandwidth-information {
      description
        "Interface bandwidth information";
      uses live_ncs_RSVP-MGMT-DSTE-MODE-INTERFACE-BW;
    }
    leaf interface-name-xr {
      type string;
      description
        "Interface Name";
    }
  }

  grouping live_ncs_RSVP-MGMT-ALL-DB-COUNTERS {
    description
      "All database counters";
    leaf sessions {
      type uint32;
      description
        "Number of sessions";
    }
    leaf incoming-paths {
      type uint32;
      description
        "Number of locally created and incoming path
         states";
    }
    leaf outgoing-paths {
      type uint32;
      description
        "Number of outgoing path states";
    }
    leaf incoming-reservations {
      type uint32;
      description
        "Number of locally created and incoming
         reservation states";
    }
    leaf outgoing-reservations {
      type uint32;
      description
        "Number of outgoing reservation states";
    }
    leaf interfaces {
      type uint32;
      description
        "Number of Interfaces";
    }
  }

  grouping live_ncs_RSVP-SYNC-COUNT-INFO {
    description
      "RSVP sync sent and received counters information";
    leaf last-cleared-timestamp {
      type uint32;
      units "second";
      description
        "The timestamp, in seconds, when these statistics
         are cleared              since 00:00:00 UTC,
         January 1, 1970";
    }
    leaf rsvp-process-role {
      type live_ncs_Rsvp-proc-role;
      description
        "Process role";
    }
    leaf last-idt-states {
      type uint32;
      description
        "Last IDT number of states";
    }
    leaf total-states {
      type uint32;
      description
        "Total number of states";
    }
    leaf total-deletions {
      type uint32;
      description
        "Total number of deletions";
    }
    leaf total-nacks {
      type uint64;
      description
        "Total number of NACKs";
    }
    leaf total-id-ts {
      type uint32;
      description
        "Total number of IDTs";
    }
  }

  grouping live_ncs_RSVP-MGMT-EVENT-COUNT-INFO {
    description
      "Count of events";
    leaf expired-paths {
      type uint32;
      description
        "Counter for Expired Path states";
    }
    leaf expired-reservations {
      type uint32;
      description
        "Counter for Expired Reservation states";
    }
    leaf nac-ks {
      type uint32;
      description
        "Counter for NACKs received";
    }
  }

  grouping live_ncs_RSVP-MGMT-COUNTERS-OOR {
    description
      "Counters for all messages dropped in OOR
       condition";
    leaf dropped-path-messages {
      type uint32;
      description
        "Count of Path messages dropped due to an out of
         resource condition";
    }
  }

  grouping live_ncs_RSVP-MGMT-COUNT-PREFIX-INTERFACE-INFO {
    description
      "Prefix filtering interface counters";
    container forwarded {
      description
        "Count of messages which got forwarded";
      uses live_ncs_RSVP-MGMT-COUNT-PREFIX-MSG;
    }
    container locally-destined {
      description
        "Count of locally destined messages";
      uses live_ncs_RSVP-MGMT-COUNT-PREFIX-MSG;
    }
    container dropped {
      description
        "Count of messages dropped";
      uses live_ncs_RSVP-MGMT-COUNT-PREFIX-MSG;
    }
    container default-action-dropped {
      description
        "Count of messages which got dropped due to
         default ACL action";
      uses live_ncs_RSVP-MGMT-COUNT-PREFIX-MSG;
    }
    container default-action-processed {
      description
        "Count of messages which were processed due to
         default ACL action";
      uses live_ncs_RSVP-MGMT-COUNT-PREFIX-MSG;
    }
    container total {
      description
        "Count of total messages";
      uses live_ncs_RSVP-MGMT-COUNT-PREFIX-MSG;
    }
  }

  grouping live_ncs_RSVP-MGMT-COUNT-PREFIX-MSG {
    description
      "Message types for prefix filtering";
    leaf path {
      type uint32;
      description
        "Count of Path messages";
    }
    leaf path-tear {
      type uint32;
      description
        "Count of PathTear messages";
    }
    leaf reservation-confirm {
      type uint32;
      description
        "Count of ReservationConfirm messages";
    }
    leaf total {
      type uint32;
      description
        "Total count of messages";
    }
  }

  grouping live_ncs_RSVP-MGMT-COUNT-PREFIX-ACL-INFO {
    description
      "Prefix filtering ACL counters";
    container forwarded {
      description
        "Count of messages which got forwarded";
      uses live_ncs_RSVP-MGMT-COUNT-PREFIX-MSG;
    }
    container locally-destined {
      description
        "Count of locally destined messages";
      uses live_ncs_RSVP-MGMT-COUNT-PREFIX-MSG;
    }
    container dropped {
      description
        "Count of messages dropped";
      uses live_ncs_RSVP-MGMT-COUNT-PREFIX-MSG;
    }
    container total {
      description
        "Count of total messages";
      uses live_ncs_RSVP-MGMT-COUNT-PREFIX-MSG;
    }
  }

  grouping live_ncs_RSVP-MGMT-COUNTS {
    description
      "Counters for all known RSVP message types";
    leaf path {
      type uint32;
      description
        "Count of Path messages";
    }
    leaf reservation {
      type uint32;
      description
        "Count of Reservation messages";
    }
    leaf path-error {
      type uint32;
      description
        "Count of PathError messages";
    }
    leaf reservation-error {
      type uint32;
      description
        "Count of ReservationError messages";
    }
    leaf path-tear {
      type uint32;
      description
        "Count of PathTear messages";
    }
    leaf reservation-tear {
      type uint32;
      description
        "Count of ReservationTear messages";
    }
    leaf reservation-confirm {
      type uint32;
      description
        "Count of ReservationConfirm messages";
    }
    leaf bundle {
      type uint32;
      description
        "Count of Bundle messages";
    }
    leaf ack {
      type uint32;
      description
        "Count of ACK messages";
    }
    leaf srefresh {
      type uint32;
      description
        "Count of Srefresh messages";
    }
    leaf hello {
      type uint32;
      description
        "Count of Hello messages";
    }
    leaf challenge {
      type uint32;
      description
        "Count of Integrity Challenge messages";
    }
    leaf response {
      type uint32;
      description
        "Count of Integrity Response messages";
    }
  }

  grouping live_ncs_RSVP-MGMT-COUNT-MESSAGE {
    description
      "Counters for all messages";
    container received-messages {
      description
        "Count of messages received";
      uses live_ncs_RSVP-MGMT-COUNTS;
    }
    container transmitted-messages {
      description
        "Count of messages transmitted";
      uses live_ncs_RSVP-MGMT-COUNTS;
    }
    container bundle-received-messages {
      description
        "Count of Bundle messages received";
      uses live_ncs_RSVP-MGMT-COUNTS;
    }
    container bundle-transmitted-messages {
      description
        "Count of Bundle messages transmitted";
      uses live_ncs_RSVP-MGMT-COUNTS;
    }
    leaf retransmitted-messages {
      type uint32;
      description
        "Count of messages retransmitted";
    }
    leaf out-of-order-messages {
      type uint32;
      description
        "Count of Out of Order messages";
    }
    leaf rate-limited-messages {
      type uint32;
      description
        "Count of Rate Limited messages";
    }
  }

  grouping live_ncs_RSVP-MGMT-RESERVATION-COMPACT {
    description
      "Compact Form of RSVP Reservation Info";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container flow-spec {
      description
        "Flow Spec Information";
      uses live_ncs_RSVP-MGMT-FLOW-SPEC;
    }
    container generic-flow-spec {
      description
        "Generic Flow Spec Info";
      uses live_ncs_RSVP-MGMT-GEN-FLOW-SPEC;
    }
    container style {
      description
        "RSVP Style";
      uses live_ncs_RSVP-MGMT-STYLE;
    }
    container filter {
      description
        "RSVP Filter";
      uses live_ncs_RSVP-MGMT-FILTER-INFO;
    }
    leaf input-interface {
      type string;
      description
        "Reservation Input Interface";
    }
  }

  grouping live_ncs_RSVP-MGMT-AUTH-RECV-TYPE-COUNTERS {
    description
      "RSVP Authentication Receive Type Counters";
    leaf authentication-received-valid-messages {
      type uint32;
      description
        "Valid messages";
    }
    leaf authentication-received-challenges-sent {
      type uint32;
      description
        "Challenges sent";
    }
    leaf authentication-received-challenge-response {
      type uint32;
      description
        "Challenge responses received";
    }
    leaf authentication-received-challenges-resent {
      type uint32;
      description
        "Challenges resent";
    }
    leaf authentication-received-challenge-timeouts {
      type uint32;
      description
        "Challenge timeouts";
    }
    leaf authentication-received-during-challenge {
      type uint32;
      description
        "Authentication received during challenge";
    }
    leaf authentication-received-incomplete {
      type uint32;
      description
        "Authentication received incomplete";
    }
    leaf authentication-received-no-integrity {
      type uint32;
      description
        "Authentication received with no integrity";
    }
    leaf authentication-received-bad-digest {
      type uint32;
      description
        "Authentication received with bad digest";
    }
    leaf authentication-received-wrong-digest-type {
      type uint32;
      description
        "Authentication received with wrong digest type";
    }
    leaf authentication-received-sequence-number-duplicate {
      type uint32;
      description
        "Authentication received with duplicate sequence
         number";
    }
    leaf authentication-received-sequence-number-outof-range {
      type uint32;
      description
        "Authentication received with sequence number out
         of range";
    }
    leaf authentication-received-wrong-challenges-response {
      type uint32;
      description
        "Incorect challenge responses received";
    }
    leaf authentication-received-challenges-response-duplicate {
      type uint32;
      description
        "Duplicate challenge responses received";
    }
    leaf authentication-received-response-late {
      type uint32;
      description
        "Challenge responses received late";
    }
    leaf authentication-received-bad-message-format {
      type uint32;
      description
        "Authentication received with bad mesage format";
    }
  }

  grouping live_ncs_RSVP-MGMT-AUTH-DIRECTION-RECV {
    description
      "RSVP Authentication Recieve Type Information";
    container counters {
      description
        "Counters";
      uses live_ncs_RSVP-MGMT-AUTH-RECV-TYPE-COUNTERS;
    }
    leaf sequence {
      type uint64;
      description
        "Sequence number";
    }
    leaf sequence-window-size {
      type uint32;
      description
        "Sequence window size";
    }
    leaf sequence-window-count {
      type uint32;
      description
        "Sequence window count";
    }
    list sequence-window {
      // NCS drop max-elements statement
      description
        "Sequence window";
      leaf entry {
        type uint64;
        description
          "Sequence window";
      }
    }
  }

  grouping live_ncs_RSVP-MGMT-AUTH-SEND-TYPE-COUNTERS {
    description
      "RSVP Authentication Send Type Counters";
    leaf authentication-sent {
      type uint32;
      description
        "Messages sent";
    }
    leaf authentication-failures {
      type uint32;
      description
        "Failures";
    }
    leaf authentication-send-challenges-received {
      type uint32;
      description
        "Challenges received";
    }
    leaf authentication-challenge-responses-sent {
      type uint32;
      description
        "Challenge responses sent";
    }
  }

  grouping live_ncs_RSVP-MGMT-AUTH-DIRECTION-SEND {
    description
      "RSVP Authentication Send Type Information";
    container counters {
      description
        "Counters";
      uses live_ncs_RSVP-MGMT-AUTH-SEND-TYPE-COUNTERS;
    }
    leaf sequence {
      type uint64;
      description
        "Sequence number";
    }
  }

  grouping live_ncs_RSVP-MGMT-AUTH-DIRECTION {
    description
      "Union of the different RSVP Authentication
       Direction types";
    container send-info {
      // NCS drop when statement
      description
        "send info";
      uses live_ncs_RSVP-MGMT-AUTH-DIRECTION-SEND;
    }
    container receive-info {
      // NCS drop when statement
      description
        "receive info";
      uses live_ncs_RSVP-MGMT-AUTH-DIRECTION-RECV;
    }
    leaf auth-direction {
      type live_ncs_Rsvp-mgmt-auth-direction;
      description
        "AuthDirection";
    }
  }

  grouping live_ncs_RSVP-MGMT-AUTHENTICATION-DETAIL {
    description
      "Authentication Detail Information";
    container auth-compact {
      description
        "Basic authentication data";
      uses live_ncs_RSVP-MGMT-AUTHENTICATION-COMPACT;
    }
    container direction-info {
      description
        "direction info";
      uses live_ncs_RSVP-MGMT-AUTH-DIRECTION;
    }
    leaf key-status {
      type uint32;
      description
        "Key status";
    }
    leaf key-digest-info {
      type uint32;
      description
        "Direction";
    }
    leaf lifetime {
      type uint32;
      units "second";
      description
        "Lifetime (seconds)";
    }
    leaf lifetime-left {
      type uint32;
      units "second";
      description
        "Remaining lifetime (seconds)";
    }
    leaf challenge-status {
      type live_ncs_Rsvp-mgmt-auth-challenge-status;
      description
        "Challenge status";
    }
  }

  grouping live_ncs_RSVP-MGMT-HELLO-INSTANCE-COMPACT {
    description
      "Compact Info for RSVP Hello Instance";
    leaf source-address-xr {
      type inet:ipv4-address;
      description
        "Source address";
    }
    leaf destination-address-xr {
      type inet:ipv4-address;
      description
        "Destination address";
    }
    leaf neighbor-hello-state {
      type live_ncs_Rsvp-mgmt-hello-state;
      description
        "Neighbor Hello state";
    }
    leaf instance-type {
      type live_ncs_Rsvp-mgmt-hello-instance;
      description
        "Hello instance type";
    }
    leaf hello-interface {
      type xr:live_ncs_Interface-name;
      description
        "Interface to use";
    }
    leaf lost-communication-total {
      type uint16;
      description
        "Total number of times communication got lost";
    }
  }

  grouping live_ncs_RSVP-MGMT-RSB-FLAGS {
    description
      "Reservation State Block Flags";
    leaf is-local-receiver {
      type boolean;
      description
        "Local Receiver";
    }
    leaf is-message-id-valid {
      type boolean;
      description
        "MessageID Valid";
    }
    leaf is-local-repair {
      type boolean;
      description
        "Rerouted";
    }
    leaf is-merge-point {
      type boolean;
      description
        "Is node a Merge Point";
    }
    leaf is-lockout {
      type boolean;
      description
        "Locked Out";
    }
  }

  grouping live_ncs_RSVP-MGMT-STYLE {
    description
      "RSVP Reservation Style";
    leaf reservation-type {
      type live_ncs_Rsvp-mgmt-reservation-type-enum;
      description
        "The Reservation Type: WF, SE or FF";
    }
  }

  grouping live_ncs_RSVP-MGMT-FLOW-SPEC-G709-OTN {
    description
      "RSVP G709 OTN FlowSpec Info";
    leaf flow-signal-type {
      type uint8;
      description
        "G709 OTN Flow Signal Type (Refer G709 v3)";
    }
    leaf flow-nvc {
      type uint16;
      description
        "G709 OTN Flow NVC";
    }
    leaf flow-multiplier {
      type uint16;
      description
        "G709 OTN Flow Multiplier";
    }
    leaf flow-bit-rate {
      type uint64;
      description
        "G709 OTN Flow Bit Rate";
    }
  }

  grouping live_ncs_RSVP-MGMT-GEN-FLOW-SPEC {
    description
      "Union of different RSVP Generic FlowSpec types";
    container g709otn-flow-spec {
      // NCS drop when statement
      description
        "G709 OTN FlowSpec";
      uses live_ncs_RSVP-MGMT-FLOW-SPEC-G709-OTN;
    }
    leaf flow-spec-type {
      type live_ncs_Rsvp-mgmt-flow-spec;
      description
        "FlowSpecType";
    }
  }

  grouping live_ncs_RSVP-MGMT-FLOW-SPEC {
    description
      "RSVP Flow Spec";
    leaf flow-average-rate {
      type uint64;
      units "byte/s";
      description
        "The Flow Average Rate in bytes per second";
    }
    leaf flow-max-burst {
      type uint64;
      description
        "The Flow Maximum Burst";
    }
    leaf flow-peak-rate {
      type uint64;
      units "byte/s";
      description
        "The Flow Peak Rate in bytes per second";
    }
    leaf flow-min-unit {
      type uint32;
      description
        "The Flow Minimum Unit";
    }
    leaf flow-max-unit {
      type uint32;
      description
        "The Flow Maximum Unit";
    }
    leaf flow-requested-rate {
      type uint64;
      units "byte/s";
      description
        "The Flow Requested Rate in bytes per second";
    }
    leaf flow-slack {
      type uint32;
      description
        "The Flow Slack";
    }
    leaf flow-qos {
      type live_ncs_Rsvp-mgmt-qos-service-enum;
      description
        "The Flow Quality of Service";
    }
  }

  grouping live_ncs_RSVP-MGMT-RESERVATION-DETAIL {
    description
      "Detailed Form of RSVP Reservation Info";
    container flow-spec {
      description
        "Flow Spec Information";
      uses live_ncs_RSVP-MGMT-FLOW-SPEC;
    }
    container generic-flow-spec {
      description
        "Generic Flow Spec Information";
      uses live_ncs_RSVP-MGMT-GEN-FLOW-SPEC;
    }
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container style {
      description
        "RSVP Style";
      uses live_ncs_RSVP-MGMT-STYLE;
    }
    container filter {
      description
        "RSVP Filter";
      uses live_ncs_RSVP-MGMT-FILTER-INFO;
    }
    container rsb-flags {
      description
        "Reservation State Block Flags";
      uses live_ncs_RSVP-MGMT-RSB-FLAGS;
    }
    container hop {
      description
        "Hop Infomation";
      uses live_ncs_RSVP-MGMT-HOP-INFO;
    }
    container policy-sources {
      description
        "RSVP Policy Sources";
      uses live_ncs_RSVP-MGMT-POLICY-SOURCES;
    }
    container header {
      description
        "RSVP Header Information";
      uses live_ncs_RSVP-MGMT-HEADER-INFO;
    }
    container policy-flags {
      description
        "RSVP Policy Flags";
      uses live_ncs_RSVP-MGMT-POLICY-FLAGS;
    }
    container expiry-time {
      description
        "Expiry Time";
      uses live_ncs_RSVP-MGMT-TIMESPEC;
    }
    container policy-query-flags {
      description
        "RSVP Query Flags";
      uses live_ncs_RSVP-MGMT-POLICY-QUERY-FLAGS;
    }
    container label-info {
      description
        "Label Information";
      uses live_ncs_RSVP-MGMT-LABEL-INFO;
    }
    leaf input-adjusted-interface {
      type string;
      description
        "Input Adjusted Interface";
    }
    leaf input-physical-interface {
      type string;
      description
        "Input Physical Interface";
    }
  }

  grouping live_ncs_RSVP-MGMT-FRR-STATE-STATUS-COUNTERS {
    description
      "FRR state counters";
    leaf total {
      type uint32;
      description
        "Total number of instances of this state";
    }
    leaf active-instances {
      type uint32;
      description
        "Number of active instances of this state";
    }
    leaf ready-instances {
      type uint32;
      description
        "Number of ready instances of this state";
    }
    leaf active-wait-instances {
      type uint32;
      description
        "Number of instances of this state awaiting Path
         messages to be sent out or Resv messages to be
         received";
    }
  }

  grouping live_ncs_RSVP-MGMT-FRR-STATES-COMPACT {
    description
      "Count of RSVP FRR States";
    container path-states {
      description
        "Path state counters";
      uses live_ncs_RSVP-MGMT-FRR-STATE-STATUS-COUNTERS;
    }
    container reservation-states {
      description
        "Rerservation state counters";
      uses live_ncs_RSVP-MGMT-FRR-STATE-STATUS-COUNTERS;
    }
  }

  grouping live_ncs_RSVP-MGMT-MESSAGEID {
    description
      "RSVP Message ID";
    leaf message-id {
      type live_ncs_Rsvp-mgmt-messageid;
      description
        "Message ID";
    }
  }

  grouping live_ncs_RSVP-MGMT-NBOR {
    description
      "Neighbor";
    container expiry-time {
      description
        "Expiry time";
      uses live_ncs_RSVP-MGMT-TIMESPEC;
    }
    leaf is-neighbor-refresh-reduction-capable {
      type boolean;
      description
        "Is neighbor capable of Refresh Reduction";
    }
    leaf neighbor-address {
      type inet:ipv4-address;
      description
        "IP address of the neighbor";
    }
    leaf message-ids {
      type uint32;
      description
        "Number of MessageIDs";
    }
    leaf outgoing-states {
      type int32;
      description
        "Number of outgoing states to the neighbour";
    }
    list neighbor-message-id {
      // NCS drop max-elements statement
      description
        "List of Neighbor MessageIDs";
      uses live_ncs_RSVP-MGMT-MESSAGEID;
    }
  }

  grouping live_ncs_RSVP-MGMT-INTERFACE-FLAGS {
    description
      "Interface related flags";
    leaf is-mpls-enabled {
      type boolean;
      description
        "MPLS enabled on interface";
    }
    leaf is-refresh-reduction-enabled {
      type boolean;
      description
        "Refresh Reduction enabled";
    }
    leaf is-pacing-enabled {
      type boolean;
      description
        "Message pacing enabled";
    }
    leaf is-refresh-enabled {
      type boolean;
      description
        "Refresh enabled";
    }
    leaf is-s-refresh-enabled {
      type boolean;
      description
        "Summary Refresh enabled";
    }
    leaf is-interface-down {
      type boolean;
      description
        "Interface is DOWN";
    }
    leaf is-interface-created {
      type boolean;
      description
        "Interface is created";
    }
    leaf is-rel-s-refresh-enabled {
      type boolean;
      description
        "Use reliable xmt for SRefresh";
    }
    leaf is-backup-tunnel {
      type boolean;
      description
        "This is backup tunnel";
    }
    leaf is-rsvp-configured {
      type boolean;
      description
        "RSVP explicitly configured";
    }
    leaf is-non-default-vrf {
      type boolean;
      description
        "Interface is defined in non-Default VRF";
    }
    leaf is-message-bundling-enabled {
      type boolean;
      description
        "Use bundling for outgoing RSVP messages.";
    }
  }

  grouping live_ncs_RSVP-MGMT-INTERFACE-DETAIL {
    description
      "Detail Form of RSVP interface Info";
    container bandwidth-information {
      description
        "Interface bandwidth information";
      uses live_ncs_RSVP-MGMT-DSTE-MODE-INTERFACE-BW;
    }
    container flags {
      description
        "Interface flags";
      uses live_ncs_RSVP-MGMT-INTERFACE-FLAGS;
    }
    leaf interface-name-xr {
      type string;
      description
        "Interface Name";
    }
    leaf signalling-ip-tos {
      type uint8;
      description
        "IP TOS (precedence/DSCP) to use in signalling
         messages";
    }
    leaf integrity-send-password {
      type string {
        length "0..40";
      }
      description
        "Integrity send password";
    }
    leaf integrity-receive-password {
      type string {
        length "0..40";
      }
      description
        "Integrity receive password";
    }
    leaf integrity-receive-password-optional {
      type uint8;
      description
        "Integrity recv password optional";
    }
    leaf refresh-timer-state {
      type live_ncs_Rsvp-timer-state;
      description
        "Refresh timer state";
    }
    leaf summary-refresh-timer-state {
      type live_ncs_Rsvp-timer-state;
      description
        "Summary refresh timer state";
    }
    leaf refresh-interval {
      type int32;
      units "millisecond";
      description
        "Refresh interval in msecs";
    }
    leaf out-of-band-refresh-interval {
      type uint32;
      units "millisecond";
      description
        "Out-of-band Refresh interval in msecs";
    }
    leaf summary-refresh-max-size {
      type uint32;
      units "byte";
      description
        "Max size in bytes of a single SRefresh";
    }
    leaf bundle-message-max-size {
      type uint32;
      units "byte";
      description
        "Max size in bytes of a single Bundle message";
    }
    leaf expiry-timer-state {
      type live_ncs_Rsvp-timer-state;
      description
        "Expiry timer state";
    }
    leaf expiry-states {
      type int32;
      description
        "Number of states for expiry check";
    }
    leaf expiry-interval {
      type int32;
      units "millisecond";
      description
        "Expiry interval in msecs";
    }
    leaf expiry-drops-tolerated {
      type int32;
      description
        "Number of missed messages tolerated";
    }
    leaf out-of-band-expiry-drops-tolerated {
      type uint32;
      description
        "Number of out-of-band missed messages tolerated";
    }
    leaf ack-hold-time {
      type uint32;
      description
        "ACK hold time in msec";
    }
    leaf ack-max-size {
      type uint32;
      description
        "Max size for ACK message";
    }
    leaf retransmit-time {
      type uint32;
      description
        "Retransmit time in msec";
    }
    leaf pacing-interval {
      type uint32;
      units "millisecond";
      description
        "Pacing interval in msecs";
    }
    leaf pacing-message-rate {
      type uint32;
      description
        "No. of messages per interval";
    }
    leaf pacing-timer-state {
      type live_ncs_Rsvp-timer-state;
      description
        "State of pacing timer";
    }
    leaf pacing-messages {
      type int32;
      description
        "Number of messages deferred for pacing";
    }
    list neighbor-array {
      // NCS drop max-elements statement
      description
        "Neighbor array";
      uses live_ncs_RSVP-MGMT-NBOR;
    }
  }

  grouping live_ncs_RSVP-MGMT-ERO-UNNUM-SUBOBJ {
    description
      "RSVP ERO UNNUM subobject";
    leaf is-strict-route {
      type boolean;
      description
        "ERO Entry Is Strict";
    }
    leaf ero-interface-id {
      type uint32;
      description
        "The Interface ID in ERO";
    }
    leaf ero-router-id {
      type inet:ipv4-address;
      description
        "The Router ID in ERO";
    }
    leaf status {
      type live_ncs_Rsvp-mgmt-ero-subobj-status;
      description
        "Status of ERO";
    }
  }

  grouping live_ncs_RSVP-MGMT-ERO-IPV4-SUBOBJ {
    description
      "RSVP ERO IPV4 subobject";
    leaf is-strict-route {
      type boolean;
      description
        "ERO Entry Is Strict";
    }
    leaf ero-address {
      type inet:ipv4-address;
      description
        "The ERO IPV4 Address";
    }
    leaf prefix-length {
      type uint8;
      description
        "ERO Prefix Length";
    }
  }

  grouping live_ncs_RSVP-MGMT-ERO-SUBOBJ {
    description
      "Union of the different RSVP ERO types";
    container ipv4ero-sub-object {
      // NCS drop when statement
      description
        "IPV4 ERO Sub Object";
      uses live_ncs_RSVP-MGMT-ERO-IPV4-SUBOBJ;
    }
    container unnumbered-ero-sub-object {
      // NCS drop when statement
      description
        "Unnumbered ERO Sub Object";
      uses live_ncs_RSVP-MGMT-ERO-UNNUM-SUBOBJ;
    }
    leaf ero-type {
      type live_ncs_Rsvp-mgmt-ero-subobj;
      description
        "EROType";
    }
  }

  grouping live_ncs_RSVP-MGMT-CT-INFO {
    description
      "Class-Type Information";
    leaf is-class-type-info-valid {
      type boolean;
      description
        "Is the Class-Type information valid";
    }
    leaf class-type {
      type uint8;
      description
        "DS-TE Class-Type";
    }
  }

  grouping live_ncs_RSVP-MGMT-GENERALIZED-LABEL {
    description
      "RSVP Generalized Label";
    list value {
      description
        "Generalized Label Value";
      leaf entry {
        type uint32;
        description
          "Generalized Label Value";
      }
    }
  }

  grouping live_ncs_RSVP-MGMT-GENERIC-LABEL {
    description
      "Union of different RSVP Generic Label types";
    container generalized-label {
      // NCS drop when statement
      description
        "Generalized Label";
      uses live_ncs_RSVP-MGMT-GENERALIZED-LABEL;
    }
    leaf generic-label-type {
      type live_ncs_Rsvp-mgmt-generic-label;
      description
        "GenericLabelType";
    }
  }

  grouping live_ncs_RSVP-MGMT-LABEL-INFO {
    description
      "Label Information";
    container generic-local-downstream-label {
      description
        "Generic Local Downstream Label";
      uses live_ncs_RSVP-MGMT-GENERIC-LABEL;
    }
    container generic-outgoing-downstream-label {
      description
        "Generic Outgoing Downstream Label";
      uses live_ncs_RSVP-MGMT-GENERIC-LABEL;
    }
    container generic-merge-point-label {
      description
        "Generic MergePoint Label";
      uses live_ncs_RSVP-MGMT-GENERIC-LABEL;
    }
    container generic-outgoing-upstream-label {
      description
        "Generic Outgoing Upstream Label";
      uses live_ncs_RSVP-MGMT-GENERIC-LABEL;
    }
    container generic-local-upstream-label {
      description
        "Generic Local Upstream Label";
      uses live_ncs_RSVP-MGMT-GENERIC-LABEL;
    }
    container generic-recovery-label {
      description
        "Generic Recovery Label";
      uses live_ncs_RSVP-MGMT-GENERIC-LABEL;
    }
    leaf is-valid {
      type boolean;
      description
        "Is the label information valid";
    }
    leaf local-downstream-label {
      type live_ncs_Rsvp-mgmt-mpls-label;
      description
        "Local Downstream Label";
    }
    leaf outgoing-downstream-label {
      type live_ncs_Rsvp-mgmt-mpls-label;
      description
        "Outgoing Downstream Label";
    }
    leaf merge-point-label {
      type live_ncs_Rsvp-mgmt-mpls-label;
      description
        "MergePoint Label";
    }
    leaf outgoing-upstream-label {
      type live_ncs_Rsvp-mgmt-mpls-label;
      description
        "Outgoing Upstream Label";
    }
    leaf local-upstream-label {
      type live_ncs_Rsvp-mgmt-mpls-label;
      description
        "Local Upstream Label";
    }
    leaf recovery-label {
      type live_ncs_Rsvp-mgmt-mpls-label;
      description
        "Recovery Label";
    }
    leaf lsp-wrap-label {
      type live_ncs_Rsvp-mgmt-mpls-label;
      description
        "LSP Wrap Label";
    }
  }

  grouping live_ncs_RSVP-PATH-FORWARDING-CONTEXT {
    description
      "RSVP Path Forwarding Context";
    container policy-flags {
      description
        "Policy Flags";
      uses live_ncs_RSVP-MGMT-POLICY-FLAGS;
    }
    container policy-query-flags {
      description
        "Policy Query Flags";
      uses live_ncs_RSVP-MGMT-POLICY-QUERY-FLAGS;
    }
    leaf output-interface {
      type string;
      description
        "Output interface";
    }
  }

  grouping live_ncs_RSVP-MGMT-POLICY-QUERY-FLAGS {
    description
      "RSVP Policy Query Flags";
    leaf is-needed {
      type boolean;
      description
        "Needed";
    }
    leaf is-report-required {
      type boolean;
      description
        "Report Required";
    }
    leaf is-resync {
      type boolean;
      description
        "Resynchronization";
    }
    leaf is-bypass {
      type boolean;
      description
        "Bypass";
    }
  }

  grouping live_ncs_RSVP-MGMT-POLICY-FLAGS {
    description
      "RSVP Policy Flags";
    leaf is-accepted {
      type boolean;
      description
        "Accepted";
    }
    leaf is-installed {
      type boolean;
      description
        "Installed";
    }
    leaf is-forwarding {
      type boolean;
      description
        "Forwarding";
    }
  }

  grouping live_ncs_RSVP-MGMT-TIMESPEC {
    description
      "RSVP Time Spec";
    leaf seconds {
      type int32;
      units "second";
      description
        "Time Value in Seconds";
    }
    leaf nanoseconds {
      type int32;
      units "nanosecond";
      description
        "Time Value in Nano-seconds";
    }
  }

  grouping live_ncs_RSVP-MGMT-HEADER-INFO {
    description
      "RSVP/IP Header Info";
    leaf rsvp-version {
      type uint8;
      description
        "RSVP Version";
    }
    leaf rsvp-header-flags {
      type uint8;
      description
        "RSVP Header Flags (defined in RFC2205 Section 3
         .1.1)";
    }
    leaf rsvp-ttl {
      type uint8;
      description
        "RSVP TTL";
    }
    leaf rsvp-message-type {
      type uint8;
      description
        "RSVP Message Type";
    }
    leaf ip-tos {
      type uint8;
      description
        "IP Type of Service";
    }
    leaf ip-ttl {
      type uint8;
      description
        "IP TTL";
    }
    leaf ip-source-address {
      type inet:ipv4-address;
      description
        "IP Source Address";
    }
  }

  grouping live_ncs_RSVP-MGMT-POLICY-SOURCES {
    description
      "RSVP Policy Sources";
    leaf is-te-link {
      type boolean;
      description
        "Policy Source is TE Link";
    }
    leaf is-local {
      type boolean;
      description
        "Policy Source is Local";
    }
    leaf is-cops {
      type boolean;
      description
        "Policy Source is COPS";
    }
    leaf is-default {
      type boolean;
      description
        "Policy Source is Default";
    }
    leaf is-cable {
      type boolean;
      description
        "Policy Source is Cable";
    }
  }

  grouping live_ncs_RSVP-MGMT-HOP-INFO {
    description
      "Hop Info";
    leaf neighbor-address {
      type inet:ipv4-address;
      description
        "IP address of the neighbor";
    }
    leaf neighbor-logical-interface-handle {
      type uint32;
      description
        "Neighbor Logical Interface Handle";
    }
  }

  grouping live_ncs_RSVP-MGMT-PATH-FLAGS {
    description
      "RSVP Path Flags";
    leaf is-non-rsvp-hop-upstream {
      type boolean;
      description
        "Non-RSVP Hop Upstream";
    }
    leaf is-local-sender {
      type boolean;
      description
        "Local Sender";
    }
    leaf is-message-id-valid {
      type boolean;
      description
        "MessageID Valid";
    }
    leaf is-local-repair {
      type boolean;
      description
        "Rerouted";
    }
    leaf is-bidirectional {
      type boolean;
      description
        "Bidirectional";
    }
    leaf is-lockout {
      type boolean;
      description
        "Locked Out";
    }
  }

  grouping live_ncs_RSVP-MGMT-TSPEC-G709-OTN {
    description
      "RSVP G709 OTN Sender Tspec Info";
    leaf traffic-signal-type {
      type uint8;
      description
        "G709 OTN Traffic Signal Type (Refer G709 v3)";
    }
    leaf traffic-nvc {
      type uint16;
      description
        "G709 OTN Traffic NVC";
    }
    leaf traffic-multiplier {
      type uint16;
      description
        "G709 OTN Traffic Multiplier";
    }
    leaf traffic-bit-rate {
      type uint64;
      description
        "G709 OTN Traffic Bit Rate";
    }
  }

  grouping live_ncs_RSVP-MGMT-GEN-TRAFFIC-SPEC {
    description
      "Union of different RSVP Generic Sender Tspec
       types";
    container g709otn-tspec {
      // NCS drop when statement
      description
        "G709 OTN Sender Tspec";
      uses live_ncs_RSVP-MGMT-TSPEC-G709-OTN;
    }
    container intsrv-tspec {
      // NCS drop when statement
      description
        "Integrated Services Sender Tspec";
      uses live_ncs_RSVP-MGMT-TRAFFIC-SPEC;
    }
    leaf tspec-type {
      type live_ncs_Rsvp-mgmt-tspec;
      description
        "TspecType";
    }
  }

  grouping live_ncs_RSVP-MGMT-TRAFFIC-SPEC {
    description
      "RSVP Traffic Spec Info";
    leaf traffic-average-rate {
      type uint64;
      units "byte/s";
      description
        "Traffic Average Rate in bytes per second";
    }
    leaf traffic-max-burst {
      type uint64;
      description
        "Traffic Maximum Burst";
    }
    leaf traffic-peak-rate {
      type uint64;
      units "byte/s";
      description
        "Traffic Peak Rate in bytes per second";
    }
    leaf traffic-min-unit {
      type uint32;
      description
        "Traffic Minimum Unit";
    }
    leaf traffic-max-unit {
      type uint32;
      description
        "Traffic Maximum Unit";
    }
  }

  grouping live_ncs_RSVP-MGMT-SESSION-ATTRIBUTE-FLAGS {
    description
      "RSVP Session Attribute Flags";
    leaf is-local-protect {
      type boolean;
      description
        "Local Protection";
    }
    leaf is-node-protect {
      type boolean;
      description
        "Node Protection";
    }
    leaf is-bandwidth-protect {
      type boolean;
      description
        "Bandwidth Protection";
    }
    leaf is-record-labels {
      type boolean;
      description
        "Records Labels";
    }
    leaf is-shared-explicit-requested {
      type boolean;
      description
        "Shared Explicit Requested";
    }
  }

  grouping live_ncs_RSVP-MGMT-SESSION-ATTRIBUTE {
    description
      "RSVP Session Attributes";
    container sess-attribute-flags {
      description
        "Session Attributes";
      uses live_ncs_RSVP-MGMT-SESSION-ATTRIBUTE-FLAGS;
    }
    leaf setup-priority {
      type uint8;
      description
        "Setup Priority";
    }
    leaf reservation-priority {
      type uint8;
      description
        "Reservation Priority";
    }
  }

  grouping live_ncs_RSVP-MGMT-FILTER-P2MP-IPV4 {
    description
      "RSVP P2MP IPv4 FilterSpec";
    leaf source-address {
      type inet:ipv4-address;
      description
        "Source Address";
    }
    leaf source-port {
      type uint16;
      description
        "Source Port";
    }
    leaf p2mp-sub-group-origin {
      type inet:ipv4-address;
      description
        "Point to Multipoint SubGroup Origin";
    }
    leaf sub-group-id {
      type uint16;
      description
        "Point to Multipoint Subgroup ID";
    }
  }

  grouping live_ncs_RSVP-MGMT-FILTER-IPV4 {
    description
      "RSVP Filter";
    leaf source-address {
      type inet:ipv4-address;
      description
        "Source Address";
    }
    leaf source-port {
      type uint16;
      description
        "Source Port";
    }
  }

  grouping live_ncs_RSVP-FILTER-UNION {
    description
      "Union of the different RSVP filterspec types";
    container udp-ipv4-session {
      // NCS drop when statement
      description
        "UDP IPV4 FilterSpec";
      uses live_ncs_RSVP-MGMT-FILTER-IPV4;
    }
    container p2mp-ipv4-session {
      // NCS drop when statement
      description
        "IPv4 P2MP LSP FilterSpec";
      uses live_ncs_RSVP-MGMT-FILTER-P2MP-IPV4;
    }
    leaf filter-type {
      type live_ncs_Rsvp-mgmt-filter;
      description
        "FilterType";
    }
  }

  grouping live_ncs_RSVP-MGMT-FILTER-INFO {
    description
      "RSVP FilterSpec Info";
    container rsvp-filter {
      description
        "RSVP Filter";
      uses live_ncs_RSVP-FILTER-UNION;
    }
  }

  grouping live_ncs_RSVP-MGMT-S2L-SUB-LSP-IPV4 {
    description
      "RSVP S2L Sub-LSP";
    leaf s2l-destination-address {
      type inet:ipv4-address;
      description
        "S2L Sub-LSP Destination Address";
    }
  }

  grouping live_ncs_RSVP-MGMT-PATH-DETAIL {
    description
      "Detailed Form of RSVP Path Info";
    container session {
      description
        "RSVP Session Information";
      uses live_ncs_RSVP-MGMT-SESSION-INFO;
    }
    container s2l-sub-lsp {
      description
        "RSVP S2L Sub-LSP information";
      uses live_ncs_RSVP-MGMT-S2L-SUB-LSP-IPV4;
    }
    container template {
      description
        "RSVP Template";
      uses live_ncs_RSVP-MGMT-FILTER-INFO;
    }
    container session-attribute {
      description
        "RSVP Session Attribute";
      uses live_ncs_RSVP-MGMT-SESSION-ATTRIBUTE;
    }
    container traffic-spec {
      description
        "RSVP Traffic Spec Info";
      uses live_ncs_RSVP-MGMT-TRAFFIC-SPEC;
    }
    container generic-traffic-spec {
      description
        "RSVP Generic Traffic Spec Info";
      uses live_ncs_RSVP-MGMT-GEN-TRAFFIC-SPEC;
    }
    container path-flags {
      description
        "Path Flags";
      uses live_ncs_RSVP-MGMT-PATH-FLAGS;
    }
    container hop {
      description
        "Path Hop Info";
      uses live_ncs_RSVP-MGMT-HOP-INFO;
    }
    container policy-source-info {
      description
        "Policy Sources Info";
      uses live_ncs_RSVP-MGMT-POLICY-SOURCES;
    }
    container header {
      description
        "RSVP Header Info";
      uses live_ncs_RSVP-MGMT-HEADER-INFO;
    }
    container expiry-time {
      description
        "Expiry Time";
      uses live_ncs_RSVP-MGMT-TIMESPEC;
    }
    container policy-flags {
      description
        "Policy Flags";
      uses live_ncs_RSVP-MGMT-POLICY-FLAGS;
    }
    container policy-query-flags {
      description
        "Policy Query Flags";
      uses live_ncs_RSVP-MGMT-POLICY-QUERY-FLAGS;
    }
    container label-info {
      description
        "Label Information";
      uses live_ncs_RSVP-MGMT-LABEL-INFO;
    }
    container class-type {
      description
        "DS-TE Class-Type";
      uses live_ncs_RSVP-MGMT-CT-INFO;
    }
    leaf input-interface {
      type string;
      description
        "Path Input Interface";
    }
    leaf backup-tunnel-name {
      type string;
      description
        "Path Backup Tunnel";
    }
    leaf is-in-ero-valid {
      type boolean;
      description
        "Incoming ERO validity";
    }
    leaf is-out-ero-valid {
      type boolean;
      description
        "Outgoing ERO validity";
    }
    list pfc {
      description
        "Path Forwarding Contexts";
      uses live_ncs_RSVP-PATH-FORWARDING-CONTEXT;
    }
    list in-ero {
      description
        "Incoming Explicit Route Sub Objects";
      uses live_ncs_RSVP-MGMT-ERO-SUBOBJ;
    }
    list out-ero {
      description
        "Outgoing Explicit Route Sub Objects";
      uses live_ncs_RSVP-MGMT-ERO-SUBOBJ;
    }
  }

  grouping live_ncs_RSVP-MGMT-SESSION-P2MP-LSP-TUNNEL-IPV4 {
    description
      "RSVP P2MP-LSP-Tunnel-IPv4 Session";
    leaf p2mp-id {
      type uint32;
      description
        "The Point to Multipoint ID";
    }
    leaf tunnel-id {
      type uint16;
      description
        "The Session Tunnel ID";
    }
    leaf extended-tunnel-id {
      type inet:ipv4-address;
      description
        "The Session Extended Tunnel ID";
    }
  }

  grouping live_ncs_RSVP-MGMT-SESSION-UNI-IPV4 {
    description
      "RSVP UNI IPv4 Session";
    leaf destination-address {
      type inet:ipv4-address;
      description
        "Destination address";
    }
    leaf tunnel-id {
      type uint16;
      description
        "The Session Tunnel ID";
    }
    leaf extended-address {
      type inet:ipv4-address;
      description
        "The Session Extended Address";
    }
  }

  grouping live_ncs_RSVP-MGMT-SESSION-LSP-TUNNEL-IPV4 {
    description
      "RSVP LSP-Tunnel-IPv4 Session";
    leaf destination-address {
      type inet:ipv4-address;
      description
        "Destination address";
    }
    leaf tunnel-id {
      type uint16;
      description
        "The Session Tunnel ID";
    }
    leaf extended-tunnel-id {
      type inet:ipv4-address;
      description
        "The Session Extended Tunnel ID";
    }
  }

  grouping live_ncs_RSVP-MGMT-SESSION-UDP-IPV4 {
    description
      "RSVP UDP IPv4 Session";
    leaf destination-address {
      type inet:ipv4-address;
      description
        "Destination address";
    }
    leaf protocol {
      type uint8;
      description
        "Protocol type (originally defined in RFC 790,
         further values in subsequent RFCs)";
    }
    leaf destination-port {
      type uint16;
      description
        "The Session Destination Port";
    }
  }

  grouping live_ncs_RSVP-SESSION-UNION {
    description
      "Union of the different RSVP session types";
    container ipv4 {
      // NCS drop when statement
      description
        "UDP IPv4 session";
      uses live_ncs_RSVP-MGMT-SESSION-UDP-IPV4;
    }
    container ipv4-lsp-session {
      // NCS drop when statement
      description
        "IPv4 LSP session";
      uses live_ncs_RSVP-MGMT-SESSION-LSP-TUNNEL-IPV4;
    }
    container ipv4-uni-session {
      // NCS drop when statement
      description
        "IPv4 UNI session";
      uses live_ncs_RSVP-MGMT-SESSION-UNI-IPV4;
    }
    container ipv4-p2mp-lsp-session {
      // NCS drop when statement
      description
        "IPv4 P2MP LSP session";
      uses live_ncs_RSVP-MGMT-SESSION-P2MP-LSP-TUNNEL-IPV4;
    }
    leaf session-type {
      type live_ncs_Rsvp-mgmt-session;
      description
        "SessionType";
    }
  }

  grouping live_ncs_RSVP-MGMT-SESSION-INFO {
    description
      "RSVP Session Info";
    container rsvp-session {
      description
        "RSVP Session";
      uses live_ncs_RSVP-SESSION-UNION;
    }
  }

  grouping live_ncs_RSVP-MGMT-SESSION-COMPACT {
    description
      "RSVP Compact Session Info";
    container session {
      description
        "RSVP Session Information";
      uses live_ncs_RSVP-MGMT-SESSION-INFO;
    }
    leaf ps-bs {
      type uint32;
      description
        "Number of path state block states";
    }
    leaf rs-bs {
      type uint32;
      description
        "Number of reservation state block states";
    }
    leaf requests {
      type uint32;
      description
        "Number of request states";
    }
    leaf detail-list-size {
      type uint32;
      description
        "Number of elements in detail list";
    }
  }

  grouping live_ncs_RSVP-MGMT-AUTHENTICATION-COMPACT {
    description
      "Authentication Compact Information";
    leaf source-address-xr {
      type inet:ipv4-address;
      description
        "Source address";
    }
    leaf destination-address-xr {
      type inet:ipv4-address;
      description
        "Destination address";
    }
    leaf neighbor-address {
      type inet:ipv4-address;
      description
        "Neighbor address";
    }
    leaf direction {
      type live_ncs_Rsvp-mgmt-auth-direction;
      description
        "Direction";
    }
    leaf key-type {
      type live_ncs_Rsvp-mgmt-auth-ki;
      description
        "Key type";
    }
    leaf key-source {
      type string;
      description
        "Key source";
    }
    leaf key-id {
      type uint64;
      description
        "Key ID";
    }
    leaf key-id-valid {
      type uint32;
      description
        "Key validity";
    }
  }

  grouping live_ncs_RSVP-MGMT-INTERFACE-BW-STD-DSTE {
    description
      "RSVP interface bandwidth info with standard based
       DSTE enabled";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-pool0-bandwidth {
      type uint64;
      units "bit/s";
      description
        "Max bandwidth (bits per second) allowed in BC0
         pool";
    }
    leaf max-pool1-bandwidth {
      type uint64;
      units "bit/s";
      description
        "Max bandwidth (bits per second) allowed in BC1
         pool";
    }
    leaf is-max-bandwidth-absolute {
      type boolean;
      description
        "True if the Max B/W is an absolute value and
         false if its a percentage";
    }
    leaf is-max-bc0-bandwidth-absolute {
      type boolean;
      description
        "True if the Max BC0 B/W is an absolute value and
         false if its a percentage";
    }
    leaf is-max-bc1-bandwidth-absolute {
      type boolean;
      description
        "True if the Max BC1 sub-pool B/W is an absolute
         value and false if its a percentage";
    }
  }

  grouping live_ncs_RSVP-MGMT-INTERFACE-BW-PRESTD-DSTE {
    description
      "Prestandard DSTE interface bandwidth information";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-subpool-bandwidth {
      type uint64;
      units "bit/s";
      description
        "Max bandwidth (bits per second) allowed in
         subpool";
    }
    leaf is-max-bandwidth-absolute {
      type boolean;
      description
        "True if the Max B/W is an absolute value and
         false if its a percentage";
    }
    leaf is-max-subpool-bandwidth-absolute {
      type boolean;
      description
        "True if the Max sub-pool B/W is an absolute
         value and false if its a percentage";
    }
  }

  grouping live_ncs_RSVP-MGMT-DSTE-MODE-INTERFACE-BW {
    description
      "Union of the different RSVP interface bandwidth
       types";
    container pre-standard-dste-interface {
      // NCS drop when statement
      description
        "Prestandard DSTE interface information";
      uses live_ncs_RSVP-MGMT-INTERFACE-BW-PRESTD-DSTE;
    }
    container standard-dste-interface {
      // NCS drop when statement
      description
        "Standard DSTE interface information";
      uses live_ncs_RSVP-MGMT-INTERFACE-BW-STD-DSTE;
    }
    leaf dste-mode {
      type live_ncs_Rsvp-mgmt-dste-modes;
      description
        "DSTEMode";
    }
  }

  grouping live_ncs_RSVP-MGMT-INTERFACE-SUMMARY {
    description
      "Summary Form of RSVP interface Info";
    container bandwidth-information {
      description
        "Interface bandwidth information";
      uses live_ncs_RSVP-MGMT-DSTE-MODE-INTERFACE-BW;
    }
    leaf interface-name-xr {
      type string;
      description
        "Interface Name";
    }
    leaf paths-in {
      type uint32;
      description
        "Number of locally created and incoming path
         states";
    }
    leaf paths-out {
      type uint32;
      description
        "Number of outgoing path states";
    }
    leaf reservations-in {
      type uint32;
      description
        "Number of locally created and incoming
         reservation states";
    }
    leaf reservations-out {
      type uint32;
      description
        "Number of outgoing reservation states";
    }
  }

  grouping live_ncs_RSVP-MGMT-IF-NBR-COMPACT {
    description
      "Compact Info for RSVP Interface Neighbor";
    leaf interface-neighbor-address {
      type inet:ipv4-address;
      description
        "Interface Neighbor address";
    }
    leaf neighbor-interface-name {
      type xr:live_ncs_Interface-name;
      description
        "Neighbor's Interface handle";
    }
  }

  grouping live_ncs_RSVP-MGMT-NBR-COMPACT {
    description
      "Compact Info for RSVP Neighbor";
    leaf node-address {
      type inet:ipv4-address;
      description
        "Neighbor node address";
    }
    list interface-neighbor-list-compact {
      description
        "Compact list of I/F Neighbors";
      uses live_ncs_RSVP-MGMT-IF-NBR-COMPACT;
    }
  }

  grouping RSVP-MGMT-RXSB-DETAIL {
    description
      "Detailed Form of RSVP Proxy Reservation";
    container session {
      description
        "RSVP Session Information";
      uses RSVP-MGMT-SESSION-INFO;
    }
    container s2l-sub-lsp {
      description
        "RSVP S2L Sub-LSP information";
      uses RSVP-MGMT-S2L-SUB-LSP-IPV4;
    }
    container style {
      description
        "RSVP Style";
      uses RSVP-MGMT-STYLE;
    }
    container filter {
      description
        "RSVP Filter";
      uses RSVP-MGMT-FILTER-INFO;
    }
    container flow-spec {
      description
        "Flow Spec Information";
      uses RSVP-MGMT-FLOW-SPEC;
    }
    container generic-flow-spec {
      description
        "Generic Flow Spec Information";
      uses RSVP-MGMT-GEN-FLOW-SPEC;
    }
    container hop {
      description
        "Path Hop Info";
      uses RSVP-MGMT-HOP-INFO;
    }
    container rsvp-header {
      description
        "RSVP Header";
      uses RSVP-MGMT-HEADER-INFO;
    }
    leaf input-interface {
      type string;
      description
        "Path Input Interface";
    }
    leaf dynamic-state {
      type uint32;
      description
        "Dynamic State Handle";
    }
  }

  grouping RSVP-MGMT-PXSB-DETAIL {
    description
      "Detailed Form of RSVP Proxy Path";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    container hop {
      description
        "Path Hop Info";
      uses RSVP-MGMT-HOP-INFO;
    }
    container rsvp-header {
      description
        "RSVP Header";
      uses RSVP-MGMT-HEADER-INFO;
    }
    leaf input-interface {
      type string;
      description
        "Path Input Interface";
    }
    leaf dynamic-state {
      type uint32;
      description
        "Dynamic State Handle";
    }
  }

  grouping RSVP-MGMT-GLBL-BW-POOL-INFO {
    description
      "Global B/W pool information";
    leaf max-res-pool-percent {
      type uint32;
      units "percentage";
      description
        "Maxium reservable I/F percent B/W";
    }
    leaf bc0-percent {
      type uint32;
      units "percentage";
      description
        "BC0 I/F percent B/W";
    }
    leaf bc1-percent {
      type uint32;
      units "percentage";
      description
        "BC1 I/F percent B/W";
    }
    leaf is-max-res-pool-percent-configured {
      type boolean;
      description
        "Is maximum reservable default I/F percent
         configured";
    }
    leaf is-bc0-percent-configured {
      type boolean;
      description
        "Is BC0 default I/F percent configured";
    }
    leaf is-bc1-percent-configured {
      type boolean;
      description
        "Is BC1 default I/F percent configured";
    }
    leaf bandwidth-configuration-model {
      type Igpte-lib-bw-model;
      description
        "Bandwith configuration model currently in use
         (MAM/RDM)";
    }
  }

  grouping RSVP-MGMT-GLBL-NBR-COMPACT {
    description
      "Compact Info for RSVP Global Neighbor";
    container global-neighbor-flags {
      description
        "Global Neighbor Flags";
      uses RSVP-MGMT-GLBL-NBR-FLAGS;
    }
    leaf is-gr-enabled {
      type boolean;
      description
        "Is GR enabled";
    }
    leaf node-address {
      type inet:ipv4-address;
      description
        "Neighbor node address";
    }
    leaf restart-state {
      type Rsvp-mgmt-restart-state;
      description
        "Restart state";
    }
    list local-node-address {
      description
        "Local node address";
      leaf entry {
        type inet:ipv4-address;
        description
          "Local node address";
      }
    }
    list neighbor-hello-state {
      description
        "Neighbor Hello state";
      leaf entry {
        type Rsvp-mgmt-hello-state;
        description
          "Neighbor Hello state";
      }
    }
    list lost-communication-reason {
      description
        "Reason why communication was lost";
      leaf entry {
        type Rsvp-mgmt-hello-down-reason;
        description
          "Reason why communication was lost";
      }
    }
    list lost-communication-total {
      description
        "Total number of times communication got lost";
      leaf entry {
        type uint16;
        description
          "Total number of times communication got lost";
      }
    }
    list up-time {
      description
        "Time hellos have been up";
      uses RSVP-MGMT-TIMESPEC;
    }
    list lost-communication-time {
      description
        "Time when communication was lost";
      uses RSVP-MGMT-TIMESPEC;
    }
  }

  grouping RSVP-MGMT-PATH-COMPACT {
    description
      "Compact Form of RSVP Path Info";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container session-attribute {
      description
        "RSVP Session Attribute";
      uses RSVP-MGMT-SESSION-ATTRIBUTE;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    leaf input-interface {
      type string;
      description
        "Path Input Interface";
    }
  }

  grouping RSVP-MGMT-GLBL-NBR-FLAGS {
    description
      "Global Neighbor Flags";
    leaf is-application-ouni {
      type boolean;
      description
        "OUNI Application";
    }
    leaf is-application-mpls {
      type boolean;
      description
        "MPLS Application";
    }
  }

  grouping RSVP-MGMT-GLBL-NBR-DETAIL {
    description
      "Detail Info for RSVP Global Neighbor";
    container global-neighbor-flags {
      description
        "Global Neighbor Flags";
      uses RSVP-MGMT-GLBL-NBR-FLAGS;
    }
    container restart-time-left {
      description
        "How much restart time remains";
      uses RSVP-MGMT-TIMESPEC;
    }
    container restart-timer-expiry-time {
      description
        "When will restart timer expire";
      uses RSVP-MGMT-TIMESPEC;
    }
    container recovery-time-left {
      description
        "How much recovery timer remains";
      uses RSVP-MGMT-TIMESPEC;
    }
    container recovery-timer-exp-time {
      description
        "Time at which recovery timer will expire";
      uses RSVP-MGMT-TIMESPEC;
    }
    leaf is-gr-enabled {
      type boolean;
      description
        "Is GR enabled";
    }
    leaf node-address {
      type inet:ipv4-address;
      description
        "Neighbor node address";
    }
    leaf restart-state {
      type Rsvp-mgmt-restart-state;
      description
        "Current restart state";
    }
    leaf restart-time {
      type uint32;
      units "millisecond";
      description
        "GR Restart Time (milliseconds)";
    }
    leaf is-restart-timer-running {
      type boolean;
      description
        "Is GR restart timer running";
    }
    leaf recovery-time {
      type uint32;
      units "millisecond";
      description
        "GR Recovery Time (milliseconds)";
    }
    leaf is-recovery-timer-running {
      type boolean;
      description
        "Is RSVP recovery timer running";
    }
    leaf hello-interval {
      type uint32;
      units "millisecond";
      description
        "Hello Interval (milliseconds)";
    }
    leaf missed-hellos {
      type uint8;
      description
        "Hello missed count";
    }
    leaf pending-states {
      type uint32;
      description
        "Number of pending states for this neighbor";
    }
    list local-node-address {
      description
        "Local node address";
      leaf entry {
        type inet:ipv4-address;
        description
          "Local node address";
      }
    }
    list interface-neighbor {
      description
        "Interface Neighbor List";
      leaf entry {
        type inet:ipv4-address;
        description
          "Interface Neighbor List";
      }
    }
    list neighbor-hello-state {
      description
        "Neighbor's hello state";
      leaf entry {
        type Rsvp-mgmt-hello-state;
        description
          "Neighbor's hello state";
      }
    }
    list lost-communication-reason {
      description
        "Reason why communication was lost";
      leaf entry {
        type Rsvp-mgmt-hello-down-reason;
        description
          "Reason why communication was lost";
      }
    }
    list lost-communication-total {
      description
        "Total number of times communication got lost";
      leaf entry {
        type uint16;
        description
          "Total number of times communication got lost";
      }
    }
    list up-time {
      description
        "Hello up time";
      uses RSVP-MGMT-TIMESPEC;
    }
    list lost-communication-time {
      description
        "Time when communication was lost";
      uses RSVP-MGMT-TIMESPEC;
    }
  }

  grouping RSVP-MGMT-HELLO-INSTANCE-DETAIL {
    description
      "Detail Info for RSVP Hello Instance";
    container up-time {
      description
        "Hello up time";
      uses RSVP-MGMT-TIMESPEC;
    }
    container communication-lost-time {
      description
        "Time when communication was lost";
      uses RSVP-MGMT-TIMESPEC;
    }
    leaf source-address-xr {
      type inet:ipv4-address;
      description
        "Source address";
    }
    leaf destination-address-xr {
      type inet:ipv4-address;
      description
        "Destination address";
    }
    leaf hello-instance-owner {
      type Rsvp-mgmt-hello-instance-owner;
      description
        "Hello instance owner";
    }
    leaf neighbor-hello-state {
      type Rsvp-mgmt-hello-state;
      description
        "Neighbor Hello state";
    }
    leaf instance-type {
      type Rsvp-mgmt-hello-instance;
      description
        "Hello instance type";
    }
    leaf hello-interface {
      type xr:Interface-name;
      description
        "Interface to use";
    }
    leaf hello-interval {
      type uint32;
      description
        "Hello Interval";
    }
    leaf missed-acks-allowed {
      type uint32;
      description
        "Number of missed Hello allowed";
    }
    leaf source-instance {
      type uint32;
      description
        "Source Instance";
    }
    leaf destination-instance {
      type uint32;
      description
        "Destination Instance";
    }
    leaf communication-lost-reason {
      type Rsvp-mgmt-hello-down-reason;
      description
        "Reason why communication was lost";
    }
    leaf total-communication-lost {
      type uint16;
      description
        "Total number of times communication got lost";
    }
    leaf communication-lost-hello-missed {
      type uint16;
      description
        "Lost Comm. Hello missed count";
    }
    leaf communication-lost-wrong-source-inst {
      type uint16;
      description
        "Count of lost comm. due to wrong Source Inst";
    }
    leaf communication-lost-wrong-destination-inst {
      type uint16;
      description
        "Count of lost comm. due to wrong Destination
         Inst";
    }
    leaf communication-lost-interface-down {
      type uint16;
      description
        "Count of lost comm. due to interface down";
    }
    leaf communication-lost-neighbor-disabled-hello {
      type uint16;
      description
        "Count of lost comm. due to nbor disabling Hellos";
    }
    leaf hello-messages-sent {
      type uint64;
      description
        "Number of hello messages sent";
    }
    leaf hello-messages-received {
      type uint64;
      description
        "Number of hello messages received";
    }
    leaf hello-request-suppressed {
      type uint64;
      description
        "Count of Hello Requests suppessed";
    }
  }

  grouping RSVP-SESSION-RSB-DETAIL {
    description
      "RSVP Detail Session Reservation Info";
    container generic-out-label {
      description
        "Generic Label for outbound traffic";
      uses RSVP-MGMT-GENERIC-LABEL;
    }
    container flow-spec {
      description
        "Flow spec object";
      uses RSVP-MGMT-FLOW-SPEC;
    }
    container generic-flow-spec {
      description
        "Generic Flow Spec object";
      uses RSVP-MGMT-GEN-FLOW-SPEC;
    }
    leaf is-valid {
      type boolean;
      description
        "Entry validity";
    }
    leaf destination-address {
      type inet:ipv4-address;
      description
        "Destination address";
    }
    leaf out-interface {
      type xr:Interface-name;
      description
        "Interface on which outbound message was sent";
    }
    leaf out-label {
      type Rsvp-mgmt-mpls-label;
      description
        "Label for outbound traffic";
    }
    leaf backup-interface {
      type xr:Interface-name;
      description
        "Backup tunnel interface";
    }
    leaf backup-label {
      type Rsvp-mgmt-mpls-label;
      description
        "Backup label";
    }
    leaf is-rro-valid {
      type boolean;
      description
        "RRO validity";
    }
    leaf is-flow-spec-valid {
      type boolean;
      description
        "FlowSpec validity";
    }
    list rro {
      description
        "Record route object";
      uses RSVP-MGMT-RRO-SUBOBJ;
    }
  }

  grouping RSVP-MGMT-REV-LSP-UNSUPPORTED-SUBOBJ {
    description
      "RSVP MGMT REV LSP UNSUPPORTED SUBOBJ";
    list rsvp-mgmt-rev-lsp-unsupported-subobj {
      description
        "rsvp mgmt rev lsp unsupported subobj";
      leaf entry {
        type uint8;
        description
          "rsvp mgmt rev lsp unsupported subobj";
      }
    }
  }

  grouping RSVP-MGMT-REVERSE-LSP {
    description
      "RSVP REVERSE_LSP Object";
    container generic-traffic-spec {
      description
        "Generic Traffic Spec object";
      uses RSVP-MGMT-GEN-TRAFFIC-SPEC;
    }
    list ero {
      description
        "Explicit Route Sub Objects";
      uses RSVP-MGMT-ERO-SUBOBJ;
    }
    list unsup-sub-object {
      description
        "Unsupported REVERSE_LSP Sub Objects";
      uses RSVP-MGMT-REV-LSP-UNSUPPORTED-SUBOBJ;
    }
  }

  grouping RSVP-MGMT-PROTECTION-LINK-FLAGS {
    description
      "RSVP PROTECTION Object Link Flags";
    leaf enhanced {
      type boolean;
      description
        "Indicates Enhanced Protection Scheme";
    }
    leaf ded1-plus1 {
      type boolean;
      description
        "Dedicated 1+1 Protection";
    }
    leaf ded1-to1 {
      type boolean;
      description
        "Dedicated 1:1 Protection";
    }
    leaf shared {
      type boolean;
      description
        "Shared Link Layer Protection";
    }
    leaf unprotected {
      type boolean;
      description
        "LSP should not use any Link Layer Protection";
    }
    leaf extra-traffic {
      type boolean;
      description
        "LSP should use Links that are protecting other
         (primary) traffic";
    }
    leaf reserved-bit1 {
      type boolean;
      description
        "Reserved Bit 1";
    }
    leaf reserved-bit2 {
      type boolean;
      description
        "Reserved Bit 2";
    }
  }

  grouping RSVP-MGMT-PROTECTION-LSP-FLAGS {
    description
      "RSVP PROTECTION Object LSP Flags";
    leaf rerouting {
      type boolean;
      description
        "Full Rerouting";
    }
    leaf rerouting-no-et {
      type boolean;
      description
        "Rerouting Without Extra-Traffic";
    }
    leaf one-to-n-protection-et {
      type boolean;
      description
        "1:N Protection with Extra-Traffic";
    }
    leaf one-plus-one-uni {
      type boolean;
      description
        "1+1 Unidirectional Protection";
    }
    leaf one-plus-one-bi {
      type boolean;
      description
        "1+1 Bidirectional Protection";
    }
  }

  grouping RSVP-MGMT-PROTECTION {
    description
      "RSVP PROTECTION Object Info";
    container lsp-flags {
      description
        "PROTECTION Object LSP Flags";
      uses RSVP-MGMT-PROTECTION-LSP-FLAGS;
    }
    container link-flags {
      description
        "PROTECTION Object Link Flags";
      uses RSVP-MGMT-PROTECTION-LINK-FLAGS;
    }
    leaf s {
      type boolean;
      description
        "Secondary Bit";
    }
    leaf p {
      type boolean;
      description
        "Protecting Bit";
    }
    leaf n {
      type boolean;
      description
        "Notification Bit";
    }
    leaf o {
      type boolean;
      description
        "Operational Bit";
    }
  }

  grouping RSVP-MGMT-ASSOCIATION-IPV6-EXT {
    description
      "RSVP EXTENDED ASSOCIATION IPv6 Object Info";
    leaf type {
      type uint16;
      description
        "Association Type (RFC 4872)";
    }
    leaf id {
      type uint16;
      description
        "Association ID";
    }
    leaf source {
      type inet:ipv6-address;
      description
        "Association IPV6 Source Address";
    }
    leaf global-source {
      type uint32;
      description
        "Global Association Source";
    }
    list extended-id {
      description
        "Extended Association ID";
      leaf entry {
        type uint32;
        description
          "Extended Association ID";
      }
    }
  }

  grouping RSVP-MGMT-ASSOCIATION-IPV4-EXT {
    description
      "RSVP EXTENDED ASSOCIATION IPv4 Object Info";
    leaf type {
      type uint16;
      description
        "Association Type (RFC 4872)";
    }
    leaf id {
      type uint16;
      description
        "Association ID";
    }
    leaf source {
      type inet:ipv4-address;
      description
        "Association IPV4 Source Address";
    }
    leaf global-source {
      type uint32;
      description
        "Global Association Source";
    }
    list extended-id {
      description
        "Extended Association ID";
      leaf entry {
        type uint32;
        description
          "Extended Association ID";
      }
    }
  }

  grouping RSVP-MGMT-ASSOCIATION-IPV6 {
    description
      "RSVP ASSOCIATION IPv6 Object Info";
    leaf type {
      type uint16;
      description
        "Association Type (RFC 4872)";
    }
    leaf id {
      type uint16;
      description
        "Association ID";
    }
    leaf source {
      type inet:ipv6-address;
      description
        "Association IPV6 Source Address";
    }
  }

  grouping RSVP-MGMT-ASSOCIATION-IPV4 {
    description
      "RSVP ASSOCIATION IPv4 Object Info";
    leaf type {
      type uint16;
      description
        "Association Type (RFC 4872)";
    }
    leaf id {
      type uint16;
      description
        "Association ID";
    }
    leaf source {
      type inet:ipv4-address;
      description
        "Association IPV4 Source Address";
    }
  }

  grouping RSVP-MGMT-ASSOCIATION {
    description
      "Union of the different ASSOCIATION types";
    container ipv4 {
      when "../association-type = 'ipv4'" {
        tailf:xpath-root 3;
        description
          "../AssociationType = 'IPv4'";
      }
      description
        "IPV4 ASSOCIATION Object";
      uses RSVP-MGMT-ASSOCIATION-IPV4;
    }
    container ipv6 {
      when "../association-type = 'ipv6'" {
        tailf:xpath-root 3;
        description
          "../AssociationType = 'IPv6'";
      }
      description
        "IPV6 ASSOCIATION Object";
      uses RSVP-MGMT-ASSOCIATION-IPV6;
    }
    container extended-ipv4 {
      when "../association-type = 'extended-ipv4'" {
        tailf:xpath-root 3;
        description
          "../AssociationType = 'ExtendedIPv4'";
      }
      description
        "EXTENDED IPV4 ASSOCIATION Object";
      uses RSVP-MGMT-ASSOCIATION-IPV4-EXT;
    }
    container extended-ipv6 {
      when "../association-type = 'extended-ipv6'" {
        tailf:xpath-root 3;
        description
          "../AssociationType = 'ExtendedIPv6'";
      }
      description
        "EXTENDED IPV6 ASSOCIATION Object";
      uses RSVP-MGMT-ASSOCIATION-IPV6-EXT;
    }
    leaf association-type {
      type Rsvp-mgmt-association;
      description
        "AssociationType";
    }
  }

  grouping RSVP-MGMT-RRO-SRLG-SUBOBJ {
    description
      "RSVP RRO SRLG subobject";
    list srl-gs {
      description
        "The RRO Subobject SRLGs";
      leaf entry {
        type uint32;
        description
          "The RRO Subobject SRLGs";
      }
    }
  }

  grouping RSVP-MGMT-RRO-UNNUMBERED-SUBOBJ-FLAGS {
    description
      "RSVP RRO UNNUMBERED Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping RSVP-MGMT-RRO-UNNUMBERED-SUBOBJ {
    description
      "RSVP RRO Unnumbered subobject";
    container flags {
      description
        "The RRO Subobject Unnumbered Flags";
      uses RSVP-MGMT-RRO-UNNUMBERED-SUBOBJ-FLAGS;
    }
    leaf interface-address {
      type inet:ipv4-address;
      description
        "The RRO Interface Address";
    }
    leaf interface-id {
      type uint32;
      description
        "The RRO Interface ID";
    }
  }

  grouping RSVP-MGMT-RRO-LABEL-SUBOBJ-FLAGS {
    description
      "RSVP RRO Label Subobject Flags";
    leaf is-global-label {
      type boolean;
      description
        "Label is Global across all interfaces";
    }
  }

  grouping RSVP-MGMT-RRO-LABEL-SUBOBJ {
    description
      "RSVP RRO Label subobject";
    container flags {
      description
        "The RRO Subobject Label Flags";
      uses RSVP-MGMT-RRO-LABEL-SUBOBJ-FLAGS;
    }
    leaf label {
      type uint32;
      description
        "The RRO Subobject Label Value";
    }
    leaf is-label-variable-length {
      type boolean;
      description
        "Is the RRO Subobject Label Variable Length";
    }
    list variable-length-label {
      description
        "The RRO Subobject Variable Length Label";
      leaf entry {
        type uint32;
        description
          "The RRO Subobject Variable Length Label";
      }
    }
  }

  grouping RSVP-MGMT-RRO-IPV4-SUBOBJ-FLAGS {
    description
      "RSVP RRO IPV4 Subobject Flags";
    leaf is-protection-available {
      type boolean;
      description
        "Local Protection Available";
    }
    leaf is-protection-in-use {
      type boolean;
      description
        "Local Protection In Use";
    }
    leaf is-bandwidth-protected {
      type boolean;
      description
        "Bandwidth Protection Available";
    }
    leaf is-node-protection-available {
      type boolean;
      description
        "Node Protection Available";
    }
    leaf is-node-id {
      type boolean;
      description
        "Node ID In Use";
    }
  }

  grouping RSVP-MGMT-RRO-IPV4-SUBOBJ {
    description
      "RSVP RRO IPV4 subobject";
    container flags {
      description
        "The RRO IPV4 Subobject Flags";
      uses RSVP-MGMT-RRO-IPV4-SUBOBJ-FLAGS;
    }
    leaf rro-address {
      type inet:ipv4-address;
      description
        "The RRO IPV4 Address";
    }
  }

  grouping RSVP-MGMT-RRO-SUBOBJ {
    description
      "Union of the different RSVP RRO types";
    container ipv4rro-sub-object {
      when "../rro-type = 'ipv4rro-type'" {
        tailf:xpath-root 3;
        description
          "../RROType = 'IPv4RROType'";
      }
      description
        "IPV4 RRO Sub Object";
      uses RSVP-MGMT-RRO-IPV4-SUBOBJ;
    }
    container label-rro-sub-object {
      when "../rro-type = 'label-rro-type'" {
        tailf:xpath-root 3;
        description
          "../RROType = 'LabelRROType'";
      }
      description
        "Label RRO Sub Object";
      uses RSVP-MGMT-RRO-LABEL-SUBOBJ;
    }
    container unnumbered-rro-sub-object {
      when "../rro-type = 'unnumbered-rro-type'" {
        tailf:xpath-root 3;
        description
          "../RROType = 'UnnumberedRROType'";
      }
      description
        "Unnumbered RRO Sub Object";
      uses RSVP-MGMT-RRO-UNNUMBERED-SUBOBJ;
    }
    container srlg-rro-sub-object {
      when "../rro-type = 'srlg-rro-type'" {
        tailf:xpath-root 3;
        description
          "../RROType = 'SRLG_RROType'";
      }
      description
        "SRLG RRO Sub Object";
      uses RSVP-MGMT-RRO-SRLG-SUBOBJ;
    }
    leaf rro-type {
      type Rsvp-mgmt-rro-subobj;
      description
        "RROType";
    }
  }

  grouping RSVP-SESSION-PSB-DETAIL {
    description
      "RSVP Detail Session Path Info";
    container generic-in-label {
      description
        "Generic Label for inbound traffic";
      uses RSVP-MGMT-GENERIC-LABEL;
    }
    container traffic-spec {
      description
        "Traffic Spec object";
      uses RSVP-MGMT-TRAFFIC-SPEC;
    }
    container generic-traffic-spec {
      description
        "Generic Traffic Spec object";
      uses RSVP-MGMT-GEN-TRAFFIC-SPEC;
    }
    container association {
      description
        "Association object";
      uses RSVP-MGMT-ASSOCIATION;
    }
    container protection {
      description
        "Protection object";
      uses RSVP-MGMT-PROTECTION;
    }
    container reverse-lsp {
      description
        "Reverse LSP object";
      uses RSVP-MGMT-REVERSE-LSP;
    }
    leaf is-valid {
      type boolean;
      description
        "Entry validity";
    }
    leaf destination-address {
      type inet:ipv4-address;
      description
        "Destination address";
    }
    leaf lsp-id {
      type uint32;
      description
        "LSP ID";
    }
    leaf p2mp-sub-group-origin {
      type inet:ipv4-address;
      description
        "Point to Multipoint SubGroup Origin";
    }
    leaf sub-group-id {
      type uint16;
      description
        "Point to Multipoint Subgroup ID";
    }
    leaf in-interface {
      type xr:Interface-name;
      description
        "Interface on which inbound message was received";
    }
    leaf in-label {
      type Rsvp-mgmt-mpls-label;
      description
        "Label for inbound traffic";
    }
    leaf lsp-wrap-label {
      type Rsvp-mgmt-mpls-label;
      description
        "LSP Wrap Label";
    }
    leaf is-bad-address {
      type boolean;
      description
        "Address validity";
    }
    leaf incoming-interface-address {
      type inet:ipv4-address;
      description
        "IP address of Path's incoming interface";
    }
    leaf is-ero-valid {
      type boolean;
      description
        "ERO validity";
    }
    leaf is-rro-valid {
      type boolean;
      description
        "RRO validity";
    }
    leaf is-traffic-spec-valid {
      type boolean;
      description
        "Traffic Spec validity";
    }
    leaf tunnel-name {
      type string;
      description
        "Tunnel name";
    }
    list ero {
      description
        "Explicit Route Sub Objects";
      uses RSVP-MGMT-ERO-SUBOBJ;
    }
    list rro {
      description
        "Record Route Sub Objects";
      uses RSVP-MGMT-RRO-SUBOBJ;
    }
  }

  grouping RSVP-SESSION-PSB-RSB-DETAIL {
    description
      "List of Path and Reservation Info";
    list psb-info {
      description
        "Path Info";
      uses RSVP-SESSION-PSB-DETAIL;
    }
    list rsb-info {
      description
        "Reservation Info";
      uses RSVP-SESSION-RSB-DETAIL;
    }
  }

  grouping RSVP-MGMT-SESSION-DETAIL {
    description
      "RSVP Detail Session Info";
    container compact {
      description
        "Compact session data";
      uses RSVP-MGMT-SESSION-COMPACT;
    }
    container s2l-sub-lsp {
      description
        "RSVP S2L Sub-LSP information";
      uses RSVP-MGMT-S2L-SUB-LSP-IPV4;
    }
    list psb-rsb-info {
      description
        "Path and Reservation Info";
      uses RSVP-SESSION-PSB-RSB-DETAIL;
    }
  }

  grouping RSVP-MGMT-KEY {
    description
      "Key to uniquely identify some RSVP records";
    leaf p2mp-id {
      type uint32;
      description
        "Point-to-multipoint ID";
    }
    leaf destination-address {
      type inet:ipv4-address;
      description
        "Destination address";
    }
    leaf destination-port-or-tunnel-id {
      type uint32;
      description
        "Destination Port or Tunnel ID. For the LSP and
         OUNI session types this represents the Tunnel ID
         whereas for the UDP session type this represents
         the Destination Port";
    }
    leaf protocol {
      type uint32;
      description
        "Protocol. UDP session type this represents the
         Protocol (UDP not supported at present)";
    }
    leaf extended-tunnel-id {
      type inet:ipv4-address;
      description
        "Protocol or Extended Tunnel ID. For the LSP and
         OUNI sesion types this represents the Extended
         Tunnel ID";
    }
    leaf session-type {
      type Rsvp-mgmt-session;
      description
        "Session Type (e.g. LSP, OUNI or UDP)";
    }
    leaf source-address {
      type inet:ipv4-address;
      description
        "Source Address";
    }
    leaf source-port-or-lsp-id {
      type uint32;
      description
        "Source Port or LSP_ID. For the LSP and OUNI
         session types this represents the LSP_ID whereas
         for the UDP session type this represents the
         SourcePort";
    }
    leaf p2mp-sub-group-origin {
      type inet:ipv4-address;
      description
        "Point to Multipoint SubGroup Origin";
    }
    leaf sub-group-id {
      type uint16;
      description
        "Point to Multipoint Subgroup ID";
    }
    leaf vrfid {
      type Rsi-vrf-id;
      description
        "Signalling VRF ID";
    }
  }

  grouping RSVP-MGMT-REQUEST-FLAGS {
    description
      "Request state flags";
    leaf is-local-receiver {
      type boolean;
      description
        "Local Receiver";
    }
    leaf is-refreshing {
      type boolean;
      description
        "Is neighbor refreshing";
    }
    leaf is-send-confirm {
      type boolean;
      description
        "Send Confirm message";
    }
    leaf is-ack-outstanding {
      type boolean;
      description
        "Is ACK message outstanding";
    }
    leaf is-message-id-allocated {
      type boolean;
      description
        "Is MessageID allocated";
    }
    leaf is-nack-received {
      type boolean;
      description
        "A NACK message was received";
    }
    leaf is-retransmit {
      type boolean;
      description
        "Retransmit the message";
    }
    leaf is-paced {
      type boolean;
      description
        "Message is paced";
    }
    leaf is-label-request-in-path {
      type boolean;
      description
        "The Path message contains Label Request";
    }
    leaf is-rro-in-path {
      type boolean;
      description
        "The Path message contains RRO";
    }
    leaf is-record-label-in-path {
      type boolean;
      description
        "Path has Session-Attr object with Record Labels
         set";
    }
    leaf is-merge-point {
      type boolean;
      description
        "Is node a Merge Point";
    }
  }

  grouping RSVP-MGMT-REQUEST-DETAIL {
    description
      "Detailed Form of RSVP Request Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Information";
      uses RSVP-MGMT-GEN-FLOW-SPEC;
    }
    container filter {
      description
        "RSVP Filter";
      uses RSVP-MGMT-FILTER-INFO;
    }
    container style {
      description
        "RSVP Style";
      uses RSVP-MGMT-STYLE;
    }
    container req-flags {
      description
        "Request flags";
      uses RSVP-MGMT-REQUEST-FLAGS;
    }
    container hop {
      description
        "Hop Infomation";
      uses RSVP-MGMT-HOP-INFO;
    }
    container header {
      description
        "RSVP Header Information";
      uses RSVP-MGMT-HEADER-INFO;
    }
    container policy-sources {
      description
        "RSVP Policy Sources";
      uses RSVP-MGMT-POLICY-SOURCES;
    }
    container policy-flags {
      description
        "RSVP Policy Flags";
      uses RSVP-MGMT-POLICY-FLAGS;
    }
    container policy-query-flags {
      description
        "RSVP Query Flags";
      uses RSVP-MGMT-POLICY-QUERY-FLAGS;
    }
    leaf output-interface {
      type string;
      description
        "output Interface";
    }
    list psb-key {
      description
        "List of RSB keys";
      uses RSVP-MGMT-KEY;
    }
    list rsb-key {
      description
        "List of RSB keys";
      uses RSVP-MGMT-KEY;
    }
  }

  grouping RSVP-MGMT-REQUEST-COMPACT {
    description
      "Compact Form of RSVP Request Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Information";
      uses RSVP-MGMT-GEN-FLOW-SPEC;
    }
    container filter {
      description
        "RSVP Filter";
      uses RSVP-MGMT-FILTER-INFO;
    }
    container style {
      description
        "RSVP Style";
      uses RSVP-MGMT-STYLE;
    }
    leaf output-interface {
      type string;
      description
        "Output Interface";
    }
  }

  grouping RSVP-MGMT-FRR-STATES-DETAIL {
    description
      "RSVP states for one FRR LSP";
    container session {
      description
        "RSVP Session Information";
      uses RSVP-MGMT-SESSION-INFO;
    }
    container s2l-sub-lsp {
      description
        "RSVP S2L Sub-LSP information";
      uses RSVP-MGMT-S2L-SUB-LSP-IPV4;
    }
    leaf path-status {
      type Rsvp-mgmt-frr-state-enum;
      description
        "RSVP FRR Path States";
    }
    leaf reservation-status {
      type Rsvp-mgmt-frr-state-enum;
      description
        "RSVP FRR Reservation States";
    }
  }

  grouping RSVP-GLOBAL-INFO {
    description
      "RSVP global information";
    container issu-status {
      description
        "Issu status";
      uses RSVP-NSR-ISSU-STATUS-INFO;
    }
    container nsr-status {
      description
        "NSR status";
      uses RSVP-NSR-ISSU-STATUS-INFO;
    }
    container database-counters {
      description
        "All database counters";
      uses RSVP-MGMT-ALL-DB-COUNTERS;
    }
    leaf interfaces {
      type uint32;
      description
        "Total interfaces";
    }
    leaf ls-ps {
      type uint32;
      description
        "Total LSPs";
    }
  }

  grouping RSVP-IDT-STATUS {
    description
      "IDT status information";
    leaf sync-status {
      type Rsvp-sync-status;
      description
        "Sync status";
    }
    leaf not-ready-reason {
      type Rsvp-proc-nsr-not-ready-reason;
      description
        "Not ready reason";
    }
    leaf idt-start-time {
      type uint32;
      units "second";
      description
        "IDT start timestamp in seconds";
    }
    leaf idt-end-time {
      type uint32;
      units "second";
      description
        "IDT end timestamp in seconds";
    }
    leaf declare-time {
      type uint32;
      units "second";
      description
        "Declare ready timestamp in seconds";
    }
    leaf withdraw-time {
      type uint32;
      units "second";
      description
        "Withdraw ready timestamp in seconds";
    }
  }

  grouping RSVP-NSR-ISSU-STATUS-INFO {
    description
      "NSR/ISSU status information";
    container idt-status {
      description
        "IDT status";
      uses RSVP-IDT-STATUS;
    }
    container previous-idt-status {
      description
        "Previous IDT status";
      uses RSVP-IDT-STATUS;
    }
    leaf role {
      type Rsvp-proc-role;
      description
        "Process role";
    }
  }

  grouping RSVP-MGMT-IF-NBR-DETAIL {
    description
      "Detail Info for RSVP Interface Neighbor";
    leaf interface-neighbor-address {
      type inet:ipv4-address;
      description
        "Interface Neighbor address";
    }
    leaf neighbor-interface-name {
      type xr:Interface-name;
      description
        "Neighbor's Interface handle";
    }
    leaf is-rr-enabled {
      type boolean;
      description
        "Is Neighbor's RR enable";
    }
    leaf neighbor-epoch {
      type uint32;
      description
        "Neighbor's epoch value";
    }
    leaf out-of-order-messages {
      type uint32;
      description
        "Number of out of order msgs";
    }
    leaf retransmitted-messages {
      type uint32;
      description
        "Number of retransmitted msgs";
    }
  }

  grouping RSVP-MGMT-NBR-DETAIL {
    description
      "Detail Info for RSVP Neighbor";
    leaf node-address {
      type inet:ipv4-address;
      description
        "Neighbor node address";
    }
    list interface-neighbor-list-detail {
      description
        "Detail list of I/F Neighbors";
      uses RSVP-MGMT-IF-NBR-DETAIL;
    }
  }

  grouping RSVP-MGMT-HELLO-IF-INSTANCE-DETAIL {
    description
      "Detail Info for IF-based RSVP Hello Instance";
    container last-message-sent-time {
      description
        "Last Ack/msg sent time";
      uses RSVP-MGMT-TIMESPEC;
    }
    leaf source-address-xr {
      type inet:ipv4-address;
      description
        "Source address";
    }
    leaf destination-address-xr {
      type inet:ipv4-address;
      description
        "Destination address";
    }
    leaf hello-global-neighbor-id {
      type inet:ipv4-address;
      description
        "Global Neighbor ID";
    }
    leaf instance-type {
      type Rsvp-mgmt-hello-instance;
      description
        "Hello instance type";
    }
    leaf hello-interface {
      type xr:Interface-name;
      description
        "Interface to use";
    }
    leaf source-instance {
      type uint32;
      description
        "Source Instance";
    }
    leaf destination-instance {
      type uint32;
      description
        "Destination Instance";
    }
    leaf hello-messages-sent {
      type uint64;
      description
        "Number of hello messages sent";
    }
    leaf hello-messages-received {
      type uint64;
      description
        "Number of hello messages received";
    }
  }

  grouping RSVP-MGMT-HELLO-IF-INSTANCE-COMPACT {
    description
      "Compact Info for IF-based RSVP Hello Instance";
    leaf source-address-xr {
      type inet:ipv4-address;
      description
        "Source address";
    }
    leaf destination-address-xr {
      type inet:ipv4-address;
      description
        "Destination address";
    }
    leaf instance-type {
      type Rsvp-mgmt-hello-instance;
      description
        "Hello instance type";
    }
    leaf hello-interface {
      type xr:Interface-name;
      description
        "Interface to use";
    }
  }

  grouping RSVP-MGMT-LOCAL-NODE-ID-IPV4 {
    description
      "Local Node-id";
    leaf local-node-ip-address {
      type inet:ipv4-address;
      description
        "Local node address";
    }
    leaf application-type {
      type Rsvp-mgmt-gr-app;
      description
        "GR local node-id app type";
    }
  }

  grouping RSVP-MGMT-GRACEFUL-RESTART {
    description
      "RSVP Graceful Restart Info";
    container recovery-time-left {
      description
        "How much recovery timer remains";
      uses RSVP-MGMT-TIMESPEC;
    }
    container recovery-timer-exp-time {
      description
        "Time at which recovery timer will expire";
      uses RSVP-MGMT-TIMESPEC;
    }
    leaf is-gr-enabled {
      type boolean;
      description
        "Whether GR is enabled";
    }
    leaf global-neighbors {
      type uint32;
      description
        "Global neighbor count";
    }
    leaf restart-time {
      type uint32;
      units "millisecond";
      description
        "Restart time (milliseconds)";
    }
    leaf recovery-time {
      type uint32;
      units "millisecond";
      description
        "Recovery time (milliseconds)";
    }
    leaf is-recovery-timer-running {
      type boolean;
      description
        "Whether recovery timer is running";
    }
    leaf hello-interval {
      type uint32;
      description
        "Interval at which hello messages are sent";
    }
    leaf missed-hellos {
      type uint8;
      description
        "Max number of hellos missed before hellos
         declared down";
    }
    leaf pending-states {
      type uint32;
      description
        "Total number of pending states";
    }
    list local-node-address {
      description
        "Local node address";
      uses RSVP-MGMT-LOCAL-NODE-ID-IPV4;
    }
  }

  grouping RSVP-MGMT-INTERFACE-COMPACT {
    description
      "Compact Form of RSVP interface Info";
    container bandwidth-information {
      description
        "Interface bandwidth information";
      uses RSVP-MGMT-DSTE-MODE-INTERFACE-BW;
    }
    leaf interface-name-xr {
      type string;
      description
        "Interface Name";
    }
  }

  grouping RSVP-MGMT-ALL-DB-COUNTERS {
    description
      "All database counters";
    leaf sessions {
      type uint32;
      description
        "Number of sessions";
    }
    leaf incoming-paths {
      type uint32;
      description
        "Number of locally created and incoming path
         states";
    }
    leaf outgoing-paths {
      type uint32;
      description
        "Number of outgoing path states";
    }
    leaf incoming-reservations {
      type uint32;
      description
        "Number of locally created and incoming
         reservation states";
    }
    leaf outgoing-reservations {
      type uint32;
      description
        "Number of outgoing reservation states";
    }
    leaf interfaces {
      type uint32;
      description
        "Number of Interfaces";
    }
  }

  grouping RSVP-SYNC-COUNT-INFO {
    description
      "RSVP sync sent and received counters information";
    leaf last-cleared-timestamp {
      type uint32;
      units "second";
      description
        "The timestamp, in seconds, when these statistics
         are cleared              since 00:00:00 UTC,
         January 1, 1970";
    }
    leaf rsvp-process-role {
      type Rsvp-proc-role;
      description
        "Process role";
    }
    leaf last-idt-states {
      type uint32;
      description
        "Last IDT number of states";
    }
    leaf total-states {
      type uint32;
      description
        "Total number of states";
    }
    leaf total-deletions {
      type uint32;
      description
        "Total number of deletions";
    }
    leaf total-nacks {
      type uint64;
      description
        "Total number of NACKs";
    }
    leaf total-id-ts {
      type uint32;
      description
        "Total number of IDTs";
    }
  }

  grouping RSVP-MGMT-EVENT-COUNT-INFO {
    description
      "Count of events";
    leaf expired-paths {
      type uint32;
      description
        "Counter for Expired Path states";
    }
    leaf expired-reservations {
      type uint32;
      description
        "Counter for Expired Reservation states";
    }
    leaf nac-ks {
      type uint32;
      description
        "Counter for NACKs received";
    }
  }

  grouping RSVP-MGMT-COUNTERS-OOR {
    description
      "Counters for all messages dropped in OOR
       condition";
    leaf dropped-path-messages {
      type uint32;
      description
        "Count of Path messages dropped due to an out of
         resource condition";
    }
  }

  grouping RSVP-MGMT-COUNT-PREFIX-INTERFACE-INFO {
    description
      "Prefix filtering interface counters";
    container forwarded {
      description
        "Count of messages which got forwarded";
      uses RSVP-MGMT-COUNT-PREFIX-MSG;
    }
    container locally-destined {
      description
        "Count of locally destined messages";
      uses RSVP-MGMT-COUNT-PREFIX-MSG;
    }
    container dropped {
      description
        "Count of messages dropped";
      uses RSVP-MGMT-COUNT-PREFIX-MSG;
    }
    container default-action-dropped {
      description
        "Count of messages which got dropped due to
         default ACL action";
      uses RSVP-MGMT-COUNT-PREFIX-MSG;
    }
    container default-action-processed {
      description
        "Count of messages which were processed due to
         default ACL action";
      uses RSVP-MGMT-COUNT-PREFIX-MSG;
    }
    container total {
      description
        "Count of total messages";
      uses RSVP-MGMT-COUNT-PREFIX-MSG;
    }
  }

  grouping RSVP-MGMT-COUNT-PREFIX-MSG {
    description
      "Message types for prefix filtering";
    leaf path {
      type uint32;
      description
        "Count of Path messages";
    }
    leaf path-tear {
      type uint32;
      description
        "Count of PathTear messages";
    }
    leaf reservation-confirm {
      type uint32;
      description
        "Count of ReservationConfirm messages";
    }
    leaf total {
      type uint32;
      description
        "Total count of messages";
    }
  }

  grouping RSVP-MGMT-COUNT-PREFIX-ACL-INFO {
    description
      "Prefix filtering ACL counters";
    container forwarded {
      description
        "Count of messages which got forwarded";
      uses RSVP-MGMT-COUNT-PREFIX-MSG;
    }
    container locally-destined {
      description
        "Count of locally destined messages";
      uses RSVP-MGMT-COUNT-PREFIX-MSG;
    }
    container dropped {
      description
        "Count of messages dropped";
      uses RSVP-MGMT-COUNT-PREFIX-MSG;
    }
    container total {
      description
        "Count of total messages";
      uses RSVP-MGMT-COUNT-PREFIX-MSG;
    }
  }

  grouping RSVP-MGMT-COUNTS {
    description
      "Counters for all known RSVP message types";
    leaf path {
      type uint32;
      description
        "Count of Path messages";
    }
    leaf reservation {
      type uint32;
      description
        "Count of Reservation messages";
    }
    leaf path-error {
      type uint32;
      description
        "Count of PathError messages";
    }
    leaf reservation-error {
      type uint32;
      description
        "Count of ReservationError messages";
    }
    leaf path-tear {
      type uint32;
      description
        "Count of PathTear messages";
    }
    leaf reservation-tear {
      type uint32;
      description
        "Count of ReservationTear messages";
    }
    leaf reservation-confirm {
      type uint32;
      description
        "Count of ReservationConfirm messages";
    }
    leaf bundle {
      type uint32;
      description
        "Count of Bundle messages";
    }
    leaf ack {
      type uint32;
      description
        "Count of ACK messages";
    }
    leaf srefresh {
      type uint32;
      description
        "Count of Srefresh messages";
    }
    leaf hello {
      type uint32;
      description
        "Count of Hello messages";
    }
    leaf challenge {
      type uint32;
      description
        "Count of Integrity Challenge messages";
    }
    leaf response {
      type uint32;
      description
        "Count of Integrity Response messages";
    }
  }

  grouping RSVP-MGMT-COUNT-MESSAGE {
    description
      "Counters for all messages";
    container received-messages {
      description
        "Count of messages received";
      uses RSVP-MGMT-COUNTS;
    }
    container transmitted-messages {
      description
        "Count of messages transmitted";
      uses RSVP-MGMT-COUNTS;
    }
    container bundle-received-messages {
      description
        "Count of Bundle messages received";
      uses RSVP-MGMT-COUNTS;
    }
    container bundle-transmitted-messages {
      description
        "Count of Bundle messages transmitted";
      uses RSVP-MGMT-COUNTS;
    }
    leaf retransmitted-messages {
      type uint32;
      description
        "Count of messages retransmitted";
    }
    leaf out-of-order-messages {
      type uint32;
      description
        "Count of Out of Order messages";
    }
    leaf rate-limited-messages {
      type uint32;
      description
        "Count of Rate Limited messages";
    }
  }

  grouping RSVP-MGMT-RESERVATION-COMPACT {
    description
      "Compact Form of RSVP Reservation Info";
    container session {
      description
        "RSVP Session Information";
      uses RSVP-MGMT-SESSION-INFO;
    }
    container s2l-sub-lsp {
      description
        "RSVP S2L Sub-LSP information";
      uses RSVP-MGMT-S2L-SUB-LSP-IPV4;
    }
    container flow-spec {
      description
        "Flow Spec Information";
      uses RSVP-MGMT-FLOW-SPEC;
    }
    container generic-flow-spec {
      description
        "Generic Flow Spec Info";
      uses RSVP-MGMT-GEN-FLOW-SPEC;
    }
    container style {
      description
        "RSVP Style";
      uses RSVP-MGMT-STYLE;
    }
    container filter {
      description
        "RSVP Filter";
      uses RSVP-MGMT-FILTER-INFO;
    }
    leaf input-interface {
      type string;
      description
        "Reservation Input Interface";
    }
  }

  grouping RSVP-MGMT-AUTH-RECV-TYPE-COUNTERS {
    description
      "RSVP Authentication Receive Type Counters";
    leaf authentication-received-valid-messages {
      type uint32;
      description
        "Valid messages";
    }
    leaf authentication-received-challenges-sent {
      type uint32;
      description
        "Challenges sent";
    }
    leaf authentication-received-challenge-response {
      type uint32;
      description
        "Challenge responses received";
    }
    leaf authentication-received-challenges-resent {
      type uint32;
      description
        "Challenges resent";
    }
    leaf authentication-received-challenge-timeouts {
      type uint32;
      description
        "Challenge timeouts";
    }
    leaf authentication-received-during-challenge {
      type uint32;
      description
        "Authentication received during challenge";
    }
    leaf authentication-received-incomplete {
      type uint32;
      description
        "Authentication received incomplete";
    }
    leaf authentication-received-no-integrity {
      type uint32;
      description
        "Authentication received with no integrity";
    }
    leaf authentication-received-bad-digest {
      type uint32;
      description
        "Authentication received with bad digest";
    }
    leaf authentication-received-wrong-digest-type {
      type uint32;
      description
        "Authentication received with wrong digest type";
    }
    leaf authentication-received-sequence-number-duplicate {
      type uint32;
      description
        "Authentication received with duplicate sequence
         number";
    }
    leaf authentication-received-sequence-number-outof-range {
      type uint32;
      description
        "Authentication received with sequence number out
         of range";
    }
    leaf authentication-received-wrong-challenges-response {
      type uint32;
      description
        "Incorect challenge responses received";
    }
    leaf authentication-received-challenges-response-duplicate {
      type uint32;
      description
        "Duplicate challenge responses received";
    }
    leaf authentication-received-response-late {
      type uint32;
      description
        "Challenge responses received late";
    }
    leaf authentication-received-bad-message-format {
      type uint32;
      description
        "Authentication received with bad mesage format";
    }
  }

  grouping RSVP-MGMT-AUTH-DIRECTION-RECV {
    description
      "RSVP Authentication Recieve Type Information";
    container counters {
      description
        "Counters";
      uses RSVP-MGMT-AUTH-RECV-TYPE-COUNTERS;
    }
    leaf sequence {
      type uint64;
      description
        "Sequence number";
    }
    leaf sequence-window-size {
      type uint32;
      description
        "Sequence window size";
    }
    leaf sequence-window-count {
      type uint32;
      description
        "Sequence window count";
    }
    list sequence-window {
      max-elements 64;
      description
        "Sequence window";
      leaf entry {
        type uint64;
        description
          "Sequence window";
      }
    }
  }

  grouping RSVP-MGMT-AUTH-SEND-TYPE-COUNTERS {
    description
      "RSVP Authentication Send Type Counters";
    leaf authentication-sent {
      type uint32;
      description
        "Messages sent";
    }
    leaf authentication-failures {
      type uint32;
      description
        "Failures";
    }
    leaf authentication-send-challenges-received {
      type uint32;
      description
        "Challenges received";
    }
    leaf authentication-challenge-responses-sent {
      type uint32;
      description
        "Challenge responses sent";
    }
  }

  grouping RSVP-MGMT-AUTH-DIRECTION-SEND {
    description
      "RSVP Authentication Send Type Information";
    container counters {
      description
        "Counters";
      uses RSVP-MGMT-AUTH-SEND-TYPE-COUNTERS;
    }
    leaf sequence {
      type uint64;
      description
        "Sequence number";
    }
  }

  grouping RSVP-MGMT-AUTH-DIRECTION {
    description
      "Union of the different RSVP Authentication
       Direction types";
    container send-info {
      when "../auth-direction = 'rsvp-mgmt-auth-direction-send'" {
        tailf:xpath-root 3;
        description
          "../AuthDirection = 'RSVPMgmtAuthDirectionSend'";
      }
      description
        "send info";
      uses RSVP-MGMT-AUTH-DIRECTION-SEND;
    }
    container receive-info {
      when "../auth-direction = 'rsvp-mgmt-auth-direction-recv'" {
        tailf:xpath-root 3;
        description
          "../AuthDirection = 'RSVPMgmtAuthDirectionRecv'";
      }
      description
        "receive info";
      uses RSVP-MGMT-AUTH-DIRECTION-RECV;
    }
    leaf auth-direction {
      type Rsvp-mgmt-auth-direction;
      description
        "AuthDirection";
    }
  }

  grouping RSVP-MGMT-AUTHENTICATION-DETAIL {
    description
      "Authentication Detail Information";
    container auth-compact {
      description
        "Basic authentication data";
      uses RSVP-MGMT-AUTHENTICATION-COMPACT;
    }
    container direction-info {
      description
        "direction info";
      uses RSVP-MGMT-AUTH-DIRECTION;
    }
    leaf key-status {
      type uint32;
      description
        "Key status";
    }
    leaf key-digest-info {
      type uint32;
      description
        "Direction";
    }
    leaf lifetime {
      type uint32;
      units "second";
      description
        "Lifetime (seconds)";
    }
    leaf lifetime-left {
      type uint32;
      units "second";
      description
        "Remaining lifetime (seconds)";
    }
    leaf challenge-status {
      type Rsvp-mgmt-auth-challenge-status;
      description
        "Challenge status";
    }
  }

  grouping RSVP-MGMT-HELLO-INSTANCE-COMPACT {
    description
      "Compact Info for RSVP Hello Instance";
    leaf source-address-xr {
      type inet:ipv4-address;
      description
        "Source address";
    }
    leaf destination-address-xr {
      type inet:ipv4-address;
      description
        "Destination address";
    }
    leaf neighbor-hello-state {
      type Rsvp-mgmt-hello-state;
      description
        "Neighbor Hello state";
    }
    leaf instance-type {
      type Rsvp-mgmt-hello-instance;
      description
        "Hello instance type";
    }
    leaf hello-interface {
      type xr:Interface-name;
      description
        "Interface to use";
    }
    leaf lost-communication-total {
      type uint16;
      description
        "Total number of times communication got lost";
    }
  }

  grouping RSVP-MGMT-RSB-FLAGS {
    description
      "Reservation State Block Flags";
    leaf is-local-receiver {
      type boolean;
      description
        "Local Receiver";
    }
    leaf is-message-id-valid {
      type boolean;
      description
        "MessageID Valid";
    }
    leaf is-local-repair {
      type boolean;
      description
        "Rerouted";
    }
    leaf is-merge-point {
      type boolean;
      description
        "Is node a Merge Point";
    }
    leaf is-lockout {
      type boolean;
      description
        "Locked Out";
    }
  }

  grouping RSVP-MGMT-STYLE {
    description
      "RSVP Reservation Style";
    leaf reservation-type {
      type Rsvp-mgmt-reservation-type-enum;
      description
        "The Reservation Type: WF, SE or FF";
    }
  }

  grouping RSVP-MGMT-FLOW-SPEC-G709-OTN {
    description
      "RSVP G709 OTN FlowSpec Info";
    leaf flow-signal-type {
      type uint8;
      description
        "G709 OTN Flow Signal Type (Refer G709 v3)";
    }
    leaf flow-nvc {
      type uint16;
      description
        "G709 OTN Flow NVC";
    }
    leaf flow-multiplier {
      type uint16;
      description
        "G709 OTN Flow Multiplier";
    }
    leaf flow-bit-rate {
      type uint64;
      description
        "G709 OTN Flow Bit Rate";
    }
  }

  grouping RSVP-MGMT-GEN-FLOW-SPEC {
    description
      "Union of different RSVP Generic FlowSpec types";
    container g709otn-flow-spec {
      when "../flow-spec-type = 'g709otn'" {
        tailf:xpath-root 3;
        description
          "../FlowSpecType = 'G709OTN'";
      }
      description
        "G709 OTN FlowSpec";
      uses RSVP-MGMT-FLOW-SPEC-G709-OTN;
    }
    leaf flow-spec-type {
      type Rsvp-mgmt-flow-spec;
      description
        "FlowSpecType";
    }
  }

  grouping RSVP-MGMT-FLOW-SPEC {
    description
      "RSVP Flow Spec";
    leaf flow-average-rate {
      type uint64;
      units "byte/s";
      description
        "The Flow Average Rate in bytes per second";
    }
    leaf flow-max-burst {
      type uint64;
      description
        "The Flow Maximum Burst";
    }
    leaf flow-peak-rate {
      type uint64;
      units "byte/s";
      description
        "The Flow Peak Rate in bytes per second";
    }
    leaf flow-min-unit {
      type uint32;
      description
        "The Flow Minimum Unit";
    }
    leaf flow-max-unit {
      type uint32;
      description
        "The Flow Maximum Unit";
    }
    leaf flow-requested-rate {
      type uint64;
      units "byte/s";
      description
        "The Flow Requested Rate in bytes per second";
    }
    leaf flow-slack {
      type uint32;
      description
        "The Flow Slack";
    }
    leaf flow-qos {
      type Rsvp-mgmt-qos-service-enum;
      description
        "The Flow Quality of Service";
    }
  }

  grouping RSVP-MGMT-RESERVATION-DETAIL {
    description
      "Detailed Form of RSVP Reservation Info";
    container flow-spec {
      description
        "Flow Spec Information";
      uses RSVP-MGMT-FLOW-SPEC;
    }
    container generic-flow-spec {
      description
        "Generic Flow Spec Information";
      uses RSVP-MGMT-GEN-FLOW-SPEC;
    }
    container session {
      description
        "RSVP Session Information";
      uses RSVP-MGMT-SESSION-INFO;
    }
    container s2l-sub-lsp {
      description
        "RSVP S2L Sub-LSP information";
      uses RSVP-MGMT-S2L-SUB-LSP-IPV4;
    }
    container style {
      description
        "RSVP Style";
      uses RSVP-MGMT-STYLE;
    }
    container filter {
      description
        "RSVP Filter";
      uses RSVP-MGMT-FILTER-INFO;
    }
    container rsb-flags {
      description
        "Reservation State Block Flags";
      uses RSVP-MGMT-RSB-FLAGS;
    }
    container hop {
      description
        "Hop Infomation";
      uses RSVP-MGMT-HOP-INFO;
    }
    container policy-sources {
      description
        "RSVP Policy Sources";
      uses RSVP-MGMT-POLICY-SOURCES;
    }
    container header {
      description
        "RSVP Header Information";
      uses RSVP-MGMT-HEADER-INFO;
    }
    container policy-flags {
      description
        "RSVP Policy Flags";
      uses RSVP-MGMT-POLICY-FLAGS;
    }
    container expiry-time {
      description
        "Expiry Time";
      uses RSVP-MGMT-TIMESPEC;
    }
    container policy-query-flags {
      description
        "RSVP Query Flags";
      uses RSVP-MGMT-POLICY-QUERY-FLAGS;
    }
    container label-info {
      description
        "Label Information";
      uses RSVP-MGMT-LABEL-INFO;
    }
    leaf input-adjusted-interface {
      type string;
      description
        "Input Adjusted Interface";
    }
    leaf input-physical-interface {
      type string;
      description
        "Input Physical Interface";
    }
  }

  grouping RSVP-MGMT-FRR-STATE-STATUS-COUNTERS {
    description
      "FRR state counters";
    leaf total {
      type uint32;
      description
        "Total number of instances of this state";
    }
    leaf active-instances {
      type uint32;
      description
        "Number of active instances of this state";
    }
    leaf ready-instances {
      type uint32;
      description
        "Number of ready instances of this state";
    }
    leaf active-wait-instances {
      type uint32;
      description
        "Number of instances of this state awaiting Path
         messages to be sent out or Resv messages to be
         received";
    }
  }

  grouping RSVP-MGMT-FRR-STATES-COMPACT {
    description
      "Count of RSVP FRR States";
    container path-states {
      description
        "Path state counters";
      uses RSVP-MGMT-FRR-STATE-STATUS-COUNTERS;
    }
    container reservation-states {
      description
        "Rerservation state counters";
      uses RSVP-MGMT-FRR-STATE-STATUS-COUNTERS;
    }
  }

  grouping RSVP-MGMT-MESSAGEID {
    description
      "RSVP Message ID";
    leaf message-id {
      type Rsvp-mgmt-messageid;
      description
        "Message ID";
    }
  }

  grouping RSVP-MGMT-NBOR {
    description
      "Neighbor";
    container expiry-time {
      description
        "Expiry time";
      uses RSVP-MGMT-TIMESPEC;
    }
    leaf is-neighbor-refresh-reduction-capable {
      type boolean;
      description
        "Is neighbor capable of Refresh Reduction";
    }
    leaf neighbor-address {
      type inet:ipv4-address;
      description
        "IP address of the neighbor";
    }
    leaf message-ids {
      type uint32;
      description
        "Number of MessageIDs";
    }
    leaf outgoing-states {
      type int32;
      description
        "Number of outgoing states to the neighbour";
    }
    list neighbor-message-id {
      max-elements 6;
      description
        "List of Neighbor MessageIDs";
      uses RSVP-MGMT-MESSAGEID;
    }
  }

  grouping RSVP-MGMT-INTERFACE-FLAGS {
    description
      "Interface related flags";
    leaf is-mpls-enabled {
      type boolean;
      description
        "MPLS enabled on interface";
    }
    leaf is-refresh-reduction-enabled {
      type boolean;
      description
        "Refresh Reduction enabled";
    }
    leaf is-pacing-enabled {
      type boolean;
      description
        "Message pacing enabled";
    }
    leaf is-refresh-enabled {
      type boolean;
      description
        "Refresh enabled";
    }
    leaf is-s-refresh-enabled {
      type boolean;
      description
        "Summary Refresh enabled";
    }
    leaf is-interface-down {
      type boolean;
      description
        "Interface is DOWN";
    }
    leaf is-interface-created {
      type boolean;
      description
        "Interface is created";
    }
    leaf is-rel-s-refresh-enabled {
      type boolean;
      description
        "Use reliable xmt for SRefresh";
    }
    leaf is-backup-tunnel {
      type boolean;
      description
        "This is backup tunnel";
    }
    leaf is-rsvp-configured {
      type boolean;
      description
        "RSVP explicitly configured";
    }
    leaf is-non-default-vrf {
      type boolean;
      description
        "Interface is defined in non-Default VRF";
    }
    leaf is-message-bundling-enabled {
      type boolean;
      description
        "Use bundling for outgoing RSVP messages.";
    }
  }

  grouping RSVP-MGMT-INTERFACE-DETAIL {
    description
      "Detail Form of RSVP interface Info";
    container bandwidth-information {
      description
        "Interface bandwidth information";
      uses RSVP-MGMT-DSTE-MODE-INTERFACE-BW;
    }
    container flags {
      description
        "Interface flags";
      uses RSVP-MGMT-INTERFACE-FLAGS;
    }
    leaf interface-name-xr {
      type string;
      description
        "Interface Name";
    }
    leaf signalling-ip-tos {
      type uint8;
      description
        "IP TOS (precedence/DSCP) to use in signalling
         messages";
    }
    leaf integrity-send-password {
      type string {
        length "0..40";
      }
      description
        "Integrity send password";
    }
    leaf integrity-receive-password {
      type string {
        length "0..40";
      }
      description
        "Integrity receive password";
    }
    leaf integrity-receive-password-optional {
      type uint8;
      description
        "Integrity recv password optional";
    }
    leaf refresh-timer-state {
      type Rsvp-timer-state;
      description
        "Refresh timer state";
    }
    leaf summary-refresh-timer-state {
      type Rsvp-timer-state;
      description
        "Summary refresh timer state";
    }
    leaf refresh-interval {
      type int32;
      units "millisecond";
      description
        "Refresh interval in msecs";
    }
    leaf out-of-band-refresh-interval {
      type uint32;
      units "millisecond";
      description
        "Out-of-band Refresh interval in msecs";
    }
    leaf summary-refresh-max-size {
      type uint32;
      units "byte";
      description
        "Max size in bytes of a single SRefresh";
    }
    leaf bundle-message-max-size {
      type uint32;
      units "byte";
      description
        "Max size in bytes of a single Bundle message";
    }
    leaf expiry-timer-state {
      type Rsvp-timer-state;
      description
        "Expiry timer state";
    }
    leaf expiry-states {
      type int32;
      description
        "Number of states for expiry check";
    }
    leaf expiry-interval {
      type int32;
      units "millisecond";
      description
        "Expiry interval in msecs";
    }
    leaf expiry-drops-tolerated {
      type int32;
      description
        "Number of missed messages tolerated";
    }
    leaf out-of-band-expiry-drops-tolerated {
      type uint32;
      description
        "Number of out-of-band missed messages tolerated";
    }
    leaf ack-hold-time {
      type uint32;
      description
        "ACK hold time in msec";
    }
    leaf ack-max-size {
      type uint32;
      description
        "Max size for ACK message";
    }
    leaf retransmit-time {
      type uint32;
      description
        "Retransmit time in msec";
    }
    leaf pacing-interval {
      type uint32;
      units "millisecond";
      description
        "Pacing interval in msecs";
    }
    leaf pacing-message-rate {
      type uint32;
      description
        "No. of messages per interval";
    }
    leaf pacing-timer-state {
      type Rsvp-timer-state;
      description
        "State of pacing timer";
    }
    leaf pacing-messages {
      type int32;
      description
        "Number of messages deferred for pacing";
    }
    list neighbor-array {
      max-elements 6;
      description
        "Neighbor array";
      uses RSVP-MGMT-NBOR;
    }
  }

  grouping RSVP-MGMT-ERO-UNNUM-SUBOBJ {
    description
      "RSVP ERO UNNUM subobject";
    leaf is-strict-route {
      type boolean;
      description
        "ERO Entry Is Strict";
    }
    leaf ero-interface-id {
      type uint32;
      description
        "The Interface ID in ERO";
    }
    leaf ero-router-id {
      type inet:ipv4-address;
      description
        "The Router ID in ERO";
    }
    leaf status {
      type Rsvp-mgmt-ero-subobj-status;
      description
        "Status of ERO";
    }
  }

  grouping RSVP-MGMT-ERO-IPV4-SUBOBJ {
    description
      "RSVP ERO IPV4 subobject";
    leaf is-strict-route {
      type boolean;
      description
        "ERO Entry Is Strict";
    }
    leaf ero-address {
      type inet:ipv4-address;
      description
        "The ERO IPV4 Address";
    }
    leaf prefix-length {
      type uint8;
      description
        "ERO Prefix Length";
    }
  }

  grouping RSVP-MGMT-ERO-SUBOBJ {
    description
      "Union of the different RSVP ERO types";
    container ipv4ero-sub-object {
      when "../ero-type = 'rsvp-mgmt-ero-type-ipv4'" {
        tailf:xpath-root 3;
        description
          "../EROType = 'RSVP_MGMT_ERO_TYPE_IPv4'";
      }
      description
        "IPV4 ERO Sub Object";
      uses RSVP-MGMT-ERO-IPV4-SUBOBJ;
    }
    container unnumbered-ero-sub-object {
      when "../ero-type = 'rsvp-mgmt-ero-type-un-num'" {
        tailf:xpath-root 3;
        description
          "../EROType = 'RSVP_MGMT_ERO_TYPE_UNNUM'";
      }
      description
        "Unnumbered ERO Sub Object";
      uses RSVP-MGMT-ERO-UNNUM-SUBOBJ;
    }
    leaf ero-type {
      type Rsvp-mgmt-ero-subobj;
      description
        "EROType";
    }
  }

  grouping RSVP-MGMT-CT-INFO {
    description
      "Class-Type Information";
    leaf is-class-type-info-valid {
      type boolean;
      description
        "Is the Class-Type information valid";
    }
    leaf class-type {
      type uint8;
      description
        "DS-TE Class-Type";
    }
  }

  grouping RSVP-MGMT-GENERALIZED-LABEL {
    description
      "RSVP Generalized Label";
    list value {
      description
        "Generalized Label Value";
      leaf entry {
        type uint32;
        description
          "Generalized Label Value";
      }
    }
  }

  grouping RSVP-MGMT-GENERIC-LABEL {
    description
      "Union of different RSVP Generic Label types";
    container generalized-label {
      when "../generic-label-type = 'rsvp-mgmt-label-type-gmpls'" {
        tailf:xpath-root 3;
        description
          "../GenericLabelType =
           'RSVP_MGMT_LABEL_TYPE_GMPLS'";
      }
      description
        "Generalized Label";
      uses RSVP-MGMT-GENERALIZED-LABEL;
    }
    leaf generic-label-type {
      type Rsvp-mgmt-generic-label;
      description
        "GenericLabelType";
    }
  }

  grouping RSVP-MGMT-LABEL-INFO {
    description
      "Label Information";
    container generic-local-downstream-label {
      description
        "Generic Local Downstream Label";
      uses RSVP-MGMT-GENERIC-LABEL;
    }
    container generic-outgoing-downstream-label {
      description
        "Generic Outgoing Downstream Label";
      uses RSVP-MGMT-GENERIC-LABEL;
    }
    container generic-merge-point-label {
      description
        "Generic MergePoint Label";
      uses RSVP-MGMT-GENERIC-LABEL;
    }
    container generic-outgoing-upstream-label {
      description
        "Generic Outgoing Upstream Label";
      uses RSVP-MGMT-GENERIC-LABEL;
    }
    container generic-local-upstream-label {
      description
        "Generic Local Upstream Label";
      uses RSVP-MGMT-GENERIC-LABEL;
    }
    container generic-recovery-label {
      description
        "Generic Recovery Label";
      uses RSVP-MGMT-GENERIC-LABEL;
    }
    leaf is-valid {
      type boolean;
      description
        "Is the label information valid";
    }
    leaf local-downstream-label {
      type Rsvp-mgmt-mpls-label;
      description
        "Local Downstream Label";
    }
    leaf outgoing-downstream-label {
      type Rsvp-mgmt-mpls-label;
      description
        "Outgoing Downstream Label";
    }
    leaf merge-point-label {
      type Rsvp-mgmt-mpls-label;
      description
        "MergePoint Label";
    }
    leaf outgoing-upstream-label {
      type Rsvp-mgmt-mpls-label;
      description
        "Outgoing Upstream Label";
    }
    leaf local-upstream-label {
      type Rsvp-mgmt-mpls-label;
      description
        "Local Upstream Label";
    }
    leaf recovery-label {
      type Rsvp-mgmt-mpls-label;
      description
        "Recovery Label";
    }
    leaf lsp-wrap-label {
      type Rsvp-mgmt-mpls-label;
      description
        "LSP Wrap Label";
    }
  }

  grouping RSVP-PATH-FORWARDING-CONTEXT {
    description
      "RSVP Path Forwarding Context";
    container policy-flags {
      description
        "Policy Flags";
      uses RSVP-MGMT-POLICY-FLAGS;
    }
    container policy-query-flags {
      description
        "Policy Query Flags";
      uses RSVP-MGMT-POLICY-QUERY-FLAGS;
    }
    leaf output-interface {
      type string;
      description
        "Output interface";
    }
  }

  grouping RSVP-MGMT-POLICY-QUERY-FLAGS {
    description
      "RSVP Policy Query Flags";
    leaf is-needed {
      type boolean;
      description
        "Needed";
    }
    leaf is-report-required {
      type boolean;
      description
        "Report Required";
    }
    leaf is-resync {
      type boolean;
      description
        "Resynchronization";
    }
    leaf is-bypass {
      type boolean;
      description
        "Bypass";
    }
  }

  grouping RSVP-MGMT-POLICY-FLAGS {
    description
      "RSVP Policy Flags";
    leaf is-accepted {
      type boolean;
      description
        "Accepted";
    }
    leaf is-installed {
      type boolean;
      description
        "Installed";
    }
    leaf is-forwarding {
      type boolean;
      description
        "Forwarding";
    }
  }

  grouping RSVP-MGMT-TIMESPEC {
    description
      "RSVP Time Spec";
    leaf seconds {
      type int32;
      units "second";
      description
        "Time Value in Seconds";
    }
    leaf nanoseconds {
      type int32;
      units "nanosecond";
      description
        "Time Value in Nano-seconds";
    }
  }

  grouping RSVP-MGMT-HEADER-INFO {
    description
      "RSVP/IP Header Info";
    leaf rsvp-version {
      type uint8;
      description
        "RSVP Version";
    }
    leaf rsvp-header-flags {
      type uint8;
      description
        "RSVP Header Flags (defined in RFC2205 Section 3
         .1.1)";
    }
    leaf rsvp-ttl {
      type uint8;
      description
        "RSVP TTL";
    }
    leaf rsvp-message-type {
      type uint8;
      description
        "RSVP Message Type";
    }
    leaf ip-tos {
      type uint8;
      description
        "IP Type of Service";
    }
    leaf ip-ttl {
      type uint8;
      description
        "IP TTL";
    }
    leaf ip-source-address {
      type inet:ipv4-address;
      description
        "IP Source Address";
    }
  }

  grouping RSVP-MGMT-POLICY-SOURCES {
    description
      "RSVP Policy Sources";
    leaf is-te-link {
      type boolean;
      description
        "Policy Source is TE Link";
    }
    leaf is-local {
      type boolean;
      description
        "Policy Source is Local";
    }
    leaf is-cops {
      type boolean;
      description
        "Policy Source is COPS";
    }
    leaf is-default {
      type boolean;
      description
        "Policy Source is Default";
    }
    leaf is-cable {
      type boolean;
      description
        "Policy Source is Cable";
    }
  }

  grouping RSVP-MGMT-HOP-INFO {
    description
      "Hop Info";
    leaf neighbor-address {
      type inet:ipv4-address;
      description
        "IP address of the neighbor";
    }
    leaf neighbor-logical-interface-handle {
      type uint32;
      description
        "Neighbor Logical Interface Handle";
    }
  }

  grouping RSVP-MGMT-PATH-FLAGS {
    description
      "RSVP Path Flags";
    leaf is-non-rsvp-hop-upstream {
      type boolean;
      description
        "Non-RSVP Hop Upstream";
    }
    leaf is-local-sender {
      type boolean;
      description
        "Local Sender";
    }
    leaf is-message-id-valid {
      type boolean;
      description
        "MessageID Valid";
    }
    leaf is-local-repair {
      type boolean;
      description
        "Rerouted";
    }
    leaf is-bidirectional {
      type boolean;
      description
        "Bidirectional";
    }
    leaf is-lockout {
      type boolean;
      description
        "Locked Out";
    }
  }

  grouping RSVP-MGMT-TSPEC-G709-OTN {
    description
      "RSVP G709 OTN Sender Tspec Info";
    leaf traffic-signal-type {
      type uint8;
      description
        "G709 OTN Traffic Signal Type (Refer G709 v3)";
    }
    leaf traffic-nvc {
      type uint16;
      description
        "G709 OTN Traffic NVC";
    }
    leaf traffic-multiplier {
      type uint16;
      description
        "G709 OTN Traffic Multiplier";
    }
    leaf traffic-bit-rate {
      type uint64;
      description
        "G709 OTN Traffic Bit Rate";
    }
  }

  grouping RSVP-MGMT-GEN-TRAFFIC-SPEC {
    description
      "Union of different RSVP Generic Sender Tspec
       types";
    container g709otn-tspec {
      when "../tspec-type = 'g709otn'" {
        tailf:xpath-root 3;
        description
          "../TspecType = 'G709OTN'";
      }
      description
        "G709 OTN Sender Tspec";
      uses RSVP-MGMT-TSPEC-G709-OTN;
    }
    container intsrv-tspec {
      when "../tspec-type = 'intsrv'" {
        tailf:xpath-root 3;
        description
          "../TspecType = 'INTSRV'";
      }
      description
        "Integrated Services Sender Tspec";
      uses RSVP-MGMT-TRAFFIC-SPEC;
    }
    leaf tspec-type {
      type Rsvp-mgmt-tspec;
      description
        "TspecType";
    }
  }

  grouping RSVP-MGMT-TRAFFIC-SPEC {
    description
      "RSVP Traffic Spec Info";
    leaf traffic-average-rate {
      type uint64;
      units "byte/s";
      description
        "Traffic Average Rate in bytes per second";
    }
    leaf traffic-max-burst {
      type uint64;
      description
        "Traffic Maximum Burst";
    }
    leaf traffic-peak-rate {
      type uint64;
      units "byte/s";
      description
        "Traffic Peak Rate in bytes per second";
    }
    leaf traffic-min-unit {
      type uint32;
      description
        "Traffic Minimum Unit";
    }
    leaf traffic-max-unit {
      type uint32;
      description
        "Traffic Maximum Unit";
    }
  }

  grouping RSVP-MGMT-SESSION-ATTRIBUTE-FLAGS {
    description
      "RSVP Session Attribute Flags";
    leaf is-local-protect {
      type boolean;
      description
        "Local Protection";
    }
    leaf is-node-protect {
      type boolean;
      description
        "Node Protection";
    }
    leaf is-bandwidth-protect {
      type boolean;
      description
        "Bandwidth Protection";
    }
    leaf is-record-labels {
      type boolean;
      description
        "Records Labels";
    }
    leaf is-shared-explicit-requested {
      type boolean;
      description
        "Shared Explicit Requested";
    }
  }

  grouping RSVP-MGMT-SESSION-ATTRIBUTE {
    description
      "RSVP Session Attributes";
    container sess-attribute-flags {
      description
        "Session Attributes";
      uses RSVP-MGMT-SESSION-ATTRIBUTE-FLAGS;
    }
    leaf setup-priority {
      type uint8;
      description
        "Setup Priority";
    }
    leaf reservation-priority {
      type uint8;
      description
        "Reservation Priority";
    }
  }

  grouping RSVP-MGMT-FILTER-P2MP-IPV4 {
    description
      "RSVP P2MP IPv4 FilterSpec";
    leaf source-address {
      type inet:ipv4-address;
      description
        "Source Address";
    }
    leaf source-port {
      type uint16;
      description
        "Source Port";
    }
    leaf p2mp-sub-group-origin {
      type inet:ipv4-address;
      description
        "Point to Multipoint SubGroup Origin";
    }
    leaf sub-group-id {
      type uint16;
      description
        "Point to Multipoint Subgroup ID";
    }
  }

  grouping RSVP-MGMT-FILTER-IPV4 {
    description
      "RSVP Filter";
    leaf source-address {
      type inet:ipv4-address;
      description
        "Source Address";
    }
    leaf source-port {
      type uint16;
      description
        "Source Port";
    }
  }

  grouping RSVP-FILTER-UNION {
    description
      "Union of the different RSVP filterspec types";
    container udp-ipv4-session {
      when "../filter-type = 'rsvp-mgmt-filter-type-ipv4'" {
        tailf:xpath-root 3;
        description
          "../FilterType = 'RSVPMgmtFilterTypeIPv4'";
      }
      description
        "UDP IPV4 FilterSpec";
      uses RSVP-MGMT-FILTER-IPV4;
    }
    container p2mp-ipv4-session {
      when "../filter-type = 'rsvp-mgmt-filter-type-p2mp-lsp-ipv4'" {
        tailf:xpath-root 3;
        description
          "../FilterType =
           'RSVPMgmtFilterTypeP2MP_LSP_IPv4'";
      }
      description
        "IPv4 P2MP LSP FilterSpec";
      uses RSVP-MGMT-FILTER-P2MP-IPV4;
    }
    leaf filter-type {
      type Rsvp-mgmt-filter;
      description
        "FilterType";
    }
  }

  grouping RSVP-MGMT-FILTER-INFO {
    description
      "RSVP FilterSpec Info";
    container rsvp-filter {
      description
        "RSVP Filter";
      uses RSVP-FILTER-UNION;
    }
  }

  grouping RSVP-MGMT-S2L-SUB-LSP-IPV4 {
    description
      "RSVP S2L Sub-LSP";
    leaf s2l-destination-address {
      type inet:ipv4-address;
      description
        "S2L Sub-LSP Destination Address";
    }
  }

  grouping RSVP-MGMT-PATH-DETAIL {
    description
      "Detailed Form of RSVP Path Info";
    container session {
      description
        "RSVP Session Information";
      uses RSVP-MGMT-SESSION-INFO;
    }
    container s2l-sub-lsp {
      description
        "RSVP S2L Sub-LSP information";
      uses RSVP-MGMT-S2L-SUB-LSP-IPV4;
    }
    container template {
      description
        "RSVP Template";
      uses RSVP-MGMT-FILTER-INFO;
    }
    container session-attribute {
      description
        "RSVP Session Attribute";
      uses RSVP-MGMT-SESSION-ATTRIBUTE;
    }
    container traffic-spec {
      description
        "RSVP Traffic Spec Info";
      uses RSVP-MGMT-TRAFFIC-SPEC;
    }
    container generic-traffic-spec {
      description
        "RSVP Generic Traffic Spec Info";
      uses RSVP-MGMT-GEN-TRAFFIC-SPEC;
    }
    container path-flags {
      description
        "Path Flags";
      uses RSVP-MGMT-PATH-FLAGS;
    }
    container hop {
      description
        "Path Hop Info";
      uses RSVP-MGMT-HOP-INFO;
    }
    container policy-source-info {
      description
        "Policy Sources Info";
      uses RSVP-MGMT-POLICY-SOURCES;
    }
    container header {
      description
        "RSVP Header Info";
      uses RSVP-MGMT-HEADER-INFO;
    }
    container expiry-time {
      description
        "Expiry Time";
      uses RSVP-MGMT-TIMESPEC;
    }
    container policy-flags {
      description
        "Policy Flags";
      uses RSVP-MGMT-POLICY-FLAGS;
    }
    container policy-query-flags {
      description
        "Policy Query Flags";
      uses RSVP-MGMT-POLICY-QUERY-FLAGS;
    }
    container label-info {
      description
        "Label Information";
      uses RSVP-MGMT-LABEL-INFO;
    }
    container class-type {
      description
        "DS-TE Class-Type";
      uses RSVP-MGMT-CT-INFO;
    }
    leaf input-interface {
      type string;
      description
        "Path Input Interface";
    }
    leaf backup-tunnel-name {
      type string;
      description
        "Path Backup Tunnel";
    }
    leaf is-in-ero-valid {
      type boolean;
      description
        "Incoming ERO validity";
    }
    leaf is-out-ero-valid {
      type boolean;
      description
        "Outgoing ERO validity";
    }
    list pfc {
      description
        "Path Forwarding Contexts";
      uses RSVP-PATH-FORWARDING-CONTEXT;
    }
    list in-ero {
      description
        "Incoming Explicit Route Sub Objects";
      uses RSVP-MGMT-ERO-SUBOBJ;
    }
    list out-ero {
      description
        "Outgoing Explicit Route Sub Objects";
      uses RSVP-MGMT-ERO-SUBOBJ;
    }
  }

  grouping RSVP-MGMT-SESSION-P2MP-LSP-TUNNEL-IPV4 {
    description
      "RSVP P2MP-LSP-Tunnel-IPv4 Session";
    leaf p2mp-id {
      type uint32;
      description
        "The Point to Multipoint ID";
    }
    leaf tunnel-id {
      type uint16;
      description
        "The Session Tunnel ID";
    }
    leaf extended-tunnel-id {
      type inet:ipv4-address;
      description
        "The Session Extended Tunnel ID";
    }
  }

  grouping RSVP-MGMT-SESSION-UNI-IPV4 {
    description
      "RSVP UNI IPv4 Session";
    leaf destination-address {
      type inet:ipv4-address;
      description
        "Destination address";
    }
    leaf tunnel-id {
      type uint16;
      description
        "The Session Tunnel ID";
    }
    leaf extended-address {
      type inet:ipv4-address;
      description
        "The Session Extended Address";
    }
  }

  grouping RSVP-MGMT-SESSION-LSP-TUNNEL-IPV4 {
    description
      "RSVP LSP-Tunnel-IPv4 Session";
    leaf destination-address {
      type inet:ipv4-address;
      description
        "Destination address";
    }
    leaf tunnel-id {
      type uint16;
      description
        "The Session Tunnel ID";
    }
    leaf extended-tunnel-id {
      type inet:ipv4-address;
      description
        "The Session Extended Tunnel ID";
    }
  }

  grouping RSVP-MGMT-SESSION-UDP-IPV4 {
    description
      "RSVP UDP IPv4 Session";
    leaf destination-address {
      type inet:ipv4-address;
      description
        "Destination address";
    }
    leaf protocol {
      type uint8;
      description
        "Protocol type (originally defined in RFC 790,
         further values in subsequent RFCs)";
    }
    leaf destination-port {
      type uint16;
      description
        "The Session Destination Port";
    }
  }

  grouping RSVP-SESSION-UNION {
    description
      "Union of the different RSVP session types";
    container ipv4 {
      when "../session-type = 'rsvp-mgmt-session-type-udp-ipv4'" {
        tailf:xpath-root 3;
        description
          "../SessionType = 'RSVPMgmtSessionTypeUDP_IPv4'";
      }
      description
        "UDP IPv4 session";
      uses RSVP-MGMT-SESSION-UDP-IPV4;
    }
    container ipv4-lsp-session {
      when "../session-type = 'rsvp-mgmt-session-type-lsp-ipv4'" {
        tailf:xpath-root 3;
        description
          "../SessionType = 'RSVPMgmtSessionTypeLSP_IPv4'";
      }
      description
        "IPv4 LSP session";
      uses RSVP-MGMT-SESSION-LSP-TUNNEL-IPV4;
    }
    container ipv4-uni-session {
      when "../session-type = 'rsvp-mgmt-session-type-uni-ipv4'" {
        tailf:xpath-root 3;
        description
          "../SessionType = 'RSVPMgmtSessionTypeUNI_IPv4'";
      }
      description
        "IPv4 UNI session";
      uses RSVP-MGMT-SESSION-UNI-IPV4;
    }
    container ipv4-p2mp-lsp-session {
      when "../session-type = 'rsvp-mgmt-session-type-p2mp-lsp-ipv4'" {
        tailf:xpath-root 3;
        description
          "../SessionType =
           'RSVPMgmtSessionTypeP2MP_LSP_IPv4'";
      }
      description
        "IPv4 P2MP LSP session";
      uses RSVP-MGMT-SESSION-P2MP-LSP-TUNNEL-IPV4;
    }
    leaf session-type {
      type Rsvp-mgmt-session;
      description
        "SessionType";
    }
  }

  grouping RSVP-MGMT-SESSION-INFO {
    description
      "RSVP Session Info";
    container rsvp-session {
      description
        "RSVP Session";
      uses RSVP-SESSION-UNION;
    }
  }

  grouping RSVP-MGMT-SESSION-COMPACT {
    description
      "RSVP Compact Session Info";
    container session {
      description
        "RSVP Session Information";
      uses RSVP-MGMT-SESSION-INFO;
    }
    leaf ps-bs {
      type uint32;
      description
        "Number of path state block states";
    }
    leaf rs-bs {
      type uint32;
      description
        "Number of reservation state block states";
    }
    leaf requests {
      type uint32;
      description
        "Number of request states";
    }
    leaf detail-list-size {
      type uint32;
      description
        "Number of elements in detail list";
    }
  }

  grouping RSVP-MGMT-AUTHENTICATION-COMPACT {
    description
      "Authentication Compact Information";
    leaf source-address-xr {
      type inet:ipv4-address;
      description
        "Source address";
    }
    leaf destination-address-xr {
      type inet:ipv4-address;
      description
        "Destination address";
    }
    leaf neighbor-address {
      type inet:ipv4-address;
      description
        "Neighbor address";
    }
    leaf direction {
      type Rsvp-mgmt-auth-direction;
      description
        "Direction";
    }
    leaf key-type {
      type Rsvp-mgmt-auth-ki;
      description
        "Key type";
    }
    leaf key-source {
      type string;
      description
        "Key source";
    }
    leaf key-id {
      type uint64;
      description
        "Key ID";
    }
    leaf key-id-valid {
      type uint32;
      description
        "Key validity";
    }
  }

  grouping RSVP-MGMT-INTERFACE-BW-STD-DSTE {
    description
      "RSVP interface bandwidth info with standard based
       DSTE enabled";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-pool0-bandwidth {
      type uint64;
      units "bit/s";
      description
        "Max bandwidth (bits per second) allowed in BC0
         pool";
    }
    leaf max-pool1-bandwidth {
      type uint64;
      units "bit/s";
      description
        "Max bandwidth (bits per second) allowed in BC1
         pool";
    }
    leaf is-max-bandwidth-absolute {
      type boolean;
      description
        "True if the Max B/W is an absolute value and
         false if its a percentage";
    }
    leaf is-max-bc0-bandwidth-absolute {
      type boolean;
      description
        "True if the Max BC0 B/W is an absolute value and
         false if its a percentage";
    }
    leaf is-max-bc1-bandwidth-absolute {
      type boolean;
      description
        "True if the Max BC1 sub-pool B/W is an absolute
         value and false if its a percentage";
    }
  }

  grouping RSVP-MGMT-INTERFACE-BW-PRESTD-DSTE {
    description
      "Prestandard DSTE interface bandwidth information";
    leaf allocated-bit-rate {
      type uint64;
      units "bit/s";
      description
        "Bandwidth (bits per second) now allocated";
    }
    leaf max-flow-bandwidth {
      type uint64;
      units "bit/s";
      description
        "Max bandwidth (bits per second) allowed per flow";
    }
    leaf max-bandwidth {
      type uint64;
      units "bit/s";
      description
        "Max bandwidth (bits per second) allowed";
    }
    leaf max-subpool-bandwidth {
      type uint64;
      units "bit/s";
      description
        "Max bandwidth (bits per second) allowed in
         subpool";
    }
    leaf is-max-bandwidth-absolute {
      type boolean;
      description
        "True if the Max B/W is an absolute value and
         false if its a percentage";
    }
    leaf is-max-subpool-bandwidth-absolute {
      type boolean;
      description
        "True if the Max sub-pool B/W is an absolute
         value and false if its a percentage";
    }
  }

  grouping RSVP-MGMT-DSTE-MODE-INTERFACE-BW {
    description
      "Union of the different RSVP interface bandwidth
       types";
    container pre-standard-dste-interface {
      when "../dste-mode = 'pre-standard'" {
        tailf:xpath-root 3;
        description
          "../DSTEMode = 'PreStandard'";
      }
      description
        "Prestandard DSTE interface information";
      uses RSVP-MGMT-INTERFACE-BW-PRESTD-DSTE;
    }
    container standard-dste-interface {
      when "../dste-mode = 'standard'" {
        tailf:xpath-root 3;
        description
          "../DSTEMode = 'Standard'";
      }
      description
        "Standard DSTE interface information";
      uses RSVP-MGMT-INTERFACE-BW-STD-DSTE;
    }
    leaf dste-mode {
      type Rsvp-mgmt-dste-modes;
      description
        "DSTEMode";
    }
  }

  grouping RSVP-MGMT-INTERFACE-SUMMARY {
    description
      "Summary Form of RSVP interface Info";
    container bandwidth-information {
      description
        "Interface bandwidth information";
      uses RSVP-MGMT-DSTE-MODE-INTERFACE-BW;
    }
    leaf interface-name-xr {
      type string;
      description
        "Interface Name";
    }
    leaf paths-in {
      type uint32;
      description
        "Number of locally created and incoming path
         states";
    }
    leaf paths-out {
      type uint32;
      description
        "Number of outgoing path states";
    }
    leaf reservations-in {
      type uint32;
      description
        "Number of locally created and incoming
         reservation states";
    }
    leaf reservations-out {
      type uint32;
      description
        "Number of outgoing reservation states";
    }
  }

  grouping RSVP-MGMT-IF-NBR-COMPACT {
    description
      "Compact Info for RSVP Interface Neighbor";
    leaf interface-neighbor-address {
      type inet:ipv4-address;
      description
        "Interface Neighbor address";
    }
    leaf neighbor-interface-name {
      type xr:Interface-name;
      description
        "Neighbor's Interface handle";
    }
  }

  grouping RSVP-MGMT-NBR-COMPACT {
    description
      "Compact Info for RSVP Neighbor";
    leaf node-address {
      type inet:ipv4-address;
      description
        "Neighbor node address";
    }
    list interface-neighbor-list-compact {
      description
        "Compact list of I/F Neighbors";
      uses RSVP-MGMT-IF-NBR-COMPACT;
    }
  }
}

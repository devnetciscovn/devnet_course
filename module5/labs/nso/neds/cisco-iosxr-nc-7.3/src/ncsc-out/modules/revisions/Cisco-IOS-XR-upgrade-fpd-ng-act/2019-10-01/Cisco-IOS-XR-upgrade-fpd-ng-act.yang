module Cisco-IOS-XR-upgrade-fpd-ng-act {
  // Generated by yanger -t ncs
  tailf:mount-id "cisco-iosxr-nc-7.3:cisco-iosxr-nc-7.3";
  tailf:ncs-device-type "netconf";

  namespace "http://cisco.com/ns/yang/Cisco-IOS-XR-upgrade-fpd-ng-act";
  prefix upgrade-fpd-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR upgrade-fpd package action data.

     This module contains definitions
     for the following management objects:
       fpd: Field programmable device (FPD) operational data

     Copyright (c) 2013-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2017-04-04 {
    description
      "IOS XR 6.3.1 revision.";
  }

  augment "/ncs:devices/ncs:device/ncs:rpc" {
    container rpc-upgrade-fpd {
      tailf:ncs-device-type "netconf";
      tailf:display-when "not(../../ncs:module) or ../../ncs:module[ncs:name='Cisco-IOS-XR-upgrade-fpd-ng-act']";
      tailf:action upgrade-fpd {
        tailf:actionpoint ncsproxy {
          tailf:internal;
        }
        description
          "Execute FPD upgrade";
        input {
          leaf location {
            type string;
            mandatory true;
            description
              "Location of the FPD to be upgraded";
          }
          leaf fpd {
            type string;
            mandatory true;
            description
              "name of the fpd to be upgraded";
          }
          leaf force {
            type empty;
            description
              "Force the upgrade process";
          }
        }
      }
    }
  }
  augment "/ncs:devices/ncs:device-group/ncs:ned-id/ncs:rpc" {
    container rpc-upgrade-fpd {
      tailf:ncs-device-type "netconf";
      tailf:display-when "/ncs:devices/ncs:device[ncs:name=current()/../../../ncs:member]/ncs:module[ncs:name='Cisco-IOS-XR-upgrade-fpd-ng-act']";
      tailf:action upgrade-fpd {
        tailf:actionpoint ncsproxy {
          tailf:internal;
        }
        description
          "Execute FPD upgrade";
        input {
          leaf location {
            type string;
            mandatory true;
            description
              "Location of the FPD to be upgraded";
          }
          leaf fpd {
            type string;
            mandatory true;
            description
              "name of the fpd to be upgraded";
          }
          leaf force {
            type empty;
            description
              "Force the upgrade process";
          }
        }
      }
    }
  }
}

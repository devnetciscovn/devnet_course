module SNMPv2-MIB {
  // Generated by yanger -t ncs
  tailf:mount-id "cisco-iosxr-nc-7.3:cisco-iosxr-nc-7.3";
  tailf:ncs-device-type "netconf";

  namespace "http://tail-f.com/ns/mibs/SNMPv2-MIB/200210160000Z";
  prefix SNMPv2_MIB;

  import ietf-yang-types {
    prefix yang;
  }
  import tailf-common {
    prefix tailf;
  }
  import SNMPv2-TC {
    prefix SNMPv2_TC;
  }
  import tailf-ncs {
    prefix ncs;
  }

  revision 2002-10-16 {
    description
      "";
  }

  typedef ncs_template_sysDescrType {
    type string;
  }

  typedef ncs_template_sysContactType {
    type string;
  }

  typedef ncs_template_sysNameType {
    type string;
  }

  typedef ncs_template_sysLocationType {
    type string;
  }

  typedef ncs_template_sysServicesType {
    type string;
  }

  typedef ncs_template_snmpEnableAuthenTrapsType {
    type string;
  }

  typedef ncs_template_sysORIndexType {
    type string;
  }

  typedef ncs_rpc_notif_sysDescrType {
    type string {
      length "min .. 255";
    }
  }

  typedef ncs_rpc_notif_sysContactType {
    type string {
      length "min .. 255";
    }
  }

  typedef ncs_rpc_notif_sysNameType {
    type string {
      length "min .. 255";
    }
  }

  typedef ncs_rpc_notif_sysLocationType {
    type string {
      length "min .. 255";
    }
  }

  typedef ncs_rpc_notif_sysServicesType {
    type int32 {
      range "0 .. 127";
    }
  }

  typedef ncs_rpc_notif_snmpEnableAuthenTrapsType {
    type enumeration {
      enum "enabled" {
        value 1;
      }
      enum "disabled" {
        value 2;
      }
    }
  }

  typedef ncs_rpc_notif_sysORIndexType {
    type int32 {
      range "1 .. 2147483647";
    }
  }

  typedef live_ncs_sysDescrType {
    type string {
      length "min .. 255";
    }
  }

  typedef live_ncs_sysContactType {
    type string {
      length "min .. 255";
    }
  }

  typedef live_ncs_sysNameType {
    type string {
      length "min .. 255";
    }
  }

  typedef live_ncs_sysLocationType {
    type string {
      length "min .. 255";
    }
  }

  typedef live_ncs_sysServicesType {
    type int32 {
      range "0 .. 127";
    }
  }

  typedef live_ncs_snmpEnableAuthenTrapsType {
    type enumeration {
      enum "enabled" {
        value 1;
      }
      enum "disabled" {
        value 2;
      }
    }
  }

  typedef live_ncs_sysORIndexType {
    type int32 {
      range "1 .. 2147483647";
    }
  }

  typedef sysDescrType {
    type string {
      length "min .. 255";
    }
  }

  typedef sysContactType {
    type string {
      length "min .. 255";
    }
  }

  typedef sysNameType {
    type string {
      length "min .. 255";
    }
  }

  typedef sysLocationType {
    type string {
      length "min .. 255";
    }
  }

  typedef sysServicesType {
    type int32 {
      range "0 .. 127";
    }
  }

  typedef snmpEnableAuthenTrapsType {
    type enumeration {
      enum "enabled" {
        value 1;
      }
      enum "disabled" {
        value 2;
      }
    }
  }

  typedef sysORIndexType {
    type int32 {
      range "1 .. 2147483647";
    }
  }

  augment "/ncs:devices/ncs:device/ncs:config" {
    container SNMPv2-MIB {
      tailf:ncs-device-type "netconf";
      tailf:display-when "not(../../ncs:module) or ../../ncs:module[ncs:name='SNMPv2-MIB']";
      container system {
        // NCS drop config false leaf sysDescr
        // NCS drop config false leaf sysObjectID
        // NCS drop config false leaf sysUpTime
        leaf sysContact {
          type sysContactType;
          default "";
        }
        leaf sysName {
          type sysNameType;
          default "";
        }
        leaf sysLocation {
          type sysLocationType;
          default "";
        }
        // NCS drop config false leaf sysServices
        // NCS drop config false leaf sysORLastChange
      }
      container snmp {
        // NCS drop config false leaf snmpInPkts
        // NCS drop config false leaf snmpInBadVersions
        // NCS drop config false leaf snmpInBadCommunityNames
        // NCS drop config false leaf snmpInBadCommunityUses
        // NCS drop config false leaf snmpInASNParseErrs
        leaf snmpEnableAuthenTraps {
          type snmpEnableAuthenTrapsType;
          default "disabled";
        }
        // NCS drop config false leaf snmpSilentDrops
        // NCS drop config false leaf snmpProxyDrops
      }
      container snmpSet {
        // NCS drop config false leaf snmpSetSerialNo
      }
      container sysORTable {
        list sysOREntry {
          key "sysORIndex";
          leaf sysORIndex {
            type sysORIndexType;
          }
          // NCS drop config false leaf sysORID
          // NCS drop config false leaf sysORDescr
          // NCS drop config false leaf sysORUpTime
        }
      }
    }
  }
  augment "/ncs:devices/ncs:device/ncs:live-status" {
    container SNMPv2-MIB {
      tailf:ncs-device-type "netconf";
      tailf:display-when "not(../../ncs:module) or ../../ncs:module[ncs:name='SNMPv2-MIB'] or (../../ncs:live-status-protocol[not(ncs:capability)]) or (../../ncs:live-status-protocol/ncs:capability/ncs:module[.='SNMPv2-MIB'])";
      container system {
        leaf sysDescr {
          type live_ncs_sysDescrType;
        }
        leaf sysObjectID {
          type yang:object-identifier;
        }
        leaf sysUpTime {
          type yang:timeticks;
        }
        leaf sysContact {
          type live_ncs_sysContactType;
          // NCS drop default statement
        }
        leaf sysName {
          type live_ncs_sysNameType;
          // NCS drop default statement
        }
        leaf sysLocation {
          type live_ncs_sysLocationType;
          // NCS drop default statement
        }
        leaf sysServices {
          type live_ncs_sysServicesType;
        }
        leaf sysORLastChange {
          type yang:timestamp;
        }
      }
      container snmp {
        leaf snmpInPkts {
          type yang:counter32;
        }
        leaf snmpInBadVersions {
          type yang:counter32;
        }
        leaf snmpInBadCommunityNames {
          type yang:counter32;
        }
        leaf snmpInBadCommunityUses {
          type yang:counter32;
        }
        leaf snmpInASNParseErrs {
          type yang:counter32;
        }
        leaf snmpEnableAuthenTraps {
          type live_ncs_snmpEnableAuthenTrapsType;
          // NCS drop default statement
        }
        leaf snmpSilentDrops {
          type yang:counter32;
        }
        leaf snmpProxyDrops {
          type yang:counter32;
        }
      }
      container snmpSet {
        leaf snmpSetSerialNo {
          type SNMPv2_TC:live_ncs_TestAndIncr;
        }
      }
      container sysORTable {
        list sysOREntry {
          key "sysORIndex";
          leaf sysORIndex {
            type live_ncs_sysORIndexType;
          }
          leaf sysORID {
            type yang:object-identifier;
          }
          leaf sysORDescr {
            type string {
              length "0 .. 255";
            }
          }
          leaf sysORUpTime {
            type yang:timestamp;
          }
        }
      }
    }
  }
  augment "/ncs:devices/ncs:template/ncs:ned-id/ncs:config" {
    container SNMPv2-MIB {
      container system {
        // NCS drop config false leaf sysDescr
        // NCS drop config false leaf sysObjectID
        // NCS drop config false leaf sysUpTime
        leaf sysContact {
          type ncs_template_sysContactType;
          // NCS drop default statement
        }
        leaf sysName {
          type ncs_template_sysNameType;
          // NCS drop default statement
        }
        leaf sysLocation {
          type ncs_template_sysLocationType;
          // NCS drop default statement
        }
        // NCS drop config false leaf sysServices
        // NCS drop config false leaf sysORLastChange
      }
      container snmp {
        // NCS drop config false leaf snmpInPkts
        // NCS drop config false leaf snmpInBadVersions
        // NCS drop config false leaf snmpInBadCommunityNames
        // NCS drop config false leaf snmpInBadCommunityUses
        // NCS drop config false leaf snmpInASNParseErrs
        leaf snmpEnableAuthenTraps {
          type ncs_template_snmpEnableAuthenTrapsType;
          // NCS drop default statement
        }
        // NCS drop config false leaf snmpSilentDrops
        // NCS drop config false leaf snmpProxyDrops
      }
      container snmpSet {
        // NCS drop config false leaf snmpSetSerialNo
      }
      container sysORTable {
        list sysOREntry {
          // NCS patched for predictable order
          ordered-by user;
          key "sysORIndex";
          leaf sysORIndex {
            type ncs_template_sysORIndexType;
          }
          // NCS drop config false leaf sysORID
          // NCS drop config false leaf sysORDescr
          // NCS drop config false leaf sysORUpTime
        }
      }
    }
  }
}

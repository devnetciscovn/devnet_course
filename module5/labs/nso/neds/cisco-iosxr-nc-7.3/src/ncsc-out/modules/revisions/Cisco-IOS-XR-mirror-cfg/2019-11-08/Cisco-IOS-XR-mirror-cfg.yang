module Cisco-IOS-XR-mirror-cfg {
  // Generated by yanger -t ncs
  tailf:mount-id "cisco-iosxr-nc-7.3:cisco-iosxr-nc-7.3";
  tailf:ncs-device-type "netconf";

  namespace "http://cisco.com/ns/yang/Cisco-IOS-XR-mirror-cfg";
  prefix mirror-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mirror package configuration.

     This module contains definitions
     for the following management objects:
       mirror-cfg: mirror directory configuration commands

     Copyright (c) 2013-2019 by Cisco Systems, Inc.
     All rights reserved.";

  revision 2019-11-08 {
    description
      "IOS XR 7.2.1 revision";
    semver:module-version "1.0.0";
  }
  revision 2019-04-05 {
    description
      "Establish semantic version baseline.";
  }
  revision 2015-11-09 {
    description
      "IOS XR 6.0 revision.";
  }

  augment "/ncs:devices/ncs:device/ncs:config" {
    container mirror-cfg {
      tailf:ncs-device-type "netconf";
      tailf:display-when "not(../../ncs:module) or ../../ncs:module[ncs:name='Cisco-IOS-XR-mirror-cfg']";
      description
        "mirror directory configuration commands";
      leaf mirror-cfg-checksum {
        type empty;
        description
          "rsync will use --checksum option for determining
           if file is in sync";
      }
      leaf mirror-cfg-enable {
        type empty;
        description
          "Enable mirror directory syncing to standby RP";
      }
    }
  }
  augment "/ncs:devices/ncs:device/ncs:live-status" {
    container mirror-cfg {
      tailf:ncs-device-type "netconf";
      tailf:display-when "not(../../ncs:module) or ../../ncs:module[ncs:name='Cisco-IOS-XR-mirror-cfg'] or (../../ncs:live-status-protocol[not(ncs:capability)]) or (../../ncs:live-status-protocol/ncs:capability/ncs:module[.='Cisco-IOS-XR-mirror-cfg'])";
      description
        "mirror directory configuration commands";
      leaf mirror-cfg-checksum {
        type empty;
        description
          "rsync will use --checksum option for determining
           if file is in sync";
      }
      leaf mirror-cfg-enable {
        type empty;
        description
          "Enable mirror directory syncing to standby RP";
      }
    }
  }
  augment "/ncs:devices/ncs:template/ncs:ned-id/ncs:config" {
    container mirror-cfg {
      description
        "mirror directory configuration commands";
      leaf mirror-cfg-checksum {
        type empty;
        description
          "rsync will use --checksum option for determining
           if file is in sync";
      }
      leaf mirror-cfg-enable {
        type empty;
        description
          "Enable mirror directory syncing to standby RP";
      }
    }
  }
}

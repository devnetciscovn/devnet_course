module Cisco-IOS-XR-l2vpn-cfg {
  // Generated by yanger -t ncs
  tailf:mount-id "cisco-iosxr-nc-7.3:cisco-iosxr-nc-7.3";
  tailf:ncs-device-type "netconf";

  namespace "http://cisco.com/ns/yang/Cisco-IOS-XR-l2vpn-cfg";
  prefix l2vpn-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import Cisco-IOS-XR-snmp-agent-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR l2vpn package configuration.

     This module contains definitions
     for the following management objects:
       l2vpn: L2VPN configuration
       generic-interface-lists: Generic Interface List configuration
       evpn: EVPN configuration

     This YANG module augments the
       Cisco-IOS-XR-ifmgr-cfg,
       Cisco-IOS-XR-snmp-agent-cfg
     modules with configuration data.

     Copyright (c) 2013-2021 by Cisco Systems, Inc.
     All rights reserved.";

  revision 2021-06-09 {
    description
      "- Added support for enforce-mtu-match CLI globally under evpn submode - Added support for transmit-l2-mtu CLI globally under evpn submode - Added support for enforce-mtu-match CLI under evpn instance submode - Added support for transmit-l2-mtu CLI under evpn instance submode";
    semver:module-version "4.1.0";
  }
  revision 2020-08-08 {
    description
      "Added support for ignore-mtu-mismatch and transmit-mtu-zero CLI globally under evpn submode.";
    semver:module-version "4.0.0";
  }
  revision 2020-06-29 {
    description
      "Changed key for Pseudowire type to IPv4 neighbor - PW-ID or IPv6 neighbor - PW-id pair.
       2019-12-20
       EVPN SRv6 related changes";
    semver:module-version "3.0.0";
  }
  revision 2019-04-05 {
    description
      "Establish semantic version baseline.";
    semver:module-version "2.0.0";
  }
  revision 2018-06-15 {
    description
      "Allow min..max in range when min == max.";
  }
  revision 2017-06-26 {
    description
      "Change identifiers to be more readable.";
  }
  revision 2017-05-01 {
    description
      "Fixing backward compatibility error in module.";
  }
  revision 2015-11-09 {
    description
      "IOS XR 6.0 revision.";
  }

  typedef ncs_template_Evpn-encapsulation {
    type string;
    description
      "Evpn encapsulation";
  }

  typedef ncs_template_Interworking {
    type string;
    description
      "Interworking";
  }

  typedef ncs_template_L2vpn-capability-mode {
    type string;
    description
      "L2vpn capability mode";
  }

  typedef ncs_template_Evpn-side {
    type string;
    description
      "Evpn side";
  }

  typedef ncs_template_Vpls-id-addr-index {
    type string;
    description
      "Vpls id addr index";
  }

  typedef ncs_template_Evpn-core-group-id-range {
    type string;
    description
      "Evpn core group id range";
  }

  typedef ncs_template_Tag-rewrite-range {
    type string;
    description
      "Tag rewrite range";
  }

  typedef ncs_template_Pseudowire-evpnacid-range {
    type string;
    description
      "Pseudowire evpnacid range";
  }

  typedef ncs_template_Evpnvpnid-range {
    type string;
    description
      "Evpnvpnid range";
  }

  typedef ncs_template_Pseudowire-label-range {
    type string;
    description
      "Pseudowire label range";
  }

  typedef ncs_template_Bridge-domain-transport-mode {
    type string;
    description
      "Bridge domain transport mode";
  }

  typedef ncs_template_Preferred-path {
    type string;
    description
      "Preferred path";
  }

  typedef ncs_template_Rd-addr-index {
    type string;
    description
      "Rd addr index";
  }

  typedef ncs_template_Vccv-verification {
    type string;
    description
      "Vccv verification";
  }

  typedef ncs_template_L2vpn-mtu-range {
    type string;
    description
      "L2vpn mtu range";
  }

  typedef ncs_template_Mac-secure-shutdown-recovery-time-range {
    type string;
    description
      "Mac secure shutdown recovery time range";
  }

  typedef ncs_template_Mac-withdraw-behavior {
    type string;
    description
      "Mac withdraw behavior";
  }

  typedef ncs_template_Port-down-flush {
    type string;
    description
      "Port down flush";
  }

  typedef ncs_template_Storm-control-pps-range {
    type string;
    description
      "Storm control pps range";
  }

  typedef ncs_template_Type-of-service-mode {
    type string;
    description
      "Type of service mode";
  }

  typedef ncs_template_L2vpn-vs-vlan-tag {
    type string;
    description
      "L2vpn vs vlan tag";
  }

  typedef ncs_template_Pseudowire-tag-range {
    type string;
    description
      "Pseudowire tag range";
  }

  typedef ncs_template_Interface-access-signal-mode {
    type string;
    description
      "Interface access signal mode";
  }

  typedef ncs_template_Multicast-p2mp-signaling {
    type string;
    description
      "BGP:BGP Signaling";
  }

  typedef ncs_template_Cedge-range {
    type string;
    description
      "Cedge range";
  }

  typedef ncs_template_Ethernet-segment-load-balance {
    type string;
    description
      "Ethernet segment load balance";
  }

  typedef ncs_template_Mpls-signaling-protocol {
    type string;
    description
      "Mpls signaling protocol";
  }

  typedef ncs_template_Erpaps {
    type string;
    description
      "Erpaps";
  }

  typedef ncs_template_Mac-secure-action {
    type string;
    description
      "Mac secure action";
  }

  typedef ncs_template_Erp-port {
    type string;
    description
      "Erp port";
  }

  typedef ncs_template_Resync-threshold-range {
    type string;
    description
      "Resync threshold range";
  }

  typedef ncs_template_Bgp-route-target-role {
    type string;
    description
      "Bgp route target role";
  }

  typedef ncs_template_Backup-disable {
    type string;
    description
      "Backup disable";
  }

  typedef ncs_template_Time-to-live-range {
    type string;
    description
      "Time to live range";
  }

  typedef ncs_template_Multicast-p2mp-transport {
    type string;
    description
      "RSVP_TE:RSVP-TE Transport";
  }

  typedef ncs_template_Transport-mode {
    type string;
    description
      "Transport mode";
  }

  typedef ncs_template_Flow-label-tlv-code {
    type string;
    description
      "Flow label tlv code";
  }

  typedef ncs_template_Bgp-route-target {
    type string;
    description
      "Bgp route target";
  }

  typedef ncs_template_Pseudowire-acid-range {
    type string;
    description
      "Pseudowire acid range";
  }

  typedef ncs_template_Pseudowire-id-range {
    type string;
    description
      "Pseudowire id range";
  }

  typedef ncs_template_Interface-profile {
    type string;
    description
      "Interface profile";
  }

  typedef ncs_template_Ethernet-segment-identifier {
    type string;
    description
      "Ethernet segment identifier";
  }

  typedef ncs_template_Rpl-role {
    type string;
    description
      "Rpl role";
  }

  typedef ncs_template_Pw-switching-point-tlv {
    type string;
    description
      "Pw switching point tlv";
  }

  typedef ncs_template_Erpaps-level-range {
    type string;
    description
      "Erpaps level range";
  }

  typedef ncs_template_Evpn-esi-type-range {
    type string;
    description
      "Evpn esi type range";
  }

  typedef ncs_template_Storm-control {
    type string;
    description
      "Storm control";
  }

  typedef ncs_template_L2tp-session-id-range {
    type string;
    description
      "L2tp session id range";
  }

  typedef ncs_template_Ethernet-segment-service-carving {
    type string;
    description
      "Ethernet segment service carving";
  }

  typedef ncs_template_Mac-learn {
    type string;
    description
      "Mac learn";
  }

  typedef ncs_template_L2tpv3-sequencing {
    type string;
    description
      "L2tpv3 sequencing";
  }

  typedef ncs_template_Veid-range {
    type string;
    description
      "Veid range";
  }

  typedef ncs_template_Load-balance {
    type string;
    description
      "Load balance";
  }

  typedef ncs_template_L2tp-signaling-protocol {
    type string;
    description
      "L2tp signaling protocol";
  }

  typedef ncs_template_Bdmac-learn {
    type string;
    description
      "Bdmac learn";
  }

  typedef ncs_template_L2mc-src-traffic-enabled {
    type string;
    description
      "L2mc src traffic enabled";
  }

  typedef ncs_template_L2vpn-verification {
    type string;
    description
      "L2vpn verification";
  }

  typedef ncs_template_Max-path-mtu-range {
    type string;
    description
      "Max path mtu range";
  }

  typedef ncs_template_Interface-traffic-flood {
    type string;
    description
      "Interface traffic flood";
  }

  typedef ncs_template_Pbbvid-range {
    type string;
    description
      "Pbbvid range";
  }

  typedef ncs_template_L2tp-cookie-value-range {
    type string;
    description
      "L2tp cookie value range";
  }

  typedef ncs_template_L2-encapsulation {
    type string;
    description
      "L2 encapsulation";
  }

  typedef ncs_template_L2vpn-logging {
    type string;
    description
      "L2vpn logging";
  }

  typedef ncs_template_Mac-aging-range {
    type string;
    description
      "Mac aging range";
  }

  typedef ncs_template_Vpls-id-as-index {
    type string;
    description
      "Vpls id as index";
  }

  typedef ncs_template_Pseudowire-gbl-id-range {
    type string;
    description
      "Pseudowire gbl id range";
  }

  typedef ncs_template_Rdas-index {
    type string;
    description
      "Rdas index";
  }

  typedef ncs_template_Mac-flush-mode {
    type string;
    description
      "Mac flush mode";
  }

  typedef ncs_template_L2tp-cookie-size {
    type string;
    description
      "L2tp cookie size";
  }

  typedef ncs_template_Mpls-sequencing {
    type string;
    description
      "Mpls sequencing";
  }

  typedef ncs_template_Erp-instance-range {
    type string;
    description
      "Erp instance range";
  }

  typedef ncs_template_Pw-redundancy-initial-delay-range {
    type string;
    description
      "Pw redundancy initial delay range";
  }

  typedef ncs_template_Vpls-id-as-range {
    type string;
    description
      "Vpls id as range";
  }

  typedef ncs_template_Rdas-range {
    type string;
    description
      "Rdas range";
  }

  typedef ncs_template_Ethernet-segment-service-carving-mcast {
    type string;
    description
      "Ethernet segment service carving mcast";
  }

  typedef ncs_template_Bridge-bd-mtu-range {
    type string;
    description
      "Bridge bd mtu range";
  }

  typedef ncs_template_Backup-disable-delay-range {
    type string;
    description
      "Backup disable delay range";
  }

  typedef ncs_template_Storm-control-kbps-range {
    type string;
    description
      "Storm control kbps range";
  }

  typedef ncs_template_Mac-limit-action {
    type string;
    description
      "Mac limit action";
  }

  typedef ncs_template_Erp-port1 {
    type string;
    description
      "Erp port1";
  }

  typedef ncs_template_Mac-notification {
    type string;
    description
      "Mac notification";
  }

  typedef ncs_template_Control-word {
    type string;
    description
      "Control word";
  }

  typedef ncs_template_Preferred-nexthop-mode {
    type string;
    description
      "Preferred nexthop mode";
  }

  typedef ncs_template_Bgp-route-distinguisher {
    type string;
    description
      "Bgp route distinguisher";
  }

  typedef ncs_template_Bgp-route-target-format {
    type string;
    description
      "Bgp route target format";
  }

  typedef ncs_template_Evpn-group-id-range {
    type string;
    description
      "Evpn group id range";
  }

  typedef ncs_template_Mac-limit-threshold-range {
    type string;
    description
      "Mac limit threshold range";
  }

  typedef ncs_template_Vedge-range {
    type string;
    description
      "Vedge range";
  }

  typedef ncs_template_Vpnid-range {
    type string;
    description
      "Vpnid range";
  }

  typedef ncs_template_Ldp-vpls-id {
    type string;
    description
      "Ldp vpls id";
  }

  typedef ncs_template_Ce-id-range {
    type string;
    description
      "Ce id range";
  }

  typedef ncs_template_Mac-aging {
    type string;
    description
      "Mac aging";
  }

  typedef ncs_template_Mac-limit-range {
    type string;
    description
      "Mac limit range";
  }

  typedef ncs_template_Pbbisid-range {
    type string;
    description
      "Pbbisid range";
  }

  typedef ncs_template_Type-of-service-range {
    type string;
    description
      "Type of service range";
  }

  typedef ncs_template_Flow-label-load-balance {
    type string;
    description
      "Flow label load balance";
  }

  typedef ncs_rpc_notif_Evpn-encapsulation {
    type enumeration {
      enum "evpn-encapsulationvxlan" {
        value 8;
        description
          "VXLAN Encapsulation";
      }
      enum "evpn-encapsulation-mpls" {
        value 10;
        description
          "MPLS Encapsulation";
      }
      enum "evpn-encapsulation-route-sync" {
        value 254;
        description
          "Route Sync Encapsulation";
      }
      enum "evpn-encapsulation-srv6" {
        value 255;
        description
          "SRv6 Encapsulation";
      }
    }
    description
      "Evpn encapsulation";
  }

  typedef ncs_rpc_notif_Interworking {
    type enumeration {
      enum "ethernet" {
        value 1;
        description
          "Ethernet interworking";
      }
      enum "ipv4" {
        value 3;
        description
          "IPv4 interworking";
      }
    }
    description
      "Interworking";
  }

  typedef ncs_rpc_notif_L2vpn-capability-mode {
    type enumeration {
      enum "high-mode" {
        value 1;
        description
          "Compute global capability as the highest node
           capability";
      }
      enum "single-mode" {
        value 2;
        description
          "Disable global capability re-computation";
      }
    }
    description
      "L2vpn capability mode";
  }

  typedef ncs_rpc_notif_Evpn-side {
    type enumeration {
      enum "evpn-side-regular" {
        value 1;
        description
          "EVPN Instance side defined as regular";
      }
      enum "evpn-side-stitching" {
        value 2;
        description
          "EVPN Instance side defined as stitching";
      }
    }
    description
      "Evpn side";
  }

  typedef ncs_rpc_notif_Vpls-id-addr-index {
    type uint32 {
      range "0..32767";
    }
    description
      "Vpls id addr index";
  }

  typedef ncs_rpc_notif_Evpn-core-group-id-range {
    type uint32 {
      range "1..4294967295";
    }
    description
      "Evpn core group id range";
  }

  typedef ncs_rpc_notif_Tag-rewrite-range {
    type uint32 {
      range "1..4094";
    }
    description
      "Tag rewrite range";
  }

  typedef ncs_rpc_notif_Pseudowire-evpnacid-range {
    type uint32 {
      range "1..16777215";
    }
    description
      "Pseudowire evpnacid range";
  }

  typedef ncs_rpc_notif_Evpnvpnid-range {
    type uint32 {
      range "1..65534";
    }
    description
      "Evpnvpnid range";
  }

  typedef ncs_rpc_notif_Pseudowire-label-range {
    type uint32 {
      range "16..1048575";
    }
    description
      "Pseudowire label range";
  }

  typedef ncs_rpc_notif_Bridge-domain-transport-mode {
    type enumeration {
      enum "vlan-passthrough" {
        value 3;
        description
          "Vlan tagged passthrough mode";
      }
    }
    description
      "Bridge domain transport mode";
  }

  typedef ncs_rpc_notif_Preferred-path {
    type enumeration {
      enum "te-tunnel" {
        value 2;
        description
          "TE Tunnel";
      }
      enum "ip-tunnel" {
        value 3;
        description
          "IP Tunnel";
      }
      enum "tp-tunnel" {
        value 4;
        description
          "TP Tunnel";
      }
      enum "sr-te-policy" {
        value 5;
        description
          "SR TE Policy";
      }
      enum "named-te-tunnel" {
        value 8;
        description
          "Named TE Tunnel";
      }
    }
    description
      "Preferred path";
  }

  typedef ncs_rpc_notif_Rd-addr-index {
    type uint32 {
      range "0..65535";
    }
    description
      "Rd addr index";
  }

  typedef ncs_rpc_notif_Vccv-verification {
    type enumeration {
      enum "none" {
        value 0;
        description
          "No connectivity verification over VCCV";
      }
      enum "lsp-ping" {
        value 2;
        description
          "LSP Ping over VCCV";
      }
    }
    description
      "Vccv verification";
  }

  typedef ncs_rpc_notif_L2vpn-mtu-range {
    type uint32 {
      range "64..65535";
    }
    description
      "L2vpn mtu range";
  }

  typedef ncs_rpc_notif_Mac-secure-shutdown-recovery-time-range {
    type uint32 {
      range "10..3600";
    }
    description
      "Mac secure shutdown recovery time range";
  }

  typedef ncs_rpc_notif_Mac-withdraw-behavior {
    type enumeration {
      enum "legacy" {
        value 1;
        description
          "MAC Withdrawal sent on state-down (legacy)";
      }
      enum "optimized" {
        value 2;
        description
          "Optimized MAC Withdrawal";
      }
    }
    description
      "Mac withdraw behavior";
  }

  typedef ncs_rpc_notif_Port-down-flush {
    type enumeration {
      enum "port-down-flush" {
        value 0;
        description
          "MAC Port Down Flush";
      }
      enum "enable-port-down-flush" {
        value 1;
        description
          "Enable Port Down Flush";
      }
      enum "disable-port-down-flush" {
        value 2;
        description
          "Disable Port Down Flush";
      }
    }
    description
      "Port down flush";
  }

  typedef ncs_rpc_notif_Storm-control-pps-range {
    type uint32 {
      range "1..160000";
    }
    description
      "Storm control pps range";
  }

  typedef ncs_rpc_notif_Type-of-service-mode {
    type enumeration {
      enum "none" {
        value 0;
        description
          "Do not reflect the type of service";
      }
      enum "reflect" {
        value 1;
        description
          "Reflect the type of service";
      }
    }
    description
      "Type of service mode";
  }

  typedef ncs_rpc_notif_L2vpn-vs-vlan-tag {
    type uint32 {
      range "1..4094";
    }
    description
      "L2vpn vs vlan tag";
  }

  typedef ncs_rpc_notif_Pseudowire-tag-range {
    type uint32 {
      range "1..4094";
    }
    description
      "Pseudowire tag range";
  }

  typedef ncs_rpc_notif_Interface-access-signal-mode {
    type enumeration {
      enum "bundle-down" {
        value 2;
        description
          "BundleDown";
      }
    }
    description
      "Interface access signal mode";
  }

  typedef ncs_rpc_notif_Multicast-p2mp-signaling {
    type string {
      pattern '(BGP)';
    }
    description
      "BGP:BGP Signaling";
  }

  typedef ncs_rpc_notif_Cedge-range {
    type uint32 {
      range "11..100";
    }
    description
      "Cedge range";
  }

  typedef ncs_rpc_notif_Ethernet-segment-load-balance {
    type enumeration {
      enum "single-active" {
        value 1;
        description
          "Single Active";
      }
      enum "port-active" {
        value 2;
        description
          "Port Active";
      }
      enum "single-flow-active" {
        value 3;
        description
          "Single Flow Active";
      }
      enum "all-active" {
        value 4;
        description
          "All Active";
      }
    }
    description
      "Ethernet segment load balance";
  }

  typedef ncs_rpc_notif_Mpls-signaling-protocol {
    type enumeration {
      enum "none" {
        value 1;
        description
          "No signaling";
      }
      enum "ldp" {
        value 4;
        description
          "LDP";
      }
    }
    description
      "Mpls signaling protocol";
  }

  typedef ncs_rpc_notif_Erpaps {
    type enumeration {
      enum "interface" {
        value 1;
        description
          "ERP APS type interface";
      }
      enum "bridge-domain" {
        value 2;
        description
          "ERP APS type bridge domain";
      }
      enum "xconnect" {
        value 3;
        description
          "ERP APS type xconnect";
      }
      enum "none" {
        value 4;
        description
          "ERP APS type none";
      }
    }
    description
      "Erpaps";
  }

  typedef ncs_rpc_notif_Mac-secure-action {
    type enumeration {
      enum "restrict" {
        value 1;
        description
          "MAC Secure Action Restrict";
      }
      enum "none" {
        value 2;
        description
          "No Action";
      }
      enum "shutdown" {
        value 3;
        description
          "MAC Secure Action Shutdown";
      }
    }
    description
      "Mac secure action";
  }

  typedef ncs_rpc_notif_Erp-port {
    type enumeration {
      enum "none" {
        value 1;
        description
          "ERP port type none";
      }
      enum "virtual" {
        value 2;
        description
          "ERP port type virtual";
      }
      enum "interface" {
        value 3;
        description
          "ERP port type interface";
      }
    }
    description
      "Erp port";
  }

  typedef ncs_rpc_notif_Resync-threshold-range {
    type uint32 {
      range "5..65535";
    }
    description
      "Resync threshold range";
  }

  typedef ncs_rpc_notif_Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef ncs_rpc_notif_Backup-disable {
    type enumeration {
      enum "never" {
        value 0;
        description
          "Never";
      }
      enum "delay" {
        value 1;
        description
          "Delay seconds";
      }
    }
    description
      "Backup disable";
  }

  typedef ncs_rpc_notif_Time-to-live-range {
    type uint32 {
      range "1..255";
    }
    description
      "Time to live range";
  }

  typedef ncs_rpc_notif_Multicast-p2mp-transport {
    type string {
      pattern '(RSVP_TE)';
    }
    description
      "RSVP_TE:RSVP-TE Transport";
  }

  typedef ncs_rpc_notif_Transport-mode {
    type enumeration {
      enum "ethernet" {
        value 1;
        description
          "Ethernet port mode";
      }
      enum "vlan" {
        value 2;
        description
          "Vlan tagged mode";
      }
      enum "vlan-passthrough" {
        value 3;
        description
          "Vlan tagged passthrough mode";
      }
    }
    description
      "Transport mode";
  }

  typedef ncs_rpc_notif_Flow-label-tlv-code {
    type enumeration {
      enum "17" {
        value 4;
        description
          "Set Flow Label Legacy TLV code (DEPRECATED)";
      }
      enum "disable" {
        value 8;
        description
          "Disable Sending Flow Label Legacy TLV";
      }
    }
    description
      "Flow label tlv code";
  }

  typedef ncs_rpc_notif_Bgp-route-target {
    type enumeration {
      enum "no-stitching" {
        value 0;
        description
          "RT is default type";
      }
      enum "stitching" {
        value 1;
        description
          "RT is for stitching (Golf-L2) (DEPRECATED)";
      }
    }
    description
      "Bgp route target";
  }

  typedef ncs_rpc_notif_Pseudowire-acid-range {
    type uint32 {
      range "1..4294967295";
    }
    description
      "Pseudowire acid range";
  }

  typedef ncs_rpc_notif_Pseudowire-id-range {
    type uint32 {
      range "1..4294967295";
    }
    description
      "Pseudowire id range";
  }

  typedef ncs_rpc_notif_Interface-profile {
    type enumeration {
      enum "snoop" {
        value 1;
        description
          "Set the snooping";
      }
      enum "dhcp-protocol" {
        value 2;
        description
          "disable DHCP protocol";
      }
    }
    description
      "Interface profile";
  }

  typedef ncs_rpc_notif_Ethernet-segment-identifier {
    type enumeration {
      enum "type0" {
        value 0;
        description
          "ESI type 0";
      }
      enum "legacy" {
        value 128;
        description
          "Legacy ESI type";
      }
      enum "override" {
        value 129;
        description
          "Override ESI type";
      }
    }
    description
      "Ethernet segment identifier";
  }

  typedef ncs_rpc_notif_Rpl-role {
    type enumeration {
      enum "owner" {
        value 1;
        description
          "ERP RPL owner";
      }
      enum "neighbor" {
        value 2;
        description
          "ERP RPL neighbor";
      }
      enum "next-neighbor" {
        value 3;
        description
          "ERP RPL next neighbor";
      }
    }
    description
      "Rpl role";
  }

  typedef ncs_rpc_notif_Pw-switching-point-tlv {
    type enumeration {
      enum "hide" {
        value 2;
        description
          "Hide TLV";
      }
    }
    description
      "Pw switching point tlv";
  }

  typedef ncs_rpc_notif_Erpaps-level-range {
    type uint32 {
      range "0..7";
    }
    description
      "Erpaps level range";
  }

  typedef ncs_rpc_notif_Evpn-esi-type-range {
    type uint32 {
      range "1";
    }
    description
      "Evpn esi type range";
  }

  typedef ncs_rpc_notif_Storm-control {
    type enumeration {
      enum "unicast" {
        value 1;
        description
          "Unknown-unicast Storm Control";
      }
      enum "multicast" {
        value 2;
        description
          "Multicast Storm Control";
      }
      enum "broadcast" {
        value 4;
        description
          "Broadcast Storm Control";
      }
    }
    description
      "Storm control";
  }

  typedef ncs_rpc_notif_L2tp-session-id-range {
    type uint32 {
      range "1..65535";
    }
    description
      "L2tp session id range";
  }

  typedef ncs_rpc_notif_Ethernet-segment-service-carving {
    type enumeration {
      enum "mod-n" {
        value 0;
        description
          "MOD N";
      }
      enum "manual" {
        value 1;
        description
          "Manual";
      }
      enum "hrw" {
        value 2;
        description
          "HRW";
      }
      enum "pref-df" {
        value 3;
        description
          "PrefDF";
      }
    }
    description
      "Ethernet segment service carving";
  }

  typedef ncs_rpc_notif_Mac-learn {
    type enumeration {
      enum "default-learning" {
        value 0;
        description
          "Mac Learning";
      }
      enum "enable-learning" {
        value 1;
        description
          "Enable Learning";
      }
      enum "disable-learning" {
        value 2;
        description
          "Disable Learning";
      }
    }
    description
      "Mac learn";
  }

  typedef ncs_rpc_notif_L2tpv3-sequencing {
    type enumeration {
      enum "off" {
        value 0;
        description
          "Sequencing is off";
      }
      enum "both" {
        value 4;
        description
          "Sequencing on both transmit and receive side";
      }
    }
    description
      "L2tpv3 sequencing";
  }

  typedef ncs_rpc_notif_Veid-range {
    type uint32 {
      range "1..16384";
    }
    description
      "Veid range";
  }

  typedef ncs_rpc_notif_Load-balance {
    type enumeration {
      enum "source-dest-mac" {
        value 1;
        description
          "Source and Destination MAC hashing";
      }
      enum "source-dest-ip" {
        value 2;
        description
          "Source and Destination IP hashing";
      }
      enum "pseudowire-label" {
        value 4;
        description
          "PW Label hashing";
      }
    }
    description
      "Load balance";
  }

  typedef ncs_rpc_notif_L2tp-signaling-protocol {
    type enumeration {
      enum "none" {
        value 1;
        description
          "No signaling";
      }
      enum "l2tpv3" {
        value 2;
        description
          "L2TPv3";
      }
    }
    description
      "L2tp signaling protocol";
  }

  typedef ncs_rpc_notif_Bdmac-learn {
    type enumeration {
      enum "disable-learning" {
        value 2;
        description
          "Disable Learning";
      }
    }
    description
      "Bdmac learn";
  }

  typedef ncs_rpc_notif_L2mc-src-traffic-enabled {
    type enumeration {
      enum "l2mc-none" {
        value 0;
        description
          "NONE";
      }
      enum "l2mc-ipv4" {
        value 1;
        description
          "Multicast Source - IPv4";
      }
      enum "l2mc-ipv6" {
        value 2;
        description
          "Multicast Source - IPv6";
      }
      enum "l2mc-ipv4-ipv6" {
        value 3;
        description
          "Multicast Source - IPv4 IPv6";
      }
    }
    description
      "L2mc src traffic enabled";
  }

  typedef ncs_rpc_notif_L2vpn-verification {
    type enumeration {
      enum "enable" {
        value 1;
        description
          "enable verification";
      }
      enum "disable" {
        value 2;
        description
          "disable verification";
      }
    }
    description
      "L2vpn verification";
  }

  typedef ncs_rpc_notif_Max-path-mtu-range {
    type uint32 {
      range "68..65535";
    }
    description
      "Max path mtu range";
  }

  typedef ncs_rpc_notif_Interface-traffic-flood {
    type enumeration {
      enum "traffic-flooding" {
        value 0;
        description
          "Traffic flooding";
      }
      enum "enable-flooding" {
        value 1;
        description
          "Enable Flooding";
      }
      enum "disable-flooding" {
        value 2;
        description
          "Disable flooding";
      }
    }
    description
      "Interface traffic flood";
  }

  typedef ncs_rpc_notif_Pbbvid-range {
    type uint32 {
      range "1..4094";
    }
    description
      "Pbbvid range";
  }

  typedef ncs_rpc_notif_L2tp-cookie-value-range {
    type uint32 {
      range "0..4294967295";
    }
    description
      "L2tp cookie value range";
  }

  typedef ncs_rpc_notif_L2-encapsulation {
    type enumeration {
      enum "vlan" {
        value 4;
        description
          "Vlan tagged mode";
      }
      enum "ethernet" {
        value 5;
        description
          "Ethernet port mode";
      }
    }
    description
      "L2 encapsulation";
  }

  typedef ncs_rpc_notif_L2vpn-logging {
    type enumeration {
      enum "enable" {
        value 1;
        description
          "enable logging";
      }
      enum "disable" {
        value 2;
        description
          "disable logging";
      }
    }
    description
      "L2vpn logging";
  }

  typedef ncs_rpc_notif_Mac-aging-range {
    type uint32 {
      range "300..30000";
    }
    description
      "Mac aging range";
  }

  typedef ncs_rpc_notif_Vpls-id-as-index {
    type uint32 {
      range "0..4294967295";
    }
    description
      "Vpls id as index";
  }

  typedef ncs_rpc_notif_Pseudowire-gbl-id-range {
    type uint32 {
      range "1..4294967295";
    }
    description
      "Pseudowire gbl id range";
  }

  typedef ncs_rpc_notif_Rdas-index {
    type uint32 {
      range "0..4294967295";
    }
    description
      "Rdas index";
  }

  typedef ncs_rpc_notif_Mac-flush-mode {
    type enumeration {
      enum "mvrp" {
        value 1;
        description
          "MVRP MAC Flushing";
      }
    }
    description
      "Mac flush mode";
  }

  typedef ncs_rpc_notif_L2tp-cookie-size {
    type enumeration {
      enum "zero" {
        value 0;
        description
          "Cookie size is zero bytes";
      }
      enum "four" {
        value 4;
        description
          "Cookie size is four bytes";
      }
      enum "eight" {
        value 8;
        description
          "Cookie size is eight bytes";
      }
    }
    description
      "L2tp cookie size";
  }

  typedef ncs_rpc_notif_Mpls-sequencing {
    type enumeration {
      enum "off" {
        value 0;
        description
          "Sequencing is off";
      }
      enum "transmit" {
        value 1;
        description
          "Sequencing on transmit side";
      }
      enum "receive" {
        value 2;
        description
          "Sequencing on receive side";
      }
      enum "both" {
        value 4;
        description
          "Sequencing on both transmit and receive side";
      }
    }
    description
      "Mpls sequencing";
  }

  typedef ncs_rpc_notif_Erp-instance-range {
    type uint32 {
      range "1..2";
    }
    description
      "Erp instance range";
  }

  typedef ncs_rpc_notif_Pw-redundancy-initial-delay-range {
    type uint32 {
      range "0..120";
    }
    description
      "Pw redundancy initial delay range";
  }

  typedef ncs_rpc_notif_Vpls-id-as-range {
    type uint32 {
      range "1..65535";
    }
    description
      "Vpls id as range";
  }

  typedef ncs_rpc_notif_Rdas-range {
    type uint32 {
      range "1..4294967295";
    }
    description
      "Rdas range";
  }

  typedef ncs_rpc_notif_Ethernet-segment-service-carving-mcast {
    type enumeration {
      enum "disabled" {
        value 0;
        description
          "Disabled";
      }
      enum "hrw-s-g" {
        value 1;
        description
          "HRW S G";
      }
      enum "hrw-g" {
        value 2;
        description
          "HRW G";
      }
    }
    description
      "Ethernet segment service carving mcast";
  }

  typedef ncs_rpc_notif_Bridge-bd-mtu-range {
    type uint32 {
      range "46..65535";
    }
    description
      "Bridge bd mtu range";
  }

  typedef ncs_rpc_notif_Backup-disable-delay-range {
    type uint32 {
      range "0..180";
    }
    description
      "Backup disable delay range";
  }

  typedef ncs_rpc_notif_Storm-control-kbps-range {
    type uint32 {
      range "64..1280000";
    }
    description
      "Storm control kbps range";
  }

  typedef ncs_rpc_notif_Mac-limit-action {
    type enumeration {
      enum "none" {
        value 0;
        description
          "No action";
      }
      enum "flood" {
        value 1;
        description
          "Flood Mac Limit Action";
      }
      enum "no-flood" {
        value 2;
        description
          "NoFlood Mac Limit Action";
      }
      enum "shutdown" {
        value 3;
        description
          "Shutdown Mac Limit Action";
      }
    }
    description
      "Mac limit action";
  }

  typedef ncs_rpc_notif_Erp-port1 {
    type enumeration {
      enum "port0" {
        value 0;
        description
          "ERP main port 0";
      }
      enum "port1" {
        value 1;
        description
          "ERP main port 1";
      }
    }
    description
      "Erp port1";
  }

  typedef ncs_rpc_notif_Mac-notification {
    type enumeration {
      enum "no-notif" {
        value 0;
        description
          "No_Notification Trap";
      }
      enum "syslog" {
        value 1;
        description
          "syslog message";
      }
      enum "trap" {
        value 2;
        description
          "Snmp Trap";
      }
      enum "syslog-snmp" {
        value 3;
        description
          "Syslog_snmp Trap";
      }
    }
    description
      "Mac notification";
  }

  typedef ncs_rpc_notif_Control-word {
    type enumeration {
      enum "enable" {
        value 1;
        description
          "Enable control word";
      }
      enum "disable" {
        value 2;
        description
          "Disable control word";
      }
    }
    description
      "Control word";
  }

  typedef ncs_rpc_notif_Preferred-nexthop-mode {
    type enumeration {
      enum "preferred-nexthop-lowest-ip" {
        value 1;
        description
          "Lowest IP Preferred";
      }
      enum "preferred-nexthop-highest-ip" {
        value 2;
        description
          "Highest IP Preferred";
      }
      enum "preferred-nexthop-modulo" {
        value 3;
        description
          "Modulo of nexthops Preferred";
      }
    }
    description
      "Preferred nexthop mode";
  }

  typedef ncs_rpc_notif_Bgp-route-distinguisher {
    type enumeration {
      enum "auto" {
        value 1;
        description
          "RD automatically assigned";
      }
      enum "two-byte-as" {
        value 2;
        description
          "RD in 2 byte AS:nn format";
      }
      enum "four-byte-as" {
        value 3;
        description
          "RD in 4 byte AS:nn format";
      }
      enum "ipv4-address" {
        value 4;
        description
          "RD in IpV4address";
      }
    }
    description
      "Bgp route distinguisher";
  }

  typedef ncs_rpc_notif_Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  typedef ncs_rpc_notif_Evpn-group-id-range {
    type uint32 {
      range "1..4294967295";
    }
    description
      "Evpn group id range";
  }

  typedef ncs_rpc_notif_Mac-limit-threshold-range {
    type uint32 {
      range "1..100";
    }
    description
      "Mac limit threshold range";
  }

  typedef ncs_rpc_notif_Vedge-range {
    type uint32 {
      range "11..100";
    }
    description
      "Vedge range";
  }

  typedef ncs_rpc_notif_Vpnid-range {
    type uint32 {
      range "1..4294967295";
    }
    description
      "Vpnid range";
  }

  typedef ncs_rpc_notif_Ldp-vpls-id {
    type enumeration {
      enum "two-byte-as" {
        value 10;
        description
          "VPLS-ID in 2 byte AS:nn format";
      }
      enum "ipv4-address" {
        value 266;
        description
          "VPLS-ID in IPv4 IP:nn format";
      }
    }
    description
      "Ldp vpls id";
  }

  typedef ncs_rpc_notif_Ce-id-range {
    type uint32 {
      range "1..16384";
    }
    description
      "Ce id range";
  }

  typedef ncs_rpc_notif_Mac-aging {
    type enumeration {
      enum "absolute" {
        value 1;
        description
          "Absolute aging type";
      }
      enum "inactivity" {
        value 2;
        description
          "Inactivity aging type";
      }
    }
    description
      "Mac aging";
  }

  typedef ncs_rpc_notif_Mac-limit-range {
    type uint32 {
      range "0..4294967295";
    }
    description
      "Mac limit range";
  }

  typedef ncs_rpc_notif_Pbbisid-range {
    type uint32 {
      range "256..16777214";
    }
    description
      "Pbbisid range";
  }

  typedef ncs_rpc_notif_Type-of-service-range {
    type uint32 {
      range "0..255";
    }
    description
      "Type of service range";
  }

  typedef ncs_rpc_notif_Flow-label-load-balance {
    type enumeration {
      enum "off" {
        value 0;
        description
          "Flow Label load balance is off";
      }
      enum "receive" {
        value 1;
        description
          "Delete Flow Label on receive side";
      }
      enum "transmit" {
        value 2;
        description
          "Insert Flow Label on transmit side";
      }
      enum "both" {
        value 3;
        description
          "Insert/Delete Flow Label on transmit/receive
           side";
      }
    }
    description
      "Flow label load balance";
  }

  typedef live_ncs_Evpn-encapsulation {
    type enumeration {
      enum "evpn-encapsulationvxlan" {
        value 8;
        description
          "VXLAN Encapsulation";
      }
      enum "evpn-encapsulation-mpls" {
        value 10;
        description
          "MPLS Encapsulation";
      }
      enum "evpn-encapsulation-route-sync" {
        value 254;
        description
          "Route Sync Encapsulation";
      }
      enum "evpn-encapsulation-srv6" {
        value 255;
        description
          "SRv6 Encapsulation";
      }
    }
    description
      "Evpn encapsulation";
  }

  typedef live_ncs_Interworking {
    type enumeration {
      enum "ethernet" {
        value 1;
        description
          "Ethernet interworking";
      }
      enum "ipv4" {
        value 3;
        description
          "IPv4 interworking";
      }
    }
    description
      "Interworking";
  }

  typedef live_ncs_L2vpn-capability-mode {
    type enumeration {
      enum "high-mode" {
        value 1;
        description
          "Compute global capability as the highest node
           capability";
      }
      enum "single-mode" {
        value 2;
        description
          "Disable global capability re-computation";
      }
    }
    description
      "L2vpn capability mode";
  }

  typedef live_ncs_Evpn-side {
    type enumeration {
      enum "evpn-side-regular" {
        value 1;
        description
          "EVPN Instance side defined as regular";
      }
      enum "evpn-side-stitching" {
        value 2;
        description
          "EVPN Instance side defined as stitching";
      }
    }
    description
      "Evpn side";
  }

  typedef live_ncs_Vpls-id-addr-index {
    type uint32 {
      range "0..32767";
    }
    description
      "Vpls id addr index";
  }

  typedef live_ncs_Evpn-core-group-id-range {
    type uint32 {
      range "1..4294967295";
    }
    description
      "Evpn core group id range";
  }

  typedef live_ncs_Tag-rewrite-range {
    type uint32 {
      range "1..4094";
    }
    description
      "Tag rewrite range";
  }

  typedef live_ncs_Pseudowire-evpnacid-range {
    type uint32 {
      range "1..16777215";
    }
    description
      "Pseudowire evpnacid range";
  }

  typedef live_ncs_Evpnvpnid-range {
    type uint32 {
      range "1..65534";
    }
    description
      "Evpnvpnid range";
  }

  typedef live_ncs_Pseudowire-label-range {
    type uint32 {
      range "16..1048575";
    }
    description
      "Pseudowire label range";
  }

  typedef live_ncs_Bridge-domain-transport-mode {
    type enumeration {
      enum "vlan-passthrough" {
        value 3;
        description
          "Vlan tagged passthrough mode";
      }
    }
    description
      "Bridge domain transport mode";
  }

  typedef live_ncs_Preferred-path {
    type enumeration {
      enum "te-tunnel" {
        value 2;
        description
          "TE Tunnel";
      }
      enum "ip-tunnel" {
        value 3;
        description
          "IP Tunnel";
      }
      enum "tp-tunnel" {
        value 4;
        description
          "TP Tunnel";
      }
      enum "sr-te-policy" {
        value 5;
        description
          "SR TE Policy";
      }
      enum "named-te-tunnel" {
        value 8;
        description
          "Named TE Tunnel";
      }
    }
    description
      "Preferred path";
  }

  typedef live_ncs_Rd-addr-index {
    type uint32 {
      range "0..65535";
    }
    description
      "Rd addr index";
  }

  typedef live_ncs_Vccv-verification {
    type enumeration {
      enum "none" {
        value 0;
        description
          "No connectivity verification over VCCV";
      }
      enum "lsp-ping" {
        value 2;
        description
          "LSP Ping over VCCV";
      }
    }
    description
      "Vccv verification";
  }

  typedef live_ncs_L2vpn-mtu-range {
    type uint32 {
      range "64..65535";
    }
    description
      "L2vpn mtu range";
  }

  typedef live_ncs_Mac-secure-shutdown-recovery-time-range {
    type uint32 {
      range "10..3600";
    }
    description
      "Mac secure shutdown recovery time range";
  }

  typedef live_ncs_Mac-withdraw-behavior {
    type enumeration {
      enum "legacy" {
        value 1;
        description
          "MAC Withdrawal sent on state-down (legacy)";
      }
      enum "optimized" {
        value 2;
        description
          "Optimized MAC Withdrawal";
      }
    }
    description
      "Mac withdraw behavior";
  }

  typedef live_ncs_Port-down-flush {
    type enumeration {
      enum "port-down-flush" {
        value 0;
        description
          "MAC Port Down Flush";
      }
      enum "enable-port-down-flush" {
        value 1;
        description
          "Enable Port Down Flush";
      }
      enum "disable-port-down-flush" {
        value 2;
        description
          "Disable Port Down Flush";
      }
    }
    description
      "Port down flush";
  }

  typedef live_ncs_Storm-control-pps-range {
    type uint32 {
      range "1..160000";
    }
    description
      "Storm control pps range";
  }

  typedef live_ncs_Type-of-service-mode {
    type enumeration {
      enum "none" {
        value 0;
        description
          "Do not reflect the type of service";
      }
      enum "reflect" {
        value 1;
        description
          "Reflect the type of service";
      }
    }
    description
      "Type of service mode";
  }

  typedef live_ncs_L2vpn-vs-vlan-tag {
    type uint32 {
      range "1..4094";
    }
    description
      "L2vpn vs vlan tag";
  }

  typedef live_ncs_Pseudowire-tag-range {
    type uint32 {
      range "1..4094";
    }
    description
      "Pseudowire tag range";
  }

  typedef live_ncs_Interface-access-signal-mode {
    type enumeration {
      enum "bundle-down" {
        value 2;
        description
          "BundleDown";
      }
    }
    description
      "Interface access signal mode";
  }

  typedef live_ncs_Multicast-p2mp-signaling {
    type string {
      pattern '(BGP)';
    }
    description
      "BGP:BGP Signaling";
  }

  typedef live_ncs_Cedge-range {
    type uint32 {
      range "11..100";
    }
    description
      "Cedge range";
  }

  typedef live_ncs_Ethernet-segment-load-balance {
    type enumeration {
      enum "single-active" {
        value 1;
        description
          "Single Active";
      }
      enum "port-active" {
        value 2;
        description
          "Port Active";
      }
      enum "single-flow-active" {
        value 3;
        description
          "Single Flow Active";
      }
      enum "all-active" {
        value 4;
        description
          "All Active";
      }
    }
    description
      "Ethernet segment load balance";
  }

  typedef live_ncs_Mpls-signaling-protocol {
    type enumeration {
      enum "none" {
        value 1;
        description
          "No signaling";
      }
      enum "ldp" {
        value 4;
        description
          "LDP";
      }
    }
    description
      "Mpls signaling protocol";
  }

  typedef live_ncs_Erpaps {
    type enumeration {
      enum "interface" {
        value 1;
        description
          "ERP APS type interface";
      }
      enum "bridge-domain" {
        value 2;
        description
          "ERP APS type bridge domain";
      }
      enum "xconnect" {
        value 3;
        description
          "ERP APS type xconnect";
      }
      enum "none" {
        value 4;
        description
          "ERP APS type none";
      }
    }
    description
      "Erpaps";
  }

  typedef live_ncs_Mac-secure-action {
    type enumeration {
      enum "restrict" {
        value 1;
        description
          "MAC Secure Action Restrict";
      }
      enum "none" {
        value 2;
        description
          "No Action";
      }
      enum "shutdown" {
        value 3;
        description
          "MAC Secure Action Shutdown";
      }
    }
    description
      "Mac secure action";
  }

  typedef live_ncs_Erp-port {
    type enumeration {
      enum "none" {
        value 1;
        description
          "ERP port type none";
      }
      enum "virtual" {
        value 2;
        description
          "ERP port type virtual";
      }
      enum "interface" {
        value 3;
        description
          "ERP port type interface";
      }
    }
    description
      "Erp port";
  }

  typedef live_ncs_Resync-threshold-range {
    type uint32 {
      range "5..65535";
    }
    description
      "Resync threshold range";
  }

  typedef live_ncs_Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef live_ncs_Backup-disable {
    type enumeration {
      enum "never" {
        value 0;
        description
          "Never";
      }
      enum "delay" {
        value 1;
        description
          "Delay seconds";
      }
    }
    description
      "Backup disable";
  }

  typedef live_ncs_Time-to-live-range {
    type uint32 {
      range "1..255";
    }
    description
      "Time to live range";
  }

  typedef live_ncs_Multicast-p2mp-transport {
    type string {
      pattern '(RSVP_TE)';
    }
    description
      "RSVP_TE:RSVP-TE Transport";
  }

  typedef live_ncs_Transport-mode {
    type enumeration {
      enum "ethernet" {
        value 1;
        description
          "Ethernet port mode";
      }
      enum "vlan" {
        value 2;
        description
          "Vlan tagged mode";
      }
      enum "vlan-passthrough" {
        value 3;
        description
          "Vlan tagged passthrough mode";
      }
    }
    description
      "Transport mode";
  }

  typedef live_ncs_Flow-label-tlv-code {
    type enumeration {
      enum "17" {
        value 4;
        description
          "Set Flow Label Legacy TLV code (DEPRECATED)";
      }
      enum "disable" {
        value 8;
        description
          "Disable Sending Flow Label Legacy TLV";
      }
    }
    description
      "Flow label tlv code";
  }

  typedef live_ncs_Bgp-route-target {
    type enumeration {
      enum "no-stitching" {
        value 0;
        description
          "RT is default type";
      }
      enum "stitching" {
        value 1;
        description
          "RT is for stitching (Golf-L2) (DEPRECATED)";
      }
    }
    description
      "Bgp route target";
  }

  typedef live_ncs_Pseudowire-acid-range {
    type uint32 {
      range "1..4294967295";
    }
    description
      "Pseudowire acid range";
  }

  typedef live_ncs_Pseudowire-id-range {
    type uint32 {
      range "1..4294967295";
    }
    description
      "Pseudowire id range";
  }

  typedef live_ncs_Interface-profile {
    type enumeration {
      enum "snoop" {
        value 1;
        description
          "Set the snooping";
      }
      enum "dhcp-protocol" {
        value 2;
        description
          "disable DHCP protocol";
      }
    }
    description
      "Interface profile";
  }

  typedef live_ncs_Ethernet-segment-identifier {
    type enumeration {
      enum "type0" {
        value 0;
        description
          "ESI type 0";
      }
      enum "legacy" {
        value 128;
        description
          "Legacy ESI type";
      }
      enum "override" {
        value 129;
        description
          "Override ESI type";
      }
    }
    description
      "Ethernet segment identifier";
  }

  typedef live_ncs_Rpl-role {
    type enumeration {
      enum "owner" {
        value 1;
        description
          "ERP RPL owner";
      }
      enum "neighbor" {
        value 2;
        description
          "ERP RPL neighbor";
      }
      enum "next-neighbor" {
        value 3;
        description
          "ERP RPL next neighbor";
      }
    }
    description
      "Rpl role";
  }

  typedef live_ncs_Pw-switching-point-tlv {
    type enumeration {
      enum "hide" {
        value 2;
        description
          "Hide TLV";
      }
    }
    description
      "Pw switching point tlv";
  }

  typedef live_ncs_Erpaps-level-range {
    type uint32 {
      range "0..7";
    }
    description
      "Erpaps level range";
  }

  typedef live_ncs_Evpn-esi-type-range {
    type uint32 {
      range "1";
    }
    description
      "Evpn esi type range";
  }

  typedef live_ncs_Storm-control {
    type enumeration {
      enum "unicast" {
        value 1;
        description
          "Unknown-unicast Storm Control";
      }
      enum "multicast" {
        value 2;
        description
          "Multicast Storm Control";
      }
      enum "broadcast" {
        value 4;
        description
          "Broadcast Storm Control";
      }
    }
    description
      "Storm control";
  }

  typedef live_ncs_L2tp-session-id-range {
    type uint32 {
      range "1..65535";
    }
    description
      "L2tp session id range";
  }

  typedef live_ncs_Ethernet-segment-service-carving {
    type enumeration {
      enum "mod-n" {
        value 0;
        description
          "MOD N";
      }
      enum "manual" {
        value 1;
        description
          "Manual";
      }
      enum "hrw" {
        value 2;
        description
          "HRW";
      }
      enum "pref-df" {
        value 3;
        description
          "PrefDF";
      }
    }
    description
      "Ethernet segment service carving";
  }

  typedef live_ncs_Mac-learn {
    type enumeration {
      enum "default-learning" {
        value 0;
        description
          "Mac Learning";
      }
      enum "enable-learning" {
        value 1;
        description
          "Enable Learning";
      }
      enum "disable-learning" {
        value 2;
        description
          "Disable Learning";
      }
    }
    description
      "Mac learn";
  }

  typedef live_ncs_L2tpv3-sequencing {
    type enumeration {
      enum "off" {
        value 0;
        description
          "Sequencing is off";
      }
      enum "both" {
        value 4;
        description
          "Sequencing on both transmit and receive side";
      }
    }
    description
      "L2tpv3 sequencing";
  }

  typedef live_ncs_Veid-range {
    type uint32 {
      range "1..16384";
    }
    description
      "Veid range";
  }

  typedef live_ncs_Load-balance {
    type enumeration {
      enum "source-dest-mac" {
        value 1;
        description
          "Source and Destination MAC hashing";
      }
      enum "source-dest-ip" {
        value 2;
        description
          "Source and Destination IP hashing";
      }
      enum "pseudowire-label" {
        value 4;
        description
          "PW Label hashing";
      }
    }
    description
      "Load balance";
  }

  typedef live_ncs_L2tp-signaling-protocol {
    type enumeration {
      enum "none" {
        value 1;
        description
          "No signaling";
      }
      enum "l2tpv3" {
        value 2;
        description
          "L2TPv3";
      }
    }
    description
      "L2tp signaling protocol";
  }

  typedef live_ncs_Bdmac-learn {
    type enumeration {
      enum "disable-learning" {
        value 2;
        description
          "Disable Learning";
      }
    }
    description
      "Bdmac learn";
  }

  typedef live_ncs_L2mc-src-traffic-enabled {
    type enumeration {
      enum "l2mc-none" {
        value 0;
        description
          "NONE";
      }
      enum "l2mc-ipv4" {
        value 1;
        description
          "Multicast Source - IPv4";
      }
      enum "l2mc-ipv6" {
        value 2;
        description
          "Multicast Source - IPv6";
      }
      enum "l2mc-ipv4-ipv6" {
        value 3;
        description
          "Multicast Source - IPv4 IPv6";
      }
    }
    description
      "L2mc src traffic enabled";
  }

  typedef live_ncs_L2vpn-verification {
    type enumeration {
      enum "enable" {
        value 1;
        description
          "enable verification";
      }
      enum "disable" {
        value 2;
        description
          "disable verification";
      }
    }
    description
      "L2vpn verification";
  }

  typedef live_ncs_Max-path-mtu-range {
    type uint32 {
      range "68..65535";
    }
    description
      "Max path mtu range";
  }

  typedef live_ncs_Interface-traffic-flood {
    type enumeration {
      enum "traffic-flooding" {
        value 0;
        description
          "Traffic flooding";
      }
      enum "enable-flooding" {
        value 1;
        description
          "Enable Flooding";
      }
      enum "disable-flooding" {
        value 2;
        description
          "Disable flooding";
      }
    }
    description
      "Interface traffic flood";
  }

  typedef live_ncs_Pbbvid-range {
    type uint32 {
      range "1..4094";
    }
    description
      "Pbbvid range";
  }

  typedef live_ncs_L2tp-cookie-value-range {
    type uint32 {
      range "0..4294967295";
    }
    description
      "L2tp cookie value range";
  }

  typedef live_ncs_L2-encapsulation {
    type enumeration {
      enum "vlan" {
        value 4;
        description
          "Vlan tagged mode";
      }
      enum "ethernet" {
        value 5;
        description
          "Ethernet port mode";
      }
    }
    description
      "L2 encapsulation";
  }

  typedef live_ncs_L2vpn-logging {
    type enumeration {
      enum "enable" {
        value 1;
        description
          "enable logging";
      }
      enum "disable" {
        value 2;
        description
          "disable logging";
      }
    }
    description
      "L2vpn logging";
  }

  typedef live_ncs_Mac-aging-range {
    type uint32 {
      range "300..30000";
    }
    description
      "Mac aging range";
  }

  typedef live_ncs_Vpls-id-as-index {
    type uint32 {
      range "0..4294967295";
    }
    description
      "Vpls id as index";
  }

  typedef live_ncs_Pseudowire-gbl-id-range {
    type uint32 {
      range "1..4294967295";
    }
    description
      "Pseudowire gbl id range";
  }

  typedef live_ncs_Rdas-index {
    type uint32 {
      range "0..4294967295";
    }
    description
      "Rdas index";
  }

  typedef live_ncs_Mac-flush-mode {
    type enumeration {
      enum "mvrp" {
        value 1;
        description
          "MVRP MAC Flushing";
      }
    }
    description
      "Mac flush mode";
  }

  typedef live_ncs_L2tp-cookie-size {
    type enumeration {
      enum "zero" {
        value 0;
        description
          "Cookie size is zero bytes";
      }
      enum "four" {
        value 4;
        description
          "Cookie size is four bytes";
      }
      enum "eight" {
        value 8;
        description
          "Cookie size is eight bytes";
      }
    }
    description
      "L2tp cookie size";
  }

  typedef live_ncs_Mpls-sequencing {
    type enumeration {
      enum "off" {
        value 0;
        description
          "Sequencing is off";
      }
      enum "transmit" {
        value 1;
        description
          "Sequencing on transmit side";
      }
      enum "receive" {
        value 2;
        description
          "Sequencing on receive side";
      }
      enum "both" {
        value 4;
        description
          "Sequencing on both transmit and receive side";
      }
    }
    description
      "Mpls sequencing";
  }

  typedef live_ncs_Erp-instance-range {
    type uint32 {
      range "1..2";
    }
    description
      "Erp instance range";
  }

  typedef live_ncs_Pw-redundancy-initial-delay-range {
    type uint32 {
      range "0..120";
    }
    description
      "Pw redundancy initial delay range";
  }

  typedef live_ncs_Vpls-id-as-range {
    type uint32 {
      range "1..65535";
    }
    description
      "Vpls id as range";
  }

  typedef live_ncs_Rdas-range {
    type uint32 {
      range "1..4294967295";
    }
    description
      "Rdas range";
  }

  typedef live_ncs_Ethernet-segment-service-carving-mcast {
    type enumeration {
      enum "disabled" {
        value 0;
        description
          "Disabled";
      }
      enum "hrw-s-g" {
        value 1;
        description
          "HRW S G";
      }
      enum "hrw-g" {
        value 2;
        description
          "HRW G";
      }
    }
    description
      "Ethernet segment service carving mcast";
  }

  typedef live_ncs_Bridge-bd-mtu-range {
    type uint32 {
      range "46..65535";
    }
    description
      "Bridge bd mtu range";
  }

  typedef live_ncs_Backup-disable-delay-range {
    type uint32 {
      range "0..180";
    }
    description
      "Backup disable delay range";
  }

  typedef live_ncs_Storm-control-kbps-range {
    type uint32 {
      range "64..1280000";
    }
    description
      "Storm control kbps range";
  }

  typedef live_ncs_Mac-limit-action {
    type enumeration {
      enum "none" {
        value 0;
        description
          "No action";
      }
      enum "flood" {
        value 1;
        description
          "Flood Mac Limit Action";
      }
      enum "no-flood" {
        value 2;
        description
          "NoFlood Mac Limit Action";
      }
      enum "shutdown" {
        value 3;
        description
          "Shutdown Mac Limit Action";
      }
    }
    description
      "Mac limit action";
  }

  typedef live_ncs_Erp-port1 {
    type enumeration {
      enum "port0" {
        value 0;
        description
          "ERP main port 0";
      }
      enum "port1" {
        value 1;
        description
          "ERP main port 1";
      }
    }
    description
      "Erp port1";
  }

  typedef live_ncs_Mac-notification {
    type enumeration {
      enum "no-notif" {
        value 0;
        description
          "No_Notification Trap";
      }
      enum "syslog" {
        value 1;
        description
          "syslog message";
      }
      enum "trap" {
        value 2;
        description
          "Snmp Trap";
      }
      enum "syslog-snmp" {
        value 3;
        description
          "Syslog_snmp Trap";
      }
    }
    description
      "Mac notification";
  }

  typedef live_ncs_Control-word {
    type enumeration {
      enum "enable" {
        value 1;
        description
          "Enable control word";
      }
      enum "disable" {
        value 2;
        description
          "Disable control word";
      }
    }
    description
      "Control word";
  }

  typedef live_ncs_Preferred-nexthop-mode {
    type enumeration {
      enum "preferred-nexthop-lowest-ip" {
        value 1;
        description
          "Lowest IP Preferred";
      }
      enum "preferred-nexthop-highest-ip" {
        value 2;
        description
          "Highest IP Preferred";
      }
      enum "preferred-nexthop-modulo" {
        value 3;
        description
          "Modulo of nexthops Preferred";
      }
    }
    description
      "Preferred nexthop mode";
  }

  typedef live_ncs_Bgp-route-distinguisher {
    type enumeration {
      enum "auto" {
        value 1;
        description
          "RD automatically assigned";
      }
      enum "two-byte-as" {
        value 2;
        description
          "RD in 2 byte AS:nn format";
      }
      enum "four-byte-as" {
        value 3;
        description
          "RD in 4 byte AS:nn format";
      }
      enum "ipv4-address" {
        value 4;
        description
          "RD in IpV4address";
      }
    }
    description
      "Bgp route distinguisher";
  }

  typedef live_ncs_Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  typedef live_ncs_Evpn-group-id-range {
    type uint32 {
      range "1..4294967295";
    }
    description
      "Evpn group id range";
  }

  typedef live_ncs_Mac-limit-threshold-range {
    type uint32 {
      range "1..100";
    }
    description
      "Mac limit threshold range";
  }

  typedef live_ncs_Vedge-range {
    type uint32 {
      range "11..100";
    }
    description
      "Vedge range";
  }

  typedef live_ncs_Vpnid-range {
    type uint32 {
      range "1..4294967295";
    }
    description
      "Vpnid range";
  }

  typedef live_ncs_Ldp-vpls-id {
    type enumeration {
      enum "two-byte-as" {
        value 10;
        description
          "VPLS-ID in 2 byte AS:nn format";
      }
      enum "ipv4-address" {
        value 266;
        description
          "VPLS-ID in IPv4 IP:nn format";
      }
    }
    description
      "Ldp vpls id";
  }

  typedef live_ncs_Ce-id-range {
    type uint32 {
      range "1..16384";
    }
    description
      "Ce id range";
  }

  typedef live_ncs_Mac-aging {
    type enumeration {
      enum "absolute" {
        value 1;
        description
          "Absolute aging type";
      }
      enum "inactivity" {
        value 2;
        description
          "Inactivity aging type";
      }
    }
    description
      "Mac aging";
  }

  typedef live_ncs_Mac-limit-range {
    type uint32 {
      range "0..4294967295";
    }
    description
      "Mac limit range";
  }

  typedef live_ncs_Pbbisid-range {
    type uint32 {
      range "256..16777214";
    }
    description
      "Pbbisid range";
  }

  typedef live_ncs_Type-of-service-range {
    type uint32 {
      range "0..255";
    }
    description
      "Type of service range";
  }

  typedef live_ncs_Flow-label-load-balance {
    type enumeration {
      enum "off" {
        value 0;
        description
          "Flow Label load balance is off";
      }
      enum "receive" {
        value 1;
        description
          "Delete Flow Label on receive side";
      }
      enum "transmit" {
        value 2;
        description
          "Insert Flow Label on transmit side";
      }
      enum "both" {
        value 3;
        description
          "Insert/Delete Flow Label on transmit/receive
           side";
      }
    }
    description
      "Flow label load balance";
  }

  typedef Evpn-encapsulation {
    type enumeration {
      enum "evpn-encapsulationvxlan" {
        value 8;
        description
          "VXLAN Encapsulation";
      }
      enum "evpn-encapsulation-mpls" {
        value 10;
        description
          "MPLS Encapsulation";
      }
      enum "evpn-encapsulation-route-sync" {
        value 254;
        description
          "Route Sync Encapsulation";
      }
      enum "evpn-encapsulation-srv6" {
        value 255;
        description
          "SRv6 Encapsulation";
      }
    }
    description
      "Evpn encapsulation";
  }

  typedef Interworking {
    type enumeration {
      enum "ethernet" {
        value 1;
        description
          "Ethernet interworking";
      }
      enum "ipv4" {
        value 3;
        description
          "IPv4 interworking";
      }
    }
    description
      "Interworking";
  }

  typedef L2vpn-capability-mode {
    type enumeration {
      enum "high-mode" {
        value 1;
        description
          "Compute global capability as the highest node
           capability";
      }
      enum "single-mode" {
        value 2;
        description
          "Disable global capability re-computation";
      }
    }
    description
      "L2vpn capability mode";
  }

  typedef Evpn-side {
    type enumeration {
      enum "evpn-side-regular" {
        value 1;
        description
          "EVPN Instance side defined as regular";
      }
      enum "evpn-side-stitching" {
        value 2;
        description
          "EVPN Instance side defined as stitching";
      }
    }
    description
      "Evpn side";
  }

  typedef Vpls-id-addr-index {
    type uint32 {
      range "0..32767";
    }
    description
      "Vpls id addr index";
  }

  typedef Evpn-core-group-id-range {
    type uint32 {
      range "1..4294967295";
    }
    description
      "Evpn core group id range";
  }

  typedef Tag-rewrite-range {
    type uint32 {
      range "1..4094";
    }
    description
      "Tag rewrite range";
  }

  typedef Pseudowire-evpnacid-range {
    type uint32 {
      range "1..16777215";
    }
    description
      "Pseudowire evpnacid range";
  }

  typedef Evpnvpnid-range {
    type uint32 {
      range "1..65534";
    }
    description
      "Evpnvpnid range";
  }

  typedef Pseudowire-label-range {
    type uint32 {
      range "16..1048575";
    }
    description
      "Pseudowire label range";
  }

  typedef Bridge-domain-transport-mode {
    type enumeration {
      enum "vlan-passthrough" {
        value 3;
        description
          "Vlan tagged passthrough mode";
      }
    }
    description
      "Bridge domain transport mode";
  }

  typedef Preferred-path {
    type enumeration {
      enum "te-tunnel" {
        value 2;
        description
          "TE Tunnel";
      }
      enum "ip-tunnel" {
        value 3;
        description
          "IP Tunnel";
      }
      enum "tp-tunnel" {
        value 4;
        description
          "TP Tunnel";
      }
      enum "sr-te-policy" {
        value 5;
        description
          "SR TE Policy";
      }
      enum "named-te-tunnel" {
        value 8;
        description
          "Named TE Tunnel";
      }
    }
    description
      "Preferred path";
  }

  typedef Rd-addr-index {
    type uint32 {
      range "0..65535";
    }
    description
      "Rd addr index";
  }

  typedef Vccv-verification {
    type enumeration {
      enum "none" {
        value 0;
        description
          "No connectivity verification over VCCV";
      }
      enum "lsp-ping" {
        value 2;
        description
          "LSP Ping over VCCV";
      }
    }
    description
      "Vccv verification";
  }

  typedef L2vpn-mtu-range {
    type uint32 {
      range "64..65535";
    }
    description
      "L2vpn mtu range";
  }

  typedef Mac-secure-shutdown-recovery-time-range {
    type uint32 {
      range "10..3600";
    }
    description
      "Mac secure shutdown recovery time range";
  }

  typedef Mac-withdraw-behavior {
    type enumeration {
      enum "legacy" {
        value 1;
        description
          "MAC Withdrawal sent on state-down (legacy)";
      }
      enum "optimized" {
        value 2;
        description
          "Optimized MAC Withdrawal";
      }
    }
    description
      "Mac withdraw behavior";
  }

  typedef Port-down-flush {
    type enumeration {
      enum "port-down-flush" {
        value 0;
        description
          "MAC Port Down Flush";
      }
      enum "enable-port-down-flush" {
        value 1;
        description
          "Enable Port Down Flush";
      }
      enum "disable-port-down-flush" {
        value 2;
        description
          "Disable Port Down Flush";
      }
    }
    description
      "Port down flush";
  }

  typedef Storm-control-pps-range {
    type uint32 {
      range "1..160000";
    }
    description
      "Storm control pps range";
  }

  typedef Type-of-service-mode {
    type enumeration {
      enum "none" {
        value 0;
        description
          "Do not reflect the type of service";
      }
      enum "reflect" {
        value 1;
        description
          "Reflect the type of service";
      }
    }
    description
      "Type of service mode";
  }

  typedef L2vpn-vs-vlan-tag {
    type uint32 {
      range "1..4094";
    }
    description
      "L2vpn vs vlan tag";
  }

  typedef Pseudowire-tag-range {
    type uint32 {
      range "1..4094";
    }
    description
      "Pseudowire tag range";
  }

  typedef Interface-access-signal-mode {
    type enumeration {
      enum "bundle-down" {
        value 2;
        description
          "BundleDown";
      }
    }
    description
      "Interface access signal mode";
  }

  typedef Multicast-p2mp-signaling {
    type string {
      pattern '(BGP)';
    }
    description
      "BGP:BGP Signaling";
  }

  typedef Cedge-range {
    type uint32 {
      range "11..100";
    }
    description
      "Cedge range";
  }

  typedef Ethernet-segment-load-balance {
    type enumeration {
      enum "single-active" {
        value 1;
        description
          "Single Active";
      }
      enum "port-active" {
        value 2;
        description
          "Port Active";
      }
      enum "single-flow-active" {
        value 3;
        description
          "Single Flow Active";
      }
      enum "all-active" {
        value 4;
        description
          "All Active";
      }
    }
    description
      "Ethernet segment load balance";
  }

  typedef Mpls-signaling-protocol {
    type enumeration {
      enum "none" {
        value 1;
        description
          "No signaling";
      }
      enum "ldp" {
        value 4;
        description
          "LDP";
      }
    }
    description
      "Mpls signaling protocol";
  }

  typedef Erpaps {
    type enumeration {
      enum "interface" {
        value 1;
        description
          "ERP APS type interface";
      }
      enum "bridge-domain" {
        value 2;
        description
          "ERP APS type bridge domain";
      }
      enum "xconnect" {
        value 3;
        description
          "ERP APS type xconnect";
      }
      enum "none" {
        value 4;
        description
          "ERP APS type none";
      }
    }
    description
      "Erpaps";
  }

  typedef Mac-secure-action {
    type enumeration {
      enum "restrict" {
        value 1;
        description
          "MAC Secure Action Restrict";
      }
      enum "none" {
        value 2;
        description
          "No Action";
      }
      enum "shutdown" {
        value 3;
        description
          "MAC Secure Action Shutdown";
      }
    }
    description
      "Mac secure action";
  }

  typedef Erp-port {
    type enumeration {
      enum "none" {
        value 1;
        description
          "ERP port type none";
      }
      enum "virtual" {
        value 2;
        description
          "ERP port type virtual";
      }
      enum "interface" {
        value 3;
        description
          "ERP port type interface";
      }
    }
    description
      "Erp port";
  }

  typedef Resync-threshold-range {
    type uint32 {
      range "5..65535";
    }
    description
      "Resync threshold range";
  }

  typedef Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef Backup-disable {
    type enumeration {
      enum "never" {
        value 0;
        description
          "Never";
      }
      enum "delay" {
        value 1;
        description
          "Delay seconds";
      }
    }
    description
      "Backup disable";
  }

  typedef Time-to-live-range {
    type uint32 {
      range "1..255";
    }
    description
      "Time to live range";
  }

  typedef Multicast-p2mp-transport {
    type string {
      pattern '(RSVP_TE)';
    }
    description
      "RSVP_TE:RSVP-TE Transport";
  }

  typedef Transport-mode {
    type enumeration {
      enum "ethernet" {
        value 1;
        description
          "Ethernet port mode";
      }
      enum "vlan" {
        value 2;
        description
          "Vlan tagged mode";
      }
      enum "vlan-passthrough" {
        value 3;
        description
          "Vlan tagged passthrough mode";
      }
    }
    description
      "Transport mode";
  }

  typedef Flow-label-tlv-code {
    type enumeration {
      enum "17" {
        value 4;
        description
          "Set Flow Label Legacy TLV code (DEPRECATED)";
      }
      enum "disable" {
        value 8;
        description
          "Disable Sending Flow Label Legacy TLV";
      }
    }
    description
      "Flow label tlv code";
  }

  typedef Bgp-route-target {
    type enumeration {
      enum "no-stitching" {
        value 0;
        description
          "RT is default type";
      }
      enum "stitching" {
        value 1;
        description
          "RT is for stitching (Golf-L2) (DEPRECATED)";
      }
    }
    description
      "Bgp route target";
  }

  typedef Pseudowire-acid-range {
    type uint32 {
      range "1..4294967295";
    }
    description
      "Pseudowire acid range";
  }

  typedef Pseudowire-id-range {
    type uint32 {
      range "1..4294967295";
    }
    description
      "Pseudowire id range";
  }

  typedef Interface-profile {
    type enumeration {
      enum "snoop" {
        value 1;
        description
          "Set the snooping";
      }
      enum "dhcp-protocol" {
        value 2;
        description
          "disable DHCP protocol";
      }
    }
    description
      "Interface profile";
  }

  typedef Ethernet-segment-identifier {
    type enumeration {
      enum "type0" {
        value 0;
        description
          "ESI type 0";
      }
      enum "legacy" {
        value 128;
        description
          "Legacy ESI type";
      }
      enum "override" {
        value 129;
        description
          "Override ESI type";
      }
    }
    description
      "Ethernet segment identifier";
  }

  typedef Rpl-role {
    type enumeration {
      enum "owner" {
        value 1;
        description
          "ERP RPL owner";
      }
      enum "neighbor" {
        value 2;
        description
          "ERP RPL neighbor";
      }
      enum "next-neighbor" {
        value 3;
        description
          "ERP RPL next neighbor";
      }
    }
    description
      "Rpl role";
  }

  typedef Pw-switching-point-tlv {
    type enumeration {
      enum "hide" {
        value 2;
        description
          "Hide TLV";
      }
    }
    description
      "Pw switching point tlv";
  }

  typedef Erpaps-level-range {
    type uint32 {
      range "0..7";
    }
    description
      "Erpaps level range";
  }

  typedef Evpn-esi-type-range {
    type uint32 {
      range "1";
    }
    description
      "Evpn esi type range";
  }

  typedef Storm-control {
    type enumeration {
      enum "unicast" {
        value 1;
        description
          "Unknown-unicast Storm Control";
      }
      enum "multicast" {
        value 2;
        description
          "Multicast Storm Control";
      }
      enum "broadcast" {
        value 4;
        description
          "Broadcast Storm Control";
      }
    }
    description
      "Storm control";
  }

  typedef L2tp-session-id-range {
    type uint32 {
      range "1..65535";
    }
    description
      "L2tp session id range";
  }

  typedef Ethernet-segment-service-carving {
    type enumeration {
      enum "mod-n" {
        value 0;
        description
          "MOD N";
      }
      enum "manual" {
        value 1;
        description
          "Manual";
      }
      enum "hrw" {
        value 2;
        description
          "HRW";
      }
      enum "pref-df" {
        value 3;
        description
          "PrefDF";
      }
    }
    description
      "Ethernet segment service carving";
  }

  typedef Mac-learn {
    type enumeration {
      enum "default-learning" {
        value 0;
        description
          "Mac Learning";
      }
      enum "enable-learning" {
        value 1;
        description
          "Enable Learning";
      }
      enum "disable-learning" {
        value 2;
        description
          "Disable Learning";
      }
    }
    description
      "Mac learn";
  }

  typedef L2tpv3-sequencing {
    type enumeration {
      enum "off" {
        value 0;
        description
          "Sequencing is off";
      }
      enum "both" {
        value 4;
        description
          "Sequencing on both transmit and receive side";
      }
    }
    description
      "L2tpv3 sequencing";
  }

  typedef Veid-range {
    type uint32 {
      range "1..16384";
    }
    description
      "Veid range";
  }

  typedef Load-balance {
    type enumeration {
      enum "source-dest-mac" {
        value 1;
        description
          "Source and Destination MAC hashing";
      }
      enum "source-dest-ip" {
        value 2;
        description
          "Source and Destination IP hashing";
      }
      enum "pseudowire-label" {
        value 4;
        description
          "PW Label hashing";
      }
    }
    description
      "Load balance";
  }

  typedef L2tp-signaling-protocol {
    type enumeration {
      enum "none" {
        value 1;
        description
          "No signaling";
      }
      enum "l2tpv3" {
        value 2;
        description
          "L2TPv3";
      }
    }
    description
      "L2tp signaling protocol";
  }

  typedef Bdmac-learn {
    type enumeration {
      enum "disable-learning" {
        value 2;
        description
          "Disable Learning";
      }
    }
    description
      "Bdmac learn";
  }

  typedef L2mc-src-traffic-enabled {
    type enumeration {
      enum "l2mc-none" {
        value 0;
        description
          "NONE";
      }
      enum "l2mc-ipv4" {
        value 1;
        description
          "Multicast Source - IPv4";
      }
      enum "l2mc-ipv6" {
        value 2;
        description
          "Multicast Source - IPv6";
      }
      enum "l2mc-ipv4-ipv6" {
        value 3;
        description
          "Multicast Source - IPv4 IPv6";
      }
    }
    description
      "L2mc src traffic enabled";
  }

  typedef L2vpn-verification {
    type enumeration {
      enum "enable" {
        value 1;
        description
          "enable verification";
      }
      enum "disable" {
        value 2;
        description
          "disable verification";
      }
    }
    description
      "L2vpn verification";
  }

  typedef Max-path-mtu-range {
    type uint32 {
      range "68..65535";
    }
    description
      "Max path mtu range";
  }

  typedef Interface-traffic-flood {
    type enumeration {
      enum "traffic-flooding" {
        value 0;
        description
          "Traffic flooding";
      }
      enum "enable-flooding" {
        value 1;
        description
          "Enable Flooding";
      }
      enum "disable-flooding" {
        value 2;
        description
          "Disable flooding";
      }
    }
    description
      "Interface traffic flood";
  }

  typedef Pbbvid-range {
    type uint32 {
      range "1..4094";
    }
    description
      "Pbbvid range";
  }

  typedef L2tp-cookie-value-range {
    type uint32 {
      range "0..4294967295";
    }
    description
      "L2tp cookie value range";
  }

  typedef L2-encapsulation {
    type enumeration {
      enum "vlan" {
        value 4;
        description
          "Vlan tagged mode";
      }
      enum "ethernet" {
        value 5;
        description
          "Ethernet port mode";
      }
    }
    description
      "L2 encapsulation";
  }

  typedef L2vpn-logging {
    type enumeration {
      enum "enable" {
        value 1;
        description
          "enable logging";
      }
      enum "disable" {
        value 2;
        description
          "disable logging";
      }
    }
    description
      "L2vpn logging";
  }

  typedef Mac-aging-range {
    type uint32 {
      range "300..30000";
    }
    description
      "Mac aging range";
  }

  typedef Vpls-id-as-index {
    type uint32 {
      range "0..4294967295";
    }
    description
      "Vpls id as index";
  }

  typedef Pseudowire-gbl-id-range {
    type uint32 {
      range "1..4294967295";
    }
    description
      "Pseudowire gbl id range";
  }

  typedef Rdas-index {
    type uint32 {
      range "0..4294967295";
    }
    description
      "Rdas index";
  }

  typedef Mac-flush-mode {
    type enumeration {
      enum "mvrp" {
        value 1;
        description
          "MVRP MAC Flushing";
      }
    }
    description
      "Mac flush mode";
  }

  typedef L2tp-cookie-size {
    type enumeration {
      enum "zero" {
        value 0;
        description
          "Cookie size is zero bytes";
      }
      enum "four" {
        value 4;
        description
          "Cookie size is four bytes";
      }
      enum "eight" {
        value 8;
        description
          "Cookie size is eight bytes";
      }
    }
    description
      "L2tp cookie size";
  }

  typedef Mpls-sequencing {
    type enumeration {
      enum "off" {
        value 0;
        description
          "Sequencing is off";
      }
      enum "transmit" {
        value 1;
        description
          "Sequencing on transmit side";
      }
      enum "receive" {
        value 2;
        description
          "Sequencing on receive side";
      }
      enum "both" {
        value 4;
        description
          "Sequencing on both transmit and receive side";
      }
    }
    description
      "Mpls sequencing";
  }

  typedef Erp-instance-range {
    type uint32 {
      range "1..2";
    }
    description
      "Erp instance range";
  }

  typedef Pw-redundancy-initial-delay-range {
    type uint32 {
      range "0..120";
    }
    description
      "Pw redundancy initial delay range";
  }

  typedef Vpls-id-as-range {
    type uint32 {
      range "1..65535";
    }
    description
      "Vpls id as range";
  }

  typedef Rdas-range {
    type uint32 {
      range "1..4294967295";
    }
    description
      "Rdas range";
  }

  typedef Ethernet-segment-service-carving-mcast {
    type enumeration {
      enum "disabled" {
        value 0;
        description
          "Disabled";
      }
      enum "hrw-s-g" {
        value 1;
        description
          "HRW S G";
      }
      enum "hrw-g" {
        value 2;
        description
          "HRW G";
      }
    }
    description
      "Ethernet segment service carving mcast";
  }

  typedef Bridge-bd-mtu-range {
    type uint32 {
      range "46..65535";
    }
    description
      "Bridge bd mtu range";
  }

  typedef Backup-disable-delay-range {
    type uint32 {
      range "0..180";
    }
    description
      "Backup disable delay range";
  }

  typedef Storm-control-kbps-range {
    type uint32 {
      range "64..1280000";
    }
    description
      "Storm control kbps range";
  }

  typedef Mac-limit-action {
    type enumeration {
      enum "none" {
        value 0;
        description
          "No action";
      }
      enum "flood" {
        value 1;
        description
          "Flood Mac Limit Action";
      }
      enum "no-flood" {
        value 2;
        description
          "NoFlood Mac Limit Action";
      }
      enum "shutdown" {
        value 3;
        description
          "Shutdown Mac Limit Action";
      }
    }
    description
      "Mac limit action";
  }

  typedef Erp-port1 {
    type enumeration {
      enum "port0" {
        value 0;
        description
          "ERP main port 0";
      }
      enum "port1" {
        value 1;
        description
          "ERP main port 1";
      }
    }
    description
      "Erp port1";
  }

  typedef Mac-notification {
    type enumeration {
      enum "no-notif" {
        value 0;
        description
          "No_Notification Trap";
      }
      enum "syslog" {
        value 1;
        description
          "syslog message";
      }
      enum "trap" {
        value 2;
        description
          "Snmp Trap";
      }
      enum "syslog-snmp" {
        value 3;
        description
          "Syslog_snmp Trap";
      }
    }
    description
      "Mac notification";
  }

  typedef Control-word {
    type enumeration {
      enum "enable" {
        value 1;
        description
          "Enable control word";
      }
      enum "disable" {
        value 2;
        description
          "Disable control word";
      }
    }
    description
      "Control word";
  }

  typedef Preferred-nexthop-mode {
    type enumeration {
      enum "preferred-nexthop-lowest-ip" {
        value 1;
        description
          "Lowest IP Preferred";
      }
      enum "preferred-nexthop-highest-ip" {
        value 2;
        description
          "Highest IP Preferred";
      }
      enum "preferred-nexthop-modulo" {
        value 3;
        description
          "Modulo of nexthops Preferred";
      }
    }
    description
      "Preferred nexthop mode";
  }

  typedef Bgp-route-distinguisher {
    type enumeration {
      enum "auto" {
        value 1;
        description
          "RD automatically assigned";
      }
      enum "two-byte-as" {
        value 2;
        description
          "RD in 2 byte AS:nn format";
      }
      enum "four-byte-as" {
        value 3;
        description
          "RD in 4 byte AS:nn format";
      }
      enum "ipv4-address" {
        value 4;
        description
          "RD in IpV4address";
      }
    }
    description
      "Bgp route distinguisher";
  }

  typedef Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  typedef Evpn-group-id-range {
    type uint32 {
      range "1..4294967295";
    }
    description
      "Evpn group id range";
  }

  typedef Mac-limit-threshold-range {
    type uint32 {
      range "1..100";
    }
    description
      "Mac limit threshold range";
  }

  typedef Vedge-range {
    type uint32 {
      range "11..100";
    }
    description
      "Vedge range";
  }

  typedef Vpnid-range {
    type uint32 {
      range "1..4294967295";
    }
    description
      "Vpnid range";
  }

  typedef Ldp-vpls-id {
    type enumeration {
      enum "two-byte-as" {
        value 10;
        description
          "VPLS-ID in 2 byte AS:nn format";
      }
      enum "ipv4-address" {
        value 266;
        description
          "VPLS-ID in IPv4 IP:nn format";
      }
    }
    description
      "Ldp vpls id";
  }

  typedef Ce-id-range {
    type uint32 {
      range "1..16384";
    }
    description
      "Ce id range";
  }

  typedef Mac-aging {
    type enumeration {
      enum "absolute" {
        value 1;
        description
          "Absolute aging type";
      }
      enum "inactivity" {
        value 2;
        description
          "Inactivity aging type";
      }
    }
    description
      "Mac aging";
  }

  typedef Mac-limit-range {
    type uint32 {
      range "0..4294967295";
    }
    description
      "Mac limit range";
  }

  typedef Pbbisid-range {
    type uint32 {
      range "256..16777214";
    }
    description
      "Pbbisid range";
  }

  typedef Type-of-service-range {
    type uint32 {
      range "0..255";
    }
    description
      "Type of service range";
  }

  typedef Flow-label-load-balance {
    type enumeration {
      enum "off" {
        value 0;
        description
          "Flow Label load balance is off";
      }
      enum "receive" {
        value 1;
        description
          "Delete Flow Label on receive side";
      }
      enum "transmit" {
        value 2;
        description
          "Insert Flow Label on transmit side";
      }
      enum "both" {
        value 3;
        description
          "Insert/Delete Flow Label on transmit/receive
           side";
      }
    }
    description
      "Flow label load balance";
  }

  grouping ncs_template_STORM-CONTROL-UNIT {
    description
      "Common node of bd-storm-control,
       bdac-storm-control-type, bdpw-storm-control-type";
    container storm-control-unit {
      // NCS drop must statement
      description
        "Specify units for Storm Control Configuration";
      leaf kbits-per-sec {
        type ncs_template_Storm-control-kbps-range;
        units "kbit/s";
        description
          "Kilobits Per Second, PktsPerSec and KbitsPerSec
           cannot be configured together";
      }
      leaf pkts-per-sec {
        type ncs_template_Storm-control-pps-range;
        units "packet/s";
        description
          "Packets Per Second, PktsPerSec and KbitsPerSec
           cannot be configured together";
      }
    }
  }

  grouping ncs_template_MANUAL-SERVICE-CARVING {
    description
      "Common node of ethernet-segment,
       evpn-virtual-ethernet-segment";
    container manual-service-carving {
      description
        "Enter Manual service carving configuration
         submode";
      container service-list {
        description
          "Manual service carving primary,secondary lists";
        leaf primary {
          type string;
          description
            "Primary services list";
        }
        leaf secondary {
          type string;
          description
            "Secondary services list";
        }
      }
      leaf enable {
        type empty;
        description
          "Enable Manual service carving";
      }
    }
  }

  grouping ncs_template_SERVICE-CARVING-MCAST-TYPE {
    description
      "Common node of ethernet-segment,
       evpn-virtual-ethernet-segment";
    leaf service-carving-mcast-type {
      type ncs_template_Ethernet-segment-service-carving-mcast;
      description
        "Ethernet-Segment Service Carving multicast mode";
    }
  }

  grouping ncs_template_ACTION {
    description
      "Common node of mac-secure, pbb-edge-mac-secure,
       interface-mac-secure, pseudowire-mac-secure";
    leaf action {
      type ncs_template_Mac-secure-action;
      description
        "MAC secure enforcement action";
    }
  }

  grouping ncs_template_EVPN-ROUTE-DISTINGUISHER {
    description
      "Common node of evpn-bgp-auto-discovery,
       evpn-instance-bgp-auto-discovery, pw-routing-bgp";
    container evpn-route-distinguisher {
      description
        "Route Distinguisher";
      leaf type {
        type ncs_template_Bgp-route-distinguisher;
        description
          "Router Distinguisher Type";
      }
      leaf as {
        // NCS drop when statement
        type ncs_template_Rdas-range;
        description
          "Two byte or 4 byte AS number";
      }
      leaf as-index {
        // NCS drop when statement
        type ncs_template_Rdas-index;
        description
          "AS:nn (hex or decimal format)";
      }
      leaf address {
        // NCS drop when statement
        type string;
        description
          "IPV4 address";
      }
      leaf addr-index {
        // NCS drop when statement
        type ncs_template_Rd-addr-index;
        description
          "Addr index";
      }
    }
  }

  grouping ncs_template_EVPN-VIRTUAL-ETHERNET-SEGMENT {
    description
      "Common node of evpn-virtual-access-pw,
       evpn-virtual-access-vfi";
    container evpn-virtual-ethernet-segment {
      description
        "Enter Ethernet Segment configuration submode";
      leaf enable {
        type empty;
        description
          "Enable Ethernet Segment";
      }
      uses ncs_template_SERVICE-CARVING-MCAST-TYPE;
      uses ncs_template_ES-IMPORT-ROUTE-TARGET;
      uses ncs_template_SERVICE-CARVING-TYPE;
      uses ncs_template_IDENTIFIER;
      uses ncs_template_PREFERENCE-BASED-SERVICE-CARVING;
      uses ncs_template_MANUAL-SERVICE-CARVING;
    }
  }

  grouping ncs_template_LOGGING {
    description
      "Common node of pbb-edge-mac-secure,
       interface-mac-secure, pseudowire-mac-secure";
    leaf logging {
      type ncs_template_L2vpn-logging;
      description
        "MAC Secure Logging";
    }
  }

  grouping ncs_template_ES-IMPORT-ROUTE-TARGET {
    description
      "Common node of ethernet-segment,
       evpn-virtual-ethernet-segment";
    leaf es-import-route-target {
      type string;
      description
        "ES-Import Route Target";
    }
  }

  grouping ncs_template_SERVICE-CARVING-TYPE {
    description
      "Common node of ethernet-segment,
       evpn-virtual-ethernet-segment";
    leaf service-carving-type {
      type ncs_template_Ethernet-segment-service-carving;
      description
        "Ethernet-Segment Service Carving mode";
    }
  }

  grouping ncs_template_IDENTIFIER {
    description
      "Common node of ethernet-segment,
       evpn-virtual-ethernet-segment";
    container identifier {
      presence "Indicates a identifier node is configured.";
      description
        "Ethernet segment identifier";
      leaf bytes01 {
        type xr:ncs_template_Hex-integer;
        // NCS drop mandatory statement
        description
          "Type 0's 1st Byte or Type Byte and 1st Byte";
      }
      leaf bytes23 {
        type xr:ncs_template_Hex-integer;
        units "byte";
        // NCS drop mandatory statement
        description
          "2nd and 3rd Bytes";
      }
      leaf bytes45 {
        type xr:ncs_template_Hex-integer;
        units "byte";
        // NCS drop mandatory statement
        description
          "4th and 5th Bytes";
      }
      leaf bytes67 {
        type xr:ncs_template_Hex-integer;
        units "byte";
        // NCS drop mandatory statement
        description
          "6th and 7th Bytes";
      }
      leaf bytes89 {
        type xr:ncs_template_Hex-integer;
        units "byte";
        // NCS drop mandatory statement
        description
          "8th and 9th Bytes";
      }
      leaf type {
        type ncs_template_Ethernet-segment-identifier;
        // NCS drop mandatory statement
        description
          "Ethernet segment identifier type";
      }
    }
  }

  grouping ncs_template_PREFERENCE-BASED-SERVICE-CARVING {
    description
      "Common node of ethernet-segment,
       evpn-virtual-ethernet-segment";
    container preference-based-service-carving {
      description
        "Preference-Based DF Election Configuration
         Options";
      leaf weight {
        type string;
        description
          "Preference DF weight. For Access-Driven DF, use
           weights of at most 32767 or less.";
      }
      leaf enable {
        type empty;
        description
          "Enable Preference Based Service Carving";
      }
      leaf access-driven {
        type empty;
        description
          "Enable Access-Driven DF Election";
      }
    }
  }

  grouping ncs_template_BRIDGE-DOMAIN-TABLE {
    description
      "Common node of bridge-domain-group, vlan-switch";
    container bridge-domains {
      description
        "List of Bridge Domain";
      list bridge-domain {
        // NCS patched for predictable order
        ordered-by user;
        key "name";
        description
          "bridge domain";
        container bd-storm-controls {
          description
            "Storm Control";
          list bd-storm-control {
            // NCS patched for predictable order
            ordered-by user;
            // NCS drop must statement
            key "sctype";
            description
              "Storm Control Type";
            leaf sctype {
              type ncs_template_Storm-control;
              description
                "Storm Control Type";
            }
            uses ncs_template_STORM-CONTROL-UNIT;
          }
        }
        container member-vnis {
          description
            "Bridge Domain VxLAN Network Identifier Table";
          list member-vni {
            // NCS patched for predictable order
            ordered-by user;
            key "vni";
            description
              "Bridge Domain Member VxLAN Network Identifier";
            container member-vni-static-mac-addresses {
              description
                "Static Mac Address Table";
              list member-vni-static-mac-address {
                // NCS patched for predictable order
                ordered-by user;
                key "mac-address";
                description
                  "Static Mac Address Configuration";
                leaf next-hop-ip {
                  type string;
                  description
                    "Enable Static Mac Address Configuration";
                }
                leaf mac-address {
                  type string;
                  description
                    "Static MAC address";
                }
              }
            }
            leaf vni {
              type string;
              description
                "VxLAN Network Identifier number";
            }
          }
        }
        container bridge-domain-mac {
          description
            "MAC configuration commands";
          container bd-mac-limit {
            description
              "MAC-Limit configuration commands";
            leaf bd-mac-limit-action {
              type ncs_template_Mac-limit-action;
              description
                "MAC address limit enforcement action";
            }
            leaf bd-mac-limit-notif {
              type ncs_template_Mac-notification;
              description
                "Mac Address Limit Notification";
            }
            leaf bd-mac-limit-max {
              type ncs_template_Mac-limit-range;
              description
                "Number of MAC addresses after which MAC
                 limit action is taken";
            }
          }
          container bd-mac-filters {
            description
              "Filter Mac Address";
            list bd-mac-filter {
              // NCS patched for predictable order
              ordered-by user;
              key "address";
              description
                "Static MAC address";
              leaf drop {
                type empty;
                description
                  "MAC address for filtering";
              }
              leaf address {
                type string;
                description
                  "Static MAC address";
              }
            }
          }
          container mac-secure {
            description
              "MAC Secure";
            leaf logging {
              type empty;
              description
                "MAC Secure Logging";
            }
            leaf enable {
              type empty;
              description
                "Enable MAC Secure";
            }
            leaf threshold {
              type empty;
              description
                "MAC Secure Threshold";
            }
            uses ncs_template_ACTION;
            uses ncs_template_SHUTDOWN-RECOVERY-TIMER;
          }
          container bd-mac-aging {
            description
              "MAC-Aging configuration commands";
            leaf bd-mac-aging-type {
              type ncs_template_Mac-aging;
              description
                "MAC address aging type";
            }
            leaf bd-mac-aging-time {
              type ncs_template_Mac-aging-range;
              description
                "Mac Aging Time";
            }
          }
          leaf bd-mac-withdraw-relay {
            type empty;
            description
              "Mac withdraw sent from access PW to access PW";
          }
          leaf bd-mac-withdraw-access-pw-disable {
            type empty;
            description
              "MAC withdraw on Access PW";
          }
          leaf bd-mac-port-down-flush {
            type empty;
            description
              "Disable MAC Flush when Port goes Down";
          }
          leaf bd-mac-withdraw {
            type empty;
            description
              "Disable Mac Withdraw";
          }
          leaf bd-mac-withdraw-behavior {
            type ncs_template_Mac-withdraw-behavior;
            description
              "MAC withdraw sent on bridge port down";
          }
          leaf bd-mac-learn {
            type ncs_template_Bdmac-learn;
            description
              "Mac Learning Type";
          }
        }
        container nv-satellite {
          description
            "nV Satellite";
          leaf offload-ipv4-multicast-enable {
            type empty;
            description
              "Enable IPv4 Multicast Offload to Satellite
               Nodes";
          }
          leaf enable {
            type empty;
            description
              "Enable nV Satellite Settings";
          }
        }
        container bridge-domain-pbb {
          description
            "Bridge Domain PBB";
          container pbb-edges {
            description
              "PBB Edge";
            list pbb-edge {
              // NCS patched for predictable order
              ordered-by user;
              key "isid core-bd-name";
              description
                "Configure BD as PBB Edge with ISID and
                 associated PBB Core BD";
              container pbb-edge-split-horizon-group {
                description
                  "Split Horizon Group";
                leaf disable {
                  type empty;
                  description
                    "Disable split horizon group";
                }
              }
              container pbb-static-mac-mappings {
                description
                  "PBB Static Mac Address Mapping Table";
                list pbb-static-mac-mapping {
                  // NCS patched for predictable order
                  ordered-by user;
                  key "address";
                  description
                    "PBB Static Mac Address Mapping
                     Configuration";
                  leaf pbb-static-mac-mapping-bmac {
                    type string;
                    description
                      "Static backbone MAC address to map with";
                  }
                  leaf address {
                    type string;
                    description
                      "Static MAC address";
                  }
                }
              }
              container pbb-edge-dhcp-profile {
                description
                  "Attach a DHCP profile";
                leaf profile-id {
                  type ncs_template_Interface-profile;
                  description
                    "Set the snooping profile";
                }
                leaf dhcp-snooping-id {
                  type string;
                  description
                    "Disable DHCP snooping";
                }
              }
              container pbb-edge-mac {
                description
                  "MAC configuration commands";
                container pbb-edge-mac-limit {
                  description
                    "MAC-Limit configuration commands";
                  leaf pbb-edge-mac-limit-action {
                    type ncs_template_Mac-limit-action;
                    description
                      "MAC address limit enforcement action";
                  }
                  leaf pbb-edge-mac-limit-max {
                    type ncs_template_Mac-limit-range;
                    description
                      "Number of MAC addresses after which MAC
                       limit action is taken";
                  }
                  leaf pbb-edge-mac-limit-notif {
                    type ncs_template_Mac-notification;
                    description
                      "MAC address limit notification action";
                  }
                }
                container pbb-edge-mac-aging {
                  description
                    "MAC-Aging configuration commands";
                  leaf pbb-edge-mac-aging-type {
                    type ncs_template_Mac-aging;
                    description
                      "MAC address aging type";
                  }
                  leaf pbb-edge-mac-aging-time {
                    type ncs_template_Mac-aging-range;
                    description
                      "Mac Aging Time";
                  }
                }
                container pbb-edge-mac-secure {
                  description
                    "MAC Secure";
                  leaf enable {
                    type empty;
                    description
                      "Enable MAC Secure";
                  }
                  leaf accept-shutdown {
                    type empty;
                    description
                      "Accept Virtual instance port to be
                       shutdown on mac violation";
                  }
                  uses ncs_template_LOGGING;
                  uses ncs_template_DISABLE;
                  uses ncs_template_ACTION;
                }
                leaf pbb-edge-mac-learning {
                  type ncs_template_Mac-learn;
                  description
                    "Enable Mac Learning";
                }
              }
              leaf pbb-edge-igmp-profile {
                type xr:ncs_template_Cisco-ios-xr-string;
                description
                  "Attach a IGMP Snooping profile";
              }
              leaf unknown-unicast-bmac {
                type string;
                description
                  "Configure Unknown Unicast BMAC address for
                   PBB Edge Port";
              }
              leaf isid {
                type ncs_template_Pbbisid-range;
                description
                  "ISID";
              }
              leaf core-bd-name {
                type xr:ncs_template_Cisco-ios-xr-string;
                description
                  "Core BD Name";
              }
            }
          }
          container pbb-core {
            description
              "PBB Core";
            container pbb-core-mac {
              description
                "MAC configuration commands";
              container pbb-core-mac-aging {
                description
                  "MAC-Aging configuration commands";
                leaf pbb-core-mac-aging-type {
                  type ncs_template_Mac-aging;
                  description
                    "MAC address aging type";
                }
                leaf pbb-core-mac-aging-time {
                  type ncs_template_Mac-aging-range;
                  description
                    "Mac Aging Time";
                }
              }
              container pbb-core-mac-limit {
                description
                  "MAC-Limit configuration commands";
                leaf pbb-core-mac-limit-max {
                  type ncs_template_Mac-limit-range;
                  description
                    "Number of MAC addresses after which MAC
                     limit action is taken";
                }
                leaf pbb-core-mac-limit-notif {
                  type ncs_template_Mac-notification;
                  description
                    "MAC address limit notification action";
                }
                leaf pbb-core-mac-limit-action {
                  type ncs_template_Mac-limit-action;
                  description
                    "MAC address limit enforcement action";
                }
              }
              leaf pbb-core-mac-learning {
                type ncs_template_Mac-learn;
                description
                  "Enable Mac Learning";
              }
            }
            container pbb-core-evis {
              description
                "PBB Core EVI Table";
              list pbb-core-evi {
                // NCS patched for predictable order
                ordered-by user;
                key "eviid";
                description
                  "PBB Core EVI";
                leaf eviid {
                  type ncs_template_Vpnid-range;
                  description
                    "Ethernet VPN ID";
                }
              }
            }
            container pbb-core-dhcp-profile {
              description
                "Attach a DHCP profile";
              leaf profile-id {
                type ncs_template_Interface-profile;
                description
                  "Set the snooping profile";
              }
              leaf dhcp-snooping-id {
                type string;
                description
                  "Disable DHCP snooping";
              }
            }
            leaf pbb-core-mmrp-flood-optimization {
              type empty;
              description
                "Enabling MMRP PBB-VPLS Flood Optimization";
            }
            leaf vlan-id {
              type ncs_template_Pbbvid-range;
              description
                "VLAN ID to push";
            }
            leaf pbb-core-igmp-profile {
              type xr:ncs_template_Cisco-ios-xr-string;
              description
                "Attach a IGMP Snooping profile";
            }
            leaf enable {
              type empty;
              description
                "Enable Bridge Domain PBB Core Configuration";
            }
          }
        }
        container bridge-domain-evis {
          description
            "Bridge Domain EVI Table";
          list bridge-domain-evi {
            // NCS patched for predictable order
            ordered-by user;
            key "vpn-id";
            description
              "Bridge Domain MPLS EVPN";
            leaf vpn-id {
              type ncs_template_Evpnvpnid-range;
              description
                "MPLS Ethernet VPN-ID";
            }
          }
        }
        container access-vfis {
          description
            "Specify the access virtual forwarding
             interface name";
          list access-vfi {
            // NCS patched for predictable order
            ordered-by user;
            key "name";
            description
              "Name of the Acess Virtual Forwarding
               Interface";
            container access-vfi-pseudowires {
              description
                "List of pseudowires";
              list access-vfi-pseudowire {
                // NCS patched for predictable order
                ordered-by user;
                key "neighbor pseudowire-id";
                description
                  "Pseudowire configuration";
                container access-vfi-pseudowire-static-mac-addresses {
                  description
                    "Static Mac Address Table";
                  list access-vfi-pseudowire-static-mac-address {
                    // NCS patched for predictable order
                    ordered-by user;
                    key "address";
                    description
                      "Static Mac Address Configuration";
                    leaf address {
                      type string;
                      description
                        "Static MAC address";
                    }
                  }
                }
                leaf access-vfi-pw-class {
                  type xr:ncs_template_Cisco-ios-xr-string;
                  description
                    "Pseudowire class template name to use for
                     this pseudowire";
                }
                leaf neighbor {
                  type string;
                  description
                    "Neighbor IP address";
                }
                leaf pseudowire-id {
                  type ncs_template_Pseudowire-id-range;
                  description
                    "Pseudowire ID";
                }
              }
            }
            leaf access-vfi-shutdown {
              type empty;
              description
                "shutdown the AccessVfi";
            }
            leaf name {
              type xr:ncs_template_Cisco-ios-xr-string;
              description
                "Name of the AccessVirtual Forwarding
                 Interface";
            }
          }
        }
        container bd-pseudowires {
          description
            "List of pseudowires";
          list bd-pseudowire {
            // NCS patched for predictable order
            ordered-by user;
            key "neighbor pseudowire-id";
            description
              "Pseudowire configuration";
            container pseudowire-dai {
              description
                "Access Pseudowire Dynamic ARP Inspection";
              container pseudowire-dai-address-validation {
                description
                  "Address Validation";
                leaf ipv4-verification {
                  type ncs_template_L2vpn-verification;
                  description
                    "IPv4 Verification";
                }
                leaf destination-mac-verification {
                  type ncs_template_L2vpn-verification;
                  description
                    "Destination MAC Verification";
                }
                leaf source-mac-verification {
                  type ncs_template_L2vpn-verification;
                  description
                    "Source MAC Verification";
                }
              }
              leaf logging {
                type ncs_template_L2vpn-logging;
                description
                  "Logging Type";
              }
              leaf disable {
                type empty;
                description
                  "Disable Dynamic ARP Inspection";
              }
              leaf enable {
                type empty;
                description
                  "Enable Access Pseudowire Dynamic ARP
                   Inspection";
              }
            }
            container bdpw-storm-control-types {
              description
                "Storm Control";
              list bdpw-storm-control-type {
                // NCS patched for predictable order
                ordered-by user;
                // NCS drop must statement
                key "sctype";
                description
                  "Storm Control Type";
                leaf sctype {
                  type ncs_template_Storm-control;
                  description
                    "Storm Control Type";
                }
                uses ncs_template_STORM-CONTROL-UNIT;
              }
            }
            container pseudowire-profile {
              description
                "Attach a DHCP profile";
              leaf profile-id {
                type ncs_template_Interface-profile;
                description
                  "Set the snooping profile";
              }
              leaf dhcp-snooping-id {
                type string;
                description
                  "Disable DHCP snooping";
              }
            }
            container bd-pw-static-mac-addresses {
              description
                "Static Mac Address Table";
              list bd-pw-static-mac-address {
                // NCS patched for predictable order
                ordered-by user;
                key "address";
                description
                  "Static Mac Address Configuration";
                leaf address {
                  type string;
                  description
                    "Static MAC address";
                }
              }
            }
            container pseudowire-ip-source-guard {
              description
                "IP Source Guard";
              leaf logging {
                type ncs_template_L2vpn-logging;
                description
                  "Logging Type";
              }
              leaf disable {
                type empty;
                description
                  "Disable Dynamic IP source guard";
              }
              leaf enable {
                type empty;
                description
                  "Enable IP Source Guard";
              }
            }
            container pseudowire-mac {
              description
                "Bridge-domain Pseudowire MAC configuration
                 commands";
              container pseudowire-mac-secure {
                description
                  "MAC Secure";
                leaf enable {
                  type empty;
                  description
                    "Enable MAC Secure";
                }
                uses ncs_template_LOGGING;
                uses ncs_template_DISABLE;
                uses ncs_template_ACTION;
                uses ncs_template_SHUTDOWN-RECOVERY-TIMER;
              }
              container pseudowire-mac-aging {
                description
                  "MAC-Aging configuration commands";
                leaf pseudowire-mac-aging-type {
                  type ncs_template_Mac-aging;
                  description
                    "MAC address aging type";
                }
                leaf pseudowire-mac-aging-time {
                  type ncs_template_Mac-aging-range;
                  description
                    "MAC Aging Time";
                }
              }
              container pseudowire-mac-limit {
                description
                  "MAC-Limit configuration commands";
                leaf pseudowire-mac-limit-action {
                  type ncs_template_Mac-limit-action;
                  description
                    "Bridge Access Pseudowire MAC address limit
                     enforcement action";
                }
                leaf pseudowire-mac-limit-notif {
                  type ncs_template_Mac-notification;
                  description
                    "MAC address limit notification action in a
                     Bridge Access Pseudowire";
                }
                leaf pseudowire-mac-limit-max {
                  type ncs_template_Mac-limit-range;
                  description
                    "Number of MAC addresses on a Bridge Access
                     Pseudowire after which MAC limit action is
                     taken";
                }
              }
              leaf pseudowire-mac-port-down-flush {
                type ncs_template_Port-down-flush;
                description
                  "Enable/Disable MAC Flush When Port goes
                   down";
              }
              leaf enable {
                type empty;
                description
                  "Bridge-domain Pseudowire MAC configuration
                   mode";
              }
              leaf pseudowire-mac-learning {
                type ncs_template_Mac-learn;
                description
                  "Enable MAC Learning";
              }
            }
            container bd-pw-split-horizon {
              description
                "Split Horizon";
              container bd-pw-split-horizon-group {
                description
                  "Split Horizon Group";
                leaf enable {
                  type empty;
                  description
                    "Enable split horizon group";
                }
              }
            }
            container bd-pw-mpls-static-labels {
              description
                "MPLS static labels";
              leaf local-static-label {
                type ncs_template_Pseudowire-label-range;
                description
                  "Pseudowire local static label";
              }
              leaf remote-static-label {
                type ncs_template_Pseudowire-label-range;
                description
                  "Pseudowire remote static label";
              }
            }
            container bridge-domain-backup-pseudowires {
              description
                "List of pseudowires";
              list bridge-domain-backup-pseudowire {
                // NCS patched for predictable order
                ordered-by user;
                key "neighbor pseudowire-id";
                description
                  "Backup pseudowire configuration";
                leaf bridge-domain-backup-pw-class {
                  type xr:ncs_template_Cisco-ios-xr-string;
                  description
                    "PW class template name to use for this
                     pseudowire";
                }
                leaf neighbor {
                  type string;
                  description
                    "Neighbor IP address";
                }
                leaf pseudowire-id {
                  type ncs_template_Pseudowire-id-range;
                  description
                    "Pseudowire ID";
                }
              }
            }
            leaf pseudowire-mld-snoop {
              type xr:ncs_template_Cisco-ios-xr-string;
              description
                "Attach a MLD Snooping profile";
            }
            leaf pseudowire-igmp-snoop {
              type xr:ncs_template_Cisco-ios-xr-string;
              description
                "Attach a IGMP Snooping profile";
            }
            leaf pseudowire-flooding {
              type ncs_template_Interface-traffic-flood;
              description
                "Bridge-domain Pseudowire flooding";
            }
            leaf bd-pw-class {
              type xr:ncs_template_Cisco-ios-xr-string;
              description
                "PW class template name to use for this
                 pseudowire";
            }
            leaf pseudowire-flooding-unknown-unicast {
              type ncs_template_Interface-traffic-flood;
              description
                "Bridge-domain Pseudowire flooding Unknown
                 Unicast";
            }
            leaf neighbor {
              type string;
              description
                "Neighbor IP address";
            }
            leaf pseudowire-id {
              type ncs_template_Pseudowire-id-range;
              description
                "Pseudowire ID";
            }
          }
        }
        container vfis {
          description
            "Specify the virtual forwarding interface name";
          list vfi {
            // NCS patched for predictable order
            ordered-by user;
            key "name";
            description
              "Name of the Virtual Forwarding Interface";
            container multicast-p2mp {
              description
                "Enable Multicast P2MP in this VFI";
              container transports {
                description
                  "Multicast P2MP Transport";
                list transport {
                  // NCS patched for predictable order
                  ordered-by user;
                  key "transport-name";
                  description
                    "Multicast P2MP Transport Type";
                  leaf attribute-set-name {
                    type xr:ncs_template_Cisco-ios-xr-string;
                    description
                      "Multicast P2MP TE Attribute Set Name";
                  }
                  leaf transport-name {
                    type ncs_template_Multicast-p2mp-transport;
                    description
                      "Transport Type";
                  }
                }
              }
              container signalings {
                description
                  "Multicast P2MP Signaling Type";
                list signaling {
                  // NCS patched for predictable order
                  ordered-by user;
                  key "signaling-name";
                  description
                    "Multicast P2MP Signaling Type";
                  leaf signaling-name {
                    type ncs_template_Multicast-p2mp-signaling;
                    description
                      "Signaling Type";
                  }
                }
              }
              leaf enable {
                type empty;
                description
                  "Enable Autodiscovery P2MP";
              }
            }
            container vfi-pseudowires {
              description
                "List of pseudowires";
              list vfi-pseudowire {
                // NCS patched for predictable order
                ordered-by user;
                key "neighbor pseudowire-id";
                description
                  "Pseudowire configuration";
                container vfi-pw-dhcp-snoop {
                  description
                    "Attach a DHCP Snooping profile";
                  leaf profile-id {
                    type ncs_template_Interface-profile;
                    description
                      "Set the snooping profile";
                  }
                  leaf dhcp-snooping-id {
                    type string;
                    description
                      "Disable DHCP snooping";
                  }
                }
                container vfi-pw-mpls-static-labels {
                  description
                    "MPLS static labels";
                  leaf local-static-label {
                    type ncs_template_Pseudowire-label-range;
                    description
                      "Pseudowire local static label";
                  }
                  leaf remote-static-label {
                    type ncs_template_Pseudowire-label-range;
                    description
                      "Pseudowire remote static label";
                  }
                }
                container pseudowire-static-mac-addresses {
                  description
                    "Static Mac Address Table";
                  list pseudowire-static-mac-address {
                    // NCS patched for predictable order
                    ordered-by user;
                    key "address";
                    description
                      "Static Mac Address Configuration";
                    leaf address {
                      type string;
                      description
                        "Static MAC address";
                    }
                  }
                }
                leaf vfi-pw-class {
                  type xr:ncs_template_Cisco-ios-xr-string;
                  description
                    "PW class template name to use for this
                     pseudowire";
                }
                leaf vfi-pw-igmp-snoop {
                  type xr:ncs_template_Cisco-ios-xr-string;
                  description
                    "Attach a IGMP Snooping profile";
                }
                leaf vfi-pw-mld-snoop {
                  type xr:ncs_template_Cisco-ios-xr-string;
                  description
                    "Attach a MLD Snooping profile";
                }
                leaf neighbor {
                  type string;
                  description
                    "Neighbor IP address";
                }
                leaf pseudowire-id {
                  type ncs_template_Pseudowire-id-range;
                  description
                    "Pseudowire ID";
                }
              }
            }
            container bgp-auto-discovery {
              description
                "Enable Autodiscovery BGP in this VFI";
              container ldp-signaling-protocol {
                description
                  "Signaling Protocol LDP in this VFI
                   configuration";
                container vpls-id {
                  description
                    "VPLS ID";
                  leaf type {
                    type ncs_template_Ldp-vpls-id;
                    description
                      "VPLS-ID Type";
                  }
                  leaf as {
                    // NCS drop when statement
                    type ncs_template_Vpls-id-as-range;
                    description
                      "Two byte AS number";
                  }
                  leaf as-index {
                    // NCS drop when statement
                    type ncs_template_Vpls-id-as-index;
                    description
                      "AS index";
                  }
                  leaf address {
                    // NCS drop when statement
                    type string;
                    description
                      "IPV4 address";
                  }
                  leaf address-index {
                    // NCS drop when statement
                    type ncs_template_Vpls-id-addr-index;
                    description
                      "Address index";
                  }
                }
                container flow-label-load-balance {
                  description
                    "Enable Flow Label based load balancing";
                  leaf flow-label {
                    type ncs_template_Flow-label-load-balance;
                    description
                      "Flow Label load balance type";
                  }
                  leaf static {
                    type empty;
                    description
                      "Static Flow Label";
                  }
                }
                leaf enable {
                  type empty;
                  description
                    "Enable LDP as Signaling Protocol.Deletion
                     of this object also causes deletion of all
                     objects under LDPSignalingProtocol.";
                }
              }
              container bgp-route-policy {
                description
                  "Route policy";
                leaf export {
                  type string;
                  description
                    "Export route policy";
                }
              }
              container route-distinguisher {
                description
                  "Route Distinguisher";
                leaf type {
                  type ncs_template_Bgp-route-distinguisher;
                  description
                    "Router Distinguisher Type";
                }
                leaf as {
                  // NCS drop when statement
                  type ncs_template_Rdas-range;
                  description
                    "Two byte or 4 byte AS number";
                }
                leaf as-index {
                  // NCS drop when statement
                  type ncs_template_Rdas-index;
                  description
                    "AS:nn (hex or decimal format)";
                }
                leaf address {
                  // NCS drop when statement
                  type string;
                  description
                    "IPV4 address";
                }
                leaf addr-index {
                  // NCS drop when statement
                  type ncs_template_Rd-addr-index;
                  description
                    "Addr index";
                }
              }
              container bgp-signaling-protocol {
                description
                  "Enable Signaling Protocol BGP in this VFI";
                container flow-label-load-balance {
                  description
                    "Enable Flow Label based load balancing";
                  leaf flow-label {
                    type ncs_template_Flow-label-load-balance;
                    description
                      "Flow Label load balance type";
                  }
                  leaf static {
                    type empty;
                    description
                      "Static Flow Label";
                  }
                }
                leaf ve-range {
                  type ncs_template_Vedge-range;
                  description
                    "Local Virtual Edge Block Configurable
                     Range";
                }
                leaf veid {
                  type ncs_template_Veid-range;
                  description
                    "Local Virtual Edge Identifier";
                }
                leaf enable {
                  type empty;
                  description
                    "Enable BGP as Signaling Protocol";
                }
              }
              container route-targets {
                description
                  "Route Target";
                list route-target {
                  // NCS patched for predictable order
                  ordered-by user;
                  // NCS drop must statement
                  key "role format";
                  description
                    "Name of the Route Target";
                  leaf role {
                    type ncs_template_Bgp-route-target-role;
                    description
                      "Role of the router target type";
                  }
                  leaf format {
                    type ncs_template_Bgp-route-target-format;
                    description
                      "Format of the route target";
                  }
                  list two-byte-as-or-four-byte-as {
                    // NCS patched for predictable order
                    ordered-by user;
                    // NCS drop when statement
                    key "as as-index";
                    description
                      "two byte as or four byte as";
                    leaf as {
                      type ncs_template_Rdas-range;
                      description
                        "Two byte or 4 byte AS number";
                    }
                    leaf as-index {
                      type ncs_template_Rdas-index;
                      description
                        "AS:nn (hex or decimal format)";
                    }
                  }
                  list ipv4-address {
                    // NCS patched for predictable order
                    ordered-by user;
                    // NCS drop when statement
                    key "address addr-index";
                    description
                      "ipv4 address";
                    leaf address {
                      type string;
                      description
                        "IPV4 address";
                    }
                    leaf addr-index {
                      type ncs_template_Rd-addr-index;
                      description
                        "Addr index";
                    }
                  }
                }
              }
              leaf table-policy {
                type string;
                description
                  "Table Policy for installation of forwarding
                   data to L2FIB";
              }
              leaf ad-control-word {
                type empty;
                description
                  "Enable control-word for this VFI";
              }
              leaf enable {
                type empty;
                description
                  "Enable Autodiscovery BGP";
              }
            }
            leaf vfi-shutdown {
              type empty;
              description
                "Enabling Shutdown";
            }
            leaf vpnid {
              type ncs_template_Vpnid-range;
              description
                "VPN Identifier";
            }
            leaf name {
              type xr:ncs_template_Cisco-ios-xr-string;
              description
                "Name of the Virtual Forwarding Interface";
            }
          }
        }
        container bridge-domainvnis {
          description
            "Bridge Domain EVPN VxLAN Network Identifier
             Table";
          list bridge-domainvni {
            // NCS patched for predictable order
            ordered-by user;
            key "vpn-id";
            description
              "Bridge Domain VxLAN EVPN";
            leaf vpn-id {
              type string;
              description
                "VxLAN Ethernet VPN-ID";
            }
          }
        }
        container bd-attachment-circuits {
          description
            "Attachment Circuit table";
          list bd-attachment-circuit {
            // NCS patched for predictable order
            ordered-by user;
            key "name";
            description
              "Name of the Attachment Circuit";
            container interface-ip-source-guard {
              description
                "IP Source Guard";
              leaf logging {
                type ncs_template_L2vpn-logging;
                description
                  "Logging Type";
              }
              leaf disable {
                type empty;
                description
                  "Disable L2 Interface Dynamic IP source
                   guard";
              }
              leaf enable {
                type empty;
                description
                  "Enable IP Source Guard";
              }
            }
            container interface-dai {
              description
                "L2 Interface Dynamic ARP Inspection";
              container interface-dai-address-validation {
                description
                  "Address Validation";
                leaf ipv4-verification {
                  type ncs_template_L2vpn-verification;
                  description
                    "IPv4 Verification";
                }
                leaf destination-mac-verification {
                  type ncs_template_L2vpn-verification;
                  description
                    "Destination MAC Verification";
                }
                leaf source-mac-verification {
                  type ncs_template_L2vpn-verification;
                  description
                    "Source MAC Verification";
                }
                leaf enable {
                  type empty;
                  description
                    "Enable Address Validation";
                }
              }
              leaf logging {
                type ncs_template_L2vpn-logging;
                description
                  "Logging Type";
              }
              leaf disable {
                type empty;
                description
                  "Disable L2 Interface Dynamic ARP Inspection";
              }
              leaf enable {
                type empty;
                description
                  "Enable L2 Interface Dynamic ARP Inspection";
              }
            }
            container interface-profile {
              description
                "Attach a DHCP profile";
              leaf profile-id {
                type ncs_template_Interface-profile;
                description
                  "Set the snooping profile";
              }
              leaf dhcp-snooping-id {
                type string;
                description
                  "Disable DHCP snooping";
              }
            }
            container bdac-storm-control-types {
              description
                "Storm Control";
              list bdac-storm-control-type {
                // NCS patched for predictable order
                ordered-by user;
                // NCS drop must statement
                key "sctype";
                description
                  "Storm Control Type";
                leaf sctype {
                  type ncs_template_Storm-control;
                  description
                    "Storm Control Type";
                }
                uses ncs_template_STORM-CONTROL-UNIT;
              }
            }
            container split-horizon {
              description
                "Split Horizon";
              container split-horizon-group-id {
                description
                  "Split Horizon Group ID";
                leaf enable {
                  type empty;
                  description
                    "Enable split horizon group";
                }
              }
            }
            container static-mac-addresses {
              description
                "Static Mac Address Table";
              list static-mac-address {
                // NCS patched for predictable order
                ordered-by user;
                key "address";
                description
                  "Static Mac Address Configuration";
                leaf address {
                  type string;
                  description
                    "Static MAC address";
                }
              }
            }
            container interface-mac {
              description
                "MAC configuration commands";
              container interface-mac-aging {
                description
                  "MAC-Aging configuration commands";
                leaf interface-mac-aging-time {
                  type ncs_template_Mac-aging-range;
                  description
                    "Mac Aging Time";
                }
                leaf interface-mac-aging-type {
                  type ncs_template_Mac-aging;
                  description
                    "MAC address aging type";
                }
              }
              container interface-mac-secure {
                description
                  "MAC Secure";
                leaf enable {
                  type empty;
                  description
                    "Enable MAC Secure";
                }
                uses ncs_template_LOGGING;
                uses ncs_template_DISABLE;
                uses ncs_template_ACTION;
                uses ncs_template_SHUTDOWN-RECOVERY-TIMER;
              }
              container interface-mac-limit {
                description
                  "MAC-Limit configuration commands";
                leaf interface-mac-limit-max {
                  type ncs_template_Mac-limit-range;
                  description
                    "Number of MAC addresses on an Interface
                     after which MAC limit action is taken";
                }
                leaf interface-mac-limit-notif {
                  type ncs_template_Mac-notification;
                  description
                    "MAC address limit notification action in a
                     Interface";
                }
                leaf interface-mac-limit-action {
                  type ncs_template_Mac-limit-action;
                  description
                    "Interface MAC address limit enforcement
                     action";
                }
              }
              leaf interface-mac-port-down-flush {
                type ncs_template_Port-down-flush;
                description
                  "Enable/Disable MAC Flush When Port goes
                   down";
              }
              leaf interface-mac-learning {
                type ncs_template_Mac-learn;
                description
                  "Enable Mac Learning";
              }
            }
            leaf interface-flooding {
              type ncs_template_Interface-traffic-flood;
              description
                "Enable or Disable Flooding";
            }
            leaf interface-igmp-snoop {
              type xr:ncs_template_Cisco-ios-xr-string;
              description
                "Attach a IGMP Snooping profile";
            }
            leaf interface-flooding-unknown-unicast {
              type ncs_template_Interface-traffic-flood;
              description
                "Enable or Disable Unknown Unicast Flooding";
            }
            leaf interface-mld-snoop {
              type xr:ncs_template_Cisco-ios-xr-string;
              description
                "Attach a MLD Snooping profile";
            }
            leaf name {
              type xr:ncs_template_Interface-name;
              description
                "The name of the Attachment Circuit";
            }
          }
        }
        container bd-pseudowire-evpns {
          description
            "List of EVPN pseudowires";
          list bd-pseudowire-evpn {
            // NCS patched for predictable order
            ordered-by user;
            key "eviid acid";
            description
              "EVPN Pseudowire configuration";
            leaf eviid {
              type ncs_template_Evpnvpnid-range;
              description
                "Ethernet VPN ID";
            }
            leaf acid {
              type ncs_template_Pseudowire-acid-range;
              description
                "AC ID";
            }
          }
        }
        container ip-source-guard {
          description
            "IP Source Guard";
          leaf logging {
            type empty;
            description
              "Enable Logging";
          }
          leaf enable {
            type empty;
            description
              "Enable IP Source Guard";
          }
        }
        container dai {
          description
            "Dynamic ARP Inspection";
          container dai-address-validation {
            description
              "Address Validation";
            leaf ipv4-verification {
              type empty;
              description
                "Enable IPv4 Verification";
            }
            leaf destination-mac-verification {
              type empty;
              description
                "Enable Destination MAC Verification";
            }
            leaf source-mac-verification {
              type empty;
              description
                "Enable Source MAC Verification";
            }
            leaf enable {
              type empty;
              description
                "Enable Address Validation";
            }
          }
          leaf logging {
            type empty;
            description
              "Enable Logging";
          }
          leaf enable {
            type empty;
            description
              "Enable Dynamic ARP Inspection";
          }
        }
        container routed-interfaces {
          description
            "Bridge Domain Routed Interface Table";
          list routed-interface {
            // NCS patched for predictable order
            ordered-by user;
            key "interface-name";
            description
              "Bridge Domain Routed Interface";
            container routed-interface-split-horizon-group {
              description
                "Routed interface split horizon group";
              leaf routed-interface-split-horizon-group-core {
                type empty;
                description
                  "Configure BVI under SHG 1";
              }
            }
            leaf interface-name {
              type xr:ncs_template_Interface-name;
              description
                "The name of the Routed Interface";
            }
          }
        }
        leaf coupled-mode {
          type empty;
          description
            "Coupled-mode configuration";
        }
        leaf shutdown {
          type empty;
          description
            "shutdown the Bridge Domain";
        }
        leaf flooding-unknown-unicast {
          type empty;
          description
            "Disable Unknown Unicast flooding";
        }
        leaf efp-visibility {
          type empty;
          description
            "Enable multicast for multiple VLANs in the
             bridge of a BVI";
        }
        leaf l2-multicast-source {
          type ncs_template_L2mc-src-traffic-enabled;
          description
            "L2MC Source Traffic Enabled";
        }
        leaf igmp-snooping-disable {
          type empty;
          description
            "Disable IGMP Snooping";
        }
        leaf transport-mode {
          type ncs_template_Bridge-domain-transport-mode;
          description
            "Bridge Domain Transport mode";
        }
        leaf mld-snooping {
          type xr:ncs_template_Cisco-ios-xr-string;
          description
            "Attach MLD Snooping Profile Name";
        }
        leaf bridge-domain-mtu {
          type ncs_template_Bridge-bd-mtu-range;
          units "byte";
          description
            "Maximum transmission unit for this Bridge
             Domain";
        }
        leaf dhcp {
          type string;
          description
            "DHCPv4 Snooping profile name";
        }
        leaf bridge-description {
          type string;
          description
            "Bridge-domain description Name";
        }
        leaf igmp-snooping {
          type xr:ncs_template_Cisco-ios-xr-string;
          description
            "Attach IGMP Snooping Profile Name";
        }
        leaf flooding {
          type empty;
          description
            "Disable flooding";
        }
        leaf name {
          type xr:ncs_template_Cisco-ios-xr-string;
          description
            "Name of the bridge domain";
        }
      }
    }
  }

  grouping ncs_template_SHUTDOWN-RECOVERY-TIMER {
    description
      "Common node of mac-secure, interface-mac-secure,
       pseudowire-mac-secure";
    leaf shutdown-recovery-timer {
      type ncs_template_Mac-secure-shutdown-recovery-time-range;
      description
        "MAC Secure Shutdown Recovery Timer";
    }
  }

  grouping ncs_template_DISABLE {
    description
      "Common node of pbb-edge-mac-secure,
       interface-mac-secure, pseudowire-mac-secure";
    leaf disable {
      type empty;
      description
        "Disable MAC Secure";
    }
  }

  grouping ncs_rpc_notif_STORM-CONTROL-UNIT {
    description
      "Common node of bd-storm-control,
       bdac-storm-control-type, bdpw-storm-control-type";
    container storm-control-unit {
      must 'kbits-per-sec or pkts-per-sec' {
        tailf:xpath-root 3;
      }
      description
        "Specify units for Storm Control Configuration";
      leaf kbits-per-sec {
        type ncs_rpc_notif_Storm-control-kbps-range;
        units "kbit/s";
        description
          "Kilobits Per Second, PktsPerSec and KbitsPerSec
           cannot be configured together";
      }
      leaf pkts-per-sec {
        type ncs_rpc_notif_Storm-control-pps-range;
        units "packet/s";
        description
          "Packets Per Second, PktsPerSec and KbitsPerSec
           cannot be configured together";
      }
    }
  }

  grouping ncs_rpc_notif_MANUAL-SERVICE-CARVING {
    description
      "Common node of ethernet-segment,
       evpn-virtual-ethernet-segment";
    container manual-service-carving {
      description
        "Enter Manual service carving configuration
         submode";
      container service-list {
        description
          "Manual service carving primary,secondary lists";
        leaf primary {
          type string {
            length "1..150";
          }
          description
            "Primary services list";
        }
        leaf secondary {
          type string {
            length "1..150";
          }
          description
            "Secondary services list";
        }
      }
      leaf enable {
        type empty;
        description
          "Enable Manual service carving";
      }
    }
  }

  grouping ncs_rpc_notif_SERVICE-CARVING-MCAST-TYPE {
    description
      "Common node of ethernet-segment,
       evpn-virtual-ethernet-segment";
    leaf service-carving-mcast-type {
      type ncs_rpc_notif_Ethernet-segment-service-carving-mcast;
      description
        "Ethernet-Segment Service Carving multicast mode";
    }
  }

  grouping ncs_rpc_notif_ACTION {
    description
      "Common node of mac-secure, pbb-edge-mac-secure,
       interface-mac-secure, pseudowire-mac-secure";
    leaf action {
      type ncs_rpc_notif_Mac-secure-action;
      description
        "MAC secure enforcement action";
    }
  }

  grouping ncs_rpc_notif_EVPN-ROUTE-DISTINGUISHER {
    description
      "Common node of evpn-bgp-auto-discovery,
       evpn-instance-bgp-auto-discovery, pw-routing-bgp";
    container evpn-route-distinguisher {
      description
        "Route Distinguisher";
      leaf type {
        type ncs_rpc_notif_Bgp-route-distinguisher;
        description
          "Router Distinguisher Type";
      }
      leaf as {
        when "../type = 'two-byte-as' or ../type = 'four-byte-as'" {
          tailf:xpath-root 3;
          description
            "../Type = TwoByteAS or ../Type = FourByteAS";
        }
        type ncs_rpc_notif_Rdas-range;
        description
          "Two byte or 4 byte AS number";
      }
      leaf as-index {
        when "../type = 'two-byte-as' or ../type = 'four-byte-as'" {
          tailf:xpath-root 3;
          description
            "../Type = TwoByteAS or ../Type = FourByteAS";
        }
        type ncs_rpc_notif_Rdas-index;
        description
          "AS:nn (hex or decimal format)";
      }
      leaf address {
        when "../type = 'ipv4-address'" {
          tailf:xpath-root 3;
          description
            "../Type = IPV4Address";
        }
        type inet:ipv4-address-no-zone;
        description
          "IPV4 address";
      }
      leaf addr-index {
        when "../type = 'ipv4-address'" {
          tailf:xpath-root 3;
          description
            "../Type = IPV4Address";
        }
        type ncs_rpc_notif_Rd-addr-index;
        description
          "Addr index";
      }
    }
  }

  grouping ncs_rpc_notif_EVPN-VIRTUAL-ETHERNET-SEGMENT {
    description
      "Common node of evpn-virtual-access-pw,
       evpn-virtual-access-vfi";
    container evpn-virtual-ethernet-segment {
      description
        "Enter Ethernet Segment configuration submode";
      leaf enable {
        type empty;
        description
          "Enable Ethernet Segment";
      }
      uses ncs_rpc_notif_SERVICE-CARVING-MCAST-TYPE;
      uses ncs_rpc_notif_ES-IMPORT-ROUTE-TARGET;
      uses ncs_rpc_notif_SERVICE-CARVING-TYPE;
      uses ncs_rpc_notif_IDENTIFIER;
      uses ncs_rpc_notif_PREFERENCE-BASED-SERVICE-CARVING;
      uses ncs_rpc_notif_MANUAL-SERVICE-CARVING;
    }
  }

  grouping ncs_rpc_notif_LOGGING {
    description
      "Common node of pbb-edge-mac-secure,
       interface-mac-secure, pseudowire-mac-secure";
    leaf logging {
      type ncs_rpc_notif_L2vpn-logging;
      description
        "MAC Secure Logging";
    }
  }

  grouping ncs_rpc_notif_ES-IMPORT-ROUTE-TARGET {
    description
      "Common node of ethernet-segment,
       evpn-virtual-ethernet-segment";
    leaf es-import-route-target {
      type yang:mac-address;
      description
        "ES-Import Route Target";
    }
  }

  grouping ncs_rpc_notif_SERVICE-CARVING-TYPE {
    description
      "Common node of ethernet-segment,
       evpn-virtual-ethernet-segment";
    leaf service-carving-type {
      type ncs_rpc_notif_Ethernet-segment-service-carving;
      description
        "Ethernet-Segment Service Carving mode";
    }
  }

  grouping ncs_rpc_notif_IDENTIFIER {
    description
      "Common node of ethernet-segment,
       evpn-virtual-ethernet-segment";
    container identifier {
      presence "Indicates a identifier node is configured.";
      description
        "Ethernet segment identifier";
      leaf bytes01 {
        type xr:ncs_rpc_notif_Hex-integer;
        mandatory true;
        description
          "Type 0's 1st Byte or Type Byte and 1st Byte";
      }
      leaf bytes23 {
        type xr:ncs_rpc_notif_Hex-integer;
        units "byte";
        mandatory true;
        description
          "2nd and 3rd Bytes";
      }
      leaf bytes45 {
        type xr:ncs_rpc_notif_Hex-integer;
        units "byte";
        mandatory true;
        description
          "4th and 5th Bytes";
      }
      leaf bytes67 {
        type xr:ncs_rpc_notif_Hex-integer;
        units "byte";
        mandatory true;
        description
          "6th and 7th Bytes";
      }
      leaf bytes89 {
        type xr:ncs_rpc_notif_Hex-integer;
        units "byte";
        mandatory true;
        description
          "8th and 9th Bytes";
      }
      leaf type {
        type ncs_rpc_notif_Ethernet-segment-identifier;
        mandatory true;
        description
          "Ethernet segment identifier type";
      }
    }
  }

  grouping ncs_rpc_notif_PREFERENCE-BASED-SERVICE-CARVING {
    description
      "Common node of ethernet-segment,
       evpn-virtual-ethernet-segment";
    container preference-based-service-carving {
      description
        "Preference-Based DF Election Configuration
         Options";
      leaf weight {
        type uint32 {
          range "0..65535";
        }
        description
          "Preference DF weight. For Access-Driven DF, use
           weights of at most 32767 or less.";
      }
      leaf enable {
        type empty;
        description
          "Enable Preference Based Service Carving";
      }
      leaf access-driven {
        type empty;
        description
          "Enable Access-Driven DF Election";
      }
    }
  }

  grouping ncs_rpc_notif_BRIDGE-DOMAIN-TABLE {
    description
      "Common node of bridge-domain-group, vlan-switch";
    container bridge-domains {
      description
        "List of Bridge Domain";
      list bridge-domain {
        key "name";
        description
          "bridge domain";
        container bd-storm-controls {
          description
            "Storm Control";
          list bd-storm-control {
            must 'storm-control-unit' {
              tailf:xpath-root 3;
            }
            key "sctype";
            description
              "Storm Control Type";
            leaf sctype {
              type ncs_rpc_notif_Storm-control;
              description
                "Storm Control Type";
            }
            uses ncs_rpc_notif_STORM-CONTROL-UNIT;
          }
        }
        container member-vnis {
          description
            "Bridge Domain VxLAN Network Identifier Table";
          list member-vni {
            key "vni";
            description
              "Bridge Domain Member VxLAN Network Identifier";
            container member-vni-static-mac-addresses {
              description
                "Static Mac Address Table";
              list member-vni-static-mac-address {
                key "mac-address";
                description
                  "Static Mac Address Configuration";
                leaf next-hop-ip {
                  type inet:ipv4-address-no-zone;
                  description
                    "Enable Static Mac Address Configuration";
                }
                leaf mac-address {
                  type yang:mac-address;
                  description
                    "Static MAC address";
                }
              }
            }
            leaf vni {
              type uint32 {
                range "1..16777215";
              }
              description
                "VxLAN Network Identifier number";
            }
          }
        }
        container bridge-domain-mac {
          description
            "MAC configuration commands";
          container bd-mac-limit {
            description
              "MAC-Limit configuration commands";
            leaf bd-mac-limit-action {
              type ncs_rpc_notif_Mac-limit-action;
              description
                "MAC address limit enforcement action";
            }
            leaf bd-mac-limit-notif {
              type ncs_rpc_notif_Mac-notification;
              description
                "Mac Address Limit Notification";
            }
            leaf bd-mac-limit-max {
              type ncs_rpc_notif_Mac-limit-range;
              description
                "Number of MAC addresses after which MAC
                 limit action is taken";
            }
          }
          container bd-mac-filters {
            description
              "Filter Mac Address";
            list bd-mac-filter {
              key "address";
              description
                "Static MAC address";
              leaf drop {
                type empty;
                description
                  "MAC address for filtering";
              }
              leaf address {
                type yang:mac-address;
                description
                  "Static MAC address";
              }
            }
          }
          container mac-secure {
            description
              "MAC Secure";
            leaf logging {
              type empty;
              description
                "MAC Secure Logging";
            }
            leaf enable {
              type empty;
              description
                "Enable MAC Secure";
            }
            leaf threshold {
              type empty;
              description
                "MAC Secure Threshold";
            }
            uses ncs_rpc_notif_ACTION;
            uses ncs_rpc_notif_SHUTDOWN-RECOVERY-TIMER;
          }
          container bd-mac-aging {
            description
              "MAC-Aging configuration commands";
            leaf bd-mac-aging-type {
              type ncs_rpc_notif_Mac-aging;
              description
                "MAC address aging type";
            }
            leaf bd-mac-aging-time {
              type ncs_rpc_notif_Mac-aging-range;
              description
                "Mac Aging Time";
            }
          }
          leaf bd-mac-withdraw-relay {
            type empty;
            description
              "Mac withdraw sent from access PW to access PW";
          }
          leaf bd-mac-withdraw-access-pw-disable {
            type empty;
            description
              "MAC withdraw on Access PW";
          }
          leaf bd-mac-port-down-flush {
            type empty;
            description
              "Disable MAC Flush when Port goes Down";
          }
          leaf bd-mac-withdraw {
            type empty;
            description
              "Disable Mac Withdraw";
          }
          leaf bd-mac-withdraw-behavior {
            type ncs_rpc_notif_Mac-withdraw-behavior;
            description
              "MAC withdraw sent on bridge port down";
          }
          leaf bd-mac-learn {
            type ncs_rpc_notif_Bdmac-learn;
            description
              "Mac Learning Type";
          }
        }
        container nv-satellite {
          description
            "nV Satellite";
          leaf offload-ipv4-multicast-enable {
            type empty;
            description
              "Enable IPv4 Multicast Offload to Satellite
               Nodes";
          }
          leaf enable {
            type empty;
            description
              "Enable nV Satellite Settings";
          }
        }
        container bridge-domain-pbb {
          description
            "Bridge Domain PBB";
          container pbb-edges {
            description
              "PBB Edge";
            list pbb-edge {
              key "isid core-bd-name";
              description
                "Configure BD as PBB Edge with ISID and
                 associated PBB Core BD";
              container pbb-edge-split-horizon-group {
                description
                  "Split Horizon Group";
                leaf disable {
                  type empty;
                  description
                    "Disable split horizon group";
                }
              }
              container pbb-static-mac-mappings {
                description
                  "PBB Static Mac Address Mapping Table";
                list pbb-static-mac-mapping {
                  key "address";
                  description
                    "PBB Static Mac Address Mapping
                     Configuration";
                  leaf pbb-static-mac-mapping-bmac {
                    type yang:mac-address;
                    description
                      "Static backbone MAC address to map with";
                  }
                  leaf address {
                    type yang:mac-address;
                    description
                      "Static MAC address";
                  }
                }
              }
              container pbb-edge-dhcp-profile {
                description
                  "Attach a DHCP profile";
                leaf profile-id {
                  type ncs_rpc_notif_Interface-profile;
                  description
                    "Set the snooping profile";
                }
                leaf dhcp-snooping-id {
                  type string;
                  description
                    "Disable DHCP snooping";
                }
              }
              container pbb-edge-mac {
                description
                  "MAC configuration commands";
                container pbb-edge-mac-limit {
                  description
                    "MAC-Limit configuration commands";
                  leaf pbb-edge-mac-limit-action {
                    type ncs_rpc_notif_Mac-limit-action;
                    description
                      "MAC address limit enforcement action";
                  }
                  leaf pbb-edge-mac-limit-max {
                    type ncs_rpc_notif_Mac-limit-range;
                    description
                      "Number of MAC addresses after which MAC
                       limit action is taken";
                  }
                  leaf pbb-edge-mac-limit-notif {
                    type ncs_rpc_notif_Mac-notification;
                    description
                      "MAC address limit notification action";
                  }
                }
                container pbb-edge-mac-aging {
                  description
                    "MAC-Aging configuration commands";
                  leaf pbb-edge-mac-aging-type {
                    type ncs_rpc_notif_Mac-aging;
                    description
                      "MAC address aging type";
                  }
                  leaf pbb-edge-mac-aging-time {
                    type ncs_rpc_notif_Mac-aging-range;
                    description
                      "Mac Aging Time";
                  }
                }
                container pbb-edge-mac-secure {
                  description
                    "MAC Secure";
                  leaf enable {
                    type empty;
                    description
                      "Enable MAC Secure";
                  }
                  leaf accept-shutdown {
                    type empty;
                    description
                      "Accept Virtual instance port to be
                       shutdown on mac violation";
                  }
                  uses ncs_rpc_notif_LOGGING;
                  uses ncs_rpc_notif_DISABLE;
                  uses ncs_rpc_notif_ACTION;
                }
                leaf pbb-edge-mac-learning {
                  type ncs_rpc_notif_Mac-learn;
                  description
                    "Enable Mac Learning";
                }
              }
              leaf pbb-edge-igmp-profile {
                type xr:ncs_rpc_notif_Cisco-ios-xr-string;
                description
                  "Attach a IGMP Snooping profile";
              }
              leaf unknown-unicast-bmac {
                type yang:mac-address;
                description
                  "Configure Unknown Unicast BMAC address for
                   PBB Edge Port";
              }
              leaf isid {
                type ncs_rpc_notif_Pbbisid-range;
                description
                  "ISID";
              }
              leaf core-bd-name {
                type xr:ncs_rpc_notif_Cisco-ios-xr-string;
                description
                  "Core BD Name";
              }
            }
          }
          container pbb-core {
            description
              "PBB Core";
            container pbb-core-mac {
              description
                "MAC configuration commands";
              container pbb-core-mac-aging {
                description
                  "MAC-Aging configuration commands";
                leaf pbb-core-mac-aging-type {
                  type ncs_rpc_notif_Mac-aging;
                  description
                    "MAC address aging type";
                }
                leaf pbb-core-mac-aging-time {
                  type ncs_rpc_notif_Mac-aging-range;
                  description
                    "Mac Aging Time";
                }
              }
              container pbb-core-mac-limit {
                description
                  "MAC-Limit configuration commands";
                leaf pbb-core-mac-limit-max {
                  type ncs_rpc_notif_Mac-limit-range;
                  description
                    "Number of MAC addresses after which MAC
                     limit action is taken";
                }
                leaf pbb-core-mac-limit-notif {
                  type ncs_rpc_notif_Mac-notification;
                  description
                    "MAC address limit notification action";
                }
                leaf pbb-core-mac-limit-action {
                  type ncs_rpc_notif_Mac-limit-action;
                  description
                    "MAC address limit enforcement action";
                }
              }
              leaf pbb-core-mac-learning {
                type ncs_rpc_notif_Mac-learn;
                description
                  "Enable Mac Learning";
              }
            }
            container pbb-core-evis {
              description
                "PBB Core EVI Table";
              list pbb-core-evi {
                key "eviid";
                description
                  "PBB Core EVI";
                leaf eviid {
                  type ncs_rpc_notif_Vpnid-range;
                  description
                    "Ethernet VPN ID";
                }
              }
            }
            container pbb-core-dhcp-profile {
              description
                "Attach a DHCP profile";
              leaf profile-id {
                type ncs_rpc_notif_Interface-profile;
                description
                  "Set the snooping profile";
              }
              leaf dhcp-snooping-id {
                type string;
                description
                  "Disable DHCP snooping";
              }
            }
            leaf pbb-core-mmrp-flood-optimization {
              type empty;
              description
                "Enabling MMRP PBB-VPLS Flood Optimization";
            }
            leaf vlan-id {
              type ncs_rpc_notif_Pbbvid-range;
              description
                "VLAN ID to push";
            }
            leaf pbb-core-igmp-profile {
              type xr:ncs_rpc_notif_Cisco-ios-xr-string;
              description
                "Attach a IGMP Snooping profile";
            }
            leaf enable {
              type empty;
              description
                "Enable Bridge Domain PBB Core Configuration";
            }
          }
        }
        container bridge-domain-evis {
          description
            "Bridge Domain EVI Table";
          list bridge-domain-evi {
            key "vpn-id";
            description
              "Bridge Domain MPLS EVPN";
            leaf vpn-id {
              type ncs_rpc_notif_Evpnvpnid-range;
              description
                "MPLS Ethernet VPN-ID";
            }
          }
        }
        container access-vfis {
          description
            "Specify the access virtual forwarding
             interface name";
          list access-vfi {
            key "name";
            description
              "Name of the Acess Virtual Forwarding
               Interface";
            container access-vfi-pseudowires {
              description
                "List of pseudowires";
              list access-vfi-pseudowire {
                key "neighbor pseudowire-id";
                description
                  "Pseudowire configuration";
                container access-vfi-pseudowire-static-mac-addresses {
                  description
                    "Static Mac Address Table";
                  list access-vfi-pseudowire-static-mac-address {
                    key "address";
                    description
                      "Static Mac Address Configuration";
                    leaf address {
                      type yang:mac-address;
                      description
                        "Static MAC address";
                    }
                  }
                }
                leaf access-vfi-pw-class {
                  type xr:ncs_rpc_notif_Cisco-ios-xr-string;
                  description
                    "Pseudowire class template name to use for
                     this pseudowire";
                }
                leaf neighbor {
                  type inet:ipv4-address-no-zone;
                  description
                    "Neighbor IP address";
                }
                leaf pseudowire-id {
                  type ncs_rpc_notif_Pseudowire-id-range;
                  description
                    "Pseudowire ID";
                }
              }
            }
            leaf access-vfi-shutdown {
              type empty;
              description
                "shutdown the AccessVfi";
            }
            leaf name {
              type xr:ncs_rpc_notif_Cisco-ios-xr-string;
              description
                "Name of the AccessVirtual Forwarding
                 Interface";
            }
          }
        }
        container bd-pseudowires {
          description
            "List of pseudowires";
          list bd-pseudowire {
            key "neighbor pseudowire-id";
            description
              "Pseudowire configuration";
            container pseudowire-dai {
              description
                "Access Pseudowire Dynamic ARP Inspection";
              container pseudowire-dai-address-validation {
                description
                  "Address Validation";
                leaf ipv4-verification {
                  type ncs_rpc_notif_L2vpn-verification;
                  description
                    "IPv4 Verification";
                }
                leaf destination-mac-verification {
                  type ncs_rpc_notif_L2vpn-verification;
                  description
                    "Destination MAC Verification";
                }
                leaf source-mac-verification {
                  type ncs_rpc_notif_L2vpn-verification;
                  description
                    "Source MAC Verification";
                }
              }
              leaf logging {
                type ncs_rpc_notif_L2vpn-logging;
                description
                  "Logging Type";
              }
              leaf disable {
                type empty;
                description
                  "Disable Dynamic ARP Inspection";
              }
              leaf enable {
                type empty;
                description
                  "Enable Access Pseudowire Dynamic ARP
                   Inspection";
              }
            }
            container bdpw-storm-control-types {
              description
                "Storm Control";
              list bdpw-storm-control-type {
                must 'storm-control-unit' {
                  tailf:xpath-root 3;
                }
                key "sctype";
                description
                  "Storm Control Type";
                leaf sctype {
                  type ncs_rpc_notif_Storm-control;
                  description
                    "Storm Control Type";
                }
                uses ncs_rpc_notif_STORM-CONTROL-UNIT;
              }
            }
            container pseudowire-profile {
              description
                "Attach a DHCP profile";
              leaf profile-id {
                type ncs_rpc_notif_Interface-profile;
                description
                  "Set the snooping profile";
              }
              leaf dhcp-snooping-id {
                type string;
                description
                  "Disable DHCP snooping";
              }
            }
            container bd-pw-static-mac-addresses {
              description
                "Static Mac Address Table";
              list bd-pw-static-mac-address {
                key "address";
                description
                  "Static Mac Address Configuration";
                leaf address {
                  type yang:mac-address;
                  description
                    "Static MAC address";
                }
              }
            }
            container pseudowire-ip-source-guard {
              description
                "IP Source Guard";
              leaf logging {
                type ncs_rpc_notif_L2vpn-logging;
                description
                  "Logging Type";
              }
              leaf disable {
                type empty;
                description
                  "Disable Dynamic IP source guard";
              }
              leaf enable {
                type empty;
                description
                  "Enable IP Source Guard";
              }
            }
            container pseudowire-mac {
              description
                "Bridge-domain Pseudowire MAC configuration
                 commands";
              container pseudowire-mac-secure {
                description
                  "MAC Secure";
                leaf enable {
                  type empty;
                  description
                    "Enable MAC Secure";
                }
                uses ncs_rpc_notif_LOGGING;
                uses ncs_rpc_notif_DISABLE;
                uses ncs_rpc_notif_ACTION;
                uses ncs_rpc_notif_SHUTDOWN-RECOVERY-TIMER;
              }
              container pseudowire-mac-aging {
                description
                  "MAC-Aging configuration commands";
                leaf pseudowire-mac-aging-type {
                  type ncs_rpc_notif_Mac-aging;
                  description
                    "MAC address aging type";
                }
                leaf pseudowire-mac-aging-time {
                  type ncs_rpc_notif_Mac-aging-range;
                  description
                    "MAC Aging Time";
                }
              }
              container pseudowire-mac-limit {
                description
                  "MAC-Limit configuration commands";
                leaf pseudowire-mac-limit-action {
                  type ncs_rpc_notif_Mac-limit-action;
                  description
                    "Bridge Access Pseudowire MAC address limit
                     enforcement action";
                }
                leaf pseudowire-mac-limit-notif {
                  type ncs_rpc_notif_Mac-notification;
                  description
                    "MAC address limit notification action in a
                     Bridge Access Pseudowire";
                }
                leaf pseudowire-mac-limit-max {
                  type ncs_rpc_notif_Mac-limit-range;
                  description
                    "Number of MAC addresses on a Bridge Access
                     Pseudowire after which MAC limit action is
                     taken";
                }
              }
              leaf pseudowire-mac-port-down-flush {
                type ncs_rpc_notif_Port-down-flush;
                description
                  "Enable/Disable MAC Flush When Port goes
                   down";
              }
              leaf enable {
                type empty;
                description
                  "Bridge-domain Pseudowire MAC configuration
                   mode";
              }
              leaf pseudowire-mac-learning {
                type ncs_rpc_notif_Mac-learn;
                description
                  "Enable MAC Learning";
              }
            }
            container bd-pw-split-horizon {
              description
                "Split Horizon";
              container bd-pw-split-horizon-group {
                description
                  "Split Horizon Group";
                leaf enable {
                  type empty;
                  description
                    "Enable split horizon group";
                }
              }
            }
            container bd-pw-mpls-static-labels {
              description
                "MPLS static labels";
              leaf local-static-label {
                type ncs_rpc_notif_Pseudowire-label-range;
                description
                  "Pseudowire local static label";
              }
              leaf remote-static-label {
                type ncs_rpc_notif_Pseudowire-label-range;
                description
                  "Pseudowire remote static label";
              }
            }
            container bridge-domain-backup-pseudowires {
              description
                "List of pseudowires";
              list bridge-domain-backup-pseudowire {
                key "neighbor pseudowire-id";
                description
                  "Backup pseudowire configuration";
                leaf bridge-domain-backup-pw-class {
                  type xr:ncs_rpc_notif_Cisco-ios-xr-string;
                  description
                    "PW class template name to use for this
                     pseudowire";
                }
                leaf neighbor {
                  type inet:ipv4-address-no-zone;
                  description
                    "Neighbor IP address";
                }
                leaf pseudowire-id {
                  type ncs_rpc_notif_Pseudowire-id-range;
                  description
                    "Pseudowire ID";
                }
              }
            }
            leaf pseudowire-mld-snoop {
              type xr:ncs_rpc_notif_Cisco-ios-xr-string;
              description
                "Attach a MLD Snooping profile";
            }
            leaf pseudowire-igmp-snoop {
              type xr:ncs_rpc_notif_Cisco-ios-xr-string;
              description
                "Attach a IGMP Snooping profile";
            }
            leaf pseudowire-flooding {
              type ncs_rpc_notif_Interface-traffic-flood;
              description
                "Bridge-domain Pseudowire flooding";
            }
            leaf bd-pw-class {
              type xr:ncs_rpc_notif_Cisco-ios-xr-string;
              description
                "PW class template name to use for this
                 pseudowire";
            }
            leaf pseudowire-flooding-unknown-unicast {
              type ncs_rpc_notif_Interface-traffic-flood;
              description
                "Bridge-domain Pseudowire flooding Unknown
                 Unicast";
            }
            leaf neighbor {
              type inet:ipv4-address-no-zone;
              description
                "Neighbor IP address";
            }
            leaf pseudowire-id {
              type ncs_rpc_notif_Pseudowire-id-range;
              description
                "Pseudowire ID";
            }
          }
        }
        container vfis {
          description
            "Specify the virtual forwarding interface name";
          list vfi {
            key "name";
            description
              "Name of the Virtual Forwarding Interface";
            container multicast-p2mp {
              description
                "Enable Multicast P2MP in this VFI";
              container transports {
                description
                  "Multicast P2MP Transport";
                list transport {
                  key "transport-name";
                  description
                    "Multicast P2MP Transport Type";
                  leaf attribute-set-name {
                    type xr:ncs_rpc_notif_Cisco-ios-xr-string;
                    description
                      "Multicast P2MP TE Attribute Set Name";
                  }
                  leaf transport-name {
                    type ncs_rpc_notif_Multicast-p2mp-transport;
                    description
                      "Transport Type";
                  }
                }
              }
              container signalings {
                description
                  "Multicast P2MP Signaling Type";
                list signaling {
                  key "signaling-name";
                  description
                    "Multicast P2MP Signaling Type";
                  leaf signaling-name {
                    type ncs_rpc_notif_Multicast-p2mp-signaling;
                    description
                      "Signaling Type";
                  }
                }
              }
              leaf enable {
                type empty;
                description
                  "Enable Autodiscovery P2MP";
              }
            }
            container vfi-pseudowires {
              description
                "List of pseudowires";
              list vfi-pseudowire {
                key "neighbor pseudowire-id";
                description
                  "Pseudowire configuration";
                container vfi-pw-dhcp-snoop {
                  description
                    "Attach a DHCP Snooping profile";
                  leaf profile-id {
                    type ncs_rpc_notif_Interface-profile;
                    description
                      "Set the snooping profile";
                  }
                  leaf dhcp-snooping-id {
                    type string;
                    description
                      "Disable DHCP snooping";
                  }
                }
                container vfi-pw-mpls-static-labels {
                  description
                    "MPLS static labels";
                  leaf local-static-label {
                    type ncs_rpc_notif_Pseudowire-label-range;
                    description
                      "Pseudowire local static label";
                  }
                  leaf remote-static-label {
                    type ncs_rpc_notif_Pseudowire-label-range;
                    description
                      "Pseudowire remote static label";
                  }
                }
                container pseudowire-static-mac-addresses {
                  description
                    "Static Mac Address Table";
                  list pseudowire-static-mac-address {
                    key "address";
                    description
                      "Static Mac Address Configuration";
                    leaf address {
                      type yang:mac-address;
                      description
                        "Static MAC address";
                    }
                  }
                }
                leaf vfi-pw-class {
                  type xr:ncs_rpc_notif_Cisco-ios-xr-string;
                  description
                    "PW class template name to use for this
                     pseudowire";
                }
                leaf vfi-pw-igmp-snoop {
                  type xr:ncs_rpc_notif_Cisco-ios-xr-string;
                  description
                    "Attach a IGMP Snooping profile";
                }
                leaf vfi-pw-mld-snoop {
                  type xr:ncs_rpc_notif_Cisco-ios-xr-string;
                  description
                    "Attach a MLD Snooping profile";
                }
                leaf neighbor {
                  type inet:ipv4-address-no-zone;
                  description
                    "Neighbor IP address";
                }
                leaf pseudowire-id {
                  type ncs_rpc_notif_Pseudowire-id-range;
                  description
                    "Pseudowire ID";
                }
              }
            }
            container bgp-auto-discovery {
              description
                "Enable Autodiscovery BGP in this VFI";
              container ldp-signaling-protocol {
                description
                  "Signaling Protocol LDP in this VFI
                   configuration";
                container vpls-id {
                  description
                    "VPLS ID";
                  leaf type {
                    type ncs_rpc_notif_Ldp-vpls-id;
                    description
                      "VPLS-ID Type";
                  }
                  leaf as {
                    when "../type = 'two-byte-as'" {
                      tailf:xpath-root 3;
                      description
                        "../Type = TwoByteAS";
                    }
                    type ncs_rpc_notif_Vpls-id-as-range;
                    description
                      "Two byte AS number";
                  }
                  leaf as-index {
                    when "../type = 'two-byte-as'" {
                      tailf:xpath-root 3;
                      description
                        "../Type = TwoByteAS";
                    }
                    type ncs_rpc_notif_Vpls-id-as-index;
                    description
                      "AS index";
                  }
                  leaf address {
                    when "../type = 'ipv4-address'" {
                      tailf:xpath-root 3;
                      description
                        "../Type = IPV4Address";
                    }
                    type inet:ipv4-address-no-zone;
                    description
                      "IPV4 address";
                  }
                  leaf address-index {
                    when "../type = 'ipv4-address'" {
                      tailf:xpath-root 3;
                      description
                        "../Type = IPV4Address";
                    }
                    type ncs_rpc_notif_Vpls-id-addr-index;
                    description
                      "Address index";
                  }
                }
                container flow-label-load-balance {
                  description
                    "Enable Flow Label based load balancing";
                  leaf flow-label {
                    type ncs_rpc_notif_Flow-label-load-balance;
                    description
                      "Flow Label load balance type";
                  }
                  leaf static {
                    type empty;
                    description
                      "Static Flow Label";
                  }
                }
                leaf enable {
                  type empty;
                  description
                    "Enable LDP as Signaling Protocol.Deletion
                     of this object also causes deletion of all
                     objects under LDPSignalingProtocol.";
                }
              }
              container bgp-route-policy {
                description
                  "Route policy";
                leaf export {
                  type string;
                  description
                    "Export route policy";
                }
              }
              container route-distinguisher {
                description
                  "Route Distinguisher";
                leaf type {
                  type ncs_rpc_notif_Bgp-route-distinguisher;
                  description
                    "Router Distinguisher Type";
                }
                leaf as {
                  when "../type = 'two-byte-as' or ../type = 'four-byte-as'" {
                    tailf:xpath-root 3;
                    description
                      "../Type = TwoByteAS or ../Type =
                       FourByteAS";
                  }
                  type ncs_rpc_notif_Rdas-range;
                  description
                    "Two byte or 4 byte AS number";
                }
                leaf as-index {
                  when "../type = 'two-byte-as' or ../type = 'four-byte-as'" {
                    tailf:xpath-root 3;
                    description
                      "../Type = TwoByteAS or ../Type =
                       FourByteAS";
                  }
                  type ncs_rpc_notif_Rdas-index;
                  description
                    "AS:nn (hex or decimal format)";
                }
                leaf address {
                  when "../type = 'ipv4-address'" {
                    tailf:xpath-root 3;
                    description
                      "../Type = IPV4Address";
                  }
                  type inet:ipv4-address-no-zone;
                  description
                    "IPV4 address";
                }
                leaf addr-index {
                  when "../type = 'ipv4-address'" {
                    tailf:xpath-root 3;
                    description
                      "../Type = IPV4Address";
                  }
                  type ncs_rpc_notif_Rd-addr-index;
                  description
                    "Addr index";
                }
              }
              container bgp-signaling-protocol {
                description
                  "Enable Signaling Protocol BGP in this VFI";
                container flow-label-load-balance {
                  description
                    "Enable Flow Label based load balancing";
                  leaf flow-label {
                    type ncs_rpc_notif_Flow-label-load-balance;
                    description
                      "Flow Label load balance type";
                  }
                  leaf static {
                    type empty;
                    description
                      "Static Flow Label";
                  }
                }
                leaf ve-range {
                  type ncs_rpc_notif_Vedge-range;
                  description
                    "Local Virtual Edge Block Configurable
                     Range";
                }
                leaf veid {
                  type ncs_rpc_notif_Veid-range;
                  description
                    "Local Virtual Edge Identifier";
                }
                leaf enable {
                  type empty;
                  description
                    "Enable BGP as Signaling Protocol";
                }
              }
              container route-targets {
                description
                  "Route Target";
                list route-target {
                  must 'two-byte-as-or-four-byte-as or ipv4-address' {
                    tailf:xpath-root 3;
                    description
                      "TwoByteAS-or-FourbyteAS or IPV4Address
                       must be present.";
                  }
                  key "role format";
                  description
                    "Name of the Route Target";
                  leaf role {
                    type ncs_rpc_notif_Bgp-route-target-role;
                    description
                      "Role of the router target type";
                  }
                  leaf format {
                    type ncs_rpc_notif_Bgp-route-target-format;
                    description
                      "Format of the route target";
                  }
                  list two-byte-as-or-four-byte-as {
                    when "../format = 'two-byte-as' or ../format = 'four-byte-as'" {
                      tailf:xpath-root 3;
                      description
                        "../Format = TwoByteAS or ../Format =
                         FourbyteAS";
                    }
                    key "as as-index";
                    description
                      "two byte as or four byte as";
                    leaf as {
                      type ncs_rpc_notif_Rdas-range;
                      description
                        "Two byte or 4 byte AS number";
                    }
                    leaf as-index {
                      type ncs_rpc_notif_Rdas-index;
                      description
                        "AS:nn (hex or decimal format)";
                    }
                  }
                  list ipv4-address {
                    when "../format = 'ipv4-address'" {
                      tailf:xpath-root 3;
                      description
                        "../Format = IPV4Address";
                    }
                    key "address addr-index";
                    description
                      "ipv4 address";
                    leaf address {
                      type inet:ipv4-address-no-zone;
                      description
                        "IPV4 address";
                    }
                    leaf addr-index {
                      type ncs_rpc_notif_Rd-addr-index;
                      description
                        "Addr index";
                    }
                  }
                }
              }
              leaf table-policy {
                type string;
                description
                  "Table Policy for installation of forwarding
                   data to L2FIB";
              }
              leaf ad-control-word {
                type empty;
                description
                  "Enable control-word for this VFI";
              }
              leaf enable {
                type empty;
                description
                  "Enable Autodiscovery BGP";
              }
            }
            leaf vfi-shutdown {
              type empty;
              description
                "Enabling Shutdown";
            }
            leaf vpnid {
              type ncs_rpc_notif_Vpnid-range;
              description
                "VPN Identifier";
            }
            leaf name {
              type xr:ncs_rpc_notif_Cisco-ios-xr-string;
              description
                "Name of the Virtual Forwarding Interface";
            }
          }
        }
        container bridge-domainvnis {
          description
            "Bridge Domain EVPN VxLAN Network Identifier
             Table";
          list bridge-domainvni {
            key "vpn-id";
            description
              "Bridge Domain VxLAN EVPN";
            leaf vpn-id {
              type uint32 {
                range "1..16777215";
              }
              description
                "VxLAN Ethernet VPN-ID";
            }
          }
        }
        container bd-attachment-circuits {
          description
            "Attachment Circuit table";
          list bd-attachment-circuit {
            key "name";
            description
              "Name of the Attachment Circuit";
            container interface-ip-source-guard {
              description
                "IP Source Guard";
              leaf logging {
                type ncs_rpc_notif_L2vpn-logging;
                description
                  "Logging Type";
              }
              leaf disable {
                type empty;
                description
                  "Disable L2 Interface Dynamic IP source
                   guard";
              }
              leaf enable {
                type empty;
                description
                  "Enable IP Source Guard";
              }
            }
            container interface-dai {
              description
                "L2 Interface Dynamic ARP Inspection";
              container interface-dai-address-validation {
                description
                  "Address Validation";
                leaf ipv4-verification {
                  type ncs_rpc_notif_L2vpn-verification;
                  description
                    "IPv4 Verification";
                }
                leaf destination-mac-verification {
                  type ncs_rpc_notif_L2vpn-verification;
                  description
                    "Destination MAC Verification";
                }
                leaf source-mac-verification {
                  type ncs_rpc_notif_L2vpn-verification;
                  description
                    "Source MAC Verification";
                }
                leaf enable {
                  type empty;
                  description
                    "Enable Address Validation";
                }
              }
              leaf logging {
                type ncs_rpc_notif_L2vpn-logging;
                description
                  "Logging Type";
              }
              leaf disable {
                type empty;
                description
                  "Disable L2 Interface Dynamic ARP Inspection";
              }
              leaf enable {
                type empty;
                description
                  "Enable L2 Interface Dynamic ARP Inspection";
              }
            }
            container interface-profile {
              description
                "Attach a DHCP profile";
              leaf profile-id {
                type ncs_rpc_notif_Interface-profile;
                description
                  "Set the snooping profile";
              }
              leaf dhcp-snooping-id {
                type string;
                description
                  "Disable DHCP snooping";
              }
            }
            container bdac-storm-control-types {
              description
                "Storm Control";
              list bdac-storm-control-type {
                must 'storm-control-unit' {
                  tailf:xpath-root 3;
                }
                key "sctype";
                description
                  "Storm Control Type";
                leaf sctype {
                  type ncs_rpc_notif_Storm-control;
                  description
                    "Storm Control Type";
                }
                uses ncs_rpc_notif_STORM-CONTROL-UNIT;
              }
            }
            container split-horizon {
              description
                "Split Horizon";
              container split-horizon-group-id {
                description
                  "Split Horizon Group ID";
                leaf enable {
                  type empty;
                  description
                    "Enable split horizon group";
                }
              }
            }
            container static-mac-addresses {
              description
                "Static Mac Address Table";
              list static-mac-address {
                key "address";
                description
                  "Static Mac Address Configuration";
                leaf address {
                  type yang:mac-address;
                  description
                    "Static MAC address";
                }
              }
            }
            container interface-mac {
              description
                "MAC configuration commands";
              container interface-mac-aging {
                description
                  "MAC-Aging configuration commands";
                leaf interface-mac-aging-time {
                  type ncs_rpc_notif_Mac-aging-range;
                  description
                    "Mac Aging Time";
                }
                leaf interface-mac-aging-type {
                  type ncs_rpc_notif_Mac-aging;
                  description
                    "MAC address aging type";
                }
              }
              container interface-mac-secure {
                description
                  "MAC Secure";
                leaf enable {
                  type empty;
                  description
                    "Enable MAC Secure";
                }
                uses ncs_rpc_notif_LOGGING;
                uses ncs_rpc_notif_DISABLE;
                uses ncs_rpc_notif_ACTION;
                uses ncs_rpc_notif_SHUTDOWN-RECOVERY-TIMER;
              }
              container interface-mac-limit {
                description
                  "MAC-Limit configuration commands";
                leaf interface-mac-limit-max {
                  type ncs_rpc_notif_Mac-limit-range;
                  description
                    "Number of MAC addresses on an Interface
                     after which MAC limit action is taken";
                }
                leaf interface-mac-limit-notif {
                  type ncs_rpc_notif_Mac-notification;
                  description
                    "MAC address limit notification action in a
                     Interface";
                }
                leaf interface-mac-limit-action {
                  type ncs_rpc_notif_Mac-limit-action;
                  description
                    "Interface MAC address limit enforcement
                     action";
                }
              }
              leaf interface-mac-port-down-flush {
                type ncs_rpc_notif_Port-down-flush;
                description
                  "Enable/Disable MAC Flush When Port goes
                   down";
              }
              leaf interface-mac-learning {
                type ncs_rpc_notif_Mac-learn;
                description
                  "Enable Mac Learning";
              }
            }
            leaf interface-flooding {
              type ncs_rpc_notif_Interface-traffic-flood;
              description
                "Enable or Disable Flooding";
            }
            leaf interface-igmp-snoop {
              type xr:ncs_rpc_notif_Cisco-ios-xr-string;
              description
                "Attach a IGMP Snooping profile";
            }
            leaf interface-flooding-unknown-unicast {
              type ncs_rpc_notif_Interface-traffic-flood;
              description
                "Enable or Disable Unknown Unicast Flooding";
            }
            leaf interface-mld-snoop {
              type xr:ncs_rpc_notif_Cisco-ios-xr-string;
              description
                "Attach a MLD Snooping profile";
            }
            leaf name {
              type xr:ncs_rpc_notif_Interface-name;
              description
                "The name of the Attachment Circuit";
            }
          }
        }
        container bd-pseudowire-evpns {
          description
            "List of EVPN pseudowires";
          list bd-pseudowire-evpn {
            key "eviid acid";
            description
              "EVPN Pseudowire configuration";
            leaf eviid {
              type ncs_rpc_notif_Evpnvpnid-range;
              description
                "Ethernet VPN ID";
            }
            leaf acid {
              type ncs_rpc_notif_Pseudowire-acid-range;
              description
                "AC ID";
            }
          }
        }
        container ip-source-guard {
          description
            "IP Source Guard";
          leaf logging {
            type empty;
            description
              "Enable Logging";
          }
          leaf enable {
            type empty;
            description
              "Enable IP Source Guard";
          }
        }
        container dai {
          description
            "Dynamic ARP Inspection";
          container dai-address-validation {
            description
              "Address Validation";
            leaf ipv4-verification {
              type empty;
              description
                "Enable IPv4 Verification";
            }
            leaf destination-mac-verification {
              type empty;
              description
                "Enable Destination MAC Verification";
            }
            leaf source-mac-verification {
              type empty;
              description
                "Enable Source MAC Verification";
            }
            leaf enable {
              type empty;
              description
                "Enable Address Validation";
            }
          }
          leaf logging {
            type empty;
            description
              "Enable Logging";
          }
          leaf enable {
            type empty;
            description
              "Enable Dynamic ARP Inspection";
          }
        }
        container routed-interfaces {
          description
            "Bridge Domain Routed Interface Table";
          list routed-interface {
            key "interface-name";
            description
              "Bridge Domain Routed Interface";
            container routed-interface-split-horizon-group {
              description
                "Routed interface split horizon group";
              leaf routed-interface-split-horizon-group-core {
                type empty;
                description
                  "Configure BVI under SHG 1";
              }
            }
            leaf interface-name {
              type xr:ncs_rpc_notif_Interface-name;
              description
                "The name of the Routed Interface";
            }
          }
        }
        leaf coupled-mode {
          type empty;
          description
            "Coupled-mode configuration";
        }
        leaf shutdown {
          type empty;
          description
            "shutdown the Bridge Domain";
        }
        leaf flooding-unknown-unicast {
          type empty;
          description
            "Disable Unknown Unicast flooding";
        }
        leaf efp-visibility {
          type empty;
          description
            "Enable multicast for multiple VLANs in the
             bridge of a BVI";
        }
        leaf l2-multicast-source {
          type ncs_rpc_notif_L2mc-src-traffic-enabled;
          description
            "L2MC Source Traffic Enabled";
        }
        leaf igmp-snooping-disable {
          type empty;
          description
            "Disable IGMP Snooping";
        }
        leaf transport-mode {
          type ncs_rpc_notif_Bridge-domain-transport-mode;
          description
            "Bridge Domain Transport mode";
        }
        leaf mld-snooping {
          type xr:ncs_rpc_notif_Cisco-ios-xr-string;
          description
            "Attach MLD Snooping Profile Name";
        }
        leaf bridge-domain-mtu {
          type ncs_rpc_notif_Bridge-bd-mtu-range;
          units "byte";
          description
            "Maximum transmission unit for this Bridge
             Domain";
        }
        leaf dhcp {
          type string {
            length "1..32";
          }
          description
            "DHCPv4 Snooping profile name";
        }
        leaf bridge-description {
          type string {
            length "1..64";
          }
          description
            "Bridge-domain description Name";
        }
        leaf igmp-snooping {
          type xr:ncs_rpc_notif_Cisco-ios-xr-string;
          description
            "Attach IGMP Snooping Profile Name";
        }
        leaf flooding {
          type empty;
          description
            "Disable flooding";
        }
        leaf name {
          type xr:ncs_rpc_notif_Cisco-ios-xr-string;
          description
            "Name of the bridge domain";
        }
      }
    }
  }

  grouping ncs_rpc_notif_SHUTDOWN-RECOVERY-TIMER {
    description
      "Common node of mac-secure, interface-mac-secure,
       pseudowire-mac-secure";
    leaf shutdown-recovery-timer {
      type ncs_rpc_notif_Mac-secure-shutdown-recovery-time-range;
      description
        "MAC Secure Shutdown Recovery Timer";
    }
  }

  grouping ncs_rpc_notif_DISABLE {
    description
      "Common node of pbb-edge-mac-secure,
       interface-mac-secure, pseudowire-mac-secure";
    leaf disable {
      type empty;
      description
        "Disable MAC Secure";
    }
  }

  grouping live_ncs_STORM-CONTROL-UNIT {
    description
      "Common node of bd-storm-control,
       bdac-storm-control-type, bdpw-storm-control-type";
    container storm-control-unit {
      // NCS drop must statement
      description
        "Specify units for Storm Control Configuration";
      leaf kbits-per-sec {
        type live_ncs_Storm-control-kbps-range;
        units "kbit/s";
        description
          "Kilobits Per Second, PktsPerSec and KbitsPerSec
           cannot be configured together";
      }
      leaf pkts-per-sec {
        type live_ncs_Storm-control-pps-range;
        units "packet/s";
        description
          "Packets Per Second, PktsPerSec and KbitsPerSec
           cannot be configured together";
      }
    }
  }

  grouping live_ncs_MANUAL-SERVICE-CARVING {
    description
      "Common node of ethernet-segment,
       evpn-virtual-ethernet-segment";
    container manual-service-carving {
      description
        "Enter Manual service carving configuration
         submode";
      container service-list {
        description
          "Manual service carving primary,secondary lists";
        leaf primary {
          type string {
            length "1..150";
          }
          description
            "Primary services list";
        }
        leaf secondary {
          type string {
            length "1..150";
          }
          description
            "Secondary services list";
        }
      }
      leaf enable {
        type empty;
        description
          "Enable Manual service carving";
      }
    }
  }

  grouping live_ncs_SERVICE-CARVING-MCAST-TYPE {
    description
      "Common node of ethernet-segment,
       evpn-virtual-ethernet-segment";
    leaf service-carving-mcast-type {
      type live_ncs_Ethernet-segment-service-carving-mcast;
      description
        "Ethernet-Segment Service Carving multicast mode";
    }
  }

  grouping live_ncs_ACTION {
    description
      "Common node of mac-secure, pbb-edge-mac-secure,
       interface-mac-secure, pseudowire-mac-secure";
    leaf action {
      type live_ncs_Mac-secure-action;
      description
        "MAC secure enforcement action";
    }
  }

  grouping live_ncs_EVPN-ROUTE-DISTINGUISHER {
    description
      "Common node of evpn-bgp-auto-discovery,
       evpn-instance-bgp-auto-discovery, pw-routing-bgp";
    container evpn-route-distinguisher {
      description
        "Route Distinguisher";
      leaf type {
        type live_ncs_Bgp-route-distinguisher;
        description
          "Router Distinguisher Type";
      }
      leaf as {
        // NCS drop when statement
        type live_ncs_Rdas-range;
        description
          "Two byte or 4 byte AS number";
      }
      leaf as-index {
        // NCS drop when statement
        type live_ncs_Rdas-index;
        description
          "AS:nn (hex or decimal format)";
      }
      leaf address {
        // NCS drop when statement
        type inet:ipv4-address-no-zone;
        description
          "IPV4 address";
      }
      leaf addr-index {
        // NCS drop when statement
        type live_ncs_Rd-addr-index;
        description
          "Addr index";
      }
    }
  }

  grouping live_ncs_EVPN-VIRTUAL-ETHERNET-SEGMENT {
    description
      "Common node of evpn-virtual-access-pw,
       evpn-virtual-access-vfi";
    container evpn-virtual-ethernet-segment {
      description
        "Enter Ethernet Segment configuration submode";
      leaf enable {
        type empty;
        description
          "Enable Ethernet Segment";
      }
      uses live_ncs_SERVICE-CARVING-MCAST-TYPE;
      uses live_ncs_ES-IMPORT-ROUTE-TARGET;
      uses live_ncs_SERVICE-CARVING-TYPE;
      uses live_ncs_IDENTIFIER;
      uses live_ncs_PREFERENCE-BASED-SERVICE-CARVING;
      uses live_ncs_MANUAL-SERVICE-CARVING;
    }
  }

  grouping live_ncs_LOGGING {
    description
      "Common node of pbb-edge-mac-secure,
       interface-mac-secure, pseudowire-mac-secure";
    leaf logging {
      type live_ncs_L2vpn-logging;
      description
        "MAC Secure Logging";
    }
  }

  grouping live_ncs_ES-IMPORT-ROUTE-TARGET {
    description
      "Common node of ethernet-segment,
       evpn-virtual-ethernet-segment";
    leaf es-import-route-target {
      type yang:mac-address;
      description
        "ES-Import Route Target";
    }
  }

  grouping live_ncs_SERVICE-CARVING-TYPE {
    description
      "Common node of ethernet-segment,
       evpn-virtual-ethernet-segment";
    leaf service-carving-type {
      type live_ncs_Ethernet-segment-service-carving;
      description
        "Ethernet-Segment Service Carving mode";
    }
  }

  grouping live_ncs_IDENTIFIER {
    description
      "Common node of ethernet-segment,
       evpn-virtual-ethernet-segment";
    container identifier {
      presence "Indicates a identifier node is configured.";
      description
        "Ethernet segment identifier";
      leaf bytes01 {
        type xr:live_ncs_Hex-integer;
        // NCS drop mandatory statement
        description
          "Type 0's 1st Byte or Type Byte and 1st Byte";
      }
      leaf bytes23 {
        type xr:live_ncs_Hex-integer;
        units "byte";
        // NCS drop mandatory statement
        description
          "2nd and 3rd Bytes";
      }
      leaf bytes45 {
        type xr:live_ncs_Hex-integer;
        units "byte";
        // NCS drop mandatory statement
        description
          "4th and 5th Bytes";
      }
      leaf bytes67 {
        type xr:live_ncs_Hex-integer;
        units "byte";
        // NCS drop mandatory statement
        description
          "6th and 7th Bytes";
      }
      leaf bytes89 {
        type xr:live_ncs_Hex-integer;
        units "byte";
        // NCS drop mandatory statement
        description
          "8th and 9th Bytes";
      }
      leaf type {
        type live_ncs_Ethernet-segment-identifier;
        // NCS drop mandatory statement
        description
          "Ethernet segment identifier type";
      }
    }
  }

  grouping live_ncs_PREFERENCE-BASED-SERVICE-CARVING {
    description
      "Common node of ethernet-segment,
       evpn-virtual-ethernet-segment";
    container preference-based-service-carving {
      description
        "Preference-Based DF Election Configuration
         Options";
      leaf weight {
        type uint32 {
          range "0..65535";
        }
        description
          "Preference DF weight. For Access-Driven DF, use
           weights of at most 32767 or less.";
      }
      leaf enable {
        type empty;
        description
          "Enable Preference Based Service Carving";
      }
      leaf access-driven {
        type empty;
        description
          "Enable Access-Driven DF Election";
      }
    }
  }

  grouping live_ncs_BRIDGE-DOMAIN-TABLE {
    description
      "Common node of bridge-domain-group, vlan-switch";
    container bridge-domains {
      description
        "List of Bridge Domain";
      list bridge-domain {
        key "name";
        description
          "bridge domain";
        container bd-storm-controls {
          description
            "Storm Control";
          list bd-storm-control {
            // NCS drop must statement
            key "sctype";
            description
              "Storm Control Type";
            leaf sctype {
              type live_ncs_Storm-control;
              description
                "Storm Control Type";
            }
            uses live_ncs_STORM-CONTROL-UNIT;
          }
        }
        container member-vnis {
          description
            "Bridge Domain VxLAN Network Identifier Table";
          list member-vni {
            key "vni";
            description
              "Bridge Domain Member VxLAN Network Identifier";
            container member-vni-static-mac-addresses {
              description
                "Static Mac Address Table";
              list member-vni-static-mac-address {
                key "mac-address";
                description
                  "Static Mac Address Configuration";
                leaf next-hop-ip {
                  type inet:ipv4-address-no-zone;
                  description
                    "Enable Static Mac Address Configuration";
                }
                leaf mac-address {
                  type yang:mac-address;
                  description
                    "Static MAC address";
                }
              }
            }
            leaf vni {
              type uint32 {
                range "1..16777215";
              }
              description
                "VxLAN Network Identifier number";
            }
          }
        }
        container bridge-domain-mac {
          description
            "MAC configuration commands";
          container bd-mac-limit {
            description
              "MAC-Limit configuration commands";
            leaf bd-mac-limit-action {
              type live_ncs_Mac-limit-action;
              description
                "MAC address limit enforcement action";
            }
            leaf bd-mac-limit-notif {
              type live_ncs_Mac-notification;
              description
                "Mac Address Limit Notification";
            }
            leaf bd-mac-limit-max {
              type live_ncs_Mac-limit-range;
              description
                "Number of MAC addresses after which MAC
                 limit action is taken";
            }
          }
          container bd-mac-filters {
            description
              "Filter Mac Address";
            list bd-mac-filter {
              key "address";
              description
                "Static MAC address";
              leaf drop {
                type empty;
                description
                  "MAC address for filtering";
              }
              leaf address {
                type yang:mac-address;
                description
                  "Static MAC address";
              }
            }
          }
          container mac-secure {
            description
              "MAC Secure";
            leaf logging {
              type empty;
              description
                "MAC Secure Logging";
            }
            leaf enable {
              type empty;
              description
                "Enable MAC Secure";
            }
            leaf threshold {
              type empty;
              description
                "MAC Secure Threshold";
            }
            uses live_ncs_ACTION;
            uses live_ncs_SHUTDOWN-RECOVERY-TIMER;
          }
          container bd-mac-aging {
            description
              "MAC-Aging configuration commands";
            leaf bd-mac-aging-type {
              type live_ncs_Mac-aging;
              description
                "MAC address aging type";
            }
            leaf bd-mac-aging-time {
              type live_ncs_Mac-aging-range;
              description
                "Mac Aging Time";
            }
          }
          leaf bd-mac-withdraw-relay {
            type empty;
            description
              "Mac withdraw sent from access PW to access PW";
          }
          leaf bd-mac-withdraw-access-pw-disable {
            type empty;
            description
              "MAC withdraw on Access PW";
          }
          leaf bd-mac-port-down-flush {
            type empty;
            description
              "Disable MAC Flush when Port goes Down";
          }
          leaf bd-mac-withdraw {
            type empty;
            description
              "Disable Mac Withdraw";
          }
          leaf bd-mac-withdraw-behavior {
            type live_ncs_Mac-withdraw-behavior;
            description
              "MAC withdraw sent on bridge port down";
          }
          leaf bd-mac-learn {
            type live_ncs_Bdmac-learn;
            description
              "Mac Learning Type";
          }
        }
        container nv-satellite {
          description
            "nV Satellite";
          leaf offload-ipv4-multicast-enable {
            type empty;
            description
              "Enable IPv4 Multicast Offload to Satellite
               Nodes";
          }
          leaf enable {
            type empty;
            description
              "Enable nV Satellite Settings";
          }
        }
        container bridge-domain-pbb {
          description
            "Bridge Domain PBB";
          container pbb-edges {
            description
              "PBB Edge";
            list pbb-edge {
              key "isid core-bd-name";
              description
                "Configure BD as PBB Edge with ISID and
                 associated PBB Core BD";
              container pbb-edge-split-horizon-group {
                description
                  "Split Horizon Group";
                leaf disable {
                  type empty;
                  description
                    "Disable split horizon group";
                }
              }
              container pbb-static-mac-mappings {
                description
                  "PBB Static Mac Address Mapping Table";
                list pbb-static-mac-mapping {
                  key "address";
                  description
                    "PBB Static Mac Address Mapping
                     Configuration";
                  leaf pbb-static-mac-mapping-bmac {
                    type yang:mac-address;
                    description
                      "Static backbone MAC address to map with";
                  }
                  leaf address {
                    type yang:mac-address;
                    description
                      "Static MAC address";
                  }
                }
              }
              container pbb-edge-dhcp-profile {
                description
                  "Attach a DHCP profile";
                leaf profile-id {
                  type live_ncs_Interface-profile;
                  description
                    "Set the snooping profile";
                }
                leaf dhcp-snooping-id {
                  type string;
                  description
                    "Disable DHCP snooping";
                }
              }
              container pbb-edge-mac {
                description
                  "MAC configuration commands";
                container pbb-edge-mac-limit {
                  description
                    "MAC-Limit configuration commands";
                  leaf pbb-edge-mac-limit-action {
                    type live_ncs_Mac-limit-action;
                    description
                      "MAC address limit enforcement action";
                  }
                  leaf pbb-edge-mac-limit-max {
                    type live_ncs_Mac-limit-range;
                    description
                      "Number of MAC addresses after which MAC
                       limit action is taken";
                  }
                  leaf pbb-edge-mac-limit-notif {
                    type live_ncs_Mac-notification;
                    description
                      "MAC address limit notification action";
                  }
                }
                container pbb-edge-mac-aging {
                  description
                    "MAC-Aging configuration commands";
                  leaf pbb-edge-mac-aging-type {
                    type live_ncs_Mac-aging;
                    description
                      "MAC address aging type";
                  }
                  leaf pbb-edge-mac-aging-time {
                    type live_ncs_Mac-aging-range;
                    description
                      "Mac Aging Time";
                  }
                }
                container pbb-edge-mac-secure {
                  description
                    "MAC Secure";
                  leaf enable {
                    type empty;
                    description
                      "Enable MAC Secure";
                  }
                  leaf accept-shutdown {
                    type empty;
                    description
                      "Accept Virtual instance port to be
                       shutdown on mac violation";
                  }
                  uses live_ncs_LOGGING;
                  uses live_ncs_DISABLE;
                  uses live_ncs_ACTION;
                }
                leaf pbb-edge-mac-learning {
                  type live_ncs_Mac-learn;
                  description
                    "Enable Mac Learning";
                }
              }
              leaf pbb-edge-igmp-profile {
                type xr:live_ncs_Cisco-ios-xr-string;
                description
                  "Attach a IGMP Snooping profile";
              }
              leaf unknown-unicast-bmac {
                type yang:mac-address;
                description
                  "Configure Unknown Unicast BMAC address for
                   PBB Edge Port";
              }
              leaf isid {
                type live_ncs_Pbbisid-range;
                description
                  "ISID";
              }
              leaf core-bd-name {
                type xr:live_ncs_Cisco-ios-xr-string;
                description
                  "Core BD Name";
              }
            }
          }
          container pbb-core {
            description
              "PBB Core";
            container pbb-core-mac {
              description
                "MAC configuration commands";
              container pbb-core-mac-aging {
                description
                  "MAC-Aging configuration commands";
                leaf pbb-core-mac-aging-type {
                  type live_ncs_Mac-aging;
                  description
                    "MAC address aging type";
                }
                leaf pbb-core-mac-aging-time {
                  type live_ncs_Mac-aging-range;
                  description
                    "Mac Aging Time";
                }
              }
              container pbb-core-mac-limit {
                description
                  "MAC-Limit configuration commands";
                leaf pbb-core-mac-limit-max {
                  type live_ncs_Mac-limit-range;
                  description
                    "Number of MAC addresses after which MAC
                     limit action is taken";
                }
                leaf pbb-core-mac-limit-notif {
                  type live_ncs_Mac-notification;
                  description
                    "MAC address limit notification action";
                }
                leaf pbb-core-mac-limit-action {
                  type live_ncs_Mac-limit-action;
                  description
                    "MAC address limit enforcement action";
                }
              }
              leaf pbb-core-mac-learning {
                type live_ncs_Mac-learn;
                description
                  "Enable Mac Learning";
              }
            }
            container pbb-core-evis {
              description
                "PBB Core EVI Table";
              list pbb-core-evi {
                key "eviid";
                description
                  "PBB Core EVI";
                leaf eviid {
                  type live_ncs_Vpnid-range;
                  description
                    "Ethernet VPN ID";
                }
              }
            }
            container pbb-core-dhcp-profile {
              description
                "Attach a DHCP profile";
              leaf profile-id {
                type live_ncs_Interface-profile;
                description
                  "Set the snooping profile";
              }
              leaf dhcp-snooping-id {
                type string;
                description
                  "Disable DHCP snooping";
              }
            }
            leaf pbb-core-mmrp-flood-optimization {
              type empty;
              description
                "Enabling MMRP PBB-VPLS Flood Optimization";
            }
            leaf vlan-id {
              type live_ncs_Pbbvid-range;
              description
                "VLAN ID to push";
            }
            leaf pbb-core-igmp-profile {
              type xr:live_ncs_Cisco-ios-xr-string;
              description
                "Attach a IGMP Snooping profile";
            }
            leaf enable {
              type empty;
              description
                "Enable Bridge Domain PBB Core Configuration";
            }
          }
        }
        container bridge-domain-evis {
          description
            "Bridge Domain EVI Table";
          list bridge-domain-evi {
            key "vpn-id";
            description
              "Bridge Domain MPLS EVPN";
            leaf vpn-id {
              type live_ncs_Evpnvpnid-range;
              description
                "MPLS Ethernet VPN-ID";
            }
          }
        }
        container access-vfis {
          description
            "Specify the access virtual forwarding
             interface name";
          list access-vfi {
            key "name";
            description
              "Name of the Acess Virtual Forwarding
               Interface";
            container access-vfi-pseudowires {
              description
                "List of pseudowires";
              list access-vfi-pseudowire {
                key "neighbor pseudowire-id";
                description
                  "Pseudowire configuration";
                container access-vfi-pseudowire-static-mac-addresses {
                  description
                    "Static Mac Address Table";
                  list access-vfi-pseudowire-static-mac-address {
                    key "address";
                    description
                      "Static Mac Address Configuration";
                    leaf address {
                      type yang:mac-address;
                      description
                        "Static MAC address";
                    }
                  }
                }
                leaf access-vfi-pw-class {
                  type xr:live_ncs_Cisco-ios-xr-string;
                  description
                    "Pseudowire class template name to use for
                     this pseudowire";
                }
                leaf neighbor {
                  type inet:ipv4-address-no-zone;
                  description
                    "Neighbor IP address";
                }
                leaf pseudowire-id {
                  type live_ncs_Pseudowire-id-range;
                  description
                    "Pseudowire ID";
                }
              }
            }
            leaf access-vfi-shutdown {
              type empty;
              description
                "shutdown the AccessVfi";
            }
            leaf name {
              type xr:live_ncs_Cisco-ios-xr-string;
              description
                "Name of the AccessVirtual Forwarding
                 Interface";
            }
          }
        }
        container bd-pseudowires {
          description
            "List of pseudowires";
          list bd-pseudowire {
            key "neighbor pseudowire-id";
            description
              "Pseudowire configuration";
            container pseudowire-dai {
              description
                "Access Pseudowire Dynamic ARP Inspection";
              container pseudowire-dai-address-validation {
                description
                  "Address Validation";
                leaf ipv4-verification {
                  type live_ncs_L2vpn-verification;
                  description
                    "IPv4 Verification";
                }
                leaf destination-mac-verification {
                  type live_ncs_L2vpn-verification;
                  description
                    "Destination MAC Verification";
                }
                leaf source-mac-verification {
                  type live_ncs_L2vpn-verification;
                  description
                    "Source MAC Verification";
                }
              }
              leaf logging {
                type live_ncs_L2vpn-logging;
                description
                  "Logging Type";
              }
              leaf disable {
                type empty;
                description
                  "Disable Dynamic ARP Inspection";
              }
              leaf enable {
                type empty;
                description
                  "Enable Access Pseudowire Dynamic ARP
                   Inspection";
              }
            }
            container bdpw-storm-control-types {
              description
                "Storm Control";
              list bdpw-storm-control-type {
                // NCS drop must statement
                key "sctype";
                description
                  "Storm Control Type";
                leaf sctype {
                  type live_ncs_Storm-control;
                  description
                    "Storm Control Type";
                }
                uses live_ncs_STORM-CONTROL-UNIT;
              }
            }
            container pseudowire-profile {
              description
                "Attach a DHCP profile";
              leaf profile-id {
                type live_ncs_Interface-profile;
                description
                  "Set the snooping profile";
              }
              leaf dhcp-snooping-id {
                type string;
                description
                  "Disable DHCP snooping";
              }
            }
            container bd-pw-static-mac-addresses {
              description
                "Static Mac Address Table";
              list bd-pw-static-mac-address {
                key "address";
                description
                  "Static Mac Address Configuration";
                leaf address {
                  type yang:mac-address;
                  description
                    "Static MAC address";
                }
              }
            }
            container pseudowire-ip-source-guard {
              description
                "IP Source Guard";
              leaf logging {
                type live_ncs_L2vpn-logging;
                description
                  "Logging Type";
              }
              leaf disable {
                type empty;
                description
                  "Disable Dynamic IP source guard";
              }
              leaf enable {
                type empty;
                description
                  "Enable IP Source Guard";
              }
            }
            container pseudowire-mac {
              description
                "Bridge-domain Pseudowire MAC configuration
                 commands";
              container pseudowire-mac-secure {
                description
                  "MAC Secure";
                leaf enable {
                  type empty;
                  description
                    "Enable MAC Secure";
                }
                uses live_ncs_LOGGING;
                uses live_ncs_DISABLE;
                uses live_ncs_ACTION;
                uses live_ncs_SHUTDOWN-RECOVERY-TIMER;
              }
              container pseudowire-mac-aging {
                description
                  "MAC-Aging configuration commands";
                leaf pseudowire-mac-aging-type {
                  type live_ncs_Mac-aging;
                  description
                    "MAC address aging type";
                }
                leaf pseudowire-mac-aging-time {
                  type live_ncs_Mac-aging-range;
                  description
                    "MAC Aging Time";
                }
              }
              container pseudowire-mac-limit {
                description
                  "MAC-Limit configuration commands";
                leaf pseudowire-mac-limit-action {
                  type live_ncs_Mac-limit-action;
                  description
                    "Bridge Access Pseudowire MAC address limit
                     enforcement action";
                }
                leaf pseudowire-mac-limit-notif {
                  type live_ncs_Mac-notification;
                  description
                    "MAC address limit notification action in a
                     Bridge Access Pseudowire";
                }
                leaf pseudowire-mac-limit-max {
                  type live_ncs_Mac-limit-range;
                  description
                    "Number of MAC addresses on a Bridge Access
                     Pseudowire after which MAC limit action is
                     taken";
                }
              }
              leaf pseudowire-mac-port-down-flush {
                type live_ncs_Port-down-flush;
                description
                  "Enable/Disable MAC Flush When Port goes
                   down";
              }
              leaf enable {
                type empty;
                description
                  "Bridge-domain Pseudowire MAC configuration
                   mode";
              }
              leaf pseudowire-mac-learning {
                type live_ncs_Mac-learn;
                description
                  "Enable MAC Learning";
              }
            }
            container bd-pw-split-horizon {
              description
                "Split Horizon";
              container bd-pw-split-horizon-group {
                description
                  "Split Horizon Group";
                leaf enable {
                  type empty;
                  description
                    "Enable split horizon group";
                }
              }
            }
            container bd-pw-mpls-static-labels {
              description
                "MPLS static labels";
              leaf local-static-label {
                type live_ncs_Pseudowire-label-range;
                description
                  "Pseudowire local static label";
              }
              leaf remote-static-label {
                type live_ncs_Pseudowire-label-range;
                description
                  "Pseudowire remote static label";
              }
            }
            container bridge-domain-backup-pseudowires {
              description
                "List of pseudowires";
              list bridge-domain-backup-pseudowire {
                key "neighbor pseudowire-id";
                description
                  "Backup pseudowire configuration";
                leaf bridge-domain-backup-pw-class {
                  type xr:live_ncs_Cisco-ios-xr-string;
                  description
                    "PW class template name to use for this
                     pseudowire";
                }
                leaf neighbor {
                  type inet:ipv4-address-no-zone;
                  description
                    "Neighbor IP address";
                }
                leaf pseudowire-id {
                  type live_ncs_Pseudowire-id-range;
                  description
                    "Pseudowire ID";
                }
              }
            }
            leaf pseudowire-mld-snoop {
              type xr:live_ncs_Cisco-ios-xr-string;
              description
                "Attach a MLD Snooping profile";
            }
            leaf pseudowire-igmp-snoop {
              type xr:live_ncs_Cisco-ios-xr-string;
              description
                "Attach a IGMP Snooping profile";
            }
            leaf pseudowire-flooding {
              type live_ncs_Interface-traffic-flood;
              description
                "Bridge-domain Pseudowire flooding";
            }
            leaf bd-pw-class {
              type xr:live_ncs_Cisco-ios-xr-string;
              description
                "PW class template name to use for this
                 pseudowire";
            }
            leaf pseudowire-flooding-unknown-unicast {
              type live_ncs_Interface-traffic-flood;
              description
                "Bridge-domain Pseudowire flooding Unknown
                 Unicast";
            }
            leaf neighbor {
              type inet:ipv4-address-no-zone;
              description
                "Neighbor IP address";
            }
            leaf pseudowire-id {
              type live_ncs_Pseudowire-id-range;
              description
                "Pseudowire ID";
            }
          }
        }
        container vfis {
          description
            "Specify the virtual forwarding interface name";
          list vfi {
            key "name";
            description
              "Name of the Virtual Forwarding Interface";
            container multicast-p2mp {
              description
                "Enable Multicast P2MP in this VFI";
              container transports {
                description
                  "Multicast P2MP Transport";
                list transport {
                  key "transport-name";
                  description
                    "Multicast P2MP Transport Type";
                  leaf attribute-set-name {
                    type xr:live_ncs_Cisco-ios-xr-string;
                    description
                      "Multicast P2MP TE Attribute Set Name";
                  }
                  leaf transport-name {
                    type live_ncs_Multicast-p2mp-transport;
                    description
                      "Transport Type";
                  }
                }
              }
              container signalings {
                description
                  "Multicast P2MP Signaling Type";
                list signaling {
                  key "signaling-name";
                  description
                    "Multicast P2MP Signaling Type";
                  leaf signaling-name {
                    type live_ncs_Multicast-p2mp-signaling;
                    description
                      "Signaling Type";
                  }
                }
              }
              leaf enable {
                type empty;
                description
                  "Enable Autodiscovery P2MP";
              }
            }
            container vfi-pseudowires {
              description
                "List of pseudowires";
              list vfi-pseudowire {
                key "neighbor pseudowire-id";
                description
                  "Pseudowire configuration";
                container vfi-pw-dhcp-snoop {
                  description
                    "Attach a DHCP Snooping profile";
                  leaf profile-id {
                    type live_ncs_Interface-profile;
                    description
                      "Set the snooping profile";
                  }
                  leaf dhcp-snooping-id {
                    type string;
                    description
                      "Disable DHCP snooping";
                  }
                }
                container vfi-pw-mpls-static-labels {
                  description
                    "MPLS static labels";
                  leaf local-static-label {
                    type live_ncs_Pseudowire-label-range;
                    description
                      "Pseudowire local static label";
                  }
                  leaf remote-static-label {
                    type live_ncs_Pseudowire-label-range;
                    description
                      "Pseudowire remote static label";
                  }
                }
                container pseudowire-static-mac-addresses {
                  description
                    "Static Mac Address Table";
                  list pseudowire-static-mac-address {
                    key "address";
                    description
                      "Static Mac Address Configuration";
                    leaf address {
                      type yang:mac-address;
                      description
                        "Static MAC address";
                    }
                  }
                }
                leaf vfi-pw-class {
                  type xr:live_ncs_Cisco-ios-xr-string;
                  description
                    "PW class template name to use for this
                     pseudowire";
                }
                leaf vfi-pw-igmp-snoop {
                  type xr:live_ncs_Cisco-ios-xr-string;
                  description
                    "Attach a IGMP Snooping profile";
                }
                leaf vfi-pw-mld-snoop {
                  type xr:live_ncs_Cisco-ios-xr-string;
                  description
                    "Attach a MLD Snooping profile";
                }
                leaf neighbor {
                  type inet:ipv4-address-no-zone;
                  description
                    "Neighbor IP address";
                }
                leaf pseudowire-id {
                  type live_ncs_Pseudowire-id-range;
                  description
                    "Pseudowire ID";
                }
              }
            }
            container bgp-auto-discovery {
              description
                "Enable Autodiscovery BGP in this VFI";
              container ldp-signaling-protocol {
                description
                  "Signaling Protocol LDP in this VFI
                   configuration";
                container vpls-id {
                  description
                    "VPLS ID";
                  leaf type {
                    type live_ncs_Ldp-vpls-id;
                    description
                      "VPLS-ID Type";
                  }
                  leaf as {
                    // NCS drop when statement
                    type live_ncs_Vpls-id-as-range;
                    description
                      "Two byte AS number";
                  }
                  leaf as-index {
                    // NCS drop when statement
                    type live_ncs_Vpls-id-as-index;
                    description
                      "AS index";
                  }
                  leaf address {
                    // NCS drop when statement
                    type inet:ipv4-address-no-zone;
                    description
                      "IPV4 address";
                  }
                  leaf address-index {
                    // NCS drop when statement
                    type live_ncs_Vpls-id-addr-index;
                    description
                      "Address index";
                  }
                }
                container flow-label-load-balance {
                  description
                    "Enable Flow Label based load balancing";
                  leaf flow-label {
                    type live_ncs_Flow-label-load-balance;
                    description
                      "Flow Label load balance type";
                  }
                  leaf static {
                    type empty;
                    description
                      "Static Flow Label";
                  }
                }
                leaf enable {
                  type empty;
                  description
                    "Enable LDP as Signaling Protocol.Deletion
                     of this object also causes deletion of all
                     objects under LDPSignalingProtocol.";
                }
              }
              container bgp-route-policy {
                description
                  "Route policy";
                leaf export {
                  type string;
                  description
                    "Export route policy";
                }
              }
              container route-distinguisher {
                description
                  "Route Distinguisher";
                leaf type {
                  type live_ncs_Bgp-route-distinguisher;
                  description
                    "Router Distinguisher Type";
                }
                leaf as {
                  // NCS drop when statement
                  type live_ncs_Rdas-range;
                  description
                    "Two byte or 4 byte AS number";
                }
                leaf as-index {
                  // NCS drop when statement
                  type live_ncs_Rdas-index;
                  description
                    "AS:nn (hex or decimal format)";
                }
                leaf address {
                  // NCS drop when statement
                  type inet:ipv4-address-no-zone;
                  description
                    "IPV4 address";
                }
                leaf addr-index {
                  // NCS drop when statement
                  type live_ncs_Rd-addr-index;
                  description
                    "Addr index";
                }
              }
              container bgp-signaling-protocol {
                description
                  "Enable Signaling Protocol BGP in this VFI";
                container flow-label-load-balance {
                  description
                    "Enable Flow Label based load balancing";
                  leaf flow-label {
                    type live_ncs_Flow-label-load-balance;
                    description
                      "Flow Label load balance type";
                  }
                  leaf static {
                    type empty;
                    description
                      "Static Flow Label";
                  }
                }
                leaf ve-range {
                  type live_ncs_Vedge-range;
                  description
                    "Local Virtual Edge Block Configurable
                     Range";
                }
                leaf veid {
                  type live_ncs_Veid-range;
                  description
                    "Local Virtual Edge Identifier";
                }
                leaf enable {
                  type empty;
                  description
                    "Enable BGP as Signaling Protocol";
                }
              }
              container route-targets {
                description
                  "Route Target";
                list route-target {
                  // NCS drop must statement
                  key "role format";
                  description
                    "Name of the Route Target";
                  leaf role {
                    type live_ncs_Bgp-route-target-role;
                    description
                      "Role of the router target type";
                  }
                  leaf format {
                    type live_ncs_Bgp-route-target-format;
                    description
                      "Format of the route target";
                  }
                  list two-byte-as-or-four-byte-as {
                    // NCS drop when statement
                    key "as as-index";
                    description
                      "two byte as or four byte as";
                    leaf as {
                      type live_ncs_Rdas-range;
                      description
                        "Two byte or 4 byte AS number";
                    }
                    leaf as-index {
                      type live_ncs_Rdas-index;
                      description
                        "AS:nn (hex or decimal format)";
                    }
                  }
                  list ipv4-address {
                    // NCS drop when statement
                    key "address addr-index";
                    description
                      "ipv4 address";
                    leaf address {
                      type inet:ipv4-address-no-zone;
                      description
                        "IPV4 address";
                    }
                    leaf addr-index {
                      type live_ncs_Rd-addr-index;
                      description
                        "Addr index";
                    }
                  }
                }
              }
              leaf table-policy {
                type string;
                description
                  "Table Policy for installation of forwarding
                   data to L2FIB";
              }
              leaf ad-control-word {
                type empty;
                description
                  "Enable control-word for this VFI";
              }
              leaf enable {
                type empty;
                description
                  "Enable Autodiscovery BGP";
              }
            }
            leaf vfi-shutdown {
              type empty;
              description
                "Enabling Shutdown";
            }
            leaf vpnid {
              type live_ncs_Vpnid-range;
              description
                "VPN Identifier";
            }
            leaf name {
              type xr:live_ncs_Cisco-ios-xr-string;
              description
                "Name of the Virtual Forwarding Interface";
            }
          }
        }
        container bridge-domainvnis {
          description
            "Bridge Domain EVPN VxLAN Network Identifier
             Table";
          list bridge-domainvni {
            key "vpn-id";
            description
              "Bridge Domain VxLAN EVPN";
            leaf vpn-id {
              type uint32 {
                range "1..16777215";
              }
              description
                "VxLAN Ethernet VPN-ID";
            }
          }
        }
        container bd-attachment-circuits {
          description
            "Attachment Circuit table";
          list bd-attachment-circuit {
            key "name";
            description
              "Name of the Attachment Circuit";
            container interface-ip-source-guard {
              description
                "IP Source Guard";
              leaf logging {
                type live_ncs_L2vpn-logging;
                description
                  "Logging Type";
              }
              leaf disable {
                type empty;
                description
                  "Disable L2 Interface Dynamic IP source
                   guard";
              }
              leaf enable {
                type empty;
                description
                  "Enable IP Source Guard";
              }
            }
            container interface-dai {
              description
                "L2 Interface Dynamic ARP Inspection";
              container interface-dai-address-validation {
                description
                  "Address Validation";
                leaf ipv4-verification {
                  type live_ncs_L2vpn-verification;
                  description
                    "IPv4 Verification";
                }
                leaf destination-mac-verification {
                  type live_ncs_L2vpn-verification;
                  description
                    "Destination MAC Verification";
                }
                leaf source-mac-verification {
                  type live_ncs_L2vpn-verification;
                  description
                    "Source MAC Verification";
                }
                leaf enable {
                  type empty;
                  description
                    "Enable Address Validation";
                }
              }
              leaf logging {
                type live_ncs_L2vpn-logging;
                description
                  "Logging Type";
              }
              leaf disable {
                type empty;
                description
                  "Disable L2 Interface Dynamic ARP Inspection";
              }
              leaf enable {
                type empty;
                description
                  "Enable L2 Interface Dynamic ARP Inspection";
              }
            }
            container interface-profile {
              description
                "Attach a DHCP profile";
              leaf profile-id {
                type live_ncs_Interface-profile;
                description
                  "Set the snooping profile";
              }
              leaf dhcp-snooping-id {
                type string;
                description
                  "Disable DHCP snooping";
              }
            }
            container bdac-storm-control-types {
              description
                "Storm Control";
              list bdac-storm-control-type {
                // NCS drop must statement
                key "sctype";
                description
                  "Storm Control Type";
                leaf sctype {
                  type live_ncs_Storm-control;
                  description
                    "Storm Control Type";
                }
                uses live_ncs_STORM-CONTROL-UNIT;
              }
            }
            container split-horizon {
              description
                "Split Horizon";
              container split-horizon-group-id {
                description
                  "Split Horizon Group ID";
                leaf enable {
                  type empty;
                  description
                    "Enable split horizon group";
                }
              }
            }
            container static-mac-addresses {
              description
                "Static Mac Address Table";
              list static-mac-address {
                key "address";
                description
                  "Static Mac Address Configuration";
                leaf address {
                  type yang:mac-address;
                  description
                    "Static MAC address";
                }
              }
            }
            container interface-mac {
              description
                "MAC configuration commands";
              container interface-mac-aging {
                description
                  "MAC-Aging configuration commands";
                leaf interface-mac-aging-time {
                  type live_ncs_Mac-aging-range;
                  description
                    "Mac Aging Time";
                }
                leaf interface-mac-aging-type {
                  type live_ncs_Mac-aging;
                  description
                    "MAC address aging type";
                }
              }
              container interface-mac-secure {
                description
                  "MAC Secure";
                leaf enable {
                  type empty;
                  description
                    "Enable MAC Secure";
                }
                uses live_ncs_LOGGING;
                uses live_ncs_DISABLE;
                uses live_ncs_ACTION;
                uses live_ncs_SHUTDOWN-RECOVERY-TIMER;
              }
              container interface-mac-limit {
                description
                  "MAC-Limit configuration commands";
                leaf interface-mac-limit-max {
                  type live_ncs_Mac-limit-range;
                  description
                    "Number of MAC addresses on an Interface
                     after which MAC limit action is taken";
                }
                leaf interface-mac-limit-notif {
                  type live_ncs_Mac-notification;
                  description
                    "MAC address limit notification action in a
                     Interface";
                }
                leaf interface-mac-limit-action {
                  type live_ncs_Mac-limit-action;
                  description
                    "Interface MAC address limit enforcement
                     action";
                }
              }
              leaf interface-mac-port-down-flush {
                type live_ncs_Port-down-flush;
                description
                  "Enable/Disable MAC Flush When Port goes
                   down";
              }
              leaf interface-mac-learning {
                type live_ncs_Mac-learn;
                description
                  "Enable Mac Learning";
              }
            }
            leaf interface-flooding {
              type live_ncs_Interface-traffic-flood;
              description
                "Enable or Disable Flooding";
            }
            leaf interface-igmp-snoop {
              type xr:live_ncs_Cisco-ios-xr-string;
              description
                "Attach a IGMP Snooping profile";
            }
            leaf interface-flooding-unknown-unicast {
              type live_ncs_Interface-traffic-flood;
              description
                "Enable or Disable Unknown Unicast Flooding";
            }
            leaf interface-mld-snoop {
              type xr:live_ncs_Cisco-ios-xr-string;
              description
                "Attach a MLD Snooping profile";
            }
            leaf name {
              type xr:live_ncs_Interface-name;
              description
                "The name of the Attachment Circuit";
            }
          }
        }
        container bd-pseudowire-evpns {
          description
            "List of EVPN pseudowires";
          list bd-pseudowire-evpn {
            key "eviid acid";
            description
              "EVPN Pseudowire configuration";
            leaf eviid {
              type live_ncs_Evpnvpnid-range;
              description
                "Ethernet VPN ID";
            }
            leaf acid {
              type live_ncs_Pseudowire-acid-range;
              description
                "AC ID";
            }
          }
        }
        container ip-source-guard {
          description
            "IP Source Guard";
          leaf logging {
            type empty;
            description
              "Enable Logging";
          }
          leaf enable {
            type empty;
            description
              "Enable IP Source Guard";
          }
        }
        container dai {
          description
            "Dynamic ARP Inspection";
          container dai-address-validation {
            description
              "Address Validation";
            leaf ipv4-verification {
              type empty;
              description
                "Enable IPv4 Verification";
            }
            leaf destination-mac-verification {
              type empty;
              description
                "Enable Destination MAC Verification";
            }
            leaf source-mac-verification {
              type empty;
              description
                "Enable Source MAC Verification";
            }
            leaf enable {
              type empty;
              description
                "Enable Address Validation";
            }
          }
          leaf logging {
            type empty;
            description
              "Enable Logging";
          }
          leaf enable {
            type empty;
            description
              "Enable Dynamic ARP Inspection";
          }
        }
        container routed-interfaces {
          description
            "Bridge Domain Routed Interface Table";
          list routed-interface {
            key "interface-name";
            description
              "Bridge Domain Routed Interface";
            container routed-interface-split-horizon-group {
              description
                "Routed interface split horizon group";
              leaf routed-interface-split-horizon-group-core {
                type empty;
                description
                  "Configure BVI under SHG 1";
              }
            }
            leaf interface-name {
              type xr:live_ncs_Interface-name;
              description
                "The name of the Routed Interface";
            }
          }
        }
        leaf coupled-mode {
          type empty;
          description
            "Coupled-mode configuration";
        }
        leaf shutdown {
          type empty;
          description
            "shutdown the Bridge Domain";
        }
        leaf flooding-unknown-unicast {
          type empty;
          description
            "Disable Unknown Unicast flooding";
        }
        leaf efp-visibility {
          type empty;
          description
            "Enable multicast for multiple VLANs in the
             bridge of a BVI";
        }
        leaf l2-multicast-source {
          type live_ncs_L2mc-src-traffic-enabled;
          description
            "L2MC Source Traffic Enabled";
        }
        leaf igmp-snooping-disable {
          type empty;
          description
            "Disable IGMP Snooping";
        }
        leaf transport-mode {
          type live_ncs_Bridge-domain-transport-mode;
          description
            "Bridge Domain Transport mode";
        }
        leaf mld-snooping {
          type xr:live_ncs_Cisco-ios-xr-string;
          description
            "Attach MLD Snooping Profile Name";
        }
        leaf bridge-domain-mtu {
          type live_ncs_Bridge-bd-mtu-range;
          units "byte";
          description
            "Maximum transmission unit for this Bridge
             Domain";
        }
        leaf dhcp {
          type string {
            length "1..32";
          }
          description
            "DHCPv4 Snooping profile name";
        }
        leaf bridge-description {
          type string {
            length "1..64";
          }
          description
            "Bridge-domain description Name";
        }
        leaf igmp-snooping {
          type xr:live_ncs_Cisco-ios-xr-string;
          description
            "Attach IGMP Snooping Profile Name";
        }
        leaf flooding {
          type empty;
          description
            "Disable flooding";
        }
        leaf name {
          type xr:live_ncs_Cisco-ios-xr-string;
          description
            "Name of the bridge domain";
        }
      }
    }
  }

  grouping live_ncs_SHUTDOWN-RECOVERY-TIMER {
    description
      "Common node of mac-secure, interface-mac-secure,
       pseudowire-mac-secure";
    leaf shutdown-recovery-timer {
      type live_ncs_Mac-secure-shutdown-recovery-time-range;
      description
        "MAC Secure Shutdown Recovery Timer";
    }
  }

  grouping live_ncs_DISABLE {
    description
      "Common node of pbb-edge-mac-secure,
       interface-mac-secure, pseudowire-mac-secure";
    leaf disable {
      type empty;
      description
        "Disable MAC Secure";
    }
  }

  grouping STORM-CONTROL-UNIT {
    description
      "Common node of bd-storm-control,
       bdac-storm-control-type, bdpw-storm-control-type";
    container storm-control-unit {
      must 'kbits-per-sec or pkts-per-sec' {
        tailf:xpath-root 3;
      }
      description
        "Specify units for Storm Control Configuration";
      leaf kbits-per-sec {
        type Storm-control-kbps-range;
        units "kbit/s";
        description
          "Kilobits Per Second, PktsPerSec and KbitsPerSec
           cannot be configured together";
      }
      leaf pkts-per-sec {
        type Storm-control-pps-range;
        units "packet/s";
        description
          "Packets Per Second, PktsPerSec and KbitsPerSec
           cannot be configured together";
      }
    }
  }

  grouping MANUAL-SERVICE-CARVING {
    description
      "Common node of ethernet-segment,
       evpn-virtual-ethernet-segment";
    container manual-service-carving {
      description
        "Enter Manual service carving configuration
         submode";
      container service-list {
        description
          "Manual service carving primary,secondary lists";
        leaf primary {
          type string {
            length "1..150";
          }
          description
            "Primary services list";
        }
        leaf secondary {
          type string {
            length "1..150";
          }
          description
            "Secondary services list";
        }
      }
      leaf enable {
        type empty;
        description
          "Enable Manual service carving";
      }
    }
  }

  grouping SERVICE-CARVING-MCAST-TYPE {
    description
      "Common node of ethernet-segment,
       evpn-virtual-ethernet-segment";
    leaf service-carving-mcast-type {
      type Ethernet-segment-service-carving-mcast;
      description
        "Ethernet-Segment Service Carving multicast mode";
    }
  }

  grouping ACTION {
    description
      "Common node of mac-secure, pbb-edge-mac-secure,
       interface-mac-secure, pseudowire-mac-secure";
    leaf action {
      type Mac-secure-action;
      description
        "MAC secure enforcement action";
    }
  }

  grouping EVPN-ROUTE-DISTINGUISHER {
    description
      "Common node of evpn-bgp-auto-discovery,
       evpn-instance-bgp-auto-discovery, pw-routing-bgp";
    container evpn-route-distinguisher {
      description
        "Route Distinguisher";
      leaf type {
        type Bgp-route-distinguisher;
        description
          "Router Distinguisher Type";
      }
      leaf as {
        when "../type = 'two-byte-as' or ../type = 'four-byte-as'" {
          tailf:xpath-root 3;
          description
            "../Type = TwoByteAS or ../Type = FourByteAS";
        }
        type Rdas-range;
        description
          "Two byte or 4 byte AS number";
      }
      leaf as-index {
        when "../type = 'two-byte-as' or ../type = 'four-byte-as'" {
          tailf:xpath-root 3;
          description
            "../Type = TwoByteAS or ../Type = FourByteAS";
        }
        type Rdas-index;
        description
          "AS:nn (hex or decimal format)";
      }
      leaf address {
        when "../type = 'ipv4-address'" {
          tailf:xpath-root 3;
          description
            "../Type = IPV4Address";
        }
        type inet:ipv4-address-no-zone;
        description
          "IPV4 address";
      }
      leaf addr-index {
        when "../type = 'ipv4-address'" {
          tailf:xpath-root 3;
          description
            "../Type = IPV4Address";
        }
        type Rd-addr-index;
        description
          "Addr index";
      }
    }
  }

  grouping EVPN-VIRTUAL-ETHERNET-SEGMENT {
    description
      "Common node of evpn-virtual-access-pw,
       evpn-virtual-access-vfi";
    container evpn-virtual-ethernet-segment {
      description
        "Enter Ethernet Segment configuration submode";
      leaf enable {
        type empty;
        description
          "Enable Ethernet Segment";
      }
      uses SERVICE-CARVING-MCAST-TYPE;
      uses ES-IMPORT-ROUTE-TARGET;
      uses SERVICE-CARVING-TYPE;
      uses IDENTIFIER;
      uses PREFERENCE-BASED-SERVICE-CARVING;
      uses MANUAL-SERVICE-CARVING;
    }
  }

  grouping LOGGING {
    description
      "Common node of pbb-edge-mac-secure,
       interface-mac-secure, pseudowire-mac-secure";
    leaf logging {
      type L2vpn-logging;
      description
        "MAC Secure Logging";
    }
  }

  grouping ES-IMPORT-ROUTE-TARGET {
    description
      "Common node of ethernet-segment,
       evpn-virtual-ethernet-segment";
    leaf es-import-route-target {
      type yang:mac-address;
      description
        "ES-Import Route Target";
    }
  }

  grouping SERVICE-CARVING-TYPE {
    description
      "Common node of ethernet-segment,
       evpn-virtual-ethernet-segment";
    leaf service-carving-type {
      type Ethernet-segment-service-carving;
      description
        "Ethernet-Segment Service Carving mode";
    }
  }

  grouping IDENTIFIER {
    description
      "Common node of ethernet-segment,
       evpn-virtual-ethernet-segment";
    container identifier {
      presence "Indicates a identifier node is configured.";
      description
        "Ethernet segment identifier";
      leaf bytes01 {
        type xr:Hex-integer;
        mandatory true;
        description
          "Type 0's 1st Byte or Type Byte and 1st Byte";
      }
      leaf bytes23 {
        type xr:Hex-integer;
        units "byte";
        mandatory true;
        description
          "2nd and 3rd Bytes";
      }
      leaf bytes45 {
        type xr:Hex-integer;
        units "byte";
        mandatory true;
        description
          "4th and 5th Bytes";
      }
      leaf bytes67 {
        type xr:Hex-integer;
        units "byte";
        mandatory true;
        description
          "6th and 7th Bytes";
      }
      leaf bytes89 {
        type xr:Hex-integer;
        units "byte";
        mandatory true;
        description
          "8th and 9th Bytes";
      }
      leaf type {
        type Ethernet-segment-identifier;
        mandatory true;
        description
          "Ethernet segment identifier type";
      }
    }
  }

  grouping PREFERENCE-BASED-SERVICE-CARVING {
    description
      "Common node of ethernet-segment,
       evpn-virtual-ethernet-segment";
    container preference-based-service-carving {
      description
        "Preference-Based DF Election Configuration
         Options";
      leaf weight {
        type uint32 {
          range "0..65535";
        }
        description
          "Preference DF weight. For Access-Driven DF, use
           weights of at most 32767 or less.";
      }
      leaf enable {
        type empty;
        description
          "Enable Preference Based Service Carving";
      }
      leaf access-driven {
        type empty;
        description
          "Enable Access-Driven DF Election";
      }
    }
  }

  grouping BRIDGE-DOMAIN-TABLE {
    description
      "Common node of bridge-domain-group, vlan-switch";
    container bridge-domains {
      description
        "List of Bridge Domain";
      list bridge-domain {
        key "name";
        description
          "bridge domain";
        container bd-storm-controls {
          description
            "Storm Control";
          list bd-storm-control {
            must 'storm-control-unit' {
              tailf:xpath-root 3;
            }
            key "sctype";
            description
              "Storm Control Type";
            leaf sctype {
              type Storm-control;
              description
                "Storm Control Type";
            }
            uses STORM-CONTROL-UNIT;
          }
        }
        container member-vnis {
          description
            "Bridge Domain VxLAN Network Identifier Table";
          list member-vni {
            key "vni";
            description
              "Bridge Domain Member VxLAN Network Identifier";
            container member-vni-static-mac-addresses {
              description
                "Static Mac Address Table";
              list member-vni-static-mac-address {
                key "mac-address";
                description
                  "Static Mac Address Configuration";
                leaf next-hop-ip {
                  type inet:ipv4-address-no-zone;
                  description
                    "Enable Static Mac Address Configuration";
                }
                leaf mac-address {
                  type yang:mac-address;
                  description
                    "Static MAC address";
                }
              }
            }
            leaf vni {
              type uint32 {
                range "1..16777215";
              }
              description
                "VxLAN Network Identifier number";
            }
          }
        }
        container bridge-domain-mac {
          description
            "MAC configuration commands";
          container bd-mac-limit {
            description
              "MAC-Limit configuration commands";
            leaf bd-mac-limit-action {
              type Mac-limit-action;
              description
                "MAC address limit enforcement action";
            }
            leaf bd-mac-limit-notif {
              type Mac-notification;
              description
                "Mac Address Limit Notification";
            }
            leaf bd-mac-limit-max {
              type Mac-limit-range;
              description
                "Number of MAC addresses after which MAC
                 limit action is taken";
            }
          }
          container bd-mac-filters {
            description
              "Filter Mac Address";
            list bd-mac-filter {
              key "address";
              description
                "Static MAC address";
              leaf drop {
                type empty;
                description
                  "MAC address for filtering";
              }
              leaf address {
                type yang:mac-address;
                description
                  "Static MAC address";
              }
            }
          }
          container mac-secure {
            description
              "MAC Secure";
            leaf logging {
              type empty;
              description
                "MAC Secure Logging";
            }
            leaf enable {
              type empty;
              description
                "Enable MAC Secure";
            }
            leaf threshold {
              type empty;
              description
                "MAC Secure Threshold";
            }
            uses ACTION;
            uses SHUTDOWN-RECOVERY-TIMER;
          }
          container bd-mac-aging {
            description
              "MAC-Aging configuration commands";
            leaf bd-mac-aging-type {
              type Mac-aging;
              description
                "MAC address aging type";
            }
            leaf bd-mac-aging-time {
              type Mac-aging-range;
              description
                "Mac Aging Time";
            }
          }
          leaf bd-mac-withdraw-relay {
            type empty;
            description
              "Mac withdraw sent from access PW to access PW";
          }
          leaf bd-mac-withdraw-access-pw-disable {
            type empty;
            description
              "MAC withdraw on Access PW";
          }
          leaf bd-mac-port-down-flush {
            type empty;
            description
              "Disable MAC Flush when Port goes Down";
          }
          leaf bd-mac-withdraw {
            type empty;
            description
              "Disable Mac Withdraw";
          }
          leaf bd-mac-withdraw-behavior {
            type Mac-withdraw-behavior;
            description
              "MAC withdraw sent on bridge port down";
          }
          leaf bd-mac-learn {
            type Bdmac-learn;
            description
              "Mac Learning Type";
          }
        }
        container nv-satellite {
          description
            "nV Satellite";
          leaf offload-ipv4-multicast-enable {
            type empty;
            description
              "Enable IPv4 Multicast Offload to Satellite
               Nodes";
          }
          leaf enable {
            type empty;
            description
              "Enable nV Satellite Settings";
          }
        }
        container bridge-domain-pbb {
          description
            "Bridge Domain PBB";
          container pbb-edges {
            description
              "PBB Edge";
            list pbb-edge {
              key "isid core-bd-name";
              description
                "Configure BD as PBB Edge with ISID and
                 associated PBB Core BD";
              container pbb-edge-split-horizon-group {
                description
                  "Split Horizon Group";
                leaf disable {
                  type empty;
                  description
                    "Disable split horizon group";
                }
              }
              container pbb-static-mac-mappings {
                description
                  "PBB Static Mac Address Mapping Table";
                list pbb-static-mac-mapping {
                  key "address";
                  description
                    "PBB Static Mac Address Mapping
                     Configuration";
                  leaf pbb-static-mac-mapping-bmac {
                    type yang:mac-address;
                    description
                      "Static backbone MAC address to map with";
                  }
                  leaf address {
                    type yang:mac-address;
                    description
                      "Static MAC address";
                  }
                }
              }
              container pbb-edge-dhcp-profile {
                description
                  "Attach a DHCP profile";
                leaf profile-id {
                  type Interface-profile;
                  description
                    "Set the snooping profile";
                }
                leaf dhcp-snooping-id {
                  type string;
                  description
                    "Disable DHCP snooping";
                }
              }
              container pbb-edge-mac {
                description
                  "MAC configuration commands";
                container pbb-edge-mac-limit {
                  description
                    "MAC-Limit configuration commands";
                  leaf pbb-edge-mac-limit-action {
                    type Mac-limit-action;
                    description
                      "MAC address limit enforcement action";
                  }
                  leaf pbb-edge-mac-limit-max {
                    type Mac-limit-range;
                    description
                      "Number of MAC addresses after which MAC
                       limit action is taken";
                  }
                  leaf pbb-edge-mac-limit-notif {
                    type Mac-notification;
                    description
                      "MAC address limit notification action";
                  }
                }
                container pbb-edge-mac-aging {
                  description
                    "MAC-Aging configuration commands";
                  leaf pbb-edge-mac-aging-type {
                    type Mac-aging;
                    description
                      "MAC address aging type";
                  }
                  leaf pbb-edge-mac-aging-time {
                    type Mac-aging-range;
                    description
                      "Mac Aging Time";
                  }
                }
                container pbb-edge-mac-secure {
                  description
                    "MAC Secure";
                  leaf enable {
                    type empty;
                    description
                      "Enable MAC Secure";
                  }
                  leaf accept-shutdown {
                    type empty;
                    description
                      "Accept Virtual instance port to be
                       shutdown on mac violation";
                  }
                  uses LOGGING;
                  uses DISABLE;
                  uses ACTION;
                }
                leaf pbb-edge-mac-learning {
                  type Mac-learn;
                  description
                    "Enable Mac Learning";
                }
              }
              leaf pbb-edge-igmp-profile {
                type xr:Cisco-ios-xr-string {
                  length "1..32";
                }
                description
                  "Attach a IGMP Snooping profile";
              }
              leaf unknown-unicast-bmac {
                type yang:mac-address;
                description
                  "Configure Unknown Unicast BMAC address for
                   PBB Edge Port";
              }
              leaf isid {
                type Pbbisid-range;
                description
                  "ISID";
              }
              leaf core-bd-name {
                type xr:Cisco-ios-xr-string {
                  length "1..27";
                }
                description
                  "Core BD Name";
              }
            }
          }
          container pbb-core {
            description
              "PBB Core";
            container pbb-core-mac {
              description
                "MAC configuration commands";
              container pbb-core-mac-aging {
                description
                  "MAC-Aging configuration commands";
                leaf pbb-core-mac-aging-type {
                  type Mac-aging;
                  description
                    "MAC address aging type";
                }
                leaf pbb-core-mac-aging-time {
                  type Mac-aging-range;
                  description
                    "Mac Aging Time";
                }
              }
              container pbb-core-mac-limit {
                description
                  "MAC-Limit configuration commands";
                leaf pbb-core-mac-limit-max {
                  type Mac-limit-range;
                  description
                    "Number of MAC addresses after which MAC
                     limit action is taken";
                }
                leaf pbb-core-mac-limit-notif {
                  type Mac-notification;
                  description
                    "MAC address limit notification action";
                }
                leaf pbb-core-mac-limit-action {
                  type Mac-limit-action;
                  description
                    "MAC address limit enforcement action";
                }
              }
              leaf pbb-core-mac-learning {
                type Mac-learn;
                description
                  "Enable Mac Learning";
              }
            }
            container pbb-core-evis {
              description
                "PBB Core EVI Table";
              list pbb-core-evi {
                key "eviid";
                description
                  "PBB Core EVI";
                leaf eviid {
                  type Vpnid-range;
                  description
                    "Ethernet VPN ID";
                }
              }
            }
            container pbb-core-dhcp-profile {
              description
                "Attach a DHCP profile";
              leaf profile-id {
                type Interface-profile;
                description
                  "Set the snooping profile";
              }
              leaf dhcp-snooping-id {
                type string;
                description
                  "Disable DHCP snooping";
              }
            }
            leaf pbb-core-mmrp-flood-optimization {
              type empty;
              description
                "Enabling MMRP PBB-VPLS Flood Optimization";
            }
            leaf vlan-id {
              type Pbbvid-range;
              description
                "VLAN ID to push";
            }
            leaf pbb-core-igmp-profile {
              type xr:Cisco-ios-xr-string {
                length "1..32";
              }
              description
                "Attach a IGMP Snooping profile";
            }
            leaf enable {
              type empty;
              description
                "Enable Bridge Domain PBB Core Configuration";
            }
          }
        }
        container bridge-domain-evis {
          description
            "Bridge Domain EVI Table";
          list bridge-domain-evi {
            key "vpn-id";
            description
              "Bridge Domain MPLS EVPN";
            leaf vpn-id {
              type Evpnvpnid-range;
              description
                "MPLS Ethernet VPN-ID";
            }
          }
        }
        container access-vfis {
          description
            "Specify the access virtual forwarding
             interface name";
          list access-vfi {
            key "name";
            description
              "Name of the Acess Virtual Forwarding
               Interface";
            container access-vfi-pseudowires {
              description
                "List of pseudowires";
              list access-vfi-pseudowire {
                key "neighbor pseudowire-id";
                description
                  "Pseudowire configuration";
                container access-vfi-pseudowire-static-mac-addresses {
                  description
                    "Static Mac Address Table";
                  list access-vfi-pseudowire-static-mac-address {
                    key "address";
                    description
                      "Static Mac Address Configuration";
                    leaf address {
                      type yang:mac-address;
                      description
                        "Static MAC address";
                    }
                  }
                }
                leaf access-vfi-pw-class {
                  type xr:Cisco-ios-xr-string {
                    length "1..32";
                  }
                  description
                    "Pseudowire class template name to use for
                     this pseudowire";
                }
                leaf neighbor {
                  type inet:ipv4-address-no-zone;
                  description
                    "Neighbor IP address";
                }
                leaf pseudowire-id {
                  type Pseudowire-id-range;
                  description
                    "Pseudowire ID";
                }
              }
            }
            leaf access-vfi-shutdown {
              type empty;
              description
                "shutdown the AccessVfi";
            }
            leaf name {
              type xr:Cisco-ios-xr-string {
                length "1..32";
              }
              description
                "Name of the AccessVirtual Forwarding
                 Interface";
            }
          }
        }
        container bd-pseudowires {
          description
            "List of pseudowires";
          list bd-pseudowire {
            key "neighbor pseudowire-id";
            description
              "Pseudowire configuration";
            container pseudowire-dai {
              description
                "Access Pseudowire Dynamic ARP Inspection";
              container pseudowire-dai-address-validation {
                description
                  "Address Validation";
                leaf ipv4-verification {
                  type L2vpn-verification;
                  description
                    "IPv4 Verification";
                }
                leaf destination-mac-verification {
                  type L2vpn-verification;
                  description
                    "Destination MAC Verification";
                }
                leaf source-mac-verification {
                  type L2vpn-verification;
                  description
                    "Source MAC Verification";
                }
              }
              leaf logging {
                type L2vpn-logging;
                description
                  "Logging Type";
              }
              leaf disable {
                type empty;
                description
                  "Disable Dynamic ARP Inspection";
              }
              leaf enable {
                type empty;
                description
                  "Enable Access Pseudowire Dynamic ARP
                   Inspection";
              }
            }
            container bdpw-storm-control-types {
              description
                "Storm Control";
              list bdpw-storm-control-type {
                must 'storm-control-unit' {
                  tailf:xpath-root 3;
                }
                key "sctype";
                description
                  "Storm Control Type";
                leaf sctype {
                  type Storm-control;
                  description
                    "Storm Control Type";
                }
                uses STORM-CONTROL-UNIT;
              }
            }
            container pseudowire-profile {
              description
                "Attach a DHCP profile";
              leaf profile-id {
                type Interface-profile;
                description
                  "Set the snooping profile";
              }
              leaf dhcp-snooping-id {
                type string;
                description
                  "Disable DHCP snooping";
              }
            }
            container bd-pw-static-mac-addresses {
              description
                "Static Mac Address Table";
              list bd-pw-static-mac-address {
                key "address";
                description
                  "Static Mac Address Configuration";
                leaf address {
                  type yang:mac-address;
                  description
                    "Static MAC address";
                }
              }
            }
            container pseudowire-ip-source-guard {
              description
                "IP Source Guard";
              leaf logging {
                type L2vpn-logging;
                description
                  "Logging Type";
              }
              leaf disable {
                type empty;
                description
                  "Disable Dynamic IP source guard";
              }
              leaf enable {
                type empty;
                description
                  "Enable IP Source Guard";
              }
            }
            container pseudowire-mac {
              description
                "Bridge-domain Pseudowire MAC configuration
                 commands";
              container pseudowire-mac-secure {
                description
                  "MAC Secure";
                leaf enable {
                  type empty;
                  description
                    "Enable MAC Secure";
                }
                uses LOGGING;
                uses DISABLE;
                uses ACTION;
                uses SHUTDOWN-RECOVERY-TIMER;
              }
              container pseudowire-mac-aging {
                description
                  "MAC-Aging configuration commands";
                leaf pseudowire-mac-aging-type {
                  type Mac-aging;
                  description
                    "MAC address aging type";
                }
                leaf pseudowire-mac-aging-time {
                  type Mac-aging-range;
                  description
                    "MAC Aging Time";
                }
              }
              container pseudowire-mac-limit {
                description
                  "MAC-Limit configuration commands";
                leaf pseudowire-mac-limit-action {
                  type Mac-limit-action;
                  description
                    "Bridge Access Pseudowire MAC address limit
                     enforcement action";
                }
                leaf pseudowire-mac-limit-notif {
                  type Mac-notification;
                  description
                    "MAC address limit notification action in a
                     Bridge Access Pseudowire";
                }
                leaf pseudowire-mac-limit-max {
                  type Mac-limit-range;
                  description
                    "Number of MAC addresses on a Bridge Access
                     Pseudowire after which MAC limit action is
                     taken";
                }
              }
              leaf pseudowire-mac-port-down-flush {
                type Port-down-flush;
                description
                  "Enable/Disable MAC Flush When Port goes
                   down";
              }
              leaf enable {
                type empty;
                description
                  "Bridge-domain Pseudowire MAC configuration
                   mode";
              }
              leaf pseudowire-mac-learning {
                type Mac-learn;
                description
                  "Enable MAC Learning";
              }
            }
            container bd-pw-split-horizon {
              description
                "Split Horizon";
              container bd-pw-split-horizon-group {
                description
                  "Split Horizon Group";
                leaf enable {
                  type empty;
                  description
                    "Enable split horizon group";
                }
              }
            }
            container bd-pw-mpls-static-labels {
              description
                "MPLS static labels";
              leaf local-static-label {
                type Pseudowire-label-range;
                description
                  "Pseudowire local static label";
              }
              leaf remote-static-label {
                type Pseudowire-label-range;
                description
                  "Pseudowire remote static label";
              }
            }
            container bridge-domain-backup-pseudowires {
              description
                "List of pseudowires";
              list bridge-domain-backup-pseudowire {
                key "neighbor pseudowire-id";
                description
                  "Backup pseudowire configuration";
                leaf bridge-domain-backup-pw-class {
                  type xr:Cisco-ios-xr-string {
                    length "1..32";
                  }
                  description
                    "PW class template name to use for this
                     pseudowire";
                }
                leaf neighbor {
                  type inet:ipv4-address-no-zone;
                  description
                    "Neighbor IP address";
                }
                leaf pseudowire-id {
                  type Pseudowire-id-range;
                  description
                    "Pseudowire ID";
                }
              }
            }
            leaf pseudowire-mld-snoop {
              type xr:Cisco-ios-xr-string {
                length "1..32";
              }
              description
                "Attach a MLD Snooping profile";
            }
            leaf pseudowire-igmp-snoop {
              type xr:Cisco-ios-xr-string {
                length "1..32";
              }
              description
                "Attach a IGMP Snooping profile";
            }
            leaf pseudowire-flooding {
              type Interface-traffic-flood;
              description
                "Bridge-domain Pseudowire flooding";
            }
            leaf bd-pw-class {
              type xr:Cisco-ios-xr-string {
                length "1..32";
              }
              description
                "PW class template name to use for this
                 pseudowire";
            }
            leaf pseudowire-flooding-unknown-unicast {
              type Interface-traffic-flood;
              description
                "Bridge-domain Pseudowire flooding Unknown
                 Unicast";
            }
            leaf neighbor {
              type inet:ipv4-address-no-zone;
              description
                "Neighbor IP address";
            }
            leaf pseudowire-id {
              type Pseudowire-id-range;
              description
                "Pseudowire ID";
            }
          }
        }
        container vfis {
          description
            "Specify the virtual forwarding interface name";
          list vfi {
            key "name";
            description
              "Name of the Virtual Forwarding Interface";
            container multicast-p2mp {
              description
                "Enable Multicast P2MP in this VFI";
              container transports {
                description
                  "Multicast P2MP Transport";
                list transport {
                  key "transport-name";
                  description
                    "Multicast P2MP Transport Type";
                  leaf attribute-set-name {
                    type xr:Cisco-ios-xr-string {
                      length "1..64";
                    }
                    description
                      "Multicast P2MP TE Attribute Set Name";
                  }
                  leaf transport-name {
                    type Multicast-p2mp-transport;
                    description
                      "Transport Type";
                  }
                }
              }
              container signalings {
                description
                  "Multicast P2MP Signaling Type";
                list signaling {
                  key "signaling-name";
                  description
                    "Multicast P2MP Signaling Type";
                  leaf signaling-name {
                    type Multicast-p2mp-signaling;
                    description
                      "Signaling Type";
                  }
                }
              }
              leaf enable {
                type empty;
                description
                  "Enable Autodiscovery P2MP";
              }
            }
            container vfi-pseudowires {
              description
                "List of pseudowires";
              list vfi-pseudowire {
                key "neighbor pseudowire-id";
                description
                  "Pseudowire configuration";
                container vfi-pw-dhcp-snoop {
                  description
                    "Attach a DHCP Snooping profile";
                  leaf profile-id {
                    type Interface-profile;
                    description
                      "Set the snooping profile";
                  }
                  leaf dhcp-snooping-id {
                    type string;
                    description
                      "Disable DHCP snooping";
                  }
                }
                container vfi-pw-mpls-static-labels {
                  description
                    "MPLS static labels";
                  leaf local-static-label {
                    type Pseudowire-label-range;
                    description
                      "Pseudowire local static label";
                  }
                  leaf remote-static-label {
                    type Pseudowire-label-range;
                    description
                      "Pseudowire remote static label";
                  }
                }
                container pseudowire-static-mac-addresses {
                  description
                    "Static Mac Address Table";
                  list pseudowire-static-mac-address {
                    key "address";
                    description
                      "Static Mac Address Configuration";
                    leaf address {
                      type yang:mac-address;
                      description
                        "Static MAC address";
                    }
                  }
                }
                leaf vfi-pw-class {
                  type xr:Cisco-ios-xr-string {
                    length "1..32";
                  }
                  description
                    "PW class template name to use for this
                     pseudowire";
                }
                leaf vfi-pw-igmp-snoop {
                  type xr:Cisco-ios-xr-string {
                    length "1..32";
                  }
                  description
                    "Attach a IGMP Snooping profile";
                }
                leaf vfi-pw-mld-snoop {
                  type xr:Cisco-ios-xr-string {
                    length "1..32";
                  }
                  description
                    "Attach a MLD Snooping profile";
                }
                leaf neighbor {
                  type inet:ipv4-address-no-zone;
                  description
                    "Neighbor IP address";
                }
                leaf pseudowire-id {
                  type Pseudowire-id-range;
                  description
                    "Pseudowire ID";
                }
              }
            }
            container bgp-auto-discovery {
              description
                "Enable Autodiscovery BGP in this VFI";
              container ldp-signaling-protocol {
                description
                  "Signaling Protocol LDP in this VFI
                   configuration";
                container vpls-id {
                  description
                    "VPLS ID";
                  leaf type {
                    type Ldp-vpls-id;
                    description
                      "VPLS-ID Type";
                  }
                  leaf as {
                    when "../type = 'two-byte-as'" {
                      tailf:xpath-root 3;
                      description
                        "../Type = TwoByteAS";
                    }
                    type Vpls-id-as-range;
                    description
                      "Two byte AS number";
                  }
                  leaf as-index {
                    when "../type = 'two-byte-as'" {
                      tailf:xpath-root 3;
                      description
                        "../Type = TwoByteAS";
                    }
                    type Vpls-id-as-index;
                    description
                      "AS index";
                  }
                  leaf address {
                    when "../type = 'ipv4-address'" {
                      tailf:xpath-root 3;
                      description
                        "../Type = IPV4Address";
                    }
                    type inet:ipv4-address-no-zone;
                    description
                      "IPV4 address";
                  }
                  leaf address-index {
                    when "../type = 'ipv4-address'" {
                      tailf:xpath-root 3;
                      description
                        "../Type = IPV4Address";
                    }
                    type Vpls-id-addr-index;
                    description
                      "Address index";
                  }
                }
                container flow-label-load-balance {
                  description
                    "Enable Flow Label based load balancing";
                  leaf flow-label {
                    type Flow-label-load-balance;
                    description
                      "Flow Label load balance type";
                  }
                  leaf static {
                    type empty;
                    description
                      "Static Flow Label";
                  }
                }
                leaf enable {
                  type empty;
                  description
                    "Enable LDP as Signaling Protocol.Deletion
                     of this object also causes deletion of all
                     objects under LDPSignalingProtocol.";
                }
              }
              container bgp-route-policy {
                description
                  "Route policy";
                leaf export {
                  type string;
                  description
                    "Export route policy";
                }
              }
              container route-distinguisher {
                description
                  "Route Distinguisher";
                leaf type {
                  type Bgp-route-distinguisher;
                  description
                    "Router Distinguisher Type";
                }
                leaf as {
                  when "../type = 'two-byte-as' or ../type = 'four-byte-as'" {
                    tailf:xpath-root 3;
                    description
                      "../Type = TwoByteAS or ../Type =
                       FourByteAS";
                  }
                  type Rdas-range;
                  description
                    "Two byte or 4 byte AS number";
                }
                leaf as-index {
                  when "../type = 'two-byte-as' or ../type = 'four-byte-as'" {
                    tailf:xpath-root 3;
                    description
                      "../Type = TwoByteAS or ../Type =
                       FourByteAS";
                  }
                  type Rdas-index;
                  description
                    "AS:nn (hex or decimal format)";
                }
                leaf address {
                  when "../type = 'ipv4-address'" {
                    tailf:xpath-root 3;
                    description
                      "../Type = IPV4Address";
                  }
                  type inet:ipv4-address-no-zone;
                  description
                    "IPV4 address";
                }
                leaf addr-index {
                  when "../type = 'ipv4-address'" {
                    tailf:xpath-root 3;
                    description
                      "../Type = IPV4Address";
                  }
                  type Rd-addr-index;
                  description
                    "Addr index";
                }
              }
              container bgp-signaling-protocol {
                description
                  "Enable Signaling Protocol BGP in this VFI";
                container flow-label-load-balance {
                  description
                    "Enable Flow Label based load balancing";
                  leaf flow-label {
                    type Flow-label-load-balance;
                    description
                      "Flow Label load balance type";
                  }
                  leaf static {
                    type empty;
                    description
                      "Static Flow Label";
                  }
                }
                leaf ve-range {
                  type Vedge-range;
                  description
                    "Local Virtual Edge Block Configurable
                     Range";
                }
                leaf veid {
                  type Veid-range;
                  description
                    "Local Virtual Edge Identifier";
                }
                leaf enable {
                  type empty;
                  description
                    "Enable BGP as Signaling Protocol";
                }
              }
              container route-targets {
                description
                  "Route Target";
                list route-target {
                  must 'two-byte-as-or-four-byte-as or ipv4-address' {
                    tailf:xpath-root 3;
                    description
                      "TwoByteAS-or-FourbyteAS or IPV4Address
                       must be present.";
                  }
                  key "role format";
                  description
                    "Name of the Route Target";
                  leaf role {
                    type Bgp-route-target-role;
                    description
                      "Role of the router target type";
                  }
                  leaf format {
                    type Bgp-route-target-format;
                    description
                      "Format of the route target";
                  }
                  list two-byte-as-or-four-byte-as {
                    when "../format = 'two-byte-as' or ../format = 'four-byte-as'" {
                      tailf:xpath-root 3;
                      description
                        "../Format = TwoByteAS or ../Format =
                         FourbyteAS";
                    }
                    key "as as-index";
                    description
                      "two byte as or four byte as";
                    leaf as {
                      type Rdas-range;
                      description
                        "Two byte or 4 byte AS number";
                    }
                    leaf as-index {
                      type Rdas-index;
                      description
                        "AS:nn (hex or decimal format)";
                    }
                  }
                  list ipv4-address {
                    when "../format = 'ipv4-address'" {
                      tailf:xpath-root 3;
                      description
                        "../Format = IPV4Address";
                    }
                    key "address addr-index";
                    description
                      "ipv4 address";
                    leaf address {
                      type inet:ipv4-address-no-zone;
                      description
                        "IPV4 address";
                    }
                    leaf addr-index {
                      type Rd-addr-index;
                      description
                        "Addr index";
                    }
                  }
                }
              }
              leaf table-policy {
                type string;
                description
                  "Table Policy for installation of forwarding
                   data to L2FIB";
              }
              leaf ad-control-word {
                type empty;
                description
                  "Enable control-word for this VFI";
              }
              leaf enable {
                type empty;
                description
                  "Enable Autodiscovery BGP";
              }
            }
            leaf vfi-shutdown {
              type empty;
              description
                "Enabling Shutdown";
            }
            leaf vpnid {
              type Vpnid-range;
              description
                "VPN Identifier";
            }
            leaf name {
              type xr:Cisco-ios-xr-string {
                length "1..32";
              }
              description
                "Name of the Virtual Forwarding Interface";
            }
          }
        }
        container bridge-domainvnis {
          description
            "Bridge Domain EVPN VxLAN Network Identifier
             Table";
          list bridge-domainvni {
            key "vpn-id";
            description
              "Bridge Domain VxLAN EVPN";
            leaf vpn-id {
              type uint32 {
                range "1..16777215";
              }
              description
                "VxLAN Ethernet VPN-ID";
            }
          }
        }
        container bd-attachment-circuits {
          description
            "Attachment Circuit table";
          list bd-attachment-circuit {
            key "name";
            description
              "Name of the Attachment Circuit";
            container interface-ip-source-guard {
              description
                "IP Source Guard";
              leaf logging {
                type L2vpn-logging;
                description
                  "Logging Type";
              }
              leaf disable {
                type empty;
                description
                  "Disable L2 Interface Dynamic IP source
                   guard";
              }
              leaf enable {
                type empty;
                description
                  "Enable IP Source Guard";
              }
            }
            container interface-dai {
              description
                "L2 Interface Dynamic ARP Inspection";
              container interface-dai-address-validation {
                description
                  "Address Validation";
                leaf ipv4-verification {
                  type L2vpn-verification;
                  description
                    "IPv4 Verification";
                }
                leaf destination-mac-verification {
                  type L2vpn-verification;
                  description
                    "Destination MAC Verification";
                }
                leaf source-mac-verification {
                  type L2vpn-verification;
                  description
                    "Source MAC Verification";
                }
                leaf enable {
                  type empty;
                  description
                    "Enable Address Validation";
                }
              }
              leaf logging {
                type L2vpn-logging;
                description
                  "Logging Type";
              }
              leaf disable {
                type empty;
                description
                  "Disable L2 Interface Dynamic ARP Inspection";
              }
              leaf enable {
                type empty;
                description
                  "Enable L2 Interface Dynamic ARP Inspection";
              }
            }
            container interface-profile {
              description
                "Attach a DHCP profile";
              leaf profile-id {
                type Interface-profile;
                description
                  "Set the snooping profile";
              }
              leaf dhcp-snooping-id {
                type string;
                description
                  "Disable DHCP snooping";
              }
            }
            container bdac-storm-control-types {
              description
                "Storm Control";
              list bdac-storm-control-type {
                must 'storm-control-unit' {
                  tailf:xpath-root 3;
                }
                key "sctype";
                description
                  "Storm Control Type";
                leaf sctype {
                  type Storm-control;
                  description
                    "Storm Control Type";
                }
                uses STORM-CONTROL-UNIT;
              }
            }
            container split-horizon {
              description
                "Split Horizon";
              container split-horizon-group-id {
                description
                  "Split Horizon Group ID";
                leaf enable {
                  type empty;
                  description
                    "Enable split horizon group";
                }
              }
            }
            container static-mac-addresses {
              description
                "Static Mac Address Table";
              list static-mac-address {
                key "address";
                description
                  "Static Mac Address Configuration";
                leaf address {
                  type yang:mac-address;
                  description
                    "Static MAC address";
                }
              }
            }
            container interface-mac {
              description
                "MAC configuration commands";
              container interface-mac-aging {
                description
                  "MAC-Aging configuration commands";
                leaf interface-mac-aging-time {
                  type Mac-aging-range;
                  description
                    "Mac Aging Time";
                }
                leaf interface-mac-aging-type {
                  type Mac-aging;
                  description
                    "MAC address aging type";
                }
              }
              container interface-mac-secure {
                description
                  "MAC Secure";
                leaf enable {
                  type empty;
                  description
                    "Enable MAC Secure";
                }
                uses LOGGING;
                uses DISABLE;
                uses ACTION;
                uses SHUTDOWN-RECOVERY-TIMER;
              }
              container interface-mac-limit {
                description
                  "MAC-Limit configuration commands";
                leaf interface-mac-limit-max {
                  type Mac-limit-range;
                  description
                    "Number of MAC addresses on an Interface
                     after which MAC limit action is taken";
                }
                leaf interface-mac-limit-notif {
                  type Mac-notification;
                  description
                    "MAC address limit notification action in a
                     Interface";
                }
                leaf interface-mac-limit-action {
                  type Mac-limit-action;
                  description
                    "Interface MAC address limit enforcement
                     action";
                }
              }
              leaf interface-mac-port-down-flush {
                type Port-down-flush;
                description
                  "Enable/Disable MAC Flush When Port goes
                   down";
              }
              leaf interface-mac-learning {
                type Mac-learn;
                description
                  "Enable Mac Learning";
              }
            }
            leaf interface-flooding {
              type Interface-traffic-flood;
              description
                "Enable or Disable Flooding";
            }
            leaf interface-igmp-snoop {
              type xr:Cisco-ios-xr-string {
                length "1..32";
              }
              description
                "Attach a IGMP Snooping profile";
            }
            leaf interface-flooding-unknown-unicast {
              type Interface-traffic-flood;
              description
                "Enable or Disable Unknown Unicast Flooding";
            }
            leaf interface-mld-snoop {
              type xr:Cisco-ios-xr-string {
                length "1..32";
              }
              description
                "Attach a MLD Snooping profile";
            }
            leaf name {
              type xr:Interface-name;
              description
                "The name of the Attachment Circuit";
            }
          }
        }
        container bd-pseudowire-evpns {
          description
            "List of EVPN pseudowires";
          list bd-pseudowire-evpn {
            key "eviid acid";
            description
              "EVPN Pseudowire configuration";
            leaf eviid {
              type Evpnvpnid-range;
              description
                "Ethernet VPN ID";
            }
            leaf acid {
              type Pseudowire-acid-range;
              description
                "AC ID";
            }
          }
        }
        container ip-source-guard {
          description
            "IP Source Guard";
          leaf logging {
            type empty;
            description
              "Enable Logging";
          }
          leaf enable {
            type empty;
            description
              "Enable IP Source Guard";
          }
        }
        container dai {
          description
            "Dynamic ARP Inspection";
          container dai-address-validation {
            description
              "Address Validation";
            leaf ipv4-verification {
              type empty;
              description
                "Enable IPv4 Verification";
            }
            leaf destination-mac-verification {
              type empty;
              description
                "Enable Destination MAC Verification";
            }
            leaf source-mac-verification {
              type empty;
              description
                "Enable Source MAC Verification";
            }
            leaf enable {
              type empty;
              description
                "Enable Address Validation";
            }
          }
          leaf logging {
            type empty;
            description
              "Enable Logging";
          }
          leaf enable {
            type empty;
            description
              "Enable Dynamic ARP Inspection";
          }
        }
        container routed-interfaces {
          description
            "Bridge Domain Routed Interface Table";
          list routed-interface {
            key "interface-name";
            description
              "Bridge Domain Routed Interface";
            container routed-interface-split-horizon-group {
              description
                "Routed interface split horizon group";
              leaf routed-interface-split-horizon-group-core {
                type empty;
                description
                  "Configure BVI under SHG 1";
              }
            }
            leaf interface-name {
              type xr:Interface-name;
              description
                "The name of the Routed Interface";
            }
          }
        }
        leaf coupled-mode {
          type empty;
          description
            "Coupled-mode configuration";
        }
        leaf shutdown {
          type empty;
          description
            "shutdown the Bridge Domain";
        }
        leaf flooding-unknown-unicast {
          type empty;
          description
            "Disable Unknown Unicast flooding";
        }
        leaf efp-visibility {
          type empty;
          description
            "Enable multicast for multiple VLANs in the
             bridge of a BVI";
        }
        leaf l2-multicast-source {
          type L2mc-src-traffic-enabled;
          description
            "L2MC Source Traffic Enabled";
        }
        leaf igmp-snooping-disable {
          type empty;
          description
            "Disable IGMP Snooping";
        }
        leaf transport-mode {
          type Bridge-domain-transport-mode;
          description
            "Bridge Domain Transport mode";
        }
        leaf mld-snooping {
          type xr:Cisco-ios-xr-string {
            length "1..32";
          }
          description
            "Attach MLD Snooping Profile Name";
        }
        leaf bridge-domain-mtu {
          type Bridge-bd-mtu-range;
          units "byte";
          description
            "Maximum transmission unit for this Bridge
             Domain";
        }
        leaf dhcp {
          type string {
            length "1..32";
          }
          description
            "DHCPv4 Snooping profile name";
        }
        leaf bridge-description {
          type string {
            length "1..64";
          }
          description
            "Bridge-domain description Name";
        }
        leaf igmp-snooping {
          type xr:Cisco-ios-xr-string {
            length "1..32";
          }
          description
            "Attach IGMP Snooping Profile Name";
        }
        leaf flooding {
          type empty;
          description
            "Disable flooding";
        }
        leaf name {
          type xr:Cisco-ios-xr-string {
            length "1..27";
          }
          description
            "Name of the bridge domain";
        }
      }
    }
  }

  grouping SHUTDOWN-RECOVERY-TIMER {
    description
      "Common node of mac-secure, interface-mac-secure,
       pseudowire-mac-secure";
    leaf shutdown-recovery-timer {
      type Mac-secure-shutdown-recovery-time-range;
      description
        "MAC Secure Shutdown Recovery Timer";
    }
  }

  grouping DISABLE {
    description
      "Common node of pbb-edge-mac-secure,
       interface-mac-secure, pseudowire-mac-secure";
    leaf disable {
      type empty;
      description
        "Disable MAC Secure";
    }
  }

  augment "/ncs:devices/ncs:device/ncs:config" {
    container l2vpn {
      tailf:ncs-device-type "netconf";
      tailf:display-when "not(../../ncs:module) or ../../ncs:module[ncs:name='Cisco-IOS-XR-l2vpn-cfg']";
      description
        "L2VPN configuration";
      container pw-routing {
        description
          "Pseudowire-routing attributes";
        container pw-routing-bgp {
          description
            "Enable Autodiscovery BGP Pseudowire-routing BGP";
          leaf enable {
            type empty;
            description
              "Enable Autodiscovery BGP";
          }
          uses EVPN-ROUTE-DISTINGUISHER;
        }
        leaf pw-routing-global-id {
          type Pseudowire-gbl-id-range;
          description
            "Pseudowire-routing Global ID";
        }
      }
      container neighbor {
        description
          "L2VPN neighbor submode";
        leaf ldp-flap {
          type empty;
          description
            "Enable targetted LDP session flap action";
        }
      }
      container database {
        description
          "L2VPN databases";
        container g8032-rings {
          description
            "List of G8032 Ring";
          list g8032-ring {
            key "g8032-ring-name";
            description
              "G8032 Ring";
            container erp-port0s {
              description
                "Ethernet ring protection port0";
              list erp-port0 {
                key "interface-name";
                description
                  "Configure ERP main port0";
                leaf monitor {
                  type xr:Interface-name;
                  description
                    "Ethernet ring protection port0 monitor";
                }
                leaf interface-name {
                  type xr:Interface-name;
                  description
                    "Port0 interface";
                }
              }
            }
            container erp-instances {
              description
                "List of ethernet ring protection instance";
              list erp-instance {
                key "erp-instance-id";
                description
                  "Ethernet ring protection instance";
                container rpl {
                  description
                    "Ring protection link";
                  leaf port {
                    type Erp-port1;
                    description
                      "ERP main port number";
                  }
                  leaf role {
                    type Rpl-role;
                    description
                      "RPL role";
                  }
                }
                container aps {
                  description
                    "Automatic protection switching";
                  container port1 {
                    description
                      "APS channel for ERP port1";
                    leaf aps-type {
                      type Erpaps;
                      description
                        "Port1 APS type";
                    }
                    leaf aps-channel {
                      type string;
                      description
                        "Port1 APS channel in the format of
                         InterfaceName, BDName or XconnectName";
                    }
                  }
                  leaf port0 {
                    type string;
                    description
                      "Port0 APS channel in the format of
                       InterfaceName";
                  }
                  leaf enable {
                    type empty;
                    description
                      "Enable automatic protection switching";
                  }
                  leaf level {
                    type Erpaps-level-range;
                    description
                      "Automatic protection switching level";
                  }
                }
                leaf description {
                  type string {
                    length "1..32";
                  }
                  description
                    "Ethernet ring protection instance
                     description";
                }
                leaf inclusion-list {
                  type string;
                  description
                    "Associates a set of VLAN IDs with the G
                     .8032 instance";
                }
                leaf profile {
                  type string {
                    length "1..32";
                  }
                  description
                    "Ethernet ring protection instance profile";
                }
                leaf erp-instance-id {
                  type Erp-instance-range;
                  description
                    "ERP instance number";
                }
              }
            }
            container erp-port1s {
              description
                "Ethernet ring protection port0";
              list erp-port1 {
                must 'none-or-virtual or interface' {
                  tailf:xpath-root 3;
                  description
                    "None-or-Virtual or Interface must be
                     present.";
                }
                key "erp-port-type";
                description
                  "Ethernet ring protection port1";

                grouping ERP-PORT1-CONTENT {
                  description
                    "ERP PORT1 CONTENT";
                  leaf monitor {
                    type xr:Interface-name;
                    description
                      "Ethernet ring protection port1 monitor";
                  }
                }
                container none-or-virtual {
                  when "../erp-port-type = 'none' or ../erp-port-type = 'virtual'" {
                    tailf:xpath-root 3;
                    description
                      "../ERPPortType = None or ../ERPPortType =
                       Virtual";
                  }
                  presence "Indicates that this node is configured.";
                  description
                    "none or virtual";
                  uses ERP-PORT1-CONTENT;
                }
                leaf erp-port-type {
                  type Erp-port;
                  description
                    "Port1 type";
                }
                list interface {
                  when "../erp-port-type = 'interface'" {
                    tailf:xpath-root 3;
                    description
                      "../ERPPortType = Interface";
                  }
                  key "interface-name";
                  description
                    "interface";
                  leaf interface-name {
                    type xr:Interface-name;
                    description
                      "Port1 interface";
                  }
                  uses ERP-PORT1-CONTENT;
                }
              }
            }
            leaf open-ring {
              type empty;
              description
                "Specify the G.8032 instance as open ring";
            }
            leaf exclusion-list {
              type string;
              description
                "Vlan IDs in the format of a-b,c,d,e-f,g
                 ,untagged";
            }
            leaf erp-provider-bridge {
              type empty;
              description
                "Ethernet ring protection provider bridge";
            }
            leaf g8032-ring-name {
              type xr:Cisco-ios-xr-string {
                length "1..32";
              }
              description
                "Name of the G8032 ring";
            }
          }
        }
        container xconnect-groups {
          description
            "List of xconnect groups";
          list xconnect-group {
            key "name";
            description
              "Xconnect group";
            container p2p-xconnects {
              description
                "List of point to point xconnects";
              list p2p-xconnect {
                key "name";
                description
                  "Point to point xconnect";
                container pseudowire-evpn-srv6s {
                  description
                    "List of EVPN SRv6 Services";
                  list pseudowire-evpn-srv6 {
                    key "eviid remote-acid source-acid";
                    description
                      "EVPN SRv6 P2P Service Configuration";
                    leaf pseudowire-evpn-srv6-locator {
                      type xr:Cisco-ios-xr-string {
                        length "1..58";
                      }
                      description
                        "Specify SRv6 locator name";
                    }
                    leaf eviid {
                      type Evpnvpnid-range;
                      description
                        "Ethernet VPN ID";
                    }
                    leaf remote-acid {
                      type Pseudowire-evpnacid-range;
                      description
                        "Remote AC ID";
                    }
                    leaf source-acid {
                      type Pseudowire-evpnacid-range;
                      description
                        "Source AC ID";
                    }
                  }
                }
                container pseudowire-evpn-srv6-services {
                  description
                    "List of EVPN SRv6 Services keyed by EVI and
                     Service ID";
                  list pseudowire-evpn-srv6-service {
                    key "eviid service-id";
                    description
                      "EVPN SRv6 P2P Service Configuration";
                    leaf pseudowire-evpn-srv6-locator {
                      type xr:Cisco-ios-xr-string {
                        length "1..58";
                      }
                      description
                        "Specify SRv6 locator name";
                    }
                    leaf eviid {
                      type Evpnvpnid-range;
                      description
                        "Ethernet VPN ID";
                    }
                    leaf service-id {
                      type Pseudowire-evpnacid-range;
                      description
                        "Service ID (Target and Source AC ID)";
                    }
                  }
                }
                container backup-attachment-circuits {
                  description
                    "List of backup attachment circuits";
                  list backup-attachment-circuit {
                    key "interface-name";
                    description
                      "Backup attachment circuit";
                    leaf interface-name {
                      type xr:Interface-name;
                      description
                        "Name of the attachment circuit interface";
                    }
                  }
                }
                container pseudowire-evpns {
                  description
                    "List of EVPN Services";
                  list pseudowire-evpn {
                    key "eviid remote-acid source-acid";
                    description
                      "EVPN P2P Service Configuration";
                    leaf class {
                      type xr:Cisco-ios-xr-string {
                        length "1..32";
                      }
                      description
                        "Name of the pseudowire class";
                    }
                    leaf eviid {
                      type Evpnvpnid-range;
                      description
                        "Ethernet VPN ID";
                    }
                    leaf remote-acid {
                      type Pseudowire-evpnacid-range;
                      description
                        "Remote AC ID";
                    }
                    leaf source-acid {
                      type Pseudowire-evpnacid-range;
                      description
                        "Source AC ID";
                    }
                  }
                }
                container pseudowire-neighbor-pseudowire-ids {
                  description
                    "List of pseudowires";

                  grouping PSEUDOWIRE-CONTENT {
                    description
                      "PSEUDOWIRE CONTENT";
                    container mpls-static-labels {
                      description
                        "MPLS static labels";
                      leaf local-static-label {
                        type Pseudowire-label-range;
                        description
                          "Pseudowire local static label";
                      }
                      leaf remote-static-label {
                        type Pseudowire-label-range;
                        description
                          "Pseudowire remote static label";
                      }
                    }
                    container backup-pseudowires {
                      description
                        "List of pseudowires";
                      list backup-pseudowire {
                        key "neighbor pseudowire-id";
                        description
                          "Backup pseudowire for the cross connect";
                        container backup-mpls-static-labels {
                          description
                            "MPLS static labels";
                          leaf local-static-label {
                            type Pseudowire-label-range;
                            description
                              "Pseudowire local static label";
                          }
                          leaf remote-static-label {
                            type Pseudowire-label-range;
                            description
                              "Pseudowire remote static label";
                          }
                        }
                        leaf backup-pw-class {
                          type xr:Cisco-ios-xr-string {
                            length "1..32";
                          }
                          description
                            "PW class template name to use for the
                             backup PW";
                        }
                        leaf neighbor {
                          type inet:ipv4-address-no-zone;
                          description
                            "Neighbor IP address";
                        }
                        leaf pseudowire-id {
                          type Pseudowire-id-range;
                          description
                            "Pseudowire ID";
                        }
                      }
                    }
                    container l2tp-static-attributes {
                      description
                        "L2TP Static Attributes";
                      container l2tp-remote-cookie {
                        description
                          "L2TP remote cookie";
                        leaf size {
                          type L2tp-cookie-size;
                          description
                            "Remote cookie size";
                        }
                        leaf lower-value {
                          type L2tp-cookie-value-range;
                          description
                            "Lower remote cookie value";
                        }
                        leaf higher-value {
                          type L2tp-cookie-value-range;
                          description
                            "Higher remote cookie value";
                        }
                      }
                      container l2tp-secondary-local-cookie {
                        description
                          "L2TP secondary local cookie";
                        leaf size {
                          type L2tp-cookie-size;
                          description
                            "Local cookie size";
                        }
                        leaf lower-value {
                          type L2tp-cookie-value-range;
                          description
                            "Lower local cookie value";
                        }
                        leaf higher-value {
                          type L2tp-cookie-value-range;
                          description
                            "Higher local cookie value";
                        }
                      }
                      container l2tp-local-cookie {
                        description
                          "L2TP local cookie";
                        leaf size {
                          type L2tp-cookie-size;
                          description
                            "Local cookie size";
                        }
                        leaf lower-value {
                          type L2tp-cookie-value-range;
                          description
                            "Lower local cookie value";
                        }
                        leaf higher-value {
                          type L2tp-cookie-value-range;
                          description
                            "Higher local cookie value";
                        }
                      }
                      leaf l2tp-remote-session-id {
                        type L2tp-session-id-range;
                        description
                          "L2TP remote session ID";
                      }
                      leaf l2tp-local-session-id {
                        type L2tp-session-id-range;
                        description
                          "L2TP local session ID";
                      }
                    }
                    container l2tp-static {
                      description
                        "Pseudowire L2TPv3 static configuration";
                      leaf enable {
                        type empty;
                        description
                          "Enable pseudowire L2TPv3 static
                           configuration";
                      }
                    }
                    leaf tag-impose {
                      type Pseudowire-tag-range;
                      description
                        "Tag Impose vlan tagged mode";
                    }
                    leaf class {
                      type xr:Cisco-ios-xr-string {
                        length "1..32";
                      }
                      description
                        "Name of the pseudowire class";
                    }
                    leaf source-address {
                      type inet:ip-address-no-zone;
                      description
                        "Value of the Pseudowire source address.
                         Must be IPv6 only.";
                    }
                    leaf bandwidth {
                      type uint32 {
                        range "0..4294967295";
                      }
                      description
                        "Pseudowire Bandwidth";
                    }
                  }
                  list pseudowire-neighbor-pseudowire-id {
                    key "neighbor pseudowire-id";
                    description
                      "Pseudowire configuration";
                    leaf neighbor {
                      type inet:ipv4-address-no-zone;
                      description
                        "Pseudowire IPv4 address";
                    }
                    leaf pseudowire-id {
                      type Pseudowire-id-range;
                      description
                        "Pseudowire ID";
                    }
                    uses PSEUDOWIRE-CONTENT;
                  }
                  list pseudowire-pseudowire-address-pseudowire-id {
                    key "pseudowire-address pseudowire-id";
                    description
                      "Pseudowire configuration";
                    leaf pseudowire-address {
                      type inet:ipv6-address-no-zone;
                      description
                        "Pseudowire IPv6 address. A pseudowire can
                         have only one address: IPv4 or IPv6";
                    }
                    leaf pseudowire-id {
                      type Pseudowire-id-range;
                      description
                        "Pseudowire ID";
                    }
                    uses PSEUDOWIRE-CONTENT;
                  }
                }
                container monitor-sessions {
                  description
                    "List of Monitor session segments";
                  list monitor-session {
                    key "name";
                    description
                      "Monitor session segment";
                    leaf enable {
                      type empty;
                      description
                        "Enable monitor session segment ";
                    }
                    leaf name {
                      type xr:Cisco-ios-xr-string {
                        length "1..64";
                      }
                      description
                        "Name of the monitor session";
                    }
                  }
                }
                container pseudowire-routeds {
                  description
                    "List of pseudowire-routed";
                  list pseudowire-routed {
                    key "global-id prefix acid sacid";
                    description
                      "Pseudowire configuration";
                    leaf tag-impose {
                      type Pseudowire-tag-range;
                      description
                        "Tag Impose vlan tagged mode";
                    }
                    leaf class {
                      type xr:Cisco-ios-xr-string {
                        length "1..32";
                      }
                      description
                        "Name of the pseudowire class";
                    }
                    leaf global-id {
                      type Pseudowire-gbl-id-range;
                      description
                        "Target Global ID";
                    }
                    leaf prefix {
                      type inet:ipv4-address-no-zone;
                      description
                        "Target Prefix";
                    }
                    leaf acid {
                      type Pseudowire-acid-range;
                      description
                        "Target AC ID";
                    }
                    leaf sacid {
                      type Pseudowire-acid-range;
                      description
                        "Source AC ID";
                    }
                  }
                }
                container pseudowire-evpn-services {
                  description
                    "List of EVPN Services keyed by EVI and
                     Service ID";
                  list pseudowire-evpn-service {
                    key "eviid service-id";
                    description
                      "EVPN P2P Service Configuration";
                    leaf class {
                      type xr:Cisco-ios-xr-string {
                        length "1..32";
                      }
                      description
                        "Name of the pseudowire class";
                    }
                    leaf eviid {
                      type Evpnvpnid-range;
                      description
                        "Ethernet VPN ID";
                    }
                    leaf service-id {
                      type Pseudowire-evpnacid-range;
                      description
                        "Service ID (Remote and Source AC ID)";
                    }
                  }
                }
                container attachment-circuits {
                  description
                    "List of attachment circuits";
                  list attachment-circuit {
                    key "name";
                    description
                      "Attachment circuit interface";
                    leaf enable {
                      type empty;
                      description
                        "Enable attachment circuit interface";
                    }
                    leaf name {
                      type xr:Interface-name;
                      description
                        "Name of the attachment circuit interface";
                    }
                  }
                }
                leaf p2p-description {
                  type string {
                    length "1..64";
                  }
                  description
                    "cross connect description Name";
                }
                leaf interworking {
                  type Interworking;
                  description
                    "Interworking";
                }
                leaf name {
                  type xr:Cisco-ios-xr-string {
                    length "1..38";
                  }
                  description
                    "Name of the point to point xconnect";
                }
              }
            }
            container mp2mp-xconnects {
              description
                "List of multi point to multi point xconnects";
              list mp2mp-xconnect {
                key "name";
                description
                  "Multi point to multi point xconnect";
                container mp2mp-auto-discovery {
                  description
                    "auto-discovery in this MP2MP";
                  container route-distinguisher {
                    description
                      "Route Distinguisher";
                    leaf type {
                      type Bgp-route-distinguisher;
                      description
                        "Router distinguisher type";
                    }
                    leaf as {
                      when "../type = 'two-byte-as' or ../type = 'four-byte-as'" {
                        tailf:xpath-root 3;
                        description
                          "../Type = TwoByteAS or ../Type =
                           FourByteAS";
                      }
                      type Rdas-range;
                      description
                        "Two byte or 4 byte AS number";
                    }
                    leaf as-index {
                      when "../type = 'two-byte-as' or ../type = 'four-byte-as'" {
                        tailf:xpath-root 3;
                        description
                          "../Type = TwoByteAS or ../Type =
                           FourByteAS";
                      }
                      type Rdas-index;
                      description
                        "AS:nn (hex or decimal format)";
                    }
                    leaf address {
                      when "../type = 'ipv4-address'" {
                        tailf:xpath-root 3;
                        description
                          "../Type = IPV4Address";
                      }
                      type inet:ipv4-address-no-zone;
                      description
                        "IPV4 address";
                    }
                    leaf addr-index {
                      when "../type = 'ipv4-address'" {
                        tailf:xpath-root 3;
                        description
                          "../Type = IPV4Address";
                      }
                      type Rd-addr-index;
                      description
                        "Addr index";
                    }
                  }
                  container mp2mp-route-policy {
                    description
                      "Route policy";
                    leaf export {
                      type string;
                      description
                        "Export route policy";
                    }
                  }
                  container mp2mp-route-targets {
                    description
                      "Route Target";
                    list mp2mp-route-target {
                      must 'two-byte-as-or-four-byte-as or ipv4-address' {
                        tailf:xpath-root 3;
                        description
                          "TwoByteAS-or-FourbyteAS or IPV4Address
                           must be present.";
                      }
                      key "role format";
                      description
                        "Name of the Route Target";
                      leaf role {
                        type Bgp-route-target-role;
                        description
                          "Role of the router target type";
                      }
                      leaf format {
                        type Bgp-route-target-format;
                        description
                          "Format of the route target";
                      }
                      list two-byte-as-or-four-byte-as {
                        when "../format = 'two-byte-as' or ../format = 'four-byte-as'" {
                          tailf:xpath-root 3;
                          description
                            "../Format = TwoByteAS or ../Format =
                             FourbyteAS";
                        }
                        key "as as-index";
                        description
                          "two byte as or four byte as";
                        leaf as {
                          type Rdas-range;
                          description
                            "Two byte or 4 byte AS number";
                        }
                        leaf as-index {
                          type Rdas-index;
                          description
                            "AS:nn (hex or decimal format)";
                        }
                      }
                      list ipv4-address {
                        when "../format = 'ipv4-address'" {
                          tailf:xpath-root 3;
                          description
                            "../Format = IPV4Address";
                        }
                        key "address addr-index";
                        description
                          "ipv4 address";
                        leaf address {
                          type inet:ipv4-address-no-zone;
                          description
                            "IPV4 address";
                        }
                        leaf addr-index {
                          type Rd-addr-index;
                          description
                            "Addr index";
                        }
                      }
                    }
                  }
                  container mp2mp-signaling-protocol {
                    description
                      "signaling protocol in this MP2MP";
                    container flow-label-load-balance {
                      description
                        "Enable Flow Label based load balancing";
                      leaf flow-label {
                        type Flow-label-load-balance;
                        description
                          "Flow Label load balance type";
                      }
                      leaf static {
                        type empty;
                        description
                          "Static Flow Label";
                      }
                    }
                    container ceids {
                      description
                        "Local Customer Edge Identifier Table";
                      list ceid {
                        key "ce-id";
                        description
                          "Local Customer Edge Identifier ";
                        container remote-ceid-attachment-circuits {
                          description
                            "AC And Remote Customer Edge Identifier
                             Table";
                          list remote-ceid-attachment-circuit {
                            key "name remote-ce-id";
                            description
                              "AC And Remote Customer Edge Identifier";
                            leaf name {
                              type xr:Interface-name;
                              description
                                "The name of the Attachment Circuit";
                            }
                            leaf remote-ce-id {
                              type Ce-id-range;
                              description
                                "Remote Customer Edge Identifier";
                            }
                          }
                        }
                        leaf ce-id {
                          type Ce-id-range;
                          description
                            "Local Customer Edge Identifier";
                        }
                      }
                    }
                    leaf ce-range {
                      type Cedge-range;
                      description
                        "Local Customer Edge Identifier";
                    }
                    leaf enable {
                      type empty;
                      description
                        "Enable signaling protocol";
                    }
                  }
                  leaf enable {
                    type empty;
                    description
                      "Enable auto-discovery";
                  }
                }
                leaf mp2mpmtu {
                  type L2vpn-mtu-range;
                  units "byte";
                  description
                    "Maximum transmission unit for this MP2MP
                     VPWS instance";
                }
                leaf mp2mp-control-word {
                  type empty;
                  description
                    "Disable control word";
                }
                leaf mp2mpl2-encapsulation {
                  type L2-encapsulation;
                  description
                    "Configure Layer 2 Encapsulation";
                }
                leaf mp2mp-interworking {
                  type Interworking;
                  description
                    "Interworking";
                }
                leaf mp2mp-shutdown {
                  type empty;
                  description
                    "shutdown this MP2MP VPWS instance";
                }
                leaf mp2mpvpn-id {
                  type Vpnid-range;
                  description
                    "VPN Identifier";
                }
                leaf name {
                  type xr:Cisco-ios-xr-string {
                    length "1..26";
                  }
                  description
                    "Name of the multi point to multi point
                     xconnect";
                }
              }
            }
            leaf name {
              type xr:Cisco-ios-xr-string {
                length "1..32";
              }
              description
                "Name of the xconnect group";
            }
          }
        }
        container bridge-domain-groups {
          description
            "List of bridge groups";
          list bridge-domain-group {
            key "name";
            description
              "Bridge group";
            leaf name {
              type xr:Cisco-ios-xr-string {
                length "1..32";
              }
              description
                "Name of the Bridge group";
            }
            uses BRIDGE-DOMAIN-TABLE;
          }
        }
        container pseudowire-classes {
          description
            "List of pseudowire classes";
          list pseudowire-class {
            key "name";
            description
              "Pseudowire class";
            container l2tpv3-encapsulation {
              description
                "L2TPv3 encapsulation";
              container sequencing {
                description
                  "Sequencing";
                leaf sequencing {
                  type L2tpv3-sequencing;
                  default "off";
                  description
                    "Sequencing";
                }
                leaf resync-threshold {
                  type Resync-threshold-range;
                  default "5";
                  description
                    "Out of sequence threshold";
                }
              }
              container type-of-service {
                description
                  "Type of service";
                leaf type-of-service-value {
                  type Type-of-service-range;
                  description
                    "Type of service value";
                }
                leaf type-of-service-mode {
                  type Type-of-service-mode;
                  description
                    "Type of service mode";
                }
              }
              container signaling-protocol {
                description
                  "L2TPv3 signaling protocol";
                leaf protocol {
                  type L2tp-signaling-protocol;
                  default "l2tpv3";
                  description
                    "L2TPv3 signaling protocol";
                }
                leaf l2tpv3-class-name {
                  type xr:Cisco-ios-xr-string {
                    length "1..32";
                  }
                  description
                    "Name of the L2TPv3 class name";
                }
              }
              container path-mtu {
                description
                  "Path maximum transmission unit";
                leaf enable {
                  type empty;
                  description
                    "Enable path MTU";
                }
                leaf max-path-mtu {
                  type Max-path-mtu-range;
                  description
                    "Maximum path maximum transmission unit";
                }
              }
              leaf df-bit-set {
                type empty;
                description
                  "Set the do not fragment bit to 1";
              }
              leaf cookie-size {
                type L2tp-cookie-size;
                default "zero";
                description
                  "Cookie size";
              }
              leaf source-address {
                type inet:ipv4-address-no-zone;
                description
                  "Source IP address";
              }
              leaf transport-mode {
                type Transport-mode;
                description
                  "Transport mode";
              }
              leaf enable {
                type empty;
                description
                  "Enable L2TPv3 encapsulation";
              }
              leaf time-to-live {
                type Time-to-live-range;
                description
                  "Time to live";
              }
            }
            container backup-disable-delay {
              description
                "Back Up Pseudowire class";
              leaf type {
                type Backup-disable;
                description
                  "Delay or Never";
              }
              leaf disable-backup {
                when "../type = 'delay'" {
                  tailf:xpath-root 3;
                  description
                    "../Type = Delay";
                }
                type Backup-disable-delay-range;
                description
                  "Disable backup delay";
              }
            }
            container mpls-encapsulation {
              description
                "MPLS encapsulation";
              container sequencing {
                description
                  "Sequencing";
                leaf sequencing {
                  type Mpls-sequencing;
                  default "off";
                  description
                    "Sequencing";
                }
                leaf resync-threshold {
                  type Resync-threshold-range;
                  default "5";
                  description
                    "Out of sequence threshold";
                }
              }
              container mpls-redundancy {
                description
                  "Redundancy options for MPLS encapsulation";
                leaf redundancy-one-way {
                  type empty;
                  description
                    "Force one-way PW redundancy behavior in
                     Redundancy Group";
                }
                leaf redundancy-initial-delay {
                  type Pw-redundancy-initial-delay-range;
                  units "second";
                  description
                    "Initial delay before activating the
                     redundant PW, in seconds";
                }
              }
              container preferred-path {
                description
                  "Preferred path";
                leaf type {
                  type Preferred-path;
                  description
                    "Preferred Path Type";
                }
                leaf interface-tunnel-number {
                  when "../type = 'te-tunnel' or ../type = 'ip-tunnel' or ../type = 'tp-tunnel'" {
                    tailf:xpath-root 3;
                    description
                      "../Type = TE-Tunnel or ../Type =
                       IP-Tunnel or ../Type = TP-Tunnel";
                  }
                  type uint32 {
                    range "0..65535";
                  }
                  description
                    "Interface Tunnel number for preferred path";
                }
                leaf fallback-disable {
                  when "../type = 'te-tunnel' or ../type = 'ip-tunnel' or ../type = 'tp-tunnel' or ../type = 'sr-te-policy' or ../type = 'named-te-tunnel'" {
                    tailf:xpath-root 3;
                    description
                      "../Type = TE-Tunnel or ../Type =
                       IP-Tunnel or ../Type = TP-Tunnel or .
                       ./Type = SR-TE-Policy or ../Type =
                       Named-TE-Tunnel";
                  }
                  type empty;
                  description
                    "Fallback disable";
                }
                leaf path-name {
                  when "../type = 'sr-te-policy' or ../type = 'named-te-tunnel'" {
                    tailf:xpath-root 3;
                    description
                      "../Type = SR-TE-Policy or ../Type =
                       Named-TE-Tunnel";
                  }
                  type xr:Cisco-ios-xr-string {
                    length "1..60";
                  }
                  description
                    "Name of the SR TE Policy or IFName";
                }
              }
              container load-balance-group {
                description
                  "Load Balancing";
                container flow-label-load-balance {
                  description
                    "Enable Flow Label based load balancing";
                  leaf flow-label {
                    type Flow-label-load-balance;
                    description
                      "Flow Label load balance type";
                  }
                  leaf static {
                    type empty;
                    description
                      "Static Flow Label";
                  }
                }
                leaf flow-label-load-balance-code {
                  type Flow-label-tlv-code;
                  description
                    "Enable Legacy Flow Label TLV code";
                }
                leaf pw-label-load-balance {
                  type Load-balance;
                  description
                    "Enable PW Label based Load Balancing";
                }
              }
              leaf pw-switching-tlv {
                type Pw-switching-point-tlv;
                description
                  "Pseudowire Switching Point Tlv";
              }
              leaf static-tag-rewrite {
                type Tag-rewrite-range;
                description
                  "Static Tag rewrite";
              }
              leaf signaling-protocol {
                type Mpls-signaling-protocol;
                default "ldp";
                description
                  "MPLS signaling protocol";
              }
              leaf vccv-type {
                type Vccv-verification;
                default "lsp-ping";
                description
                  "VCCV verification type";
              }
              leaf source-address {
                type inet:ipv4-address-no-zone;
                description
                  "Source IP address";
              }
              leaf transport-mode {
                type Transport-mode;
                description
                  "Transport mode";
              }
              leaf enable {
                type empty;
                description
                  "Enable MPLS encapsulation";
              }
              leaf control-word {
                type Control-word;
                description
                  "Enable control word";
              }
            }
            leaf mac-withdraw {
              type empty;
              description
                "Enable backup MAC withdraw";
            }
            leaf enable {
              type empty;
              description
                "Enable pseudowire class";
            }
            leaf name {
              type xr:Cisco-ios-xr-string {
                length "1..32";
              }
              description
                "Name of the pseudowire class";
            }
          }
        }
        container vlan-switches {
          description
            "List of VLAN Switches";
          list vlan-switch {
            key "name";
            description
              "VLAN Switch";
            container vlan-switch-ports {
              description
                "List of VLAN Switched Ports";
              list vlan-switch-port {
                key "interface-name";
                description
                  "VLAN Switched Port";
                leaf interface-name {
                  type xr:Interface-name;
                  description
                    "Interface name";
                }
              }
            }
            container vni-ranges {
              description
                "Configure VLAN Switch VxLAN Ethernet VPN-ID
                 ranges";
              leaf vni-range1-min {
                type uint32;
                description
                  "Minimum value of VNI range #1";
              }
              leaf vni-range1-max {
                type uint32;
                description
                  "Maximum value of VNI range #1";
              }
              leaf vni-range2-min {
                type uint32;
                description
                  "Minimum value of VNI range #2";
              }
              leaf vni-range2-max {
                type uint32;
                description
                  "Maximum value of VNI range #2";
              }
              leaf vni-range3-min {
                type uint32;
                description
                  "Minimum value of VNI range #3";
              }
              leaf vni-range3-max {
                type uint32;
                description
                  "Maximum value of VNI range #3";
              }
              leaf vni-range4-min {
                type uint32;
                description
                  "Minimum value of VNI range #4";
              }
              leaf vni-range4-max {
                type uint32;
                description
                  "Maximum value of VNI range #4";
              }
              leaf vni-range5-min {
                type uint32;
                description
                  "Minimum value of VNI range #5";
              }
              leaf vni-range5-max {
                type uint32;
                description
                  "Maximum value of VNI range #5";
              }
              leaf vni-range6-min {
                type uint32;
                description
                  "Minimum value of VNI range #6";
              }
              leaf vni-range6-max {
                type uint32;
                description
                  "Maximum value of VNI range #6";
              }
              leaf vni-range7-min {
                type uint32;
                description
                  "Minimum value of VNI range #7";
              }
              leaf vni-range7-max {
                type uint32;
                description
                  "Maximum value of VNI range #7";
              }
              leaf vni-range8-min {
                type uint32;
                description
                  "Minimum value of VNI range #8";
              }
              leaf vni-range8-max {
                type uint32;
                description
                  "Maximum value of VNI range #8";
              }
              leaf vni-range9-min {
                type uint32;
                description
                  "Minimum value of VNI range #9";
              }
              leaf vni-range9-max {
                type uint32;
                description
                  "Maximum value of VNI range #9";
              }
            }
            container vlan-ranges {
              description
                "Configure VLAN Switch VLAN ranges";
              leaf vlan-range1-min {
                type L2vpn-vs-vlan-tag;
                description
                  "Minimum value of VLAN range #1";
              }
              leaf vlan-range1-max {
                type L2vpn-vs-vlan-tag;
                description
                  "Maximum value of VLAN range #1";
              }
              leaf vlan-range2-min {
                type L2vpn-vs-vlan-tag;
                description
                  "Minimum value of VLAN range #2";
              }
              leaf vlan-range2-max {
                type L2vpn-vs-vlan-tag;
                description
                  "Maximum value of VLAN range #2";
              }
              leaf vlan-range3-min {
                type L2vpn-vs-vlan-tag;
                description
                  "Minimum value of VLAN range #3";
              }
              leaf vlan-range3-max {
                type L2vpn-vs-vlan-tag;
                description
                  "Maximum value of VLAN range #3";
              }
              leaf vlan-range4-min {
                type L2vpn-vs-vlan-tag;
                description
                  "Minimum value of VLAN range #4";
              }
              leaf vlan-range4-max {
                type L2vpn-vs-vlan-tag;
                description
                  "Maximum value of VLAN range #4";
              }
              leaf vlan-range5-min {
                type L2vpn-vs-vlan-tag;
                description
                  "Minimum value of VLAN range #5";
              }
              leaf vlan-range5-max {
                type L2vpn-vs-vlan-tag;
                description
                  "Maximum value of VLAN range #5";
              }
              leaf vlan-range6-min {
                type L2vpn-vs-vlan-tag;
                description
                  "Minimum value of VLAN range #6";
              }
              leaf vlan-range6-max {
                type L2vpn-vs-vlan-tag;
                description
                  "Maximum value of VLAN range #6";
              }
              leaf vlan-range7-min {
                type L2vpn-vs-vlan-tag;
                description
                  "Minimum value of VLAN range #7";
              }
              leaf vlan-range7-max {
                type L2vpn-vs-vlan-tag;
                description
                  "Maximum value of VLAN range #7";
              }
              leaf vlan-range8-min {
                type L2vpn-vs-vlan-tag;
                description
                  "Minimum value of VLAN range #8";
              }
              leaf vlan-range8-max {
                type L2vpn-vs-vlan-tag;
                description
                  "Maximum value of VLAN range #8";
              }
              leaf vlan-range9-min {
                type L2vpn-vs-vlan-tag;
                description
                  "Minimum value of VLAN range #9";
              }
              leaf vlan-range9-max {
                type L2vpn-vs-vlan-tag;
                description
                  "Maximum value of VLAN range #9";
              }
            }
            container routed-interface-ranges {
              description
                "Configure VLAN Switch Routed BVI Interface
                 ranges";
              leaf interface-range1-min {
                type uint32;
                description
                  "Minimum value of Interface range #1";
              }
              leaf interface-range1-max {
                type uint32;
                description
                  "Maximum value of Interface range #1";
              }
              leaf interface-range2-min {
                type uint32;
                description
                  "Minimum value of Interface range #2";
              }
              leaf interface-range2-max {
                type uint32;
                description
                  "Maximum value of Interface range #2";
              }
              leaf interface-range3-min {
                type uint32;
                description
                  "Minimum value of Interface range #3";
              }
              leaf interface-range3-max {
                type uint32;
                description
                  "Maximum value of Interface range #3";
              }
              leaf interface-range4-min {
                type uint32;
                description
                  "Minimum value of Interface range #4";
              }
              leaf interface-range4-max {
                type uint32;
                description
                  "Maximum value of Interface range #4";
              }
              leaf interface-range5-min {
                type uint32;
                description
                  "Minimum value of Interface range #5";
              }
              leaf interface-range5-max {
                type uint32;
                description
                  "Maximum value of Interface range #5";
              }
              leaf interface-range6-min {
                type uint32;
                description
                  "Minimum value of Interface range #6";
              }
              leaf interface-range6-max {
                type uint32;
                description
                  "Maximum value of Interface range #6";
              }
              leaf interface-range7-min {
                type uint32;
                description
                  "Minimum value of Interface range #7";
              }
              leaf interface-range7-max {
                type uint32;
                description
                  "Maximum value of Interface range #7";
              }
              leaf interface-range8-min {
                type uint32;
                description
                  "Minimum value of Interface range #8";
              }
              leaf interface-range8-max {
                type uint32;
                description
                  "Maximum value of Interface range #8";
              }
              leaf interface-range9-min {
                type uint32;
                description
                  "Minimum value of Interface range #9";
              }
              leaf interface-range9-max {
                type uint32;
                description
                  "Maximum value of Interface range #9";
              }
            }
            leaf name {
              type xr:Cisco-ios-xr-string {
                length "1..32";
              }
              description
                "Name of the VLAN Switch";
            }
            uses BRIDGE-DOMAIN-TABLE;
          }
        }
        container flexible-xconnect-service-table {
          description
            "List of Flexible XConnect Services";
          container vlan-unaware-flexible-xconnect-services {
            description
              "List of Vlan-Unaware Flexible XConnect
               Services";
            list vlan-unaware-flexible-xconnect-service {
              key "name";
              description
                "Flexible XConnect Service";
              container vlan-unaware-fxc-attachment-circuits {
                description
                  "List of attachment circuits";
                list vlan-unaware-fxc-attachment-circuit {
                  key "name";
                  description
                    "Attachment circuit interface";
                  leaf name {
                    type xr:Interface-name;
                    description
                      "Name of the attachment circuit interface";
                  }
                }
              }
              container vlan-unaware-fxc-pseudowire-evpns {
                description
                  "List of EVPN Services";
                list vlan-unaware-fxc-pseudowire-evpn {
                  key "eviid acid";
                  description
                    "EVPN FXC Service Configuration";
                  leaf eviid {
                    type Evpnvpnid-range;
                    description
                      "Ethernet VPN ID";
                  }
                  leaf acid {
                    type Pseudowire-acid-range;
                    description
                      "AC ID";
                  }
                }
              }
              leaf name {
                type xr:Cisco-ios-xr-string {
                  length "1..23";
                }
                description
                  "Name of the Flexible XConnect Service";
              }
            }
          }
          container vlan-aware-flexible-xconnect-services {
            description
              "List of Vlan-Aware Flexible XConnect Services";
            list vlan-aware-flexible-xconnect-service {
              key "eviid";
              description
                "Flexible XConnect Service";
              container vlan-aware-fxc-attachment-circuits {
                description
                  "List of attachment circuits";
                list vlan-aware-fxc-attachment-circuit {
                  key "name";
                  description
                    "Attachment circuit interface";
                  leaf name {
                    type xr:Interface-name;
                    description
                      "Name of the attachment circuit interface";
                  }
                }
              }
              leaf eviid {
                type Evpnvpnid-range;
                description
                  "Ethernet VPN ID";
              }
            }
          }
        }
        container redundancy {
          description
            "Redundancy groups";
          container iccp-redundancy-groups {
            description
              "List of Inter-Chassis Communication Protocol
               redundancy groups";
            list iccp-redundancy-group {
              key "group-id";
              description
                "ICCP Redundancy group";
              container iccp-interfaces {
                description
                  "List of interfaces";
                list iccp-interface {
                  key "interface-name";
                  description
                    "Interface name";
                  leaf secondary-vlan-range {
                    type string;
                    description
                      "Secondary VLAN range, in the form of 1-3,5
                       ,8-11";
                  }
                  leaf recovery-delay {
                    type uint32 {
                      range "30..3600";
                    }
                    default "180";
                    description
                      "Failure clear recovery delay";
                  }
                  leaf primary-vlan-range {
                    type string;
                    description
                      "Primary VLAN range, in the form of 1-3,5
                       ,8-11";
                  }
                  leaf mac-flush-tcn {
                    type empty;
                    description
                      "Enable STP-TCN MAC flushing";
                  }
                  leaf interface-name {
                    type xr:Interface-name;
                    description
                      "Interface name";
                  }
                }
              }
              leaf multi-homing-node-id {
                type uint32 {
                  range "0..254";
                }
                description
                  "ICCP-based service multi-homing node ID";
              }
              leaf group-id {
                type uint32 {
                  range "1..4294967295";
                }
                description
                  "Group ID";
              }
            }
          }
          leaf enable {
            type empty;
            description
              "Enable redundancy groups";
          }
        }
      }
      container pbb {
        description
          "L2VPN PBB Global";
        leaf backbone-source-mac {
          type yang:mac-address;
          description
            "Backbone Source MAC";
        }
      }
      container auto-discovery {
        description
          "Global auto-discovery attributes";
        container bgp-signaling {
          description
            "Global bgp signaling attributes";
          leaf mtu-mismatch-ignore {
            type empty;
            description
              "Ignore MTU mismatch for auto-discovered
               pseudowires";
          }
        }
      }
      container utility {
        description
          "L2VPN utilities";
        container logging {
          description
            "L2VPN logging utility";
          leaf bridge-domain-state-change {
            type empty;
            description
              "Enable Bridge Domain state change logging";
          }
          leaf pseudowire-state-change {
            type empty;
            description
              "Enable pseudowire state change logging";
          }
          leaf vfi {
            type empty;
            description
              "Enable VFI state change logging";
          }
          leaf nsr-state-change {
            type empty;
            description
              "Enable Non Stop Routing state change logging";
          }
          leaf pwhe-replication-state-change {
            type empty;
            description
              "Enable PW-HE Replication state change logging";
          }
        }
      }
      container snmp {
        description
          "SNMP related configuration";
        container mib {
          description
            "MIB related configuration";
          container mib-interface {
            description
              "Interface related configuration for MIB";
            container format {
              description
                "MIB interface name output format";
              leaf external-interface-format {
                type empty;
                description
                  "Set MIB interface name output in slash
                   format (/)";
              }
            }
          }
          container mib-pseudowire {
            description
              "Pseudowire related configuration for MIB";
            leaf statistics {
              type empty;
              description
                "Enable pseudowire statistics in MIB output";
            }
          }
        }
      }
      leaf nsr {
        type empty;
        description
          "Enable Non-Stop Routing";
      }
      leaf mtu-mismatch-ignore {
        type empty;
        description
          "Ignore MTU Mismatch for XCs";
      }
      leaf tcn-propagation {
        type empty;
        description
          "Topology change notification propagation";
      }
      leaf pwoam-refresh {
        type uint32 {
          range "1..4095";
        }
        units "second";
        description
          "Configure PW OAM refresh interval";
      }
      leaf load-balance {
        type Load-balance;
        description
          "Enable flow load balancing on l2vpn bridges";
      }
      leaf mspw-description {
        type string {
          length "1..64";
        }
        description
          "MS-PW global description";
      }
      leaf mac-limit-threshold {
        type Mac-limit-threshold-range;
        units "percentage";
        description
          "Configure MAC limit threshold percent";
      }
      leaf pw-status-disable {
        type empty;
        description
          "Disable PW status";
      }
      leaf enable {
        type empty;
        description
          "Enable L2VPN feature";
      }
      leaf pw-grouping {
        type empty;
        description
          "Enable PW grouping";
      }
      leaf capability {
        type L2vpn-capability-mode;
        description
          "L2VPN Capability Mode";
      }
      leaf l2vpn-router-id {
        type inet:ipv4-address-no-zone;
        description
          "Global L2VPN Router ID";
      }
    }
    container generic-interface-lists {
      tailf:ncs-device-type "netconf";
      tailf:display-when "not(../../ncs:module) or ../../ncs:module[ncs:name='Cisco-IOS-XR-l2vpn-cfg']";
      description
        "Generic Interface List configuration";
      list generic-interface-list {
        key "generic-interface-list-name";
        description
          "Generic interface list";
        container interfaces {
          description
            "Interface table";
          list interface {
            key "interface-name";
            description
              "Interface";
            leaf enable {
              type empty;
              description
                "Enable interface";
            }
            leaf interface-name {
              type xr:Interface-name;
              description
                "Name of the interface";
            }
          }
        }
        leaf enable {
          type empty;
          description
            "Enable interface list";
        }
        leaf generic-interface-list-name {
          type xr:Cisco-ios-xr-string {
            length "1..32";
          }
          description
            "Name of the interface list";
        }
      }
    }
    container evpn {
      tailf:ncs-device-type "netconf";
      tailf:display-when "not(../../ncs:module) or ../../ncs:module[ncs:name='Cisco-IOS-XR-l2vpn-cfg']";
      description
        "EVPN configuration";
      container evpn-tables {
        description
          "EVPN submodes";
        container evpn-timers {
          description
            "Enter EVPN timers configuration submode";
          leaf evpn-carving {
            type uint32 {
              range "0..300";
            }
            default "0";
            description
              "Global Carving timer";
          }
          leaf evpn-recovery {
            type uint32 {
              range "0..3600";
            }
            default "30";
            description
              "Global Recovery timer";
          }
          leaf enable {
            type empty;
            description
              "Enable EVPN timers";
          }
          leaf evpn-peering {
            type uint32 {
              range "0..300";
            }
            default "3";
            description
              "Global Peering timer";
          }
        }
        container evpn-virtual-access-vfis {
          description
            "Virtual Access VFI interfaces";
          list evpn-virtual-access-vfi {
            key "name";
            description
              "Virtual Access VFI";
            container evpn-virtual-access-vfi-timers {
              description
                "Enter Virtual Forwarding Interface timers
                 configuration submode";
              leaf evpn-virtual-access-vfi-recovery {
                type uint32 {
                  range "0..3600";
                }
                default "30";
                description
                  "Virtual Forwarding Interface-specific
                   Recovery timer";
              }
              leaf evpn-virtual-access-vfi-peering {
                type uint32 {
                  range "0..300";
                }
                default "3";
                description
                  "Virtual Forwarding Interface-specific
                   Peering timer";
              }
              leaf evpn-virtual-access-vfi-carving {
                type uint32 {
                  range "0..300";
                }
                default "0";
                description
                  "Virtual Forwarding Interface-specific
                   Carving timer";
              }
              leaf enable {
                type empty;
                description
                  "Enable Virtual Forwarding Interface timers";
              }
            }
            leaf name {
              type xr:Cisco-ios-xr-string {
                length "1..32";
              }
              description
                "Name of the Virtual Access VFI";
            }
            uses EVPN-VIRTUAL-ETHERNET-SEGMENT;
          }
        }
        container evpn-load-balancing {
          description
            "Enter EVPN Loadbalancing configuration submode";
          leaf evpn-static-flow-label {
            type empty;
            description
              "Enable Static Flow Label based load balancing";
          }
          leaf enable {
            type empty;
            description
              "Enable EVPN Loadbalancing";
          }
        }
        container evpn-bgp-auto-discovery {
          description
            "Enable Autodiscovery BGP in EVPN";
          leaf enable {
            type empty;
            description
              "Enable Autodiscovery BGP";
          }
          uses EVPN-ROUTE-DISTINGUISHER;
        }
        container evpn-groups {
          description
            "Enter EVPN Group Table submode";
          list evpn-group {
            key "group-id";
            description
              "Enter EVPN Group submode";
            container evpn-group-core-interfaces {
              description
                "EVPN Group core interfaces";
              list evpn-group-core-interface {
                key "interface-name";
                description
                  "EVPN Group Core interface";
                leaf interface-name {
                  type xr:Interface-name;
                  description
                    "Name of the EVPN Group core interface";
                }
              }
            }
            leaf group-id {
              type Evpn-group-id-range;
              description
                "Group ID";
            }
          }
        }
        container evpn-instances {
          description
            "Enter EVPN Instance configuration submode";
          list evpn-instance {
            key "vpn-id encapsulation side";
            description
              "Enter EVPN Instance configuration submode";
            container evpn-instance-bgp-auto-discovery {
              description
                "Enable Autodiscovery BGP in EVPN Instance";
              container evpn-route-policy {
                description
                  "Route policy";
                leaf export {
                  type string;
                  description
                    "Export route policy";
                }
                leaf import {
                  type string;
                  description
                    "Import route policy";
                }
              }
              container evpn-route-targets {
                description
                  "Route Target";
                list evpn-route-target {
                  must 'none or two-byte-as-or-four-byte-as or ipv4-address' {
                    tailf:xpath-root 3;
                    description
                      "None or TwoByteAS-or-FourByteAS or
                       IPV4Address must be present.";
                  }
                  key "role format";
                  description
                    "Name of the Route Target";
                  leaf format {
                    type Bgp-route-target-format;
                    description
                      "Format of the route target";
                  }
                  leaf role {
                    type Bgp-route-target-role;
                    description
                      "Role of the router target type";
                  }
                  list none {
                    when "../format = 'none'" {
                      tailf:xpath-root 3;
                      description
                        "../Format = None";
                    }
                    key "stitching";
                    description
                      "none";
                    leaf stitching {
                      type Bgp-route-target;
                      description
                        "whether RT is Stitching RT (DEPRECATED)";
                    }
                  }
                  list two-byte-as-or-four-byte-as {
                    when "../format = 'two-byte-as' or ../format = 'four-byte-as'" {
                      tailf:xpath-root 3;
                      description
                        "../Format = TwoByteAS or ../Format =
                         FourByteAS";
                    }
                    key "as as-index stitching";
                    description
                      "two byte as or four byte as";
                    leaf as {
                      type Rdas-range;
                      description
                        "Two byte or 4 byte AS number";
                    }
                    leaf as-index {
                      type Rdas-index;
                      description
                        "AS:nn (hex or decimal format)";
                    }
                    leaf stitching {
                      type Bgp-route-target;
                      description
                        "whether RT is Stitching RT (DEPRECATED)";
                    }
                  }
                  list ipv4-address {
                    when "../format = 'ipv4-address'" {
                      tailf:xpath-root 3;
                      description
                        "../Format = IPV4Address";
                    }
                    key "address addr-index stitching";
                    description
                      "ipv4 address";
                    leaf address {
                      type inet:ipv4-address-no-zone;
                      description
                        "IPV4 address";
                    }
                    leaf addr-index {
                      type Rd-addr-index;
                      description
                        "Addr index";
                    }
                    leaf stitching {
                      type Bgp-route-target;
                      description
                        "whether RT is Stitching RT (DEPRECATED)";
                    }
                  }
                }
              }
              leaf table-policy {
                type string;
                description
                  "Table Policy for installation of forwarding
                   data to L2FIB";
              }
              leaf implicit-import-disable {
                type empty;
                description
                  "Disables BGP Implicit Import";
              }
              leaf enable {
                type empty;
                description
                  "Enable Autodiscovery BGP";
              }
              uses EVPN-ROUTE-DISTINGUISHER;
            }
            container evpn-instance-etree {
              description
                "Enter EVPN E-Tree configuration submode";
              leaf evpn-instance-etree-rt-leaf {
                type empty;
                description
                  "Configure E-Tree as Route-Target leaf";
              }
              leaf evpn-instance-etree-leaf {
                type empty;
                description
                  "Configure E-Tree as leaf";
              }
              leaf enable {
                type empty;
                description
                  "Enable EVPN E-Tree";
              }
            }
            container evpn-instance-advertise-mac {
              description
                "Enter Advertise local MAC-only routes
                 configuration submode";
              leaf evi-advertise-mac-bvi {
                type empty;
                description
                  "Advertise local MAC-only and BVI MAC routes";
              }
              leaf enable {
                type empty;
                description
                  "Enable Advertise local MAC-only routes";
              }
            }
            container evpn-instance-multicast {
              description
                "Enter Multicast configuration submode";
              leaf evi-mcast-source-connected {
                type empty;
                description
                  "Enable Multicast source connectivity";
              }
              leaf enable {
                type empty;
                description
                  "Enable Multicast";
              }
            }
            container evpn-instance-load-balancing {
              description
                "Enter Loadbalancing configuration submode";
              leaf evi-static-flow-label {
                type empty;
                description
                  "Enable Static Flow Label based load
                   balancing";
              }
              leaf enable {
                type empty;
                description
                  "Enable Loadbalancing";
              }
            }
            leaf evpn-route-sync-vrf-default {
              type xr:Cisco-ios-xr-string {
                length "1..32";
              }
              description
                "Set EVI for default VRF";
            }
            leaf evi-srv6-locator {
              type string {
                length "1..58";
              }
              description
                "Specify SRv6 locator name";
            }
            leaf evi-reorig-disable {
              type empty;
              description
                "Disable route re-origination";
            }
            leaf evi-advertise-mac-deprecated {
              type empty;
              description
                "DEPRECATED: Advertise local MAC-only and BVI
                 MAC routes";
            }
            leaf evi-preferred-nexthop {
              type Preferred-nexthop-mode;
              description
                "Enable Preferred Nexthop mode on this EVI";
            }
            leaf evpn-evi-transmit-mtu-zero {
              type boolean;
              description
                "Transmit MTU zero to remote for this EVPN EVI
                 .";
            }
            leaf evpn-instance-description {
              type string {
                length "1..64";
              }
              description
                "Description for EVPN Instance";
            }
            leaf evpn-evi-mtu-mismatch-ignore {
              type boolean;
              description
                "Ignore mismatch between local and remote MTUs
                 for this EVPN EVI.";
            }
            leaf evi-ecmp-disable {
              type empty;
              description
                "Disable ECMP on the EVI";
            }
            leaf evpn-evi-mtu-match-enforce {
              type empty;
              description
                "Enforce matching between local and remote
                 MTUs for this EVPN EVI.";
            }
            leaf evpn-instance-vpws-single-active-backup-suppression {
              type empty;
              description
                "Configure EVPN VPWS Single-Active Backup
                 Suppression";
            }
            leaf evpn-evi-transmit-l2-mtu {
              type empty;
              description
                "Transmit L2 MTU to remote for this EVPN EVI.";
            }
            leaf evi-unknown-unicast-flooding-disable {
              type empty;
              description
                "Disable Unknown Unicast Flooding on this EVI";
            }
            leaf evpn-evi-cw-disable {
              type empty;
              description
                "CW disable for EVPN EVI";
            }
            leaf vpn-id {
              type Vpnid-range;
              description
                "EVPN Instance ID";
            }
            leaf encapsulation {
              type Evpn-encapsulation;
              description
                "EVPN Instance Encapsulation";
            }
            leaf side {
              type Evpn-side;
              description
                "EVPN Instance Side";
            }
          }
        }
        container evpn-logging {
          description
            "Enter EVPN Logging configuration submode";
          leaf evpn-df-election {
            type empty;
            description
              "Enable Designated Forwarder election logging";
          }
          leaf enable {
            type empty;
            description
              "Enable EVPN Logging";
          }
        }
        container evpn-segment-routing-srv6 {
          description
            "Enter EVPN Segment-Routing SRv6 submode";
          leaf evpn-srv6-locator {
            type string {
              length "1..58";
            }
            description
              "Specify default SRv6 locator name";
          }
          leaf enable {
            type empty;
            description
              "Enable EVPN Segment-Routing SRv6";
          }
        }
        container evpn-interfaces {
          description
            "Attachment Circuit interfaces";
          list evpn-interface {
            key "interface-name";
            description
              "Attachment circuit interface";
            container evpnac-timers {
              description
                "Enter Interface-specific timers configuration
                 submode";
              leaf evpnac-peering {
                type uint32 {
                  range "0..300";
                }
                default "3";
                description
                  "Interface-specific Peering timer";
              }
              leaf evpnac-carving {
                type uint32 {
                  range "0..300";
                }
                default "0";
                description
                  "Interface-specific Carving timer";
              }
              leaf enable {
                type empty;
                description
                  "Enable Interface-specific timers";
              }
              leaf evpnac-recovery {
                type uint32 {
                  range "0..3600";
                }
                default "30";
                description
                  "Interface-specific Recovery timer";
              }
            }
            container ethernet-segment {
              description
                "Enter Ethernet Segment configuration submode";
              container es-convergence {
                description
                  "Convergence mode(s) and configuration
                   options";
                leaf mac-mobility {
                  type empty;
                  description
                    "Enable MAC-mobility triggered flush";
                }
                leaf nh-tracking {
                  type empty;
                  description
                    "Nexthop-tracking influenced DF Election";
                }
                leaf reroute {
                  type empty;
                  description
                    "Enable reroute to backup peer";
                }
                leaf enable {
                  type empty;
                  description
                    "Enable Convergence configuration options";
                }
              }
              leaf force-single-homed {
                type empty;
                description
                  "Force ethernet segment to remain
                   single-homed";
              }
              leaf load-balancing-mode {
                type Ethernet-segment-load-balance;
                description
                  "Ethernet-Segment Load Balancing mode";
              }
              leaf enable {
                type empty;
                description
                  "Enable Ethernet Segment";
              }
              leaf backbone-source-mac {
                type yang:mac-address;
                description
                  "Backbone Source MAC";
              }
              uses SERVICE-CARVING-MCAST-TYPE;
              uses ES-IMPORT-ROUTE-TARGET;
              uses SERVICE-CARVING-TYPE;
              uses IDENTIFIER;
              uses PREFERENCE-BASED-SERVICE-CARVING;
              uses MANUAL-SERVICE-CARVING;
            }
            leaf evpn-core-isolation-group {
              type Evpn-core-group-id-range;
              description
                "Enter EVPN Core Isolation Group ID";
            }
            leaf evpn-access-signal-mode {
              type Interface-access-signal-mode;
              description
                "Override default signal sent to bring down
                 access circuit";
            }
            leaf mac-flush {
              type Mac-flush-mode;
              description
                "Enable MAC Flushing";
            }
            leaf interface-name {
              type xr:Interface-name;
              description
                "Name of the attachment circuit interface";
            }
          }
        }
        container evpn-virtual-access-pws {
          description
            "Virtual Access Pseudowire interfaces";
          list evpn-virtual-access-pw {
            key "neighbor pseudowire-id";
            description
              "Virtual Access Pseudowire";
            container evpn-virtual-access-pw-timers {
              description
                "Enter Virtual Access Pseudowire-specific
                 timers configuration submode";
              leaf evpn-virtual-access-pw-recovery {
                type uint32 {
                  range "0..3600";
                }
                default "30";
                description
                  "Virtual Access Pseudowire-specific Recovery
                   timer";
              }
              leaf evpn-virtual-access-pw-peering {
                type uint32 {
                  range "0..300";
                }
                default "3";
                description
                  "Virtual Access Pseudowire-specific Peering
                   timer";
              }
              leaf enable {
                type empty;
                description
                  "Enable Virtual Access Pseudowire-specific
                   timers";
              }
              leaf evpn-virtual-access-pw-carving {
                type uint32 {
                  range "0..300";
                }
                default "0";
                description
                  "Virtual Access Pseudowire-specific Carving
                   timer";
              }
            }
            leaf neighbor {
              type inet:ipv4-address-no-zone;
              description
                "Neighbor IP address";
            }
            leaf pseudowire-id {
              type Pseudowire-id-range;
              description
                "Pseudowire ID";
            }
            uses EVPN-VIRTUAL-ETHERNET-SEGMENT;
          }
        }
        container evpn-ethernet-segment {
          description
            "EVPN Global Ethernet Segment submode";
          container evpn-esi-types {
            description
              "EVPN ESI type table";
            list evpn-esi-type {
              key "esi-type";
              description
                "ESI type";
              leaf disable-auto-generation {
                type empty;
                description
                  "Disable ESI Autogeneration";
              }
              leaf esi-type {
                type Evpn-esi-type-range;
                description
                  "ESI type";
              }
            }
          }
          leaf enable {
            type empty;
            description
              "Enable EVPN Global Ethernet Segment submode";
          }
        }
        leaf evpn-global-transmit-mtu-zero {
          type empty;
          description
            "Transmit MTU zero to remote for all EVIs";
        }
        leaf evpn-global-mtu-mismatch-ignore {
          type empty;
          description
            "Ignore mismatch between local and remote MTUs
             for all EVIs.";
        }
        leaf evpn-global-mtu-match-enforce {
          type empty;
          description
            "Enforce matching between local and remote MTUs
             for all EVIs.";
        }
        leaf evpn-global-transmit-l2-mtu {
          type empty;
          description
            "Transmit L2 MTU to remote for all EVIs";
        }
        leaf evpn-staggered-bringup {
          type uint32 {
            range "0..300000";
          }
          units "millisecond";
          default "5000";
          description
            "Staggered bringup (milliseconds) timer";
        }
        leaf evi-cost-out {
          type empty;
          description
            "Configure node to cost-out";
        }
        leaf evpn-source-interface {
          type xr:Interface-name;
          description
            "Configure EVPN router-id implicitly through
             Loopback Interface";
        }
        leaf evpn-cost-in-startup {
          type uint32 {
            range "30..86400";
          }
          units "second";
          description
            "Cost-in node after given time (seconds) on
             startup timer";
        }
      }
      leaf enable {
        type empty;
        description
          "Enable EVPN feature";
      }
    }
  }
  augment "/ncs:devices/ncs:device/ncs:live-status" {
    container l2vpn {
      tailf:ncs-device-type "netconf";
      tailf:display-when "not(../../ncs:module) or ../../ncs:module[ncs:name='Cisco-IOS-XR-l2vpn-cfg'] or (../../ncs:live-status-protocol[not(ncs:capability)]) or (../../ncs:live-status-protocol/ncs:capability/ncs:module[.='Cisco-IOS-XR-l2vpn-cfg'])";
      description
        "L2VPN configuration";
      container pw-routing {
        description
          "Pseudowire-routing attributes";
        container pw-routing-bgp {
          description
            "Enable Autodiscovery BGP Pseudowire-routing BGP";
          leaf enable {
            type empty;
            description
              "Enable Autodiscovery BGP";
          }
          uses live_ncs_EVPN-ROUTE-DISTINGUISHER;
        }
        leaf pw-routing-global-id {
          type live_ncs_Pseudowire-gbl-id-range;
          description
            "Pseudowire-routing Global ID";
        }
      }
      container neighbor {
        description
          "L2VPN neighbor submode";
        leaf ldp-flap {
          type empty;
          description
            "Enable targetted LDP session flap action";
        }
      }
      container database {
        description
          "L2VPN databases";
        container g8032-rings {
          description
            "List of G8032 Ring";
          list g8032-ring {
            key "g8032-ring-name";
            description
              "G8032 Ring";
            container erp-port0s {
              description
                "Ethernet ring protection port0";
              list erp-port0 {
                key "interface-name";
                description
                  "Configure ERP main port0";
                leaf monitor {
                  type xr:live_ncs_Interface-name;
                  description
                    "Ethernet ring protection port0 monitor";
                }
                leaf interface-name {
                  type xr:live_ncs_Interface-name;
                  description
                    "Port0 interface";
                }
              }
            }
            container erp-instances {
              description
                "List of ethernet ring protection instance";
              list erp-instance {
                key "erp-instance-id";
                description
                  "Ethernet ring protection instance";
                container rpl {
                  description
                    "Ring protection link";
                  leaf port {
                    type live_ncs_Erp-port1;
                    description
                      "ERP main port number";
                  }
                  leaf role {
                    type live_ncs_Rpl-role;
                    description
                      "RPL role";
                  }
                }
                container aps {
                  description
                    "Automatic protection switching";
                  container port1 {
                    description
                      "APS channel for ERP port1";
                    leaf aps-type {
                      type live_ncs_Erpaps;
                      description
                        "Port1 APS type";
                    }
                    leaf aps-channel {
                      type string;
                      description
                        "Port1 APS channel in the format of
                         InterfaceName, BDName or XconnectName";
                    }
                  }
                  leaf port0 {
                    type string;
                    description
                      "Port0 APS channel in the format of
                       InterfaceName";
                  }
                  leaf enable {
                    type empty;
                    description
                      "Enable automatic protection switching";
                  }
                  leaf level {
                    type live_ncs_Erpaps-level-range;
                    description
                      "Automatic protection switching level";
                  }
                }
                leaf description {
                  type string {
                    length "1..32";
                  }
                  description
                    "Ethernet ring protection instance
                     description";
                }
                leaf inclusion-list {
                  type string;
                  description
                    "Associates a set of VLAN IDs with the G
                     .8032 instance";
                }
                leaf profile {
                  type string {
                    length "1..32";
                  }
                  description
                    "Ethernet ring protection instance profile";
                }
                leaf erp-instance-id {
                  type live_ncs_Erp-instance-range;
                  description
                    "ERP instance number";
                }
              }
            }
            container erp-port1s {
              description
                "Ethernet ring protection port0";
              list erp-port1 {
                // NCS drop must statement
                key "erp-port-type";
                description
                  "Ethernet ring protection port1";

                grouping ERP-PORT1-CONTENT {
                  description
                    "ERP PORT1 CONTENT";
                  leaf monitor {
                    type xr:live_ncs_Interface-name;
                    description
                      "Ethernet ring protection port1 monitor";
                  }
                }
                container none-or-virtual {
                  // NCS drop when statement
                  presence "Indicates that this node is configured.";
                  description
                    "none or virtual";
                  uses ERP-PORT1-CONTENT;
                }
                leaf erp-port-type {
                  type live_ncs_Erp-port;
                  description
                    "Port1 type";
                }
                list interface {
                  // NCS drop when statement
                  key "interface-name";
                  description
                    "interface";
                  leaf interface-name {
                    type xr:live_ncs_Interface-name;
                    description
                      "Port1 interface";
                  }
                  uses ERP-PORT1-CONTENT;
                }
              }
            }
            leaf open-ring {
              type empty;
              description
                "Specify the G.8032 instance as open ring";
            }
            leaf exclusion-list {
              type string;
              description
                "Vlan IDs in the format of a-b,c,d,e-f,g
                 ,untagged";
            }
            leaf erp-provider-bridge {
              type empty;
              description
                "Ethernet ring protection provider bridge";
            }
            leaf g8032-ring-name {
              type xr:live_ncs_Cisco-ios-xr-string;
              description
                "Name of the G8032 ring";
            }
          }
        }
        container xconnect-groups {
          description
            "List of xconnect groups";
          list xconnect-group {
            key "name";
            description
              "Xconnect group";
            container p2p-xconnects {
              description
                "List of point to point xconnects";
              list p2p-xconnect {
                key "name";
                description
                  "Point to point xconnect";
                container pseudowire-evpn-srv6s {
                  description
                    "List of EVPN SRv6 Services";
                  list pseudowire-evpn-srv6 {
                    key "eviid remote-acid source-acid";
                    description
                      "EVPN SRv6 P2P Service Configuration";
                    leaf pseudowire-evpn-srv6-locator {
                      type xr:live_ncs_Cisco-ios-xr-string;
                      description
                        "Specify SRv6 locator name";
                    }
                    leaf eviid {
                      type live_ncs_Evpnvpnid-range;
                      description
                        "Ethernet VPN ID";
                    }
                    leaf remote-acid {
                      type live_ncs_Pseudowire-evpnacid-range;
                      description
                        "Remote AC ID";
                    }
                    leaf source-acid {
                      type live_ncs_Pseudowire-evpnacid-range;
                      description
                        "Source AC ID";
                    }
                  }
                }
                container pseudowire-evpn-srv6-services {
                  description
                    "List of EVPN SRv6 Services keyed by EVI and
                     Service ID";
                  list pseudowire-evpn-srv6-service {
                    key "eviid service-id";
                    description
                      "EVPN SRv6 P2P Service Configuration";
                    leaf pseudowire-evpn-srv6-locator {
                      type xr:live_ncs_Cisco-ios-xr-string;
                      description
                        "Specify SRv6 locator name";
                    }
                    leaf eviid {
                      type live_ncs_Evpnvpnid-range;
                      description
                        "Ethernet VPN ID";
                    }
                    leaf service-id {
                      type live_ncs_Pseudowire-evpnacid-range;
                      description
                        "Service ID (Target and Source AC ID)";
                    }
                  }
                }
                container backup-attachment-circuits {
                  description
                    "List of backup attachment circuits";
                  list backup-attachment-circuit {
                    key "interface-name";
                    description
                      "Backup attachment circuit";
                    leaf interface-name {
                      type xr:live_ncs_Interface-name;
                      description
                        "Name of the attachment circuit interface";
                    }
                  }
                }
                container pseudowire-evpns {
                  description
                    "List of EVPN Services";
                  list pseudowire-evpn {
                    key "eviid remote-acid source-acid";
                    description
                      "EVPN P2P Service Configuration";
                    leaf class {
                      type xr:live_ncs_Cisco-ios-xr-string;
                      description
                        "Name of the pseudowire class";
                    }
                    leaf eviid {
                      type live_ncs_Evpnvpnid-range;
                      description
                        "Ethernet VPN ID";
                    }
                    leaf remote-acid {
                      type live_ncs_Pseudowire-evpnacid-range;
                      description
                        "Remote AC ID";
                    }
                    leaf source-acid {
                      type live_ncs_Pseudowire-evpnacid-range;
                      description
                        "Source AC ID";
                    }
                  }
                }
                container pseudowire-neighbor-pseudowire-ids {
                  description
                    "List of pseudowires";

                  grouping PSEUDOWIRE-CONTENT {
                    description
                      "PSEUDOWIRE CONTENT";
                    container mpls-static-labels {
                      description
                        "MPLS static labels";
                      leaf local-static-label {
                        type live_ncs_Pseudowire-label-range;
                        description
                          "Pseudowire local static label";
                      }
                      leaf remote-static-label {
                        type live_ncs_Pseudowire-label-range;
                        description
                          "Pseudowire remote static label";
                      }
                    }
                    container backup-pseudowires {
                      description
                        "List of pseudowires";
                      list backup-pseudowire {
                        key "neighbor pseudowire-id";
                        description
                          "Backup pseudowire for the cross connect";
                        container backup-mpls-static-labels {
                          description
                            "MPLS static labels";
                          leaf local-static-label {
                            type live_ncs_Pseudowire-label-range;
                            description
                              "Pseudowire local static label";
                          }
                          leaf remote-static-label {
                            type live_ncs_Pseudowire-label-range;
                            description
                              "Pseudowire remote static label";
                          }
                        }
                        leaf backup-pw-class {
                          type xr:live_ncs_Cisco-ios-xr-string;
                          description
                            "PW class template name to use for the
                             backup PW";
                        }
                        leaf neighbor {
                          type inet:ipv4-address-no-zone;
                          description
                            "Neighbor IP address";
                        }
                        leaf pseudowire-id {
                          type live_ncs_Pseudowire-id-range;
                          description
                            "Pseudowire ID";
                        }
                      }
                    }
                    container l2tp-static-attributes {
                      description
                        "L2TP Static Attributes";
                      container l2tp-remote-cookie {
                        description
                          "L2TP remote cookie";
                        leaf size {
                          type live_ncs_L2tp-cookie-size;
                          description
                            "Remote cookie size";
                        }
                        leaf lower-value {
                          type live_ncs_L2tp-cookie-value-range;
                          description
                            "Lower remote cookie value";
                        }
                        leaf higher-value {
                          type live_ncs_L2tp-cookie-value-range;
                          description
                            "Higher remote cookie value";
                        }
                      }
                      container l2tp-secondary-local-cookie {
                        description
                          "L2TP secondary local cookie";
                        leaf size {
                          type live_ncs_L2tp-cookie-size;
                          description
                            "Local cookie size";
                        }
                        leaf lower-value {
                          type live_ncs_L2tp-cookie-value-range;
                          description
                            "Lower local cookie value";
                        }
                        leaf higher-value {
                          type live_ncs_L2tp-cookie-value-range;
                          description
                            "Higher local cookie value";
                        }
                      }
                      container l2tp-local-cookie {
                        description
                          "L2TP local cookie";
                        leaf size {
                          type live_ncs_L2tp-cookie-size;
                          description
                            "Local cookie size";
                        }
                        leaf lower-value {
                          type live_ncs_L2tp-cookie-value-range;
                          description
                            "Lower local cookie value";
                        }
                        leaf higher-value {
                          type live_ncs_L2tp-cookie-value-range;
                          description
                            "Higher local cookie value";
                        }
                      }
                      leaf l2tp-remote-session-id {
                        type live_ncs_L2tp-session-id-range;
                        description
                          "L2TP remote session ID";
                      }
                      leaf l2tp-local-session-id {
                        type live_ncs_L2tp-session-id-range;
                        description
                          "L2TP local session ID";
                      }
                    }
                    container l2tp-static {
                      description
                        "Pseudowire L2TPv3 static configuration";
                      leaf enable {
                        type empty;
                        description
                          "Enable pseudowire L2TPv3 static
                           configuration";
                      }
                    }
                    leaf tag-impose {
                      type live_ncs_Pseudowire-tag-range;
                      description
                        "Tag Impose vlan tagged mode";
                    }
                    leaf class {
                      type xr:live_ncs_Cisco-ios-xr-string;
                      description
                        "Name of the pseudowire class";
                    }
                    leaf source-address {
                      type inet:ip-address-no-zone;
                      description
                        "Value of the Pseudowire source address.
                         Must be IPv6 only.";
                    }
                    leaf bandwidth {
                      type uint32 {
                        range "0..4294967295";
                      }
                      description
                        "Pseudowire Bandwidth";
                    }
                  }
                  list pseudowire-neighbor-pseudowire-id {
                    key "neighbor pseudowire-id";
                    description
                      "Pseudowire configuration";
                    leaf neighbor {
                      type inet:ipv4-address-no-zone;
                      description
                        "Pseudowire IPv4 address";
                    }
                    leaf pseudowire-id {
                      type live_ncs_Pseudowire-id-range;
                      description
                        "Pseudowire ID";
                    }
                    uses PSEUDOWIRE-CONTENT;
                  }
                  list pseudowire-pseudowire-address-pseudowire-id {
                    key "pseudowire-address pseudowire-id";
                    description
                      "Pseudowire configuration";
                    leaf pseudowire-address {
                      type inet:ipv6-address-no-zone;
                      description
                        "Pseudowire IPv6 address. A pseudowire can
                         have only one address: IPv4 or IPv6";
                    }
                    leaf pseudowire-id {
                      type live_ncs_Pseudowire-id-range;
                      description
                        "Pseudowire ID";
                    }
                    uses PSEUDOWIRE-CONTENT;
                  }
                }
                container monitor-sessions {
                  description
                    "List of Monitor session segments";
                  list monitor-session {
                    key "name";
                    description
                      "Monitor session segment";
                    leaf enable {
                      type empty;
                      description
                        "Enable monitor session segment ";
                    }
                    leaf name {
                      type xr:live_ncs_Cisco-ios-xr-string;
                      description
                        "Name of the monitor session";
                    }
                  }
                }
                container pseudowire-routeds {
                  description
                    "List of pseudowire-routed";
                  list pseudowire-routed {
                    key "global-id prefix acid sacid";
                    description
                      "Pseudowire configuration";
                    leaf tag-impose {
                      type live_ncs_Pseudowire-tag-range;
                      description
                        "Tag Impose vlan tagged mode";
                    }
                    leaf class {
                      type xr:live_ncs_Cisco-ios-xr-string;
                      description
                        "Name of the pseudowire class";
                    }
                    leaf global-id {
                      type live_ncs_Pseudowire-gbl-id-range;
                      description
                        "Target Global ID";
                    }
                    leaf prefix {
                      type inet:ipv4-address-no-zone;
                      description
                        "Target Prefix";
                    }
                    leaf acid {
                      type live_ncs_Pseudowire-acid-range;
                      description
                        "Target AC ID";
                    }
                    leaf sacid {
                      type live_ncs_Pseudowire-acid-range;
                      description
                        "Source AC ID";
                    }
                  }
                }
                container pseudowire-evpn-services {
                  description
                    "List of EVPN Services keyed by EVI and
                     Service ID";
                  list pseudowire-evpn-service {
                    key "eviid service-id";
                    description
                      "EVPN P2P Service Configuration";
                    leaf class {
                      type xr:live_ncs_Cisco-ios-xr-string;
                      description
                        "Name of the pseudowire class";
                    }
                    leaf eviid {
                      type live_ncs_Evpnvpnid-range;
                      description
                        "Ethernet VPN ID";
                    }
                    leaf service-id {
                      type live_ncs_Pseudowire-evpnacid-range;
                      description
                        "Service ID (Remote and Source AC ID)";
                    }
                  }
                }
                container attachment-circuits {
                  description
                    "List of attachment circuits";
                  list attachment-circuit {
                    key "name";
                    description
                      "Attachment circuit interface";
                    leaf enable {
                      type empty;
                      description
                        "Enable attachment circuit interface";
                    }
                    leaf name {
                      type xr:live_ncs_Interface-name;
                      description
                        "Name of the attachment circuit interface";
                    }
                  }
                }
                leaf p2p-description {
                  type string {
                    length "1..64";
                  }
                  description
                    "cross connect description Name";
                }
                leaf interworking {
                  type live_ncs_Interworking;
                  description
                    "Interworking";
                }
                leaf name {
                  type xr:live_ncs_Cisco-ios-xr-string;
                  description
                    "Name of the point to point xconnect";
                }
              }
            }
            container mp2mp-xconnects {
              description
                "List of multi point to multi point xconnects";
              list mp2mp-xconnect {
                key "name";
                description
                  "Multi point to multi point xconnect";
                container mp2mp-auto-discovery {
                  description
                    "auto-discovery in this MP2MP";
                  container route-distinguisher {
                    description
                      "Route Distinguisher";
                    leaf type {
                      type live_ncs_Bgp-route-distinguisher;
                      description
                        "Router distinguisher type";
                    }
                    leaf as {
                      // NCS drop when statement
                      type live_ncs_Rdas-range;
                      description
                        "Two byte or 4 byte AS number";
                    }
                    leaf as-index {
                      // NCS drop when statement
                      type live_ncs_Rdas-index;
                      description
                        "AS:nn (hex or decimal format)";
                    }
                    leaf address {
                      // NCS drop when statement
                      type inet:ipv4-address-no-zone;
                      description
                        "IPV4 address";
                    }
                    leaf addr-index {
                      // NCS drop when statement
                      type live_ncs_Rd-addr-index;
                      description
                        "Addr index";
                    }
                  }
                  container mp2mp-route-policy {
                    description
                      "Route policy";
                    leaf export {
                      type string;
                      description
                        "Export route policy";
                    }
                  }
                  container mp2mp-route-targets {
                    description
                      "Route Target";
                    list mp2mp-route-target {
                      // NCS drop must statement
                      key "role format";
                      description
                        "Name of the Route Target";
                      leaf role {
                        type live_ncs_Bgp-route-target-role;
                        description
                          "Role of the router target type";
                      }
                      leaf format {
                        type live_ncs_Bgp-route-target-format;
                        description
                          "Format of the route target";
                      }
                      list two-byte-as-or-four-byte-as {
                        // NCS drop when statement
                        key "as as-index";
                        description
                          "two byte as or four byte as";
                        leaf as {
                          type live_ncs_Rdas-range;
                          description
                            "Two byte or 4 byte AS number";
                        }
                        leaf as-index {
                          type live_ncs_Rdas-index;
                          description
                            "AS:nn (hex or decimal format)";
                        }
                      }
                      list ipv4-address {
                        // NCS drop when statement
                        key "address addr-index";
                        description
                          "ipv4 address";
                        leaf address {
                          type inet:ipv4-address-no-zone;
                          description
                            "IPV4 address";
                        }
                        leaf addr-index {
                          type live_ncs_Rd-addr-index;
                          description
                            "Addr index";
                        }
                      }
                    }
                  }
                  container mp2mp-signaling-protocol {
                    description
                      "signaling protocol in this MP2MP";
                    container flow-label-load-balance {
                      description
                        "Enable Flow Label based load balancing";
                      leaf flow-label {
                        type live_ncs_Flow-label-load-balance;
                        description
                          "Flow Label load balance type";
                      }
                      leaf static {
                        type empty;
                        description
                          "Static Flow Label";
                      }
                    }
                    container ceids {
                      description
                        "Local Customer Edge Identifier Table";
                      list ceid {
                        key "ce-id";
                        description
                          "Local Customer Edge Identifier ";
                        container remote-ceid-attachment-circuits {
                          description
                            "AC And Remote Customer Edge Identifier
                             Table";
                          list remote-ceid-attachment-circuit {
                            key "name remote-ce-id";
                            description
                              "AC And Remote Customer Edge Identifier";
                            leaf name {
                              type xr:live_ncs_Interface-name;
                              description
                                "The name of the Attachment Circuit";
                            }
                            leaf remote-ce-id {
                              type live_ncs_Ce-id-range;
                              description
                                "Remote Customer Edge Identifier";
                            }
                          }
                        }
                        leaf ce-id {
                          type live_ncs_Ce-id-range;
                          description
                            "Local Customer Edge Identifier";
                        }
                      }
                    }
                    leaf ce-range {
                      type live_ncs_Cedge-range;
                      description
                        "Local Customer Edge Identifier";
                    }
                    leaf enable {
                      type empty;
                      description
                        "Enable signaling protocol";
                    }
                  }
                  leaf enable {
                    type empty;
                    description
                      "Enable auto-discovery";
                  }
                }
                leaf mp2mpmtu {
                  type live_ncs_L2vpn-mtu-range;
                  units "byte";
                  description
                    "Maximum transmission unit for this MP2MP
                     VPWS instance";
                }
                leaf mp2mp-control-word {
                  type empty;
                  description
                    "Disable control word";
                }
                leaf mp2mpl2-encapsulation {
                  type live_ncs_L2-encapsulation;
                  description
                    "Configure Layer 2 Encapsulation";
                }
                leaf mp2mp-interworking {
                  type live_ncs_Interworking;
                  description
                    "Interworking";
                }
                leaf mp2mp-shutdown {
                  type empty;
                  description
                    "shutdown this MP2MP VPWS instance";
                }
                leaf mp2mpvpn-id {
                  type live_ncs_Vpnid-range;
                  description
                    "VPN Identifier";
                }
                leaf name {
                  type xr:live_ncs_Cisco-ios-xr-string;
                  description
                    "Name of the multi point to multi point
                     xconnect";
                }
              }
            }
            leaf name {
              type xr:live_ncs_Cisco-ios-xr-string;
              description
                "Name of the xconnect group";
            }
          }
        }
        container bridge-domain-groups {
          description
            "List of bridge groups";
          list bridge-domain-group {
            key "name";
            description
              "Bridge group";
            leaf name {
              type xr:live_ncs_Cisco-ios-xr-string;
              description
                "Name of the Bridge group";
            }
            uses live_ncs_BRIDGE-DOMAIN-TABLE;
          }
        }
        container pseudowire-classes {
          description
            "List of pseudowire classes";
          list pseudowire-class {
            key "name";
            description
              "Pseudowire class";
            container l2tpv3-encapsulation {
              description
                "L2TPv3 encapsulation";
              container sequencing {
                description
                  "Sequencing";
                leaf sequencing {
                  type live_ncs_L2tpv3-sequencing;
                  // NCS drop default statement
                  description
                    "Sequencing";
                }
                leaf resync-threshold {
                  type live_ncs_Resync-threshold-range;
                  // NCS drop default statement
                  description
                    "Out of sequence threshold";
                }
              }
              container type-of-service {
                description
                  "Type of service";
                leaf type-of-service-value {
                  type live_ncs_Type-of-service-range;
                  description
                    "Type of service value";
                }
                leaf type-of-service-mode {
                  type live_ncs_Type-of-service-mode;
                  description
                    "Type of service mode";
                }
              }
              container signaling-protocol {
                description
                  "L2TPv3 signaling protocol";
                leaf protocol {
                  type live_ncs_L2tp-signaling-protocol;
                  // NCS drop default statement
                  description
                    "L2TPv3 signaling protocol";
                }
                leaf l2tpv3-class-name {
                  type xr:live_ncs_Cisco-ios-xr-string;
                  description
                    "Name of the L2TPv3 class name";
                }
              }
              container path-mtu {
                description
                  "Path maximum transmission unit";
                leaf enable {
                  type empty;
                  description
                    "Enable path MTU";
                }
                leaf max-path-mtu {
                  type live_ncs_Max-path-mtu-range;
                  description
                    "Maximum path maximum transmission unit";
                }
              }
              leaf df-bit-set {
                type empty;
                description
                  "Set the do not fragment bit to 1";
              }
              leaf cookie-size {
                type live_ncs_L2tp-cookie-size;
                // NCS drop default statement
                description
                  "Cookie size";
              }
              leaf source-address {
                type inet:ipv4-address-no-zone;
                description
                  "Source IP address";
              }
              leaf transport-mode {
                type live_ncs_Transport-mode;
                description
                  "Transport mode";
              }
              leaf enable {
                type empty;
                description
                  "Enable L2TPv3 encapsulation";
              }
              leaf time-to-live {
                type live_ncs_Time-to-live-range;
                description
                  "Time to live";
              }
            }
            container backup-disable-delay {
              description
                "Back Up Pseudowire class";
              leaf type {
                type live_ncs_Backup-disable;
                description
                  "Delay or Never";
              }
              leaf disable-backup {
                // NCS drop when statement
                type live_ncs_Backup-disable-delay-range;
                description
                  "Disable backup delay";
              }
            }
            container mpls-encapsulation {
              description
                "MPLS encapsulation";
              container sequencing {
                description
                  "Sequencing";
                leaf sequencing {
                  type live_ncs_Mpls-sequencing;
                  // NCS drop default statement
                  description
                    "Sequencing";
                }
                leaf resync-threshold {
                  type live_ncs_Resync-threshold-range;
                  // NCS drop default statement
                  description
                    "Out of sequence threshold";
                }
              }
              container mpls-redundancy {
                description
                  "Redundancy options for MPLS encapsulation";
                leaf redundancy-one-way {
                  type empty;
                  description
                    "Force one-way PW redundancy behavior in
                     Redundancy Group";
                }
                leaf redundancy-initial-delay {
                  type live_ncs_Pw-redundancy-initial-delay-range;
                  units "second";
                  description
                    "Initial delay before activating the
                     redundant PW, in seconds";
                }
              }
              container preferred-path {
                description
                  "Preferred path";
                leaf type {
                  type live_ncs_Preferred-path;
                  description
                    "Preferred Path Type";
                }
                leaf interface-tunnel-number {
                  // NCS drop when statement
                  type uint32 {
                    range "0..65535";
                  }
                  description
                    "Interface Tunnel number for preferred path";
                }
                leaf fallback-disable {
                  // NCS drop when statement
                  type empty;
                  description
                    "Fallback disable";
                }
                leaf path-name {
                  // NCS drop when statement
                  type xr:live_ncs_Cisco-ios-xr-string;
                  description
                    "Name of the SR TE Policy or IFName";
                }
              }
              container load-balance-group {
                description
                  "Load Balancing";
                container flow-label-load-balance {
                  description
                    "Enable Flow Label based load balancing";
                  leaf flow-label {
                    type live_ncs_Flow-label-load-balance;
                    description
                      "Flow Label load balance type";
                  }
                  leaf static {
                    type empty;
                    description
                      "Static Flow Label";
                  }
                }
                leaf flow-label-load-balance-code {
                  type live_ncs_Flow-label-tlv-code;
                  description
                    "Enable Legacy Flow Label TLV code";
                }
                leaf pw-label-load-balance {
                  type live_ncs_Load-balance;
                  description
                    "Enable PW Label based Load Balancing";
                }
              }
              leaf pw-switching-tlv {
                type live_ncs_Pw-switching-point-tlv;
                description
                  "Pseudowire Switching Point Tlv";
              }
              leaf static-tag-rewrite {
                type live_ncs_Tag-rewrite-range;
                description
                  "Static Tag rewrite";
              }
              leaf signaling-protocol {
                type live_ncs_Mpls-signaling-protocol;
                // NCS drop default statement
                description
                  "MPLS signaling protocol";
              }
              leaf vccv-type {
                type live_ncs_Vccv-verification;
                // NCS drop default statement
                description
                  "VCCV verification type";
              }
              leaf source-address {
                type inet:ipv4-address-no-zone;
                description
                  "Source IP address";
              }
              leaf transport-mode {
                type live_ncs_Transport-mode;
                description
                  "Transport mode";
              }
              leaf enable {
                type empty;
                description
                  "Enable MPLS encapsulation";
              }
              leaf control-word {
                type live_ncs_Control-word;
                description
                  "Enable control word";
              }
            }
            leaf mac-withdraw {
              type empty;
              description
                "Enable backup MAC withdraw";
            }
            leaf enable {
              type empty;
              description
                "Enable pseudowire class";
            }
            leaf name {
              type xr:live_ncs_Cisco-ios-xr-string;
              description
                "Name of the pseudowire class";
            }
          }
        }
        container vlan-switches {
          description
            "List of VLAN Switches";
          list vlan-switch {
            key "name";
            description
              "VLAN Switch";
            container vlan-switch-ports {
              description
                "List of VLAN Switched Ports";
              list vlan-switch-port {
                key "interface-name";
                description
                  "VLAN Switched Port";
                leaf interface-name {
                  type xr:live_ncs_Interface-name;
                  description
                    "Interface name";
                }
              }
            }
            container vni-ranges {
              description
                "Configure VLAN Switch VxLAN Ethernet VPN-ID
                 ranges";
              leaf vni-range1-min {
                type uint32;
                description
                  "Minimum value of VNI range #1";
              }
              leaf vni-range1-max {
                type uint32;
                description
                  "Maximum value of VNI range #1";
              }
              leaf vni-range2-min {
                type uint32;
                description
                  "Minimum value of VNI range #2";
              }
              leaf vni-range2-max {
                type uint32;
                description
                  "Maximum value of VNI range #2";
              }
              leaf vni-range3-min {
                type uint32;
                description
                  "Minimum value of VNI range #3";
              }
              leaf vni-range3-max {
                type uint32;
                description
                  "Maximum value of VNI range #3";
              }
              leaf vni-range4-min {
                type uint32;
                description
                  "Minimum value of VNI range #4";
              }
              leaf vni-range4-max {
                type uint32;
                description
                  "Maximum value of VNI range #4";
              }
              leaf vni-range5-min {
                type uint32;
                description
                  "Minimum value of VNI range #5";
              }
              leaf vni-range5-max {
                type uint32;
                description
                  "Maximum value of VNI range #5";
              }
              leaf vni-range6-min {
                type uint32;
                description
                  "Minimum value of VNI range #6";
              }
              leaf vni-range6-max {
                type uint32;
                description
                  "Maximum value of VNI range #6";
              }
              leaf vni-range7-min {
                type uint32;
                description
                  "Minimum value of VNI range #7";
              }
              leaf vni-range7-max {
                type uint32;
                description
                  "Maximum value of VNI range #7";
              }
              leaf vni-range8-min {
                type uint32;
                description
                  "Minimum value of VNI range #8";
              }
              leaf vni-range8-max {
                type uint32;
                description
                  "Maximum value of VNI range #8";
              }
              leaf vni-range9-min {
                type uint32;
                description
                  "Minimum value of VNI range #9";
              }
              leaf vni-range9-max {
                type uint32;
                description
                  "Maximum value of VNI range #9";
              }
            }
            container vlan-ranges {
              description
                "Configure VLAN Switch VLAN ranges";
              leaf vlan-range1-min {
                type live_ncs_L2vpn-vs-vlan-tag;
                description
                  "Minimum value of VLAN range #1";
              }
              leaf vlan-range1-max {
                type live_ncs_L2vpn-vs-vlan-tag;
                description
                  "Maximum value of VLAN range #1";
              }
              leaf vlan-range2-min {
                type live_ncs_L2vpn-vs-vlan-tag;
                description
                  "Minimum value of VLAN range #2";
              }
              leaf vlan-range2-max {
                type live_ncs_L2vpn-vs-vlan-tag;
                description
                  "Maximum value of VLAN range #2";
              }
              leaf vlan-range3-min {
                type live_ncs_L2vpn-vs-vlan-tag;
                description
                  "Minimum value of VLAN range #3";
              }
              leaf vlan-range3-max {
                type live_ncs_L2vpn-vs-vlan-tag;
                description
                  "Maximum value of VLAN range #3";
              }
              leaf vlan-range4-min {
                type live_ncs_L2vpn-vs-vlan-tag;
                description
                  "Minimum value of VLAN range #4";
              }
              leaf vlan-range4-max {
                type live_ncs_L2vpn-vs-vlan-tag;
                description
                  "Maximum value of VLAN range #4";
              }
              leaf vlan-range5-min {
                type live_ncs_L2vpn-vs-vlan-tag;
                description
                  "Minimum value of VLAN range #5";
              }
              leaf vlan-range5-max {
                type live_ncs_L2vpn-vs-vlan-tag;
                description
                  "Maximum value of VLAN range #5";
              }
              leaf vlan-range6-min {
                type live_ncs_L2vpn-vs-vlan-tag;
                description
                  "Minimum value of VLAN range #6";
              }
              leaf vlan-range6-max {
                type live_ncs_L2vpn-vs-vlan-tag;
                description
                  "Maximum value of VLAN range #6";
              }
              leaf vlan-range7-min {
                type live_ncs_L2vpn-vs-vlan-tag;
                description
                  "Minimum value of VLAN range #7";
              }
              leaf vlan-range7-max {
                type live_ncs_L2vpn-vs-vlan-tag;
                description
                  "Maximum value of VLAN range #7";
              }
              leaf vlan-range8-min {
                type live_ncs_L2vpn-vs-vlan-tag;
                description
                  "Minimum value of VLAN range #8";
              }
              leaf vlan-range8-max {
                type live_ncs_L2vpn-vs-vlan-tag;
                description
                  "Maximum value of VLAN range #8";
              }
              leaf vlan-range9-min {
                type live_ncs_L2vpn-vs-vlan-tag;
                description
                  "Minimum value of VLAN range #9";
              }
              leaf vlan-range9-max {
                type live_ncs_L2vpn-vs-vlan-tag;
                description
                  "Maximum value of VLAN range #9";
              }
            }
            container routed-interface-ranges {
              description
                "Configure VLAN Switch Routed BVI Interface
                 ranges";
              leaf interface-range1-min {
                type uint32;
                description
                  "Minimum value of Interface range #1";
              }
              leaf interface-range1-max {
                type uint32;
                description
                  "Maximum value of Interface range #1";
              }
              leaf interface-range2-min {
                type uint32;
                description
                  "Minimum value of Interface range #2";
              }
              leaf interface-range2-max {
                type uint32;
                description
                  "Maximum value of Interface range #2";
              }
              leaf interface-range3-min {
                type uint32;
                description
                  "Minimum value of Interface range #3";
              }
              leaf interface-range3-max {
                type uint32;
                description
                  "Maximum value of Interface range #3";
              }
              leaf interface-range4-min {
                type uint32;
                description
                  "Minimum value of Interface range #4";
              }
              leaf interface-range4-max {
                type uint32;
                description
                  "Maximum value of Interface range #4";
              }
              leaf interface-range5-min {
                type uint32;
                description
                  "Minimum value of Interface range #5";
              }
              leaf interface-range5-max {
                type uint32;
                description
                  "Maximum value of Interface range #5";
              }
              leaf interface-range6-min {
                type uint32;
                description
                  "Minimum value of Interface range #6";
              }
              leaf interface-range6-max {
                type uint32;
                description
                  "Maximum value of Interface range #6";
              }
              leaf interface-range7-min {
                type uint32;
                description
                  "Minimum value of Interface range #7";
              }
              leaf interface-range7-max {
                type uint32;
                description
                  "Maximum value of Interface range #7";
              }
              leaf interface-range8-min {
                type uint32;
                description
                  "Minimum value of Interface range #8";
              }
              leaf interface-range8-max {
                type uint32;
                description
                  "Maximum value of Interface range #8";
              }
              leaf interface-range9-min {
                type uint32;
                description
                  "Minimum value of Interface range #9";
              }
              leaf interface-range9-max {
                type uint32;
                description
                  "Maximum value of Interface range #9";
              }
            }
            leaf name {
              type xr:live_ncs_Cisco-ios-xr-string;
              description
                "Name of the VLAN Switch";
            }
            uses live_ncs_BRIDGE-DOMAIN-TABLE;
          }
        }
        container flexible-xconnect-service-table {
          description
            "List of Flexible XConnect Services";
          container vlan-unaware-flexible-xconnect-services {
            description
              "List of Vlan-Unaware Flexible XConnect
               Services";
            list vlan-unaware-flexible-xconnect-service {
              key "name";
              description
                "Flexible XConnect Service";
              container vlan-unaware-fxc-attachment-circuits {
                description
                  "List of attachment circuits";
                list vlan-unaware-fxc-attachment-circuit {
                  key "name";
                  description
                    "Attachment circuit interface";
                  leaf name {
                    type xr:live_ncs_Interface-name;
                    description
                      "Name of the attachment circuit interface";
                  }
                }
              }
              container vlan-unaware-fxc-pseudowire-evpns {
                description
                  "List of EVPN Services";
                list vlan-unaware-fxc-pseudowire-evpn {
                  key "eviid acid";
                  description
                    "EVPN FXC Service Configuration";
                  leaf eviid {
                    type live_ncs_Evpnvpnid-range;
                    description
                      "Ethernet VPN ID";
                  }
                  leaf acid {
                    type live_ncs_Pseudowire-acid-range;
                    description
                      "AC ID";
                  }
                }
              }
              leaf name {
                type xr:live_ncs_Cisco-ios-xr-string;
                description
                  "Name of the Flexible XConnect Service";
              }
            }
          }
          container vlan-aware-flexible-xconnect-services {
            description
              "List of Vlan-Aware Flexible XConnect Services";
            list vlan-aware-flexible-xconnect-service {
              key "eviid";
              description
                "Flexible XConnect Service";
              container vlan-aware-fxc-attachment-circuits {
                description
                  "List of attachment circuits";
                list vlan-aware-fxc-attachment-circuit {
                  key "name";
                  description
                    "Attachment circuit interface";
                  leaf name {
                    type xr:live_ncs_Interface-name;
                    description
                      "Name of the attachment circuit interface";
                  }
                }
              }
              leaf eviid {
                type live_ncs_Evpnvpnid-range;
                description
                  "Ethernet VPN ID";
              }
            }
          }
        }
        container redundancy {
          description
            "Redundancy groups";
          container iccp-redundancy-groups {
            description
              "List of Inter-Chassis Communication Protocol
               redundancy groups";
            list iccp-redundancy-group {
              key "group-id";
              description
                "ICCP Redundancy group";
              container iccp-interfaces {
                description
                  "List of interfaces";
                list iccp-interface {
                  key "interface-name";
                  description
                    "Interface name";
                  leaf secondary-vlan-range {
                    type string;
                    description
                      "Secondary VLAN range, in the form of 1-3,5
                       ,8-11";
                  }
                  leaf recovery-delay {
                    type uint32 {
                      range "30..3600";
                    }
                    // NCS drop default statement
                    description
                      "Failure clear recovery delay";
                  }
                  leaf primary-vlan-range {
                    type string;
                    description
                      "Primary VLAN range, in the form of 1-3,5
                       ,8-11";
                  }
                  leaf mac-flush-tcn {
                    type empty;
                    description
                      "Enable STP-TCN MAC flushing";
                  }
                  leaf interface-name {
                    type xr:live_ncs_Interface-name;
                    description
                      "Interface name";
                  }
                }
              }
              leaf multi-homing-node-id {
                type uint32 {
                  range "0..254";
                }
                description
                  "ICCP-based service multi-homing node ID";
              }
              leaf group-id {
                type uint32 {
                  range "1..4294967295";
                }
                description
                  "Group ID";
              }
            }
          }
          leaf enable {
            type empty;
            description
              "Enable redundancy groups";
          }
        }
      }
      container pbb {
        description
          "L2VPN PBB Global";
        leaf backbone-source-mac {
          type yang:mac-address;
          description
            "Backbone Source MAC";
        }
      }
      container auto-discovery {
        description
          "Global auto-discovery attributes";
        container bgp-signaling {
          description
            "Global bgp signaling attributes";
          leaf mtu-mismatch-ignore {
            type empty;
            description
              "Ignore MTU mismatch for auto-discovered
               pseudowires";
          }
        }
      }
      container utility {
        description
          "L2VPN utilities";
        container logging {
          description
            "L2VPN logging utility";
          leaf bridge-domain-state-change {
            type empty;
            description
              "Enable Bridge Domain state change logging";
          }
          leaf pseudowire-state-change {
            type empty;
            description
              "Enable pseudowire state change logging";
          }
          leaf vfi {
            type empty;
            description
              "Enable VFI state change logging";
          }
          leaf nsr-state-change {
            type empty;
            description
              "Enable Non Stop Routing state change logging";
          }
          leaf pwhe-replication-state-change {
            type empty;
            description
              "Enable PW-HE Replication state change logging";
          }
        }
      }
      container snmp {
        description
          "SNMP related configuration";
        container mib {
          description
            "MIB related configuration";
          container mib-interface {
            description
              "Interface related configuration for MIB";
            container format {
              description
                "MIB interface name output format";
              leaf external-interface-format {
                type empty;
                description
                  "Set MIB interface name output in slash
                   format (/)";
              }
            }
          }
          container mib-pseudowire {
            description
              "Pseudowire related configuration for MIB";
            leaf statistics {
              type empty;
              description
                "Enable pseudowire statistics in MIB output";
            }
          }
        }
      }
      leaf nsr {
        type empty;
        description
          "Enable Non-Stop Routing";
      }
      leaf mtu-mismatch-ignore {
        type empty;
        description
          "Ignore MTU Mismatch for XCs";
      }
      leaf tcn-propagation {
        type empty;
        description
          "Topology change notification propagation";
      }
      leaf pwoam-refresh {
        type uint32 {
          range "1..4095";
        }
        units "second";
        description
          "Configure PW OAM refresh interval";
      }
      leaf load-balance {
        type live_ncs_Load-balance;
        description
          "Enable flow load balancing on l2vpn bridges";
      }
      leaf mspw-description {
        type string {
          length "1..64";
        }
        description
          "MS-PW global description";
      }
      leaf mac-limit-threshold {
        type live_ncs_Mac-limit-threshold-range;
        units "percentage";
        description
          "Configure MAC limit threshold percent";
      }
      leaf pw-status-disable {
        type empty;
        description
          "Disable PW status";
      }
      leaf enable {
        type empty;
        description
          "Enable L2VPN feature";
      }
      leaf pw-grouping {
        type empty;
        description
          "Enable PW grouping";
      }
      leaf capability {
        type live_ncs_L2vpn-capability-mode;
        description
          "L2VPN Capability Mode";
      }
      leaf l2vpn-router-id {
        type inet:ipv4-address-no-zone;
        description
          "Global L2VPN Router ID";
      }
    }
    container generic-interface-lists {
      tailf:ncs-device-type "netconf";
      tailf:display-when "not(../../ncs:module) or ../../ncs:module[ncs:name='Cisco-IOS-XR-l2vpn-cfg'] or (../../ncs:live-status-protocol[not(ncs:capability)]) or (../../ncs:live-status-protocol/ncs:capability/ncs:module[.='Cisco-IOS-XR-l2vpn-cfg'])";
      description
        "Generic Interface List configuration";
      list generic-interface-list {
        key "generic-interface-list-name";
        description
          "Generic interface list";
        container interfaces {
          description
            "Interface table";
          list interface {
            key "interface-name";
            description
              "Interface";
            leaf enable {
              type empty;
              description
                "Enable interface";
            }
            leaf interface-name {
              type xr:live_ncs_Interface-name;
              description
                "Name of the interface";
            }
          }
        }
        leaf enable {
          type empty;
          description
            "Enable interface list";
        }
        leaf generic-interface-list-name {
          type xr:live_ncs_Cisco-ios-xr-string;
          description
            "Name of the interface list";
        }
      }
    }
    container evpn {
      tailf:ncs-device-type "netconf";
      tailf:display-when "not(../../ncs:module) or ../../ncs:module[ncs:name='Cisco-IOS-XR-l2vpn-cfg'] or (../../ncs:live-status-protocol[not(ncs:capability)]) or (../../ncs:live-status-protocol/ncs:capability/ncs:module[.='Cisco-IOS-XR-l2vpn-cfg'])";
      description
        "EVPN configuration";
      container evpn-tables {
        description
          "EVPN submodes";
        container evpn-timers {
          description
            "Enter EVPN timers configuration submode";
          leaf evpn-carving {
            type uint32 {
              range "0..300";
            }
            // NCS drop default statement
            description
              "Global Carving timer";
          }
          leaf evpn-recovery {
            type uint32 {
              range "0..3600";
            }
            // NCS drop default statement
            description
              "Global Recovery timer";
          }
          leaf enable {
            type empty;
            description
              "Enable EVPN timers";
          }
          leaf evpn-peering {
            type uint32 {
              range "0..300";
            }
            // NCS drop default statement
            description
              "Global Peering timer";
          }
        }
        container evpn-virtual-access-vfis {
          description
            "Virtual Access VFI interfaces";
          list evpn-virtual-access-vfi {
            key "name";
            description
              "Virtual Access VFI";
            container evpn-virtual-access-vfi-timers {
              description
                "Enter Virtual Forwarding Interface timers
                 configuration submode";
              leaf evpn-virtual-access-vfi-recovery {
                type uint32 {
                  range "0..3600";
                }
                // NCS drop default statement
                description
                  "Virtual Forwarding Interface-specific
                   Recovery timer";
              }
              leaf evpn-virtual-access-vfi-peering {
                type uint32 {
                  range "0..300";
                }
                // NCS drop default statement
                description
                  "Virtual Forwarding Interface-specific
                   Peering timer";
              }
              leaf evpn-virtual-access-vfi-carving {
                type uint32 {
                  range "0..300";
                }
                // NCS drop default statement
                description
                  "Virtual Forwarding Interface-specific
                   Carving timer";
              }
              leaf enable {
                type empty;
                description
                  "Enable Virtual Forwarding Interface timers";
              }
            }
            leaf name {
              type xr:live_ncs_Cisco-ios-xr-string;
              description
                "Name of the Virtual Access VFI";
            }
            uses live_ncs_EVPN-VIRTUAL-ETHERNET-SEGMENT;
          }
        }
        container evpn-load-balancing {
          description
            "Enter EVPN Loadbalancing configuration submode";
          leaf evpn-static-flow-label {
            type empty;
            description
              "Enable Static Flow Label based load balancing";
          }
          leaf enable {
            type empty;
            description
              "Enable EVPN Loadbalancing";
          }
        }
        container evpn-bgp-auto-discovery {
          description
            "Enable Autodiscovery BGP in EVPN";
          leaf enable {
            type empty;
            description
              "Enable Autodiscovery BGP";
          }
          uses live_ncs_EVPN-ROUTE-DISTINGUISHER;
        }
        container evpn-groups {
          description
            "Enter EVPN Group Table submode";
          list evpn-group {
            key "group-id";
            description
              "Enter EVPN Group submode";
            container evpn-group-core-interfaces {
              description
                "EVPN Group core interfaces";
              list evpn-group-core-interface {
                key "interface-name";
                description
                  "EVPN Group Core interface";
                leaf interface-name {
                  type xr:live_ncs_Interface-name;
                  description
                    "Name of the EVPN Group core interface";
                }
              }
            }
            leaf group-id {
              type live_ncs_Evpn-group-id-range;
              description
                "Group ID";
            }
          }
        }
        container evpn-instances {
          description
            "Enter EVPN Instance configuration submode";
          list evpn-instance {
            key "vpn-id encapsulation side";
            description
              "Enter EVPN Instance configuration submode";
            container evpn-instance-bgp-auto-discovery {
              description
                "Enable Autodiscovery BGP in EVPN Instance";
              container evpn-route-policy {
                description
                  "Route policy";
                leaf export {
                  type string;
                  description
                    "Export route policy";
                }
                leaf import {
                  type string;
                  description
                    "Import route policy";
                }
              }
              container evpn-route-targets {
                description
                  "Route Target";
                list evpn-route-target {
                  // NCS drop must statement
                  key "role format";
                  description
                    "Name of the Route Target";
                  leaf format {
                    type live_ncs_Bgp-route-target-format;
                    description
                      "Format of the route target";
                  }
                  leaf role {
                    type live_ncs_Bgp-route-target-role;
                    description
                      "Role of the router target type";
                  }
                  list none {
                    // NCS drop when statement
                    key "stitching";
                    description
                      "none";
                    leaf stitching {
                      type live_ncs_Bgp-route-target;
                      description
                        "whether RT is Stitching RT (DEPRECATED)";
                    }
                  }
                  list two-byte-as-or-four-byte-as {
                    // NCS drop when statement
                    key "as as-index stitching";
                    description
                      "two byte as or four byte as";
                    leaf as {
                      type live_ncs_Rdas-range;
                      description
                        "Two byte or 4 byte AS number";
                    }
                    leaf as-index {
                      type live_ncs_Rdas-index;
                      description
                        "AS:nn (hex or decimal format)";
                    }
                    leaf stitching {
                      type live_ncs_Bgp-route-target;
                      description
                        "whether RT is Stitching RT (DEPRECATED)";
                    }
                  }
                  list ipv4-address {
                    // NCS drop when statement
                    key "address addr-index stitching";
                    description
                      "ipv4 address";
                    leaf address {
                      type inet:ipv4-address-no-zone;
                      description
                        "IPV4 address";
                    }
                    leaf addr-index {
                      type live_ncs_Rd-addr-index;
                      description
                        "Addr index";
                    }
                    leaf stitching {
                      type live_ncs_Bgp-route-target;
                      description
                        "whether RT is Stitching RT (DEPRECATED)";
                    }
                  }
                }
              }
              leaf table-policy {
                type string;
                description
                  "Table Policy for installation of forwarding
                   data to L2FIB";
              }
              leaf implicit-import-disable {
                type empty;
                description
                  "Disables BGP Implicit Import";
              }
              leaf enable {
                type empty;
                description
                  "Enable Autodiscovery BGP";
              }
              uses live_ncs_EVPN-ROUTE-DISTINGUISHER;
            }
            container evpn-instance-etree {
              description
                "Enter EVPN E-Tree configuration submode";
              leaf evpn-instance-etree-rt-leaf {
                type empty;
                description
                  "Configure E-Tree as Route-Target leaf";
              }
              leaf evpn-instance-etree-leaf {
                type empty;
                description
                  "Configure E-Tree as leaf";
              }
              leaf enable {
                type empty;
                description
                  "Enable EVPN E-Tree";
              }
            }
            container evpn-instance-advertise-mac {
              description
                "Enter Advertise local MAC-only routes
                 configuration submode";
              leaf evi-advertise-mac-bvi {
                type empty;
                description
                  "Advertise local MAC-only and BVI MAC routes";
              }
              leaf enable {
                type empty;
                description
                  "Enable Advertise local MAC-only routes";
              }
            }
            container evpn-instance-multicast {
              description
                "Enter Multicast configuration submode";
              leaf evi-mcast-source-connected {
                type empty;
                description
                  "Enable Multicast source connectivity";
              }
              leaf enable {
                type empty;
                description
                  "Enable Multicast";
              }
            }
            container evpn-instance-load-balancing {
              description
                "Enter Loadbalancing configuration submode";
              leaf evi-static-flow-label {
                type empty;
                description
                  "Enable Static Flow Label based load
                   balancing";
              }
              leaf enable {
                type empty;
                description
                  "Enable Loadbalancing";
              }
            }
            leaf evpn-route-sync-vrf-default {
              type xr:live_ncs_Cisco-ios-xr-string;
              description
                "Set EVI for default VRF";
            }
            leaf evi-srv6-locator {
              type string {
                length "1..58";
              }
              description
                "Specify SRv6 locator name";
            }
            leaf evi-reorig-disable {
              type empty;
              description
                "Disable route re-origination";
            }
            leaf evi-advertise-mac-deprecated {
              type empty;
              description
                "DEPRECATED: Advertise local MAC-only and BVI
                 MAC routes";
            }
            leaf evi-preferred-nexthop {
              type live_ncs_Preferred-nexthop-mode;
              description
                "Enable Preferred Nexthop mode on this EVI";
            }
            leaf evpn-evi-transmit-mtu-zero {
              type boolean;
              description
                "Transmit MTU zero to remote for this EVPN EVI
                 .";
            }
            leaf evpn-instance-description {
              type string {
                length "1..64";
              }
              description
                "Description for EVPN Instance";
            }
            leaf evpn-evi-mtu-mismatch-ignore {
              type boolean;
              description
                "Ignore mismatch between local and remote MTUs
                 for this EVPN EVI.";
            }
            leaf evi-ecmp-disable {
              type empty;
              description
                "Disable ECMP on the EVI";
            }
            leaf evpn-evi-mtu-match-enforce {
              type empty;
              description
                "Enforce matching between local and remote
                 MTUs for this EVPN EVI.";
            }
            leaf evpn-instance-vpws-single-active-backup-suppression {
              type empty;
              description
                "Configure EVPN VPWS Single-Active Backup
                 Suppression";
            }
            leaf evpn-evi-transmit-l2-mtu {
              type empty;
              description
                "Transmit L2 MTU to remote for this EVPN EVI.";
            }
            leaf evi-unknown-unicast-flooding-disable {
              type empty;
              description
                "Disable Unknown Unicast Flooding on this EVI";
            }
            leaf evpn-evi-cw-disable {
              type empty;
              description
                "CW disable for EVPN EVI";
            }
            leaf vpn-id {
              type live_ncs_Vpnid-range;
              description
                "EVPN Instance ID";
            }
            leaf encapsulation {
              type live_ncs_Evpn-encapsulation;
              description
                "EVPN Instance Encapsulation";
            }
            leaf side {
              type live_ncs_Evpn-side;
              description
                "EVPN Instance Side";
            }
          }
        }
        container evpn-logging {
          description
            "Enter EVPN Logging configuration submode";
          leaf evpn-df-election {
            type empty;
            description
              "Enable Designated Forwarder election logging";
          }
          leaf enable {
            type empty;
            description
              "Enable EVPN Logging";
          }
        }
        container evpn-segment-routing-srv6 {
          description
            "Enter EVPN Segment-Routing SRv6 submode";
          leaf evpn-srv6-locator {
            type string {
              length "1..58";
            }
            description
              "Specify default SRv6 locator name";
          }
          leaf enable {
            type empty;
            description
              "Enable EVPN Segment-Routing SRv6";
          }
        }
        container evpn-interfaces {
          description
            "Attachment Circuit interfaces";
          list evpn-interface {
            key "interface-name";
            description
              "Attachment circuit interface";
            container evpnac-timers {
              description
                "Enter Interface-specific timers configuration
                 submode";
              leaf evpnac-peering {
                type uint32 {
                  range "0..300";
                }
                // NCS drop default statement
                description
                  "Interface-specific Peering timer";
              }
              leaf evpnac-carving {
                type uint32 {
                  range "0..300";
                }
                // NCS drop default statement
                description
                  "Interface-specific Carving timer";
              }
              leaf enable {
                type empty;
                description
                  "Enable Interface-specific timers";
              }
              leaf evpnac-recovery {
                type uint32 {
                  range "0..3600";
                }
                // NCS drop default statement
                description
                  "Interface-specific Recovery timer";
              }
            }
            container ethernet-segment {
              description
                "Enter Ethernet Segment configuration submode";
              container es-convergence {
                description
                  "Convergence mode(s) and configuration
                   options";
                leaf mac-mobility {
                  type empty;
                  description
                    "Enable MAC-mobility triggered flush";
                }
                leaf nh-tracking {
                  type empty;
                  description
                    "Nexthop-tracking influenced DF Election";
                }
                leaf reroute {
                  type empty;
                  description
                    "Enable reroute to backup peer";
                }
                leaf enable {
                  type empty;
                  description
                    "Enable Convergence configuration options";
                }
              }
              leaf force-single-homed {
                type empty;
                description
                  "Force ethernet segment to remain
                   single-homed";
              }
              leaf load-balancing-mode {
                type live_ncs_Ethernet-segment-load-balance;
                description
                  "Ethernet-Segment Load Balancing mode";
              }
              leaf enable {
                type empty;
                description
                  "Enable Ethernet Segment";
              }
              leaf backbone-source-mac {
                type yang:mac-address;
                description
                  "Backbone Source MAC";
              }
              uses live_ncs_SERVICE-CARVING-MCAST-TYPE;
              uses live_ncs_ES-IMPORT-ROUTE-TARGET;
              uses live_ncs_SERVICE-CARVING-TYPE;
              uses live_ncs_IDENTIFIER;
              uses live_ncs_PREFERENCE-BASED-SERVICE-CARVING;
              uses live_ncs_MANUAL-SERVICE-CARVING;
            }
            leaf evpn-core-isolation-group {
              type live_ncs_Evpn-core-group-id-range;
              description
                "Enter EVPN Core Isolation Group ID";
            }
            leaf evpn-access-signal-mode {
              type live_ncs_Interface-access-signal-mode;
              description
                "Override default signal sent to bring down
                 access circuit";
            }
            leaf mac-flush {
              type live_ncs_Mac-flush-mode;
              description
                "Enable MAC Flushing";
            }
            leaf interface-name {
              type xr:live_ncs_Interface-name;
              description
                "Name of the attachment circuit interface";
            }
          }
        }
        container evpn-virtual-access-pws {
          description
            "Virtual Access Pseudowire interfaces";
          list evpn-virtual-access-pw {
            key "neighbor pseudowire-id";
            description
              "Virtual Access Pseudowire";
            container evpn-virtual-access-pw-timers {
              description
                "Enter Virtual Access Pseudowire-specific
                 timers configuration submode";
              leaf evpn-virtual-access-pw-recovery {
                type uint32 {
                  range "0..3600";
                }
                // NCS drop default statement
                description
                  "Virtual Access Pseudowire-specific Recovery
                   timer";
              }
              leaf evpn-virtual-access-pw-peering {
                type uint32 {
                  range "0..300";
                }
                // NCS drop default statement
                description
                  "Virtual Access Pseudowire-specific Peering
                   timer";
              }
              leaf enable {
                type empty;
                description
                  "Enable Virtual Access Pseudowire-specific
                   timers";
              }
              leaf evpn-virtual-access-pw-carving {
                type uint32 {
                  range "0..300";
                }
                // NCS drop default statement
                description
                  "Virtual Access Pseudowire-specific Carving
                   timer";
              }
            }
            leaf neighbor {
              type inet:ipv4-address-no-zone;
              description
                "Neighbor IP address";
            }
            leaf pseudowire-id {
              type live_ncs_Pseudowire-id-range;
              description
                "Pseudowire ID";
            }
            uses live_ncs_EVPN-VIRTUAL-ETHERNET-SEGMENT;
          }
        }
        container evpn-ethernet-segment {
          description
            "EVPN Global Ethernet Segment submode";
          container evpn-esi-types {
            description
              "EVPN ESI type table";
            list evpn-esi-type {
              key "esi-type";
              description
                "ESI type";
              leaf disable-auto-generation {
                type empty;
                description
                  "Disable ESI Autogeneration";
              }
              leaf esi-type {
                type live_ncs_Evpn-esi-type-range;
                description
                  "ESI type";
              }
            }
          }
          leaf enable {
            type empty;
            description
              "Enable EVPN Global Ethernet Segment submode";
          }
        }
        leaf evpn-global-transmit-mtu-zero {
          type empty;
          description
            "Transmit MTU zero to remote for all EVIs";
        }
        leaf evpn-global-mtu-mismatch-ignore {
          type empty;
          description
            "Ignore mismatch between local and remote MTUs
             for all EVIs.";
        }
        leaf evpn-global-mtu-match-enforce {
          type empty;
          description
            "Enforce matching between local and remote MTUs
             for all EVIs.";
        }
        leaf evpn-global-transmit-l2-mtu {
          type empty;
          description
            "Transmit L2 MTU to remote for all EVIs";
        }
        leaf evpn-staggered-bringup {
          type uint32 {
            range "0..300000";
          }
          units "millisecond";
          // NCS drop default statement
          description
            "Staggered bringup (milliseconds) timer";
        }
        leaf evi-cost-out {
          type empty;
          description
            "Configure node to cost-out";
        }
        leaf evpn-source-interface {
          type xr:live_ncs_Interface-name;
          description
            "Configure EVPN router-id implicitly through
             Loopback Interface";
        }
        leaf evpn-cost-in-startup {
          type uint32 {
            range "30..86400";
          }
          units "second";
          description
            "Cost-in node after given time (seconds) on
             startup timer";
        }
      }
      leaf enable {
        type empty;
        description
          "Enable EVPN feature";
      }
    }
  }
  augment "/ncs:devices/ncs:template/ncs:ned-id/ncs:config" {
    container l2vpn {
      description
        "L2VPN configuration";
      container pw-routing {
        description
          "Pseudowire-routing attributes";
        container pw-routing-bgp {
          description
            "Enable Autodiscovery BGP Pseudowire-routing BGP";
          leaf enable {
            type empty;
            description
              "Enable Autodiscovery BGP";
          }
          uses ncs_template_EVPN-ROUTE-DISTINGUISHER;
        }
        leaf pw-routing-global-id {
          type ncs_template_Pseudowire-gbl-id-range;
          description
            "Pseudowire-routing Global ID";
        }
      }
      container neighbor {
        description
          "L2VPN neighbor submode";
        leaf ldp-flap {
          type empty;
          description
            "Enable targetted LDP session flap action";
        }
      }
      container database {
        description
          "L2VPN databases";
        container g8032-rings {
          description
            "List of G8032 Ring";
          list g8032-ring {
            // NCS patched for predictable order
            ordered-by user;
            key "g8032-ring-name";
            description
              "G8032 Ring";
            container erp-port0s {
              description
                "Ethernet ring protection port0";
              list erp-port0 {
                // NCS patched for predictable order
                ordered-by user;
                key "interface-name";
                description
                  "Configure ERP main port0";
                leaf monitor {
                  type xr:ncs_template_Interface-name;
                  description
                    "Ethernet ring protection port0 monitor";
                }
                leaf interface-name {
                  type xr:ncs_template_Interface-name;
                  description
                    "Port0 interface";
                }
              }
            }
            container erp-instances {
              description
                "List of ethernet ring protection instance";
              list erp-instance {
                // NCS patched for predictable order
                ordered-by user;
                key "erp-instance-id";
                description
                  "Ethernet ring protection instance";
                container rpl {
                  description
                    "Ring protection link";
                  leaf port {
                    type ncs_template_Erp-port1;
                    description
                      "ERP main port number";
                  }
                  leaf role {
                    type ncs_template_Rpl-role;
                    description
                      "RPL role";
                  }
                }
                container aps {
                  description
                    "Automatic protection switching";
                  container port1 {
                    description
                      "APS channel for ERP port1";
                    leaf aps-type {
                      type ncs_template_Erpaps;
                      description
                        "Port1 APS type";
                    }
                    leaf aps-channel {
                      type string;
                      description
                        "Port1 APS channel in the format of
                         InterfaceName, BDName or XconnectName";
                    }
                  }
                  leaf port0 {
                    type string;
                    description
                      "Port0 APS channel in the format of
                       InterfaceName";
                  }
                  leaf enable {
                    type empty;
                    description
                      "Enable automatic protection switching";
                  }
                  leaf level {
                    type ncs_template_Erpaps-level-range;
                    description
                      "Automatic protection switching level";
                  }
                }
                leaf description {
                  type string;
                  description
                    "Ethernet ring protection instance
                     description";
                }
                leaf inclusion-list {
                  type string;
                  description
                    "Associates a set of VLAN IDs with the G
                     .8032 instance";
                }
                leaf profile {
                  type string;
                  description
                    "Ethernet ring protection instance profile";
                }
                leaf erp-instance-id {
                  type ncs_template_Erp-instance-range;
                  description
                    "ERP instance number";
                }
              }
            }
            container erp-port1s {
              description
                "Ethernet ring protection port0";
              list erp-port1 {
                // NCS patched for predictable order
                ordered-by user;
                // NCS drop must statement
                key "erp-port-type";
                description
                  "Ethernet ring protection port1";

                grouping ERP-PORT1-CONTENT {
                  description
                    "ERP PORT1 CONTENT";
                  leaf monitor {
                    type xr:ncs_template_Interface-name;
                    description
                      "Ethernet ring protection port1 monitor";
                  }
                }
                container none-or-virtual {
                  // NCS drop when statement
                  presence "Indicates that this node is configured.";
                  description
                    "none or virtual";
                  uses ERP-PORT1-CONTENT;
                }
                leaf erp-port-type {
                  type ncs_template_Erp-port;
                  description
                    "Port1 type";
                }
                list interface {
                  // NCS patched for predictable order
                  ordered-by user;
                  // NCS drop when statement
                  key "interface-name";
                  description
                    "interface";
                  leaf interface-name {
                    type xr:ncs_template_Interface-name;
                    description
                      "Port1 interface";
                  }
                  uses ERP-PORT1-CONTENT;
                }
              }
            }
            leaf open-ring {
              type empty;
              description
                "Specify the G.8032 instance as open ring";
            }
            leaf exclusion-list {
              type string;
              description
                "Vlan IDs in the format of a-b,c,d,e-f,g
                 ,untagged";
            }
            leaf erp-provider-bridge {
              type empty;
              description
                "Ethernet ring protection provider bridge";
            }
            leaf g8032-ring-name {
              type xr:ncs_template_Cisco-ios-xr-string;
              description
                "Name of the G8032 ring";
            }
          }
        }
        container xconnect-groups {
          description
            "List of xconnect groups";
          list xconnect-group {
            // NCS patched for predictable order
            ordered-by user;
            key "name";
            description
              "Xconnect group";
            container p2p-xconnects {
              description
                "List of point to point xconnects";
              list p2p-xconnect {
                // NCS patched for predictable order
                ordered-by user;
                key "name";
                description
                  "Point to point xconnect";
                container pseudowire-evpn-srv6s {
                  description
                    "List of EVPN SRv6 Services";
                  list pseudowire-evpn-srv6 {
                    // NCS patched for predictable order
                    ordered-by user;
                    key "eviid remote-acid source-acid";
                    description
                      "EVPN SRv6 P2P Service Configuration";
                    leaf pseudowire-evpn-srv6-locator {
                      type xr:ncs_template_Cisco-ios-xr-string;
                      description
                        "Specify SRv6 locator name";
                    }
                    leaf eviid {
                      type ncs_template_Evpnvpnid-range;
                      description
                        "Ethernet VPN ID";
                    }
                    leaf remote-acid {
                      type ncs_template_Pseudowire-evpnacid-range;
                      description
                        "Remote AC ID";
                    }
                    leaf source-acid {
                      type ncs_template_Pseudowire-evpnacid-range;
                      description
                        "Source AC ID";
                    }
                  }
                }
                container pseudowire-evpn-srv6-services {
                  description
                    "List of EVPN SRv6 Services keyed by EVI and
                     Service ID";
                  list pseudowire-evpn-srv6-service {
                    // NCS patched for predictable order
                    ordered-by user;
                    key "eviid service-id";
                    description
                      "EVPN SRv6 P2P Service Configuration";
                    leaf pseudowire-evpn-srv6-locator {
                      type xr:ncs_template_Cisco-ios-xr-string;
                      description
                        "Specify SRv6 locator name";
                    }
                    leaf eviid {
                      type ncs_template_Evpnvpnid-range;
                      description
                        "Ethernet VPN ID";
                    }
                    leaf service-id {
                      type ncs_template_Pseudowire-evpnacid-range;
                      description
                        "Service ID (Target and Source AC ID)";
                    }
                  }
                }
                container backup-attachment-circuits {
                  description
                    "List of backup attachment circuits";
                  list backup-attachment-circuit {
                    // NCS patched for predictable order
                    ordered-by user;
                    key "interface-name";
                    description
                      "Backup attachment circuit";
                    leaf interface-name {
                      type xr:ncs_template_Interface-name;
                      description
                        "Name of the attachment circuit interface";
                    }
                  }
                }
                container pseudowire-evpns {
                  description
                    "List of EVPN Services";
                  list pseudowire-evpn {
                    // NCS patched for predictable order
                    ordered-by user;
                    key "eviid remote-acid source-acid";
                    description
                      "EVPN P2P Service Configuration";
                    leaf class {
                      type xr:ncs_template_Cisco-ios-xr-string;
                      description
                        "Name of the pseudowire class";
                    }
                    leaf eviid {
                      type ncs_template_Evpnvpnid-range;
                      description
                        "Ethernet VPN ID";
                    }
                    leaf remote-acid {
                      type ncs_template_Pseudowire-evpnacid-range;
                      description
                        "Remote AC ID";
                    }
                    leaf source-acid {
                      type ncs_template_Pseudowire-evpnacid-range;
                      description
                        "Source AC ID";
                    }
                  }
                }
                container pseudowire-neighbor-pseudowire-ids {
                  description
                    "List of pseudowires";

                  grouping PSEUDOWIRE-CONTENT {
                    description
                      "PSEUDOWIRE CONTENT";
                    container mpls-static-labels {
                      description
                        "MPLS static labels";
                      leaf local-static-label {
                        type ncs_template_Pseudowire-label-range;
                        description
                          "Pseudowire local static label";
                      }
                      leaf remote-static-label {
                        type ncs_template_Pseudowire-label-range;
                        description
                          "Pseudowire remote static label";
                      }
                    }
                    container backup-pseudowires {
                      description
                        "List of pseudowires";
                      list backup-pseudowire {
                        // NCS patched for predictable order
                        ordered-by user;
                        key "neighbor pseudowire-id";
                        description
                          "Backup pseudowire for the cross connect";
                        container backup-mpls-static-labels {
                          description
                            "MPLS static labels";
                          leaf local-static-label {
                            type ncs_template_Pseudowire-label-range;
                            description
                              "Pseudowire local static label";
                          }
                          leaf remote-static-label {
                            type ncs_template_Pseudowire-label-range;
                            description
                              "Pseudowire remote static label";
                          }
                        }
                        leaf backup-pw-class {
                          type xr:ncs_template_Cisco-ios-xr-string;
                          description
                            "PW class template name to use for the
                             backup PW";
                        }
                        leaf neighbor {
                          type string;
                          description
                            "Neighbor IP address";
                        }
                        leaf pseudowire-id {
                          type ncs_template_Pseudowire-id-range;
                          description
                            "Pseudowire ID";
                        }
                      }
                    }
                    container l2tp-static-attributes {
                      description
                        "L2TP Static Attributes";
                      container l2tp-remote-cookie {
                        description
                          "L2TP remote cookie";
                        leaf size {
                          type ncs_template_L2tp-cookie-size;
                          description
                            "Remote cookie size";
                        }
                        leaf lower-value {
                          type ncs_template_L2tp-cookie-value-range;
                          description
                            "Lower remote cookie value";
                        }
                        leaf higher-value {
                          type ncs_template_L2tp-cookie-value-range;
                          description
                            "Higher remote cookie value";
                        }
                      }
                      container l2tp-secondary-local-cookie {
                        description
                          "L2TP secondary local cookie";
                        leaf size {
                          type ncs_template_L2tp-cookie-size;
                          description
                            "Local cookie size";
                        }
                        leaf lower-value {
                          type ncs_template_L2tp-cookie-value-range;
                          description
                            "Lower local cookie value";
                        }
                        leaf higher-value {
                          type ncs_template_L2tp-cookie-value-range;
                          description
                            "Higher local cookie value";
                        }
                      }
                      container l2tp-local-cookie {
                        description
                          "L2TP local cookie";
                        leaf size {
                          type ncs_template_L2tp-cookie-size;
                          description
                            "Local cookie size";
                        }
                        leaf lower-value {
                          type ncs_template_L2tp-cookie-value-range;
                          description
                            "Lower local cookie value";
                        }
                        leaf higher-value {
                          type ncs_template_L2tp-cookie-value-range;
                          description
                            "Higher local cookie value";
                        }
                      }
                      leaf l2tp-remote-session-id {
                        type ncs_template_L2tp-session-id-range;
                        description
                          "L2TP remote session ID";
                      }
                      leaf l2tp-local-session-id {
                        type ncs_template_L2tp-session-id-range;
                        description
                          "L2TP local session ID";
                      }
                    }
                    container l2tp-static {
                      description
                        "Pseudowire L2TPv3 static configuration";
                      leaf enable {
                        type empty;
                        description
                          "Enable pseudowire L2TPv3 static
                           configuration";
                      }
                    }
                    leaf tag-impose {
                      type ncs_template_Pseudowire-tag-range;
                      description
                        "Tag Impose vlan tagged mode";
                    }
                    leaf class {
                      type xr:ncs_template_Cisco-ios-xr-string;
                      description
                        "Name of the pseudowire class";
                    }
                    leaf source-address {
                      type string;
                      description
                        "Value of the Pseudowire source address.
                         Must be IPv6 only.";
                    }
                    leaf bandwidth {
                      type string;
                      description
                        "Pseudowire Bandwidth";
                    }
                  }
                  list pseudowire-neighbor-pseudowire-id {
                    // NCS patched for predictable order
                    ordered-by user;
                    key "neighbor pseudowire-id";
                    description
                      "Pseudowire configuration";
                    leaf neighbor {
                      type string;
                      description
                        "Pseudowire IPv4 address";
                    }
                    leaf pseudowire-id {
                      type ncs_template_Pseudowire-id-range;
                      description
                        "Pseudowire ID";
                    }
                    uses PSEUDOWIRE-CONTENT;
                  }
                  list pseudowire-pseudowire-address-pseudowire-id {
                    // NCS patched for predictable order
                    ordered-by user;
                    key "pseudowire-address pseudowire-id";
                    description
                      "Pseudowire configuration";
                    leaf pseudowire-address {
                      type string;
                      description
                        "Pseudowire IPv6 address. A pseudowire can
                         have only one address: IPv4 or IPv6";
                    }
                    leaf pseudowire-id {
                      type ncs_template_Pseudowire-id-range;
                      description
                        "Pseudowire ID";
                    }
                    uses PSEUDOWIRE-CONTENT;
                  }
                }
                container monitor-sessions {
                  description
                    "List of Monitor session segments";
                  list monitor-session {
                    // NCS patched for predictable order
                    ordered-by user;
                    key "name";
                    description
                      "Monitor session segment";
                    leaf enable {
                      type empty;
                      description
                        "Enable monitor session segment ";
                    }
                    leaf name {
                      type xr:ncs_template_Cisco-ios-xr-string;
                      description
                        "Name of the monitor session";
                    }
                  }
                }
                container pseudowire-routeds {
                  description
                    "List of pseudowire-routed";
                  list pseudowire-routed {
                    // NCS patched for predictable order
                    ordered-by user;
                    key "global-id prefix acid sacid";
                    description
                      "Pseudowire configuration";
                    leaf tag-impose {
                      type ncs_template_Pseudowire-tag-range;
                      description
                        "Tag Impose vlan tagged mode";
                    }
                    leaf class {
                      type xr:ncs_template_Cisco-ios-xr-string;
                      description
                        "Name of the pseudowire class";
                    }
                    leaf global-id {
                      type ncs_template_Pseudowire-gbl-id-range;
                      description
                        "Target Global ID";
                    }
                    leaf prefix {
                      type string;
                      description
                        "Target Prefix";
                    }
                    leaf acid {
                      type ncs_template_Pseudowire-acid-range;
                      description
                        "Target AC ID";
                    }
                    leaf sacid {
                      type ncs_template_Pseudowire-acid-range;
                      description
                        "Source AC ID";
                    }
                  }
                }
                container pseudowire-evpn-services {
                  description
                    "List of EVPN Services keyed by EVI and
                     Service ID";
                  list pseudowire-evpn-service {
                    // NCS patched for predictable order
                    ordered-by user;
                    key "eviid service-id";
                    description
                      "EVPN P2P Service Configuration";
                    leaf class {
                      type xr:ncs_template_Cisco-ios-xr-string;
                      description
                        "Name of the pseudowire class";
                    }
                    leaf eviid {
                      type ncs_template_Evpnvpnid-range;
                      description
                        "Ethernet VPN ID";
                    }
                    leaf service-id {
                      type ncs_template_Pseudowire-evpnacid-range;
                      description
                        "Service ID (Remote and Source AC ID)";
                    }
                  }
                }
                container attachment-circuits {
                  description
                    "List of attachment circuits";
                  list attachment-circuit {
                    // NCS patched for predictable order
                    ordered-by user;
                    key "name";
                    description
                      "Attachment circuit interface";
                    leaf enable {
                      type empty;
                      description
                        "Enable attachment circuit interface";
                    }
                    leaf name {
                      type xr:ncs_template_Interface-name;
                      description
                        "Name of the attachment circuit interface";
                    }
                  }
                }
                leaf p2p-description {
                  type string;
                  description
                    "cross connect description Name";
                }
                leaf interworking {
                  type ncs_template_Interworking;
                  description
                    "Interworking";
                }
                leaf name {
                  type xr:ncs_template_Cisco-ios-xr-string;
                  description
                    "Name of the point to point xconnect";
                }
              }
            }
            container mp2mp-xconnects {
              description
                "List of multi point to multi point xconnects";
              list mp2mp-xconnect {
                // NCS patched for predictable order
                ordered-by user;
                key "name";
                description
                  "Multi point to multi point xconnect";
                container mp2mp-auto-discovery {
                  description
                    "auto-discovery in this MP2MP";
                  container route-distinguisher {
                    description
                      "Route Distinguisher";
                    leaf type {
                      type ncs_template_Bgp-route-distinguisher;
                      description
                        "Router distinguisher type";
                    }
                    leaf as {
                      // NCS drop when statement
                      type ncs_template_Rdas-range;
                      description
                        "Two byte or 4 byte AS number";
                    }
                    leaf as-index {
                      // NCS drop when statement
                      type ncs_template_Rdas-index;
                      description
                        "AS:nn (hex or decimal format)";
                    }
                    leaf address {
                      // NCS drop when statement
                      type string;
                      description
                        "IPV4 address";
                    }
                    leaf addr-index {
                      // NCS drop when statement
                      type ncs_template_Rd-addr-index;
                      description
                        "Addr index";
                    }
                  }
                  container mp2mp-route-policy {
                    description
                      "Route policy";
                    leaf export {
                      type string;
                      description
                        "Export route policy";
                    }
                  }
                  container mp2mp-route-targets {
                    description
                      "Route Target";
                    list mp2mp-route-target {
                      // NCS patched for predictable order
                      ordered-by user;
                      // NCS drop must statement
                      key "role format";
                      description
                        "Name of the Route Target";
                      leaf role {
                        type ncs_template_Bgp-route-target-role;
                        description
                          "Role of the router target type";
                      }
                      leaf format {
                        type ncs_template_Bgp-route-target-format;
                        description
                          "Format of the route target";
                      }
                      list two-byte-as-or-four-byte-as {
                        // NCS patched for predictable order
                        ordered-by user;
                        // NCS drop when statement
                        key "as as-index";
                        description
                          "two byte as or four byte as";
                        leaf as {
                          type ncs_template_Rdas-range;
                          description
                            "Two byte or 4 byte AS number";
                        }
                        leaf as-index {
                          type ncs_template_Rdas-index;
                          description
                            "AS:nn (hex or decimal format)";
                        }
                      }
                      list ipv4-address {
                        // NCS patched for predictable order
                        ordered-by user;
                        // NCS drop when statement
                        key "address addr-index";
                        description
                          "ipv4 address";
                        leaf address {
                          type string;
                          description
                            "IPV4 address";
                        }
                        leaf addr-index {
                          type ncs_template_Rd-addr-index;
                          description
                            "Addr index";
                        }
                      }
                    }
                  }
                  container mp2mp-signaling-protocol {
                    description
                      "signaling protocol in this MP2MP";
                    container flow-label-load-balance {
                      description
                        "Enable Flow Label based load balancing";
                      leaf flow-label {
                        type ncs_template_Flow-label-load-balance;
                        description
                          "Flow Label load balance type";
                      }
                      leaf static {
                        type empty;
                        description
                          "Static Flow Label";
                      }
                    }
                    container ceids {
                      description
                        "Local Customer Edge Identifier Table";
                      list ceid {
                        // NCS patched for predictable order
                        ordered-by user;
                        key "ce-id";
                        description
                          "Local Customer Edge Identifier ";
                        container remote-ceid-attachment-circuits {
                          description
                            "AC And Remote Customer Edge Identifier
                             Table";
                          list remote-ceid-attachment-circuit {
                            // NCS patched for predictable order
                            ordered-by user;
                            key "name remote-ce-id";
                            description
                              "AC And Remote Customer Edge Identifier";
                            leaf name {
                              type xr:ncs_template_Interface-name;
                              description
                                "The name of the Attachment Circuit";
                            }
                            leaf remote-ce-id {
                              type ncs_template_Ce-id-range;
                              description
                                "Remote Customer Edge Identifier";
                            }
                          }
                        }
                        leaf ce-id {
                          type ncs_template_Ce-id-range;
                          description
                            "Local Customer Edge Identifier";
                        }
                      }
                    }
                    leaf ce-range {
                      type ncs_template_Cedge-range;
                      description
                        "Local Customer Edge Identifier";
                    }
                    leaf enable {
                      type empty;
                      description
                        "Enable signaling protocol";
                    }
                  }
                  leaf enable {
                    type empty;
                    description
                      "Enable auto-discovery";
                  }
                }
                leaf mp2mpmtu {
                  type ncs_template_L2vpn-mtu-range;
                  units "byte";
                  description
                    "Maximum transmission unit for this MP2MP
                     VPWS instance";
                }
                leaf mp2mp-control-word {
                  type empty;
                  description
                    "Disable control word";
                }
                leaf mp2mpl2-encapsulation {
                  type ncs_template_L2-encapsulation;
                  description
                    "Configure Layer 2 Encapsulation";
                }
                leaf mp2mp-interworking {
                  type ncs_template_Interworking;
                  description
                    "Interworking";
                }
                leaf mp2mp-shutdown {
                  type empty;
                  description
                    "shutdown this MP2MP VPWS instance";
                }
                leaf mp2mpvpn-id {
                  type ncs_template_Vpnid-range;
                  description
                    "VPN Identifier";
                }
                leaf name {
                  type xr:ncs_template_Cisco-ios-xr-string;
                  description
                    "Name of the multi point to multi point
                     xconnect";
                }
              }
            }
            leaf name {
              type xr:ncs_template_Cisco-ios-xr-string;
              description
                "Name of the xconnect group";
            }
          }
        }
        container bridge-domain-groups {
          description
            "List of bridge groups";
          list bridge-domain-group {
            // NCS patched for predictable order
            ordered-by user;
            key "name";
            description
              "Bridge group";
            leaf name {
              type xr:ncs_template_Cisco-ios-xr-string;
              description
                "Name of the Bridge group";
            }
            uses ncs_template_BRIDGE-DOMAIN-TABLE;
          }
        }
        container pseudowire-classes {
          description
            "List of pseudowire classes";
          list pseudowire-class {
            // NCS patched for predictable order
            ordered-by user;
            key "name";
            description
              "Pseudowire class";
            container l2tpv3-encapsulation {
              description
                "L2TPv3 encapsulation";
              container sequencing {
                description
                  "Sequencing";
                leaf sequencing {
                  type ncs_template_L2tpv3-sequencing;
                  // NCS drop default statement
                  description
                    "Sequencing";
                }
                leaf resync-threshold {
                  type ncs_template_Resync-threshold-range;
                  // NCS drop default statement
                  description
                    "Out of sequence threshold";
                }
              }
              container type-of-service {
                description
                  "Type of service";
                leaf type-of-service-value {
                  type ncs_template_Type-of-service-range;
                  description
                    "Type of service value";
                }
                leaf type-of-service-mode {
                  type ncs_template_Type-of-service-mode;
                  description
                    "Type of service mode";
                }
              }
              container signaling-protocol {
                description
                  "L2TPv3 signaling protocol";
                leaf protocol {
                  type ncs_template_L2tp-signaling-protocol;
                  // NCS drop default statement
                  description
                    "L2TPv3 signaling protocol";
                }
                leaf l2tpv3-class-name {
                  type xr:ncs_template_Cisco-ios-xr-string;
                  description
                    "Name of the L2TPv3 class name";
                }
              }
              container path-mtu {
                description
                  "Path maximum transmission unit";
                leaf enable {
                  type empty;
                  description
                    "Enable path MTU";
                }
                leaf max-path-mtu {
                  type ncs_template_Max-path-mtu-range;
                  description
                    "Maximum path maximum transmission unit";
                }
              }
              leaf df-bit-set {
                type empty;
                description
                  "Set the do not fragment bit to 1";
              }
              leaf cookie-size {
                type ncs_template_L2tp-cookie-size;
                // NCS drop default statement
                description
                  "Cookie size";
              }
              leaf source-address {
                type string;
                description
                  "Source IP address";
              }
              leaf transport-mode {
                type ncs_template_Transport-mode;
                description
                  "Transport mode";
              }
              leaf enable {
                type empty;
                description
                  "Enable L2TPv3 encapsulation";
              }
              leaf time-to-live {
                type ncs_template_Time-to-live-range;
                description
                  "Time to live";
              }
            }
            container backup-disable-delay {
              description
                "Back Up Pseudowire class";
              leaf type {
                type ncs_template_Backup-disable;
                description
                  "Delay or Never";
              }
              leaf disable-backup {
                // NCS drop when statement
                type ncs_template_Backup-disable-delay-range;
                description
                  "Disable backup delay";
              }
            }
            container mpls-encapsulation {
              description
                "MPLS encapsulation";
              container sequencing {
                description
                  "Sequencing";
                leaf sequencing {
                  type ncs_template_Mpls-sequencing;
                  // NCS drop default statement
                  description
                    "Sequencing";
                }
                leaf resync-threshold {
                  type ncs_template_Resync-threshold-range;
                  // NCS drop default statement
                  description
                    "Out of sequence threshold";
                }
              }
              container mpls-redundancy {
                description
                  "Redundancy options for MPLS encapsulation";
                leaf redundancy-one-way {
                  type empty;
                  description
                    "Force one-way PW redundancy behavior in
                     Redundancy Group";
                }
                leaf redundancy-initial-delay {
                  type ncs_template_Pw-redundancy-initial-delay-range;
                  units "second";
                  description
                    "Initial delay before activating the
                     redundant PW, in seconds";
                }
              }
              container preferred-path {
                description
                  "Preferred path";
                leaf type {
                  type ncs_template_Preferred-path;
                  description
                    "Preferred Path Type";
                }
                leaf interface-tunnel-number {
                  // NCS drop when statement
                  type string;
                  description
                    "Interface Tunnel number for preferred path";
                }
                leaf fallback-disable {
                  // NCS drop when statement
                  type empty;
                  description
                    "Fallback disable";
                }
                leaf path-name {
                  // NCS drop when statement
                  type xr:ncs_template_Cisco-ios-xr-string;
                  description
                    "Name of the SR TE Policy or IFName";
                }
              }
              container load-balance-group {
                description
                  "Load Balancing";
                container flow-label-load-balance {
                  description
                    "Enable Flow Label based load balancing";
                  leaf flow-label {
                    type ncs_template_Flow-label-load-balance;
                    description
                      "Flow Label load balance type";
                  }
                  leaf static {
                    type empty;
                    description
                      "Static Flow Label";
                  }
                }
                leaf flow-label-load-balance-code {
                  type ncs_template_Flow-label-tlv-code;
                  description
                    "Enable Legacy Flow Label TLV code";
                }
                leaf pw-label-load-balance {
                  type ncs_template_Load-balance;
                  description
                    "Enable PW Label based Load Balancing";
                }
              }
              leaf pw-switching-tlv {
                type ncs_template_Pw-switching-point-tlv;
                description
                  "Pseudowire Switching Point Tlv";
              }
              leaf static-tag-rewrite {
                type ncs_template_Tag-rewrite-range;
                description
                  "Static Tag rewrite";
              }
              leaf signaling-protocol {
                type ncs_template_Mpls-signaling-protocol;
                // NCS drop default statement
                description
                  "MPLS signaling protocol";
              }
              leaf vccv-type {
                type ncs_template_Vccv-verification;
                // NCS drop default statement
                description
                  "VCCV verification type";
              }
              leaf source-address {
                type string;
                description
                  "Source IP address";
              }
              leaf transport-mode {
                type ncs_template_Transport-mode;
                description
                  "Transport mode";
              }
              leaf enable {
                type empty;
                description
                  "Enable MPLS encapsulation";
              }
              leaf control-word {
                type ncs_template_Control-word;
                description
                  "Enable control word";
              }
            }
            leaf mac-withdraw {
              type empty;
              description
                "Enable backup MAC withdraw";
            }
            leaf enable {
              type empty;
              description
                "Enable pseudowire class";
            }
            leaf name {
              type xr:ncs_template_Cisco-ios-xr-string;
              description
                "Name of the pseudowire class";
            }
          }
        }
        container vlan-switches {
          description
            "List of VLAN Switches";
          list vlan-switch {
            // NCS patched for predictable order
            ordered-by user;
            key "name";
            description
              "VLAN Switch";
            container vlan-switch-ports {
              description
                "List of VLAN Switched Ports";
              list vlan-switch-port {
                // NCS patched for predictable order
                ordered-by user;
                key "interface-name";
                description
                  "VLAN Switched Port";
                leaf interface-name {
                  type xr:ncs_template_Interface-name;
                  description
                    "Interface name";
                }
              }
            }
            container vni-ranges {
              description
                "Configure VLAN Switch VxLAN Ethernet VPN-ID
                 ranges";
              leaf vni-range1-min {
                type string;
                description
                  "Minimum value of VNI range #1";
              }
              leaf vni-range1-max {
                type string;
                description
                  "Maximum value of VNI range #1";
              }
              leaf vni-range2-min {
                type string;
                description
                  "Minimum value of VNI range #2";
              }
              leaf vni-range2-max {
                type string;
                description
                  "Maximum value of VNI range #2";
              }
              leaf vni-range3-min {
                type string;
                description
                  "Minimum value of VNI range #3";
              }
              leaf vni-range3-max {
                type string;
                description
                  "Maximum value of VNI range #3";
              }
              leaf vni-range4-min {
                type string;
                description
                  "Minimum value of VNI range #4";
              }
              leaf vni-range4-max {
                type string;
                description
                  "Maximum value of VNI range #4";
              }
              leaf vni-range5-min {
                type string;
                description
                  "Minimum value of VNI range #5";
              }
              leaf vni-range5-max {
                type string;
                description
                  "Maximum value of VNI range #5";
              }
              leaf vni-range6-min {
                type string;
                description
                  "Minimum value of VNI range #6";
              }
              leaf vni-range6-max {
                type string;
                description
                  "Maximum value of VNI range #6";
              }
              leaf vni-range7-min {
                type string;
                description
                  "Minimum value of VNI range #7";
              }
              leaf vni-range7-max {
                type string;
                description
                  "Maximum value of VNI range #7";
              }
              leaf vni-range8-min {
                type string;
                description
                  "Minimum value of VNI range #8";
              }
              leaf vni-range8-max {
                type string;
                description
                  "Maximum value of VNI range #8";
              }
              leaf vni-range9-min {
                type string;
                description
                  "Minimum value of VNI range #9";
              }
              leaf vni-range9-max {
                type string;
                description
                  "Maximum value of VNI range #9";
              }
            }
            container vlan-ranges {
              description
                "Configure VLAN Switch VLAN ranges";
              leaf vlan-range1-min {
                type ncs_template_L2vpn-vs-vlan-tag;
                description
                  "Minimum value of VLAN range #1";
              }
              leaf vlan-range1-max {
                type ncs_template_L2vpn-vs-vlan-tag;
                description
                  "Maximum value of VLAN range #1";
              }
              leaf vlan-range2-min {
                type ncs_template_L2vpn-vs-vlan-tag;
                description
                  "Minimum value of VLAN range #2";
              }
              leaf vlan-range2-max {
                type ncs_template_L2vpn-vs-vlan-tag;
                description
                  "Maximum value of VLAN range #2";
              }
              leaf vlan-range3-min {
                type ncs_template_L2vpn-vs-vlan-tag;
                description
                  "Minimum value of VLAN range #3";
              }
              leaf vlan-range3-max {
                type ncs_template_L2vpn-vs-vlan-tag;
                description
                  "Maximum value of VLAN range #3";
              }
              leaf vlan-range4-min {
                type ncs_template_L2vpn-vs-vlan-tag;
                description
                  "Minimum value of VLAN range #4";
              }
              leaf vlan-range4-max {
                type ncs_template_L2vpn-vs-vlan-tag;
                description
                  "Maximum value of VLAN range #4";
              }
              leaf vlan-range5-min {
                type ncs_template_L2vpn-vs-vlan-tag;
                description
                  "Minimum value of VLAN range #5";
              }
              leaf vlan-range5-max {
                type ncs_template_L2vpn-vs-vlan-tag;
                description
                  "Maximum value of VLAN range #5";
              }
              leaf vlan-range6-min {
                type ncs_template_L2vpn-vs-vlan-tag;
                description
                  "Minimum value of VLAN range #6";
              }
              leaf vlan-range6-max {
                type ncs_template_L2vpn-vs-vlan-tag;
                description
                  "Maximum value of VLAN range #6";
              }
              leaf vlan-range7-min {
                type ncs_template_L2vpn-vs-vlan-tag;
                description
                  "Minimum value of VLAN range #7";
              }
              leaf vlan-range7-max {
                type ncs_template_L2vpn-vs-vlan-tag;
                description
                  "Maximum value of VLAN range #7";
              }
              leaf vlan-range8-min {
                type ncs_template_L2vpn-vs-vlan-tag;
                description
                  "Minimum value of VLAN range #8";
              }
              leaf vlan-range8-max {
                type ncs_template_L2vpn-vs-vlan-tag;
                description
                  "Maximum value of VLAN range #8";
              }
              leaf vlan-range9-min {
                type ncs_template_L2vpn-vs-vlan-tag;
                description
                  "Minimum value of VLAN range #9";
              }
              leaf vlan-range9-max {
                type ncs_template_L2vpn-vs-vlan-tag;
                description
                  "Maximum value of VLAN range #9";
              }
            }
            container routed-interface-ranges {
              description
                "Configure VLAN Switch Routed BVI Interface
                 ranges";
              leaf interface-range1-min {
                type string;
                description
                  "Minimum value of Interface range #1";
              }
              leaf interface-range1-max {
                type string;
                description
                  "Maximum value of Interface range #1";
              }
              leaf interface-range2-min {
                type string;
                description
                  "Minimum value of Interface range #2";
              }
              leaf interface-range2-max {
                type string;
                description
                  "Maximum value of Interface range #2";
              }
              leaf interface-range3-min {
                type string;
                description
                  "Minimum value of Interface range #3";
              }
              leaf interface-range3-max {
                type string;
                description
                  "Maximum value of Interface range #3";
              }
              leaf interface-range4-min {
                type string;
                description
                  "Minimum value of Interface range #4";
              }
              leaf interface-range4-max {
                type string;
                description
                  "Maximum value of Interface range #4";
              }
              leaf interface-range5-min {
                type string;
                description
                  "Minimum value of Interface range #5";
              }
              leaf interface-range5-max {
                type string;
                description
                  "Maximum value of Interface range #5";
              }
              leaf interface-range6-min {
                type string;
                description
                  "Minimum value of Interface range #6";
              }
              leaf interface-range6-max {
                type string;
                description
                  "Maximum value of Interface range #6";
              }
              leaf interface-range7-min {
                type string;
                description
                  "Minimum value of Interface range #7";
              }
              leaf interface-range7-max {
                type string;
                description
                  "Maximum value of Interface range #7";
              }
              leaf interface-range8-min {
                type string;
                description
                  "Minimum value of Interface range #8";
              }
              leaf interface-range8-max {
                type string;
                description
                  "Maximum value of Interface range #8";
              }
              leaf interface-range9-min {
                type string;
                description
                  "Minimum value of Interface range #9";
              }
              leaf interface-range9-max {
                type string;
                description
                  "Maximum value of Interface range #9";
              }
            }
            leaf name {
              type xr:ncs_template_Cisco-ios-xr-string;
              description
                "Name of the VLAN Switch";
            }
            uses ncs_template_BRIDGE-DOMAIN-TABLE;
          }
        }
        container flexible-xconnect-service-table {
          description
            "List of Flexible XConnect Services";
          container vlan-unaware-flexible-xconnect-services {
            description
              "List of Vlan-Unaware Flexible XConnect
               Services";
            list vlan-unaware-flexible-xconnect-service {
              // NCS patched for predictable order
              ordered-by user;
              key "name";
              description
                "Flexible XConnect Service";
              container vlan-unaware-fxc-attachment-circuits {
                description
                  "List of attachment circuits";
                list vlan-unaware-fxc-attachment-circuit {
                  // NCS patched for predictable order
                  ordered-by user;
                  key "name";
                  description
                    "Attachment circuit interface";
                  leaf name {
                    type xr:ncs_template_Interface-name;
                    description
                      "Name of the attachment circuit interface";
                  }
                }
              }
              container vlan-unaware-fxc-pseudowire-evpns {
                description
                  "List of EVPN Services";
                list vlan-unaware-fxc-pseudowire-evpn {
                  // NCS patched for predictable order
                  ordered-by user;
                  key "eviid acid";
                  description
                    "EVPN FXC Service Configuration";
                  leaf eviid {
                    type ncs_template_Evpnvpnid-range;
                    description
                      "Ethernet VPN ID";
                  }
                  leaf acid {
                    type ncs_template_Pseudowire-acid-range;
                    description
                      "AC ID";
                  }
                }
              }
              leaf name {
                type xr:ncs_template_Cisco-ios-xr-string;
                description
                  "Name of the Flexible XConnect Service";
              }
            }
          }
          container vlan-aware-flexible-xconnect-services {
            description
              "List of Vlan-Aware Flexible XConnect Services";
            list vlan-aware-flexible-xconnect-service {
              // NCS patched for predictable order
              ordered-by user;
              key "eviid";
              description
                "Flexible XConnect Service";
              container vlan-aware-fxc-attachment-circuits {
                description
                  "List of attachment circuits";
                list vlan-aware-fxc-attachment-circuit {
                  // NCS patched for predictable order
                  ordered-by user;
                  key "name";
                  description
                    "Attachment circuit interface";
                  leaf name {
                    type xr:ncs_template_Interface-name;
                    description
                      "Name of the attachment circuit interface";
                  }
                }
              }
              leaf eviid {
                type ncs_template_Evpnvpnid-range;
                description
                  "Ethernet VPN ID";
              }
            }
          }
        }
        container redundancy {
          description
            "Redundancy groups";
          container iccp-redundancy-groups {
            description
              "List of Inter-Chassis Communication Protocol
               redundancy groups";
            list iccp-redundancy-group {
              // NCS patched for predictable order
              ordered-by user;
              key "group-id";
              description
                "ICCP Redundancy group";
              container iccp-interfaces {
                description
                  "List of interfaces";
                list iccp-interface {
                  // NCS patched for predictable order
                  ordered-by user;
                  key "interface-name";
                  description
                    "Interface name";
                  leaf secondary-vlan-range {
                    type string;
                    description
                      "Secondary VLAN range, in the form of 1-3,5
                       ,8-11";
                  }
                  leaf recovery-delay {
                    type string;
                    // NCS drop default statement
                    description
                      "Failure clear recovery delay";
                  }
                  leaf primary-vlan-range {
                    type string;
                    description
                      "Primary VLAN range, in the form of 1-3,5
                       ,8-11";
                  }
                  leaf mac-flush-tcn {
                    type empty;
                    description
                      "Enable STP-TCN MAC flushing";
                  }
                  leaf interface-name {
                    type xr:ncs_template_Interface-name;
                    description
                      "Interface name";
                  }
                }
              }
              leaf multi-homing-node-id {
                type string;
                description
                  "ICCP-based service multi-homing node ID";
              }
              leaf group-id {
                type string;
                description
                  "Group ID";
              }
            }
          }
          leaf enable {
            type empty;
            description
              "Enable redundancy groups";
          }
        }
      }
      container pbb {
        description
          "L2VPN PBB Global";
        leaf backbone-source-mac {
          type string;
          description
            "Backbone Source MAC";
        }
      }
      container auto-discovery {
        description
          "Global auto-discovery attributes";
        container bgp-signaling {
          description
            "Global bgp signaling attributes";
          leaf mtu-mismatch-ignore {
            type empty;
            description
              "Ignore MTU mismatch for auto-discovered
               pseudowires";
          }
        }
      }
      container utility {
        description
          "L2VPN utilities";
        container logging {
          description
            "L2VPN logging utility";
          leaf bridge-domain-state-change {
            type empty;
            description
              "Enable Bridge Domain state change logging";
          }
          leaf pseudowire-state-change {
            type empty;
            description
              "Enable pseudowire state change logging";
          }
          leaf vfi {
            type empty;
            description
              "Enable VFI state change logging";
          }
          leaf nsr-state-change {
            type empty;
            description
              "Enable Non Stop Routing state change logging";
          }
          leaf pwhe-replication-state-change {
            type empty;
            description
              "Enable PW-HE Replication state change logging";
          }
        }
      }
      container snmp {
        description
          "SNMP related configuration";
        container mib {
          description
            "MIB related configuration";
          container mib-interface {
            description
              "Interface related configuration for MIB";
            container format {
              description
                "MIB interface name output format";
              leaf external-interface-format {
                type empty;
                description
                  "Set MIB interface name output in slash
                   format (/)";
              }
            }
          }
          container mib-pseudowire {
            description
              "Pseudowire related configuration for MIB";
            leaf statistics {
              type empty;
              description
                "Enable pseudowire statistics in MIB output";
            }
          }
        }
      }
      leaf nsr {
        type empty;
        description
          "Enable Non-Stop Routing";
      }
      leaf mtu-mismatch-ignore {
        type empty;
        description
          "Ignore MTU Mismatch for XCs";
      }
      leaf tcn-propagation {
        type empty;
        description
          "Topology change notification propagation";
      }
      leaf pwoam-refresh {
        type string;
        units "second";
        description
          "Configure PW OAM refresh interval";
      }
      leaf load-balance {
        type ncs_template_Load-balance;
        description
          "Enable flow load balancing on l2vpn bridges";
      }
      leaf mspw-description {
        type string;
        description
          "MS-PW global description";
      }
      leaf mac-limit-threshold {
        type ncs_template_Mac-limit-threshold-range;
        units "percentage";
        description
          "Configure MAC limit threshold percent";
      }
      leaf pw-status-disable {
        type empty;
        description
          "Disable PW status";
      }
      leaf enable {
        type empty;
        description
          "Enable L2VPN feature";
      }
      leaf pw-grouping {
        type empty;
        description
          "Enable PW grouping";
      }
      leaf capability {
        type ncs_template_L2vpn-capability-mode;
        description
          "L2VPN Capability Mode";
      }
      leaf l2vpn-router-id {
        type string;
        description
          "Global L2VPN Router ID";
      }
    }
    container generic-interface-lists {
      description
        "Generic Interface List configuration";
      list generic-interface-list {
        // NCS patched for predictable order
        ordered-by user;
        key "generic-interface-list-name";
        description
          "Generic interface list";
        container interfaces {
          description
            "Interface table";
          list interface {
            // NCS patched for predictable order
            ordered-by user;
            key "interface-name";
            description
              "Interface";
            leaf enable {
              type empty;
              description
                "Enable interface";
            }
            leaf interface-name {
              type xr:ncs_template_Interface-name;
              description
                "Name of the interface";
            }
          }
        }
        leaf enable {
          type empty;
          description
            "Enable interface list";
        }
        leaf generic-interface-list-name {
          type xr:ncs_template_Cisco-ios-xr-string;
          description
            "Name of the interface list";
        }
      }
    }
    container evpn {
      description
        "EVPN configuration";
      container evpn-tables {
        description
          "EVPN submodes";
        container evpn-timers {
          description
            "Enter EVPN timers configuration submode";
          leaf evpn-carving {
            type string;
            // NCS drop default statement
            description
              "Global Carving timer";
          }
          leaf evpn-recovery {
            type string;
            // NCS drop default statement
            description
              "Global Recovery timer";
          }
          leaf enable {
            type empty;
            description
              "Enable EVPN timers";
          }
          leaf evpn-peering {
            type string;
            // NCS drop default statement
            description
              "Global Peering timer";
          }
        }
        container evpn-virtual-access-vfis {
          description
            "Virtual Access VFI interfaces";
          list evpn-virtual-access-vfi {
            // NCS patched for predictable order
            ordered-by user;
            key "name";
            description
              "Virtual Access VFI";
            container evpn-virtual-access-vfi-timers {
              description
                "Enter Virtual Forwarding Interface timers
                 configuration submode";
              leaf evpn-virtual-access-vfi-recovery {
                type string;
                // NCS drop default statement
                description
                  "Virtual Forwarding Interface-specific
                   Recovery timer";
              }
              leaf evpn-virtual-access-vfi-peering {
                type string;
                // NCS drop default statement
                description
                  "Virtual Forwarding Interface-specific
                   Peering timer";
              }
              leaf evpn-virtual-access-vfi-carving {
                type string;
                // NCS drop default statement
                description
                  "Virtual Forwarding Interface-specific
                   Carving timer";
              }
              leaf enable {
                type empty;
                description
                  "Enable Virtual Forwarding Interface timers";
              }
            }
            leaf name {
              type xr:ncs_template_Cisco-ios-xr-string;
              description
                "Name of the Virtual Access VFI";
            }
            uses ncs_template_EVPN-VIRTUAL-ETHERNET-SEGMENT;
          }
        }
        container evpn-load-balancing {
          description
            "Enter EVPN Loadbalancing configuration submode";
          leaf evpn-static-flow-label {
            type empty;
            description
              "Enable Static Flow Label based load balancing";
          }
          leaf enable {
            type empty;
            description
              "Enable EVPN Loadbalancing";
          }
        }
        container evpn-bgp-auto-discovery {
          description
            "Enable Autodiscovery BGP in EVPN";
          leaf enable {
            type empty;
            description
              "Enable Autodiscovery BGP";
          }
          uses ncs_template_EVPN-ROUTE-DISTINGUISHER;
        }
        container evpn-groups {
          description
            "Enter EVPN Group Table submode";
          list evpn-group {
            // NCS patched for predictable order
            ordered-by user;
            key "group-id";
            description
              "Enter EVPN Group submode";
            container evpn-group-core-interfaces {
              description
                "EVPN Group core interfaces";
              list evpn-group-core-interface {
                // NCS patched for predictable order
                ordered-by user;
                key "interface-name";
                description
                  "EVPN Group Core interface";
                leaf interface-name {
                  type xr:ncs_template_Interface-name;
                  description
                    "Name of the EVPN Group core interface";
                }
              }
            }
            leaf group-id {
              type ncs_template_Evpn-group-id-range;
              description
                "Group ID";
            }
          }
        }
        container evpn-instances {
          description
            "Enter EVPN Instance configuration submode";
          list evpn-instance {
            // NCS patched for predictable order
            ordered-by user;
            key "vpn-id encapsulation side";
            description
              "Enter EVPN Instance configuration submode";
            container evpn-instance-bgp-auto-discovery {
              description
                "Enable Autodiscovery BGP in EVPN Instance";
              container evpn-route-policy {
                description
                  "Route policy";
                leaf export {
                  type string;
                  description
                    "Export route policy";
                }
                leaf import {
                  type string;
                  description
                    "Import route policy";
                }
              }
              container evpn-route-targets {
                description
                  "Route Target";
                list evpn-route-target {
                  // NCS patched for predictable order
                  ordered-by user;
                  // NCS drop must statement
                  key "role format";
                  description
                    "Name of the Route Target";
                  leaf format {
                    type ncs_template_Bgp-route-target-format;
                    description
                      "Format of the route target";
                  }
                  leaf role {
                    type ncs_template_Bgp-route-target-role;
                    description
                      "Role of the router target type";
                  }
                  list none {
                    // NCS patched for predictable order
                    ordered-by user;
                    // NCS drop when statement
                    key "stitching";
                    description
                      "none";
                    leaf stitching {
                      type ncs_template_Bgp-route-target;
                      description
                        "whether RT is Stitching RT (DEPRECATED)";
                    }
                  }
                  list two-byte-as-or-four-byte-as {
                    // NCS patched for predictable order
                    ordered-by user;
                    // NCS drop when statement
                    key "as as-index stitching";
                    description
                      "two byte as or four byte as";
                    leaf as {
                      type ncs_template_Rdas-range;
                      description
                        "Two byte or 4 byte AS number";
                    }
                    leaf as-index {
                      type ncs_template_Rdas-index;
                      description
                        "AS:nn (hex or decimal format)";
                    }
                    leaf stitching {
                      type ncs_template_Bgp-route-target;
                      description
                        "whether RT is Stitching RT (DEPRECATED)";
                    }
                  }
                  list ipv4-address {
                    // NCS patched for predictable order
                    ordered-by user;
                    // NCS drop when statement
                    key "address addr-index stitching";
                    description
                      "ipv4 address";
                    leaf address {
                      type string;
                      description
                        "IPV4 address";
                    }
                    leaf addr-index {
                      type ncs_template_Rd-addr-index;
                      description
                        "Addr index";
                    }
                    leaf stitching {
                      type ncs_template_Bgp-route-target;
                      description
                        "whether RT is Stitching RT (DEPRECATED)";
                    }
                  }
                }
              }
              leaf table-policy {
                type string;
                description
                  "Table Policy for installation of forwarding
                   data to L2FIB";
              }
              leaf implicit-import-disable {
                type empty;
                description
                  "Disables BGP Implicit Import";
              }
              leaf enable {
                type empty;
                description
                  "Enable Autodiscovery BGP";
              }
              uses ncs_template_EVPN-ROUTE-DISTINGUISHER;
            }
            container evpn-instance-etree {
              description
                "Enter EVPN E-Tree configuration submode";
              leaf evpn-instance-etree-rt-leaf {
                type empty;
                description
                  "Configure E-Tree as Route-Target leaf";
              }
              leaf evpn-instance-etree-leaf {
                type empty;
                description
                  "Configure E-Tree as leaf";
              }
              leaf enable {
                type empty;
                description
                  "Enable EVPN E-Tree";
              }
            }
            container evpn-instance-advertise-mac {
              description
                "Enter Advertise local MAC-only routes
                 configuration submode";
              leaf evi-advertise-mac-bvi {
                type empty;
                description
                  "Advertise local MAC-only and BVI MAC routes";
              }
              leaf enable {
                type empty;
                description
                  "Enable Advertise local MAC-only routes";
              }
            }
            container evpn-instance-multicast {
              description
                "Enter Multicast configuration submode";
              leaf evi-mcast-source-connected {
                type empty;
                description
                  "Enable Multicast source connectivity";
              }
              leaf enable {
                type empty;
                description
                  "Enable Multicast";
              }
            }
            container evpn-instance-load-balancing {
              description
                "Enter Loadbalancing configuration submode";
              leaf evi-static-flow-label {
                type empty;
                description
                  "Enable Static Flow Label based load
                   balancing";
              }
              leaf enable {
                type empty;
                description
                  "Enable Loadbalancing";
              }
            }
            leaf evpn-route-sync-vrf-default {
              type xr:ncs_template_Cisco-ios-xr-string;
              description
                "Set EVI for default VRF";
            }
            leaf evi-srv6-locator {
              type string;
              description
                "Specify SRv6 locator name";
            }
            leaf evi-reorig-disable {
              type empty;
              description
                "Disable route re-origination";
            }
            leaf evi-advertise-mac-deprecated {
              type empty;
              description
                "DEPRECATED: Advertise local MAC-only and BVI
                 MAC routes";
            }
            leaf evi-preferred-nexthop {
              type ncs_template_Preferred-nexthop-mode;
              description
                "Enable Preferred Nexthop mode on this EVI";
            }
            leaf evpn-evi-transmit-mtu-zero {
              type string;
              description
                "Transmit MTU zero to remote for this EVPN EVI
                 .";
            }
            leaf evpn-instance-description {
              type string;
              description
                "Description for EVPN Instance";
            }
            leaf evpn-evi-mtu-mismatch-ignore {
              type string;
              description
                "Ignore mismatch between local and remote MTUs
                 for this EVPN EVI.";
            }
            leaf evi-ecmp-disable {
              type empty;
              description
                "Disable ECMP on the EVI";
            }
            leaf evpn-evi-mtu-match-enforce {
              type empty;
              description
                "Enforce matching between local and remote
                 MTUs for this EVPN EVI.";
            }
            leaf evpn-instance-vpws-single-active-backup-suppression {
              type empty;
              description
                "Configure EVPN VPWS Single-Active Backup
                 Suppression";
            }
            leaf evpn-evi-transmit-l2-mtu {
              type empty;
              description
                "Transmit L2 MTU to remote for this EVPN EVI.";
            }
            leaf evi-unknown-unicast-flooding-disable {
              type empty;
              description
                "Disable Unknown Unicast Flooding on this EVI";
            }
            leaf evpn-evi-cw-disable {
              type empty;
              description
                "CW disable for EVPN EVI";
            }
            leaf vpn-id {
              type ncs_template_Vpnid-range;
              description
                "EVPN Instance ID";
            }
            leaf encapsulation {
              type ncs_template_Evpn-encapsulation;
              description
                "EVPN Instance Encapsulation";
            }
            leaf side {
              type ncs_template_Evpn-side;
              description
                "EVPN Instance Side";
            }
          }
        }
        container evpn-logging {
          description
            "Enter EVPN Logging configuration submode";
          leaf evpn-df-election {
            type empty;
            description
              "Enable Designated Forwarder election logging";
          }
          leaf enable {
            type empty;
            description
              "Enable EVPN Logging";
          }
        }
        container evpn-segment-routing-srv6 {
          description
            "Enter EVPN Segment-Routing SRv6 submode";
          leaf evpn-srv6-locator {
            type string;
            description
              "Specify default SRv6 locator name";
          }
          leaf enable {
            type empty;
            description
              "Enable EVPN Segment-Routing SRv6";
          }
        }
        container evpn-interfaces {
          description
            "Attachment Circuit interfaces";
          list evpn-interface {
            // NCS patched for predictable order
            ordered-by user;
            key "interface-name";
            description
              "Attachment circuit interface";
            container evpnac-timers {
              description
                "Enter Interface-specific timers configuration
                 submode";
              leaf evpnac-peering {
                type string;
                // NCS drop default statement
                description
                  "Interface-specific Peering timer";
              }
              leaf evpnac-carving {
                type string;
                // NCS drop default statement
                description
                  "Interface-specific Carving timer";
              }
              leaf enable {
                type empty;
                description
                  "Enable Interface-specific timers";
              }
              leaf evpnac-recovery {
                type string;
                // NCS drop default statement
                description
                  "Interface-specific Recovery timer";
              }
            }
            container ethernet-segment {
              description
                "Enter Ethernet Segment configuration submode";
              container es-convergence {
                description
                  "Convergence mode(s) and configuration
                   options";
                leaf mac-mobility {
                  type empty;
                  description
                    "Enable MAC-mobility triggered flush";
                }
                leaf nh-tracking {
                  type empty;
                  description
                    "Nexthop-tracking influenced DF Election";
                }
                leaf reroute {
                  type empty;
                  description
                    "Enable reroute to backup peer";
                }
                leaf enable {
                  type empty;
                  description
                    "Enable Convergence configuration options";
                }
              }
              leaf force-single-homed {
                type empty;
                description
                  "Force ethernet segment to remain
                   single-homed";
              }
              leaf load-balancing-mode {
                type ncs_template_Ethernet-segment-load-balance;
                description
                  "Ethernet-Segment Load Balancing mode";
              }
              leaf enable {
                type empty;
                description
                  "Enable Ethernet Segment";
              }
              leaf backbone-source-mac {
                type string;
                description
                  "Backbone Source MAC";
              }
              uses ncs_template_SERVICE-CARVING-MCAST-TYPE;
              uses ncs_template_ES-IMPORT-ROUTE-TARGET;
              uses ncs_template_SERVICE-CARVING-TYPE;
              uses ncs_template_IDENTIFIER;
              uses ncs_template_PREFERENCE-BASED-SERVICE-CARVING;
              uses ncs_template_MANUAL-SERVICE-CARVING;
            }
            leaf evpn-core-isolation-group {
              type ncs_template_Evpn-core-group-id-range;
              description
                "Enter EVPN Core Isolation Group ID";
            }
            leaf evpn-access-signal-mode {
              type ncs_template_Interface-access-signal-mode;
              description
                "Override default signal sent to bring down
                 access circuit";
            }
            leaf mac-flush {
              type ncs_template_Mac-flush-mode;
              description
                "Enable MAC Flushing";
            }
            leaf interface-name {
              type xr:ncs_template_Interface-name;
              description
                "Name of the attachment circuit interface";
            }
          }
        }
        container evpn-virtual-access-pws {
          description
            "Virtual Access Pseudowire interfaces";
          list evpn-virtual-access-pw {
            // NCS patched for predictable order
            ordered-by user;
            key "neighbor pseudowire-id";
            description
              "Virtual Access Pseudowire";
            container evpn-virtual-access-pw-timers {
              description
                "Enter Virtual Access Pseudowire-specific
                 timers configuration submode";
              leaf evpn-virtual-access-pw-recovery {
                type string;
                // NCS drop default statement
                description
                  "Virtual Access Pseudowire-specific Recovery
                   timer";
              }
              leaf evpn-virtual-access-pw-peering {
                type string;
                // NCS drop default statement
                description
                  "Virtual Access Pseudowire-specific Peering
                   timer";
              }
              leaf enable {
                type empty;
                description
                  "Enable Virtual Access Pseudowire-specific
                   timers";
              }
              leaf evpn-virtual-access-pw-carving {
                type string;
                // NCS drop default statement
                description
                  "Virtual Access Pseudowire-specific Carving
                   timer";
              }
            }
            leaf neighbor {
              type string;
              description
                "Neighbor IP address";
            }
            leaf pseudowire-id {
              type ncs_template_Pseudowire-id-range;
              description
                "Pseudowire ID";
            }
            uses ncs_template_EVPN-VIRTUAL-ETHERNET-SEGMENT;
          }
        }
        container evpn-ethernet-segment {
          description
            "EVPN Global Ethernet Segment submode";
          container evpn-esi-types {
            description
              "EVPN ESI type table";
            list evpn-esi-type {
              // NCS patched for predictable order
              ordered-by user;
              key "esi-type";
              description
                "ESI type";
              leaf disable-auto-generation {
                type empty;
                description
                  "Disable ESI Autogeneration";
              }
              leaf esi-type {
                type ncs_template_Evpn-esi-type-range;
                description
                  "ESI type";
              }
            }
          }
          leaf enable {
            type empty;
            description
              "Enable EVPN Global Ethernet Segment submode";
          }
        }
        leaf evpn-global-transmit-mtu-zero {
          type empty;
          description
            "Transmit MTU zero to remote for all EVIs";
        }
        leaf evpn-global-mtu-mismatch-ignore {
          type empty;
          description
            "Ignore mismatch between local and remote MTUs
             for all EVIs.";
        }
        leaf evpn-global-mtu-match-enforce {
          type empty;
          description
            "Enforce matching between local and remote MTUs
             for all EVIs.";
        }
        leaf evpn-global-transmit-l2-mtu {
          type empty;
          description
            "Transmit L2 MTU to remote for all EVIs";
        }
        leaf evpn-staggered-bringup {
          type string;
          units "millisecond";
          // NCS drop default statement
          description
            "Staggered bringup (milliseconds) timer";
        }
        leaf evi-cost-out {
          type empty;
          description
            "Configure node to cost-out";
        }
        leaf evpn-source-interface {
          type xr:ncs_template_Interface-name;
          description
            "Configure EVPN router-id implicitly through
             Loopback Interface";
        }
        leaf evpn-cost-in-startup {
          type string;
          units "second";
          description
            "Cost-in node after given time (seconds) on
             startup timer";
        }
      }
      leaf enable {
        type empty;
        description
          "Enable EVPN feature";
      }
    }
  }
  augment "/ncs:devices/ncs:template/ncs:ned-id/ncs:config/a1:interface-configurations/a1:interface-configuration" {
    description
      "This augment extends the configuration data of
       'Cisco-IOS-XR-ifmgr-cfg'";
    container pseudowire-ether {
      description
        "PW-Ether attributes";
      leaf generic-interface-list {
        type xr:ncs_template_Cisco-ios-xr-string;
        description
          "Name of the interface list";
      }
      leaf l2-overhead {
        type string;
        description
          "PW Ether L2 overhead requirement";
      }
    }
  }
  augment "/ncs:devices/ncs:device/ncs:live-status/a1:interface-configurations/a1:interface-configuration" {
    description
      "This augment extends the configuration data of
       'Cisco-IOS-XR-ifmgr-cfg'";
    container pseudowire-ether {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "PW-Ether attributes";
      leaf generic-interface-list {
        type xr:live_ncs_Cisco-ios-xr-string;
        description
          "Name of the interface list";
      }
      leaf l2-overhead {
        type uint32 {
          range "1..64";
        }
        description
          "PW Ether L2 overhead requirement";
      }
    }
  }
  augment "/ncs:devices/ncs:device/ncs:config/a1:interface-configurations/a1:interface-configuration" {
    description
      "This augment extends the configuration data of
       'Cisco-IOS-XR-ifmgr-cfg'";
    container pseudowire-ether {
      tailf:ncs-device-type "netconf";
      tailf:display-when "not(../../../../ncs:module) or ../../../../ncs:module[ncs:name='Cisco-IOS-XR-l2vpn-cfg']";
      description
        "PW-Ether attributes";
      leaf generic-interface-list {
        type xr:Cisco-ios-xr-string {
          length "1..32";
        }
        description
          "Name of the interface list";
      }
      leaf l2-overhead {
        type uint32 {
          range "1..64";
        }
        description
          "PW Ether L2 overhead requirement";
      }
    }
  }
  augment "/ncs:devices/ncs:template/ncs:ned-id/ncs:config/a1:interface-configurations/a1:interface-configuration" {
    description
      "This augment extends the configuration data of
       'Cisco-IOS-XR-ifmgr-cfg'";
    container pseudowire-iw {
      description
        "PW-IW attributes";
      leaf l2-overhead {
        type string;
        units "byte";
        description
          "L2 overhead size in bytes";
      }
      leaf generic-interface-list {
        type xr:ncs_template_Cisco-ios-xr-string;
        description
          "Name of the interface list";
      }
    }
  }
  augment "/ncs:devices/ncs:device/ncs:live-status/a1:interface-configurations/a1:interface-configuration" {
    description
      "This augment extends the configuration data of
       'Cisco-IOS-XR-ifmgr-cfg'";
    container pseudowire-iw {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "PW-IW attributes";
      leaf l2-overhead {
        type uint32 {
          range "1..64";
        }
        units "byte";
        description
          "L2 overhead size in bytes";
      }
      leaf generic-interface-list {
        type xr:live_ncs_Cisco-ios-xr-string;
        description
          "Name of the interface list";
      }
    }
  }
  augment "/ncs:devices/ncs:device/ncs:config/a1:interface-configurations/a1:interface-configuration" {
    description
      "This augment extends the configuration data of
       'Cisco-IOS-XR-ifmgr-cfg'";
    container pseudowire-iw {
      tailf:ncs-device-type "netconf";
      tailf:display-when "not(../../../../ncs:module) or ../../../../ncs:module[ncs:name='Cisco-IOS-XR-l2vpn-cfg']";
      description
        "PW-IW attributes";
      leaf l2-overhead {
        type uint32 {
          range "1..64";
        }
        units "byte";
        description
          "L2 overhead size in bytes";
      }
      leaf generic-interface-list {
        type xr:Cisco-ios-xr-string {
          length "1..32";
        }
        description
          "Name of the interface list";
      }
    }
  }
  augment "/ncs:devices/ncs:template/ncs:ned-id/ncs:config/a1:interface-configurations/a1:interface-configuration" {
    description
      "This augment extends the configuration data of
       'Cisco-IOS-XR-ifmgr-cfg'";
    container bvi {
      description
        "BVI attributes";
      container gratuitous-announcement-timer {
        description
          "Enter Gratuitous Announcement Timer
           configuration submode";
        leaf enable {
          type empty;
          description
            "Enable Gratuitous Announcement Timer";
        }
        leaf timer-jitter {
          type string;
          units "percentage";
          description
            "Gratuitous announcement jitter percentage";
        }
        leaf timer-interval {
          type string;
          units "second";
          description
            "Gratuitous announcement timer interval in
             seconds";
        }
      }
      leaf host-routing {
        type empty;
        description
          "Enable host-routing on this BVI";
      }
    }
  }
  augment "/ncs:devices/ncs:device/ncs:live-status/a1:interface-configurations/a1:interface-configuration" {
    description
      "This augment extends the configuration data of
       'Cisco-IOS-XR-ifmgr-cfg'";
    container bvi {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "BVI attributes";
      container gratuitous-announcement-timer {
        description
          "Enter Gratuitous Announcement Timer
           configuration submode";
        leaf enable {
          type empty;
          description
            "Enable Gratuitous Announcement Timer";
        }
        leaf timer-jitter {
          type uint32;
          units "percentage";
          description
            "Gratuitous announcement jitter percentage";
        }
        leaf timer-interval {
          type uint32;
          units "second";
          description
            "Gratuitous announcement timer interval in
             seconds";
        }
      }
      leaf host-routing {
        type empty;
        description
          "Enable host-routing on this BVI";
      }
    }
  }
  augment "/ncs:devices/ncs:device/ncs:config/a1:interface-configurations/a1:interface-configuration" {
    description
      "This augment extends the configuration data of
       'Cisco-IOS-XR-ifmgr-cfg'";
    container bvi {
      tailf:ncs-device-type "netconf";
      tailf:display-when "not(../../../../ncs:module) or ../../../../ncs:module[ncs:name='Cisco-IOS-XR-l2vpn-cfg']";
      description
        "BVI attributes";
      container gratuitous-announcement-timer {
        description
          "Enter Gratuitous Announcement Timer
           configuration submode";
        leaf enable {
          type empty;
          description
            "Enable Gratuitous Announcement Timer";
        }
        leaf timer-jitter {
          type uint32;
          units "percentage";
          description
            "Gratuitous announcement jitter percentage";
        }
        leaf timer-interval {
          type uint32;
          units "second";
          description
            "Gratuitous announcement timer interval in
             seconds";
        }
      }
      leaf host-routing {
        type empty;
        description
          "Enable host-routing on this BVI";
      }
    }
  }
  augment "/ncs:devices/ncs:template/ncs:ned-id/ncs:config/a1:interface-configurations/a1:interface-configuration" {
    description
      "This augment extends the configuration data of
       'Cisco-IOS-XR-ifmgr-cfg'";
    container l2-transport {
      description
        "Interface Layer 2 Transport service
         configuration data";
      leaf enabled {
        type empty;
        description
          "This object is only valid on physical
           interfaces and it controls whether that
           interface is a port mode Layer 2 attachment
           circuit (note that for subinterfaces, the Layer
           2 property is specified when the subinterface
           is created).The object must be set before any
           other L2Transport configuration is supplied for
           the interface, and must be the last
           per-interface configuration object to be
           removed.";
      }
    }
  }
  augment "/ncs:devices/ncs:device/ncs:live-status/a1:interface-configurations/a1:interface-configuration" {
    description
      "This augment extends the configuration data of
       'Cisco-IOS-XR-ifmgr-cfg'";
    container l2-transport {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "Interface Layer 2 Transport service
         configuration data";
      leaf enabled {
        type empty;
        description
          "This object is only valid on physical
           interfaces and it controls whether that
           interface is a port mode Layer 2 attachment
           circuit (note that for subinterfaces, the Layer
           2 property is specified when the subinterface
           is created).The object must be set before any
           other L2Transport configuration is supplied for
           the interface, and must be the last
           per-interface configuration object to be
           removed.";
      }
    }
  }
  augment "/ncs:devices/ncs:device/ncs:config/a1:interface-configurations/a1:interface-configuration" {
    description
      "This augment extends the configuration data of
       'Cisco-IOS-XR-ifmgr-cfg'";
    container l2-transport {
      tailf:ncs-device-type "netconf";
      tailf:display-when "not(../../../../ncs:module) or ../../../../ncs:module[ncs:name='Cisco-IOS-XR-l2vpn-cfg']";
      description
        "Interface Layer 2 Transport service
         configuration data";
      leaf enabled {
        type empty;
        description
          "This object is only valid on physical
           interfaces and it controls whether that
           interface is a port mode Layer 2 attachment
           circuit (note that for subinterfaces, the Layer
           2 property is specified when the subinterface
           is created).The object must be set before any
           other L2Transport configuration is supplied for
           the interface, and must be the last
           per-interface configuration object to be
           removed.";
      }
    }
  }
  augment "/ncs:devices/ncs:template/ncs:ned-id/ncs:config/a2:snmp/a2:notification" {
    description
      "This augment extends the configuration data of
       'Cisco-IOS-XR-snmp-agent-cfg'";
    container vpls {
      description
        "CISCO-IETF-VPLS-GENERIC-MIB notification
         configuration";
      leaf full-clear {
        type empty;
        description
          "Enable cvplsFwdFullAlarmCleared notification";
      }
      leaf status {
        type empty;
        description
          "Enable cvplsStatusChanged notification";
      }
      leaf enable {
        type empty;
        description
          "Enable CISCO-IETF-VPLS-GENERIC-MIB
           notifications";
      }
      leaf full-raise {
        type empty;
        description
          "Enable cvplsFwdFullAlarmRaised notification";
      }
    }
  }
  augment "/ncs:devices/ncs:device/ncs:live-status/a2:snmp/a2:notification" {
    description
      "This augment extends the configuration data of
       'Cisco-IOS-XR-snmp-agent-cfg'";
    container vpls {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "CISCO-IETF-VPLS-GENERIC-MIB notification
         configuration";
      leaf full-clear {
        type empty;
        description
          "Enable cvplsFwdFullAlarmCleared notification";
      }
      leaf status {
        type empty;
        description
          "Enable cvplsStatusChanged notification";
      }
      leaf enable {
        type empty;
        description
          "Enable CISCO-IETF-VPLS-GENERIC-MIB
           notifications";
      }
      leaf full-raise {
        type empty;
        description
          "Enable cvplsFwdFullAlarmRaised notification";
      }
    }
  }
  augment "/ncs:devices/ncs:device/ncs:config/a2:snmp/a2:notification" {
    description
      "This augment extends the configuration data of
       'Cisco-IOS-XR-snmp-agent-cfg'";
    container vpls {
      tailf:ncs-device-type "netconf";
      tailf:display-when "not(../../../../ncs:module) or ../../../../ncs:module[ncs:name='Cisco-IOS-XR-l2vpn-cfg']";
      description
        "CISCO-IETF-VPLS-GENERIC-MIB notification
         configuration";
      leaf full-clear {
        type empty;
        description
          "Enable cvplsFwdFullAlarmCleared notification";
      }
      leaf status {
        type empty;
        description
          "Enable cvplsStatusChanged notification";
      }
      leaf enable {
        type empty;
        description
          "Enable CISCO-IETF-VPLS-GENERIC-MIB
           notifications";
      }
      leaf full-raise {
        type empty;
        description
          "Enable cvplsFwdFullAlarmRaised notification";
      }
    }
  }
  augment "/ncs:devices/ncs:template/ncs:ned-id/ncs:config/a2:snmp/a2:notification" {
    description
      "This augment extends the configuration data of
       'Cisco-IOS-XR-snmp-agent-cfg'";
    container l2vpn {
      description
        "CISCO-IETF-PW-MIB notification configuration";
      leaf cisco {
        type empty;
        description
          "Enable Cisco format including extra varbinds";
      }
      leaf enable {
        type empty;
        description
          "Enable CISCO-IETF-PW-MIB notifications";
      }
      leaf vc-down {
        type empty;
        description
          "Enable cpwVcDown notification";
      }
      leaf vc-up {
        type empty;
        description
          "Enable cpwVcUp notification";
      }
    }
  }
  augment "/ncs:devices/ncs:device/ncs:live-status/a2:snmp/a2:notification" {
    description
      "This augment extends the configuration data of
       'Cisco-IOS-XR-snmp-agent-cfg'";
    container l2vpn {
      tailf:ncs-device-type "netconf";
      tailf:display-when "not(../../../../ncs:module) or ../../../../ncs:module[ncs:name='Cisco-IOS-XR-l2vpn-cfg'] or (../../../../ncs:live-status-protocol[not(ncs:capability)]) or (../../../../ncs:live-status-protocol/ncs:capability/ncs:module[.='Cisco-IOS-XR-l2vpn-cfg'])";
      description
        "CISCO-IETF-PW-MIB notification configuration";
      leaf cisco {
        type empty;
        description
          "Enable Cisco format including extra varbinds";
      }
      leaf enable {
        type empty;
        description
          "Enable CISCO-IETF-PW-MIB notifications";
      }
      leaf vc-down {
        type empty;
        description
          "Enable cpwVcDown notification";
      }
      leaf vc-up {
        type empty;
        description
          "Enable cpwVcUp notification";
      }
    }
  }
  augment "/ncs:devices/ncs:device/ncs:config/a2:snmp/a2:notification" {
    description
      "This augment extends the configuration data of
       'Cisco-IOS-XR-snmp-agent-cfg'";
    container l2vpn {
      tailf:ncs-device-type "netconf";
      tailf:display-when "not(../../../../ncs:module) or ../../../../ncs:module[ncs:name='Cisco-IOS-XR-l2vpn-cfg']";
      description
        "CISCO-IETF-PW-MIB notification configuration";
      leaf cisco {
        type empty;
        description
          "Enable Cisco format including extra varbinds";
      }
      leaf enable {
        type empty;
        description
          "Enable CISCO-IETF-PW-MIB notifications";
      }
      leaf vc-down {
        type empty;
        description
          "Enable cpwVcDown notification";
      }
      leaf vc-up {
        type empty;
        description
          "Enable cpwVcUp notification";
      }
    }
  }
}

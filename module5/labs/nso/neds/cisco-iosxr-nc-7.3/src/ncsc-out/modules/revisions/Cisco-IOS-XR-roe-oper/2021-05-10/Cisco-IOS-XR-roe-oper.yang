module Cisco-IOS-XR-roe-oper {
  // Generated by yanger -t ncs
  tailf:mount-id "cisco-iosxr-nc-7.3:cisco-iosxr-nc-7.3";
  tailf:ncs-device-type "netconf";

  namespace "http://cisco.com/ns/yang/Cisco-IOS-XR-roe-oper";
  prefix roe-oper;

  import cisco-semver {
    prefix semver;
  }
  include Cisco-IOS-XR-roe-oper-sub1 {
    revision-date 2021-05-10;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR roe package operational data.

     This module contains definitions
     for the following management objects:
       roe: ROE Operational Data

     Copyright (c) 2013-2021 by Cisco Systems, Inc.
     All rights reserved.";

  revision 2021-05-10 {
    description
      "Added leaf hfn-sync-disable to grouping ROE-PROFILE-INFO.
       2021-05-03
         Added mapper,demapper roe-profile parameters presync-match-threshold, resync-match-threshold, resync-mismatch-threshold. Added demapper roe-profile parameters sync-threshold, drain-threshold, presync-match-count, resync-match-count, resync-mismatch-count.";
    semver:module-version "1.1.0";
  }
  revision 2020-09-01 {
    description
      "Removed container protocol-stats. Changed type of leaf order-info-type.";
    semver:module-version "1.0.0";
  }
  revision 2020-02-27 {
    description
      "Show command subtype added for ROE";
  }
  revision 2019-04-05 {
    description
      "Establish semantic version baseline.";
  }
  revision 2015-11-09 {
    description
      "IOS XR 6.0 revision.";
  }

  augment "/ncs:devices/ncs:device/ncs:config" {
    // NCS drop config false container roe
  }
  augment "/ncs:devices/ncs:device/ncs:live-status" {
    container roe {
      tailf:ncs-device-type "netconf";
      tailf:display-when "not(../../ncs:module) or ../../ncs:module[ncs:name='Cisco-IOS-XR-roe-oper'] or (../../ncs:live-status-protocol[not(ncs:capability)]) or (../../ncs:live-status-protocol/ncs:capability/ncs:module[.='Cisco-IOS-XR-roe-oper'])";
      description
        "ROE Operational Data";
      container profiles {
        description
          "List of ROE profiles configured";
        list profile {
          key "profile-id";
          description
            "ROE profile parameters";
          leaf profile-id {
            type uint32;
            description
              "Profile identifier";
          }
          uses live_ncs_ROE-PROFILE-INFO;
        }
      }
      container ethlinks {
        description
          "List of ROE ethlink profiles configured";
        list ethlink {
          key "ethlink-id";
          description
            "ROE Eth link profile parameters";
          leaf ethlink-id {
            type uint32;
            description
              "Ethlink identifier";
          }
          uses live_ncs_ROE-ETHLINK-INFO;
        }
      }
    }
  }
  augment "/ncs:devices/ncs:template/ncs:ned-id/ncs:config" {
    // NCS drop config false container roe
  }
}

module Cisco-IOS-XR-sysadmin-zapdisk {
  // Generated by yanger -t ncs
  tailf:mount-id "cisco-iosxr-nc-7.3:cisco-iosxr-nc-7.3";
  tailf:ncs-device-type "netconf";

  namespace "http://www.cisco.com/ns/yang/Cisco-IOS-XR-sysadmin-zapdisk";
  prefix zapdisk;

  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR Zapdisk module.

     This module zapdisk is for factory card reset feature.

     Copyright (c) 2016-2020 by Cisco Systems, Inc.
     All rights reserved.";

  revision 2019-04-15 {
    description
      "Establish semantic version baseline.";
    semver:module-version "1.0.0";
  }
  revision 2017-05-23 {
    description
      "Changed namespace and module name";
  }
  revision 2017-03-25 {
    description
      "zapdisk [set|unset] [location L] support";
  }

  augment "/ncs:devices/ncs:device/ncs:rpc" {
    container rpc-zapdisk {
      tailf:ncs-device-type "netconf";
      tailf:display-when "not(../../ncs:module) or ../../ncs:module[ncs:name='Cisco-IOS-XR-sysadmin-zapdisk']";
      tailf:action zapdisk {
        tailf:actionpoint ncsproxy {
          tailf:internal;
        }
        input {
          choice zapdisk-input {
            mandatory true;
            case target-set {
              leaf set {
                type empty;
                mandatory false;
              }
            }
            case target-unset {
              container czapdisk-unset {
                leaf unset {
                  type empty;
                  mandatory false;
                }
              }
            }
          }
        }
        output {
          leaf result {
            type string;
            mandatory true;
          }
        }
      }
    }
  }
  augment "/ncs:devices/ncs:device-group/ncs:ned-id/ncs:rpc" {
    container rpc-zapdisk {
      tailf:ncs-device-type "netconf";
      tailf:display-when "/ncs:devices/ncs:device[ncs:name=current()/../../../ncs:member]/ncs:module[ncs:name='Cisco-IOS-XR-sysadmin-zapdisk']";
      tailf:action zapdisk {
        tailf:actionpoint ncsproxy {
          tailf:internal;
        }
        input {
          choice zapdisk-input {
            mandatory true;
            case target-set {
              leaf set {
                type empty;
                mandatory false;
              }
            }
            case target-unset {
              container czapdisk-unset {
                leaf unset {
                  type empty;
                  mandatory false;
                }
              }
            }
          }
        }
        output {
          container "device" {
            leaf "name" {
              type string;
            }
            leaf "info" {
              type string;
            }
            container "result" {
              leaf result {
                type string;
                mandatory true;
              }
            }
          }
        }
      }
    }
  }
}

module Cisco-IOS-XR-erp-oper {
  // Generated by yanger -t ncs
  tailf:mount-id "cisco-iosxr-nc-7.3:cisco-iosxr-nc-7.3";
  tailf:ncs-device-type "netconf";

  namespace "http://cisco.com/ns/yang/Cisco-IOS-XR-erp-oper";
  prefix erp-oper;

  import Cisco-IOS-XR-types {
    prefix xr;
  }
  import cisco-semver {
    prefix semver;
  }
  include Cisco-IOS-XR-erp-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR erp package operational data.

     This module contains definitions
     for the following management objects:
       ethernet-ring: Ethernet Ring Protection operational data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'ethernet-ring'
  }
  augment "/ncs:devices/ncs:device/ncs:live-status" {
    container ethernet-ring {
      tailf:ncs-device-type "netconf";
      tailf:display-when "not(../../ncs:module) or ../../ncs:module[ncs:name='Cisco-IOS-XR-erp-oper'] or (../../ncs:live-status-protocol[not(ncs:capability)]) or (../../ncs:live-status-protocol/ncs:capability/ncs:module[.='Cisco-IOS-XR-erp-oper'])";
      description
        "Ethernet Ring Protection operational data";
      container global {
        description
          "G.8032 Ethernet Ring Protection global
           operational data";
        container g8032 {
          description
            "G.8032 Ethernet Ring Protection operational
             data";
          container statuses {
            description
              "Detailed status information for Ethernet ring";
            list status {
              description
                "Detailed status information on a particular
                 ring instance";
              leaf ring-name {
                type xr:live_ncs_Cisco-ios-xr-string;
                description
                  "Ring name";
              }
              leaf instance-id {
                type uint32 {
                  range "1..2";
                }
                description
                  "Ring instance ID";
              }
              uses live_ncs_ERP-STATUS-INFO;
            }
          }
          container profiles {
            description
              "G.8032 Ethernet ring profile table";
            list profile {
              key "profile-name";
              description
                "Ethernet ring profile information for a
                 specified profile name";
              leaf profile-name {
                type xr:live_ncs_Cisco-ios-xr-string;
                description
                  "Profile name";
              }
              uses live_ncs_ERP-PROFILE-INFO;
            }
          }
          container statistics {
            description
              "Ethernet ring statistics for events and
               messages received";
            list statistic {
              description
                "Statistics for a particular ring instance";
              leaf ring-name {
                type xr:live_ncs_Cisco-ios-xr-string;
                description
                  "Ring Name";
              }
              leaf instance-id {
                type uint32 {
                  range "1..2";
                }
                description
                  "Ring instance ID";
              }
              uses live_ncs_ERP-STATS-INFO;
            }
          }
          container summary {
            description
              "Summary count of Ethernet ring instances in
               each state";
            uses live_ncs_ERP-SUMMARY-INFO;
          }
          container briefs {
            description
              "Brief functional state of Ethernet ring
               instances";
            list brief {
              description
                "Brief functional state on a particular ring
                 instance";
              leaf ring-name {
                type xr:live_ncs_Cisco-ios-xr-string;
                description
                  "Ring Name";
              }
              leaf instance-id {
                type uint32 {
                  range "1..2";
                }
                description
                  "Ring instance ID";
              }
              uses live_ncs_ERP-BRIEF-INFO;
            }
          }
        }
      }
    }
  }
  augment "/ncs:devices/ncs:template/ncs:ned-id/ncs:config" {
    // NCS drop config false container 'ethernet-ring'
  }
}

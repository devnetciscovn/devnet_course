module Cisco-IOS-XR-subscriber-nal-cfg {
  // Generated by yanger -t ncs
  tailf:mount-id "cisco-iosxr-nc-7.3:cisco-iosxr-nc-7.3";
  tailf:ncs-device-type "netconf";

  namespace "http://cisco.com/ns/yang/Cisco-IOS-XR-subscriber-nal-cfg";
  prefix subscriber-nal-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-nal package configuration.

     This module contains definitions
     for the following management objects:
       subscriber-cnbng-nal-locs: Table of SubscriberCnbngNalLoc

     This YANG module augments the
       Cisco-IOS-XR-ifmgr-cfg
     module with configuration data.

     Copyright (c) 2013-2021 by Cisco Systems, Inc.
     All rights reserved.";

  revision 2021-07-07 {
    description
      "Added support for pre-configuration.";
    semver:module-version "2.0.0";
  }
  revision 2020-12-01 {
    description
      "NAL access interface config.";
    semver:module-version "1.0.0";
  }
  revision 2020-11-24 {
    description
      "Auto loopback primary address.";
  }
  revision 2019-04-05 {
    description
      "Establish semantic version baseline.";
  }
  revision 2015-11-09 {
    description
      "IOS XR 6.0 revision.";
  }

  augment "/ncs:devices/ncs:device/ncs:config" {
    container subscriber-cnbng-nal-locs {
      tailf:ncs-device-type "netconf";
      tailf:display-when "not(../../ncs:module) or ../../ncs:module[ncs:name='Cisco-IOS-XR-subscriber-nal-cfg']";
      description
        "Table of SubscriberCnbngNalLoc";
      list subscriber-cnbng-nal-loc {
        key "preconfigure node-name";
        description
          "Location Specification";
        container nal-auto-lb-classes {
          description
            "Table of NALAutoLBClass";
          list nal-auto-lb-class {
            key "vrf-name";
            description
              "NAL Auto-Loopback configurations";
            container nal-auto-lb-int-classes {
              description
                "Table of NALAutoLBIntClass";
              list nal-auto-lb-int-class {
                key "nal-auto-lb-int-name";
                description
                  "None";
                leaf nal-auto-lb-int-addr-class {
                  type inet:ipv4-address-no-zone;
                  description
                    "NAL auto-loopback Interface Primary-IP
                     address";
                }
                leaf nal-auto-lb-int-name {
                  type xr:Interface-name;
                  description
                    "NAL auto-loopback Interface";
                }
              }
            }
            leaf vrf-name {
              type xr:Cisco-ios-xr-string;
              description
                "Set constant string";
            }
          }
        }
        container nal-trans-cp-server-cfg {
          description
            "None";
          leaf nal-cp-primary-srv-cfg {
            type inet:ipv4-address-no-zone;
            description
              "IPv4 address of the CP's primary-server";
          }
        }
        container groups {
          description
            "Table of Group";
          list group {
            key "group-id";
            description
              "CnBNG NAL Group configuration";
            container interfaces {
              description
                "Table of Interface";
              list interface {
                key "interface-name interface-id";
                description
                  "Interface for this Group";
                leaf interface-name {
                  type xr:Interface-name;
                  description
                    "Interface name";
                }
                leaf interface-id {
                  type uint32 {
                    range "1..65535";
                  }
                  description
                    "ID for the interface to be mapped on to
                     slave";
                }
                leaf mac-address {
                  type yang:mac-address;
                  mandatory true;
                  description
                    "MAC address";
                }
              }
            }
            leaf description {
              type string {
                length "1..256";
              }
              description
                "Description for this Group";
            }
            leaf tracking-object {
              type string;
              description
                "Core Tracking Object for this Group";
            }
            leaf group-id {
              type uint32 {
                range "1..4000";
              }
              description
                "Group ID";
            }
          }
        }
        container nal-trans-up-server-cfg {
          description
            "None";
          leaf prefix-string {
            type inet:ipv4-address-no-zone;
            description
              "IPv4 address for the UP-Server source
               connection";
          }
          leaf intf-name {
            type xr:Interface-name;
            description
              "Source Interface";
          }
          leaf gtp-port-num {
            type uint32 {
              range "15002..15051";
            }
            description
              "UP-server source GTP port-number";
          }
          leaf pcfp-port-num {
            type uint32 {
              range "15002..15051";
            }
            description
              "UP-server source PFCP port-number";
          }
          leaf vrf-name {
            type xr:Cisco-ios-xr-string {
              length "1..32";
            }
            description
              "UP server's VRF Name";
          }
        }
        leaf nal-host-name {
          type xr:Cisco-ios-xr-string {
            length "1..64";
          }
          description
            "NAL Host-name";
        }
        leaf nal-route-summary-tag {
          type uint32 {
            range "1..4294967295";
          }
          description
            "Tag value";
        }
        leaf nal-enable-sec-addr-upd {
          type uint32;
          description
            "Enable secondary address update";
        }
        leaf description {
          type string {
            length "1..256";
          }
          description
            "Config User-description";
        }
        leaf nal-disconnect-history-file-logging {
          type uint32;
          description
            "Set constant integer";
        }
        leaf nal-cp-assoc-retry-cnt {
          type uint32 {
            range "5..20";
          }
          description
            "Retry count";
        }
        leaf spa-request-response-history-file-logging {
          type uint32;
          description
            "Set constant integer";
        }
        leaf preconfigure {
          type xr:Cisco-ios-xr-string;
          description
            "'Act' if location exists in the box;'Pre'
             otherwise;";
        }
        leaf node-name {
          type xr:Node-id;
          description
            "Enter Location";
        }
      }
    }
  }
  augment "/ncs:devices/ncs:device/ncs:live-status" {
    container subscriber-cnbng-nal-locs {
      tailf:ncs-device-type "netconf";
      tailf:display-when "not(../../ncs:module) or ../../ncs:module[ncs:name='Cisco-IOS-XR-subscriber-nal-cfg'] or (../../ncs:live-status-protocol[not(ncs:capability)]) or (../../ncs:live-status-protocol/ncs:capability/ncs:module[.='Cisco-IOS-XR-subscriber-nal-cfg'])";
      description
        "Table of SubscriberCnbngNalLoc";
      list subscriber-cnbng-nal-loc {
        key "preconfigure node-name";
        description
          "Location Specification";
        container nal-auto-lb-classes {
          description
            "Table of NALAutoLBClass";
          list nal-auto-lb-class {
            key "vrf-name";
            description
              "NAL Auto-Loopback configurations";
            container nal-auto-lb-int-classes {
              description
                "Table of NALAutoLBIntClass";
              list nal-auto-lb-int-class {
                key "nal-auto-lb-int-name";
                description
                  "None";
                leaf nal-auto-lb-int-addr-class {
                  type inet:ipv4-address-no-zone;
                  description
                    "NAL auto-loopback Interface Primary-IP
                     address";
                }
                leaf nal-auto-lb-int-name {
                  type xr:live_ncs_Interface-name;
                  description
                    "NAL auto-loopback Interface";
                }
              }
            }
            leaf vrf-name {
              type xr:live_ncs_Cisco-ios-xr-string;
              description
                "Set constant string";
            }
          }
        }
        container nal-trans-cp-server-cfg {
          description
            "None";
          leaf nal-cp-primary-srv-cfg {
            type inet:ipv4-address-no-zone;
            description
              "IPv4 address of the CP's primary-server";
          }
        }
        container groups {
          description
            "Table of Group";
          list group {
            key "group-id";
            description
              "CnBNG NAL Group configuration";
            container interfaces {
              description
                "Table of Interface";
              list interface {
                key "interface-name interface-id";
                description
                  "Interface for this Group";
                leaf interface-name {
                  type xr:live_ncs_Interface-name;
                  description
                    "Interface name";
                }
                leaf interface-id {
                  type uint32 {
                    range "1..65535";
                  }
                  description
                    "ID for the interface to be mapped on to
                     slave";
                }
                leaf mac-address {
                  type yang:mac-address;
                  // NCS drop mandatory statement
                  description
                    "MAC address";
                }
              }
            }
            leaf description {
              type string {
                length "1..256";
              }
              description
                "Description for this Group";
            }
            leaf tracking-object {
              type string;
              description
                "Core Tracking Object for this Group";
            }
            leaf group-id {
              type uint32 {
                range "1..4000";
              }
              description
                "Group ID";
            }
          }
        }
        container nal-trans-up-server-cfg {
          description
            "None";
          leaf prefix-string {
            type inet:ipv4-address-no-zone;
            description
              "IPv4 address for the UP-Server source
               connection";
          }
          leaf intf-name {
            type xr:live_ncs_Interface-name;
            description
              "Source Interface";
          }
          leaf gtp-port-num {
            type uint32 {
              range "15002..15051";
            }
            description
              "UP-server source GTP port-number";
          }
          leaf pcfp-port-num {
            type uint32 {
              range "15002..15051";
            }
            description
              "UP-server source PFCP port-number";
          }
          leaf vrf-name {
            type xr:live_ncs_Cisco-ios-xr-string;
            description
              "UP server's VRF Name";
          }
        }
        leaf nal-host-name {
          type xr:live_ncs_Cisco-ios-xr-string;
          description
            "NAL Host-name";
        }
        leaf nal-route-summary-tag {
          type uint32 {
            range "1..4294967295";
          }
          description
            "Tag value";
        }
        leaf nal-enable-sec-addr-upd {
          type uint32;
          description
            "Enable secondary address update";
        }
        leaf description {
          type string {
            length "1..256";
          }
          description
            "Config User-description";
        }
        leaf nal-disconnect-history-file-logging {
          type uint32;
          description
            "Set constant integer";
        }
        leaf nal-cp-assoc-retry-cnt {
          type uint32 {
            range "5..20";
          }
          description
            "Retry count";
        }
        leaf spa-request-response-history-file-logging {
          type uint32;
          description
            "Set constant integer";
        }
        leaf preconfigure {
          type xr:live_ncs_Cisco-ios-xr-string;
          description
            "'Act' if location exists in the box;'Pre'
             otherwise;";
        }
        leaf node-name {
          type xr:live_ncs_Node-id;
          description
            "Enter Location";
        }
      }
    }
  }
  augment "/ncs:devices/ncs:template/ncs:ned-id/ncs:config" {
    container subscriber-cnbng-nal-locs {
      description
        "Table of SubscriberCnbngNalLoc";
      list subscriber-cnbng-nal-loc {
        // NCS patched for predictable order
        ordered-by user;
        key "preconfigure node-name";
        description
          "Location Specification";
        container nal-auto-lb-classes {
          description
            "Table of NALAutoLBClass";
          list nal-auto-lb-class {
            // NCS patched for predictable order
            ordered-by user;
            key "vrf-name";
            description
              "NAL Auto-Loopback configurations";
            container nal-auto-lb-int-classes {
              description
                "Table of NALAutoLBIntClass";
              list nal-auto-lb-int-class {
                // NCS patched for predictable order
                ordered-by user;
                key "nal-auto-lb-int-name";
                description
                  "None";
                leaf nal-auto-lb-int-addr-class {
                  type string;
                  description
                    "NAL auto-loopback Interface Primary-IP
                     address";
                }
                leaf nal-auto-lb-int-name {
                  type xr:ncs_template_Interface-name;
                  description
                    "NAL auto-loopback Interface";
                }
              }
            }
            leaf vrf-name {
              type xr:ncs_template_Cisco-ios-xr-string;
              description
                "Set constant string";
            }
          }
        }
        container nal-trans-cp-server-cfg {
          description
            "None";
          leaf nal-cp-primary-srv-cfg {
            type string;
            description
              "IPv4 address of the CP's primary-server";
          }
        }
        container groups {
          description
            "Table of Group";
          list group {
            // NCS patched for predictable order
            ordered-by user;
            key "group-id";
            description
              "CnBNG NAL Group configuration";
            container interfaces {
              description
                "Table of Interface";
              list interface {
                // NCS patched for predictable order
                ordered-by user;
                key "interface-name interface-id";
                description
                  "Interface for this Group";
                leaf interface-name {
                  type xr:ncs_template_Interface-name;
                  description
                    "Interface name";
                }
                leaf interface-id {
                  type string;
                  description
                    "ID for the interface to be mapped on to
                     slave";
                }
                leaf mac-address {
                  type string;
                  // NCS drop mandatory statement
                  description
                    "MAC address";
                }
              }
            }
            leaf description {
              type string;
              description
                "Description for this Group";
            }
            leaf tracking-object {
              type string;
              description
                "Core Tracking Object for this Group";
            }
            leaf group-id {
              type string;
              description
                "Group ID";
            }
          }
        }
        container nal-trans-up-server-cfg {
          description
            "None";
          leaf prefix-string {
            type string;
            description
              "IPv4 address for the UP-Server source
               connection";
          }
          leaf intf-name {
            type xr:ncs_template_Interface-name;
            description
              "Source Interface";
          }
          leaf gtp-port-num {
            type string;
            description
              "UP-server source GTP port-number";
          }
          leaf pcfp-port-num {
            type string;
            description
              "UP-server source PFCP port-number";
          }
          leaf vrf-name {
            type xr:ncs_template_Cisco-ios-xr-string;
            description
              "UP server's VRF Name";
          }
        }
        leaf nal-host-name {
          type xr:ncs_template_Cisco-ios-xr-string;
          description
            "NAL Host-name";
        }
        leaf nal-route-summary-tag {
          type string;
          description
            "Tag value";
        }
        leaf nal-enable-sec-addr-upd {
          type string;
          description
            "Enable secondary address update";
        }
        leaf description {
          type string;
          description
            "Config User-description";
        }
        leaf nal-disconnect-history-file-logging {
          type string;
          description
            "Set constant integer";
        }
        leaf nal-cp-assoc-retry-cnt {
          type string;
          description
            "Retry count";
        }
        leaf spa-request-response-history-file-logging {
          type string;
          description
            "Set constant integer";
        }
        leaf preconfigure {
          type xr:ncs_template_Cisco-ios-xr-string;
          description
            "'Act' if location exists in the box;'Pre'
             otherwise;";
        }
        leaf node-name {
          type xr:ncs_template_Node-id;
          description
            "Enter Location";
        }
      }
    }
  }
  augment "/ncs:devices/ncs:template/ncs:ned-id/ncs:config/a1:interface-configurations/a1:interface-configuration" {
    description
      "This augment extends the configuration data of
       'Cisco-IOS-XR-ifmgr-cfg'";
    list cnbng-nal-ip-subscriber {
      // NCS patched for predictable order
      ordered-by user;
      key "ip-sub";
      description
        "None";
      leaf enable {
        type empty;
        description
          "Enable None. Deletion of this object also
           causes deletion of all associated objects under
           CnbngNalIpSubscriber.";
      }
      leaf ip-sub {
        type xr:ncs_template_Cisco-ios-xr-string;
        description
          "Set string";
      }
      list cnbng-nal-ipv4-sub-enable {
        // NCS patched for predictable order
        ordered-by user;
        key "ipv4 ipv4l2-conn";
        description
          "None";
        leaf enable {
          type empty;
          description
            "Enable None. Deletion of this object also
             causes deletion of all associated objects
             under CnbngNalIpv4SubEnable.";
        }
        leaf cnbng-nal-ipv4-sub-init-dhcp {
          type empty;
          description
            "Enable";
        }
        leaf ipv4 {
          type xr:ncs_template_Cisco-ios-xr-string;
          description
            "Set string";
        }
        leaf ipv4l2-conn {
          type xr:ncs_template_Cisco-ios-xr-string;
          description
            "Set string";
        }
      }
      list cnbng-nal-ipv6-sub-enable {
        // NCS patched for predictable order
        ordered-by user;
        key "ipv6 ipv6l2-conn";
        description
          "None";
        leaf cnbng-nal-ipv6-sub-init-dhcp {
          type empty;
          description
            "Enable";
        }
        leaf enable {
          type empty;
          description
            "Enable None. Deletion of this object also
             causes deletion of all associated objects
             under CnbngNalIpv6SubEnable.";
        }
        leaf ipv6 {
          type xr:ncs_template_Cisco-ios-xr-string;
          description
            "Set string";
        }
        leaf ipv6l2-conn {
          type xr:ncs_template_Cisco-ios-xr-string;
          description
            "Set string";
        }
      }
    }
  }
  augment "/ncs:devices/ncs:device/ncs:live-status/a1:interface-configurations/a1:interface-configuration" {
    description
      "This augment extends the configuration data of
       'Cisco-IOS-XR-ifmgr-cfg'";
    list cnbng-nal-ip-subscriber {
      tailf:ncs-device-type "netconf";
      tailf:display-when "not(../../../ncs:module) or ../../../ncs:module[ncs:name='Cisco-IOS-XR-subscriber-nal-cfg'] or (../../../ncs:live-status-protocol[not(ncs:capability)]) or (../../../ncs:live-status-protocol/ncs:capability/ncs:module[.='Cisco-IOS-XR-subscriber-nal-cfg'])";
      key "ip-sub";
      description
        "None";
      leaf enable {
        type empty;
        description
          "Enable None. Deletion of this object also
           causes deletion of all associated objects under
           CnbngNalIpSubscriber.";
      }
      leaf ip-sub {
        type xr:live_ncs_Cisco-ios-xr-string;
        description
          "Set string";
      }
      list cnbng-nal-ipv4-sub-enable {
        key "ipv4 ipv4l2-conn";
        description
          "None";
        leaf enable {
          type empty;
          description
            "Enable None. Deletion of this object also
             causes deletion of all associated objects
             under CnbngNalIpv4SubEnable.";
        }
        leaf cnbng-nal-ipv4-sub-init-dhcp {
          type empty;
          description
            "Enable";
        }
        leaf ipv4 {
          type xr:live_ncs_Cisco-ios-xr-string;
          description
            "Set string";
        }
        leaf ipv4l2-conn {
          type xr:live_ncs_Cisco-ios-xr-string;
          description
            "Set string";
        }
      }
      list cnbng-nal-ipv6-sub-enable {
        key "ipv6 ipv6l2-conn";
        description
          "None";
        leaf cnbng-nal-ipv6-sub-init-dhcp {
          type empty;
          description
            "Enable";
        }
        leaf enable {
          type empty;
          description
            "Enable None. Deletion of this object also
             causes deletion of all associated objects
             under CnbngNalIpv6SubEnable.";
        }
        leaf ipv6 {
          type xr:live_ncs_Cisco-ios-xr-string;
          description
            "Set string";
        }
        leaf ipv6l2-conn {
          type xr:live_ncs_Cisco-ios-xr-string;
          description
            "Set string";
        }
      }
    }
  }
  augment "/ncs:devices/ncs:device/ncs:config/a1:interface-configurations/a1:interface-configuration" {
    description
      "This augment extends the configuration data of
       'Cisco-IOS-XR-ifmgr-cfg'";
    list cnbng-nal-ip-subscriber {
      tailf:ncs-device-type "netconf";
      tailf:display-when "not(../../../ncs:module) or ../../../ncs:module[ncs:name='Cisco-IOS-XR-subscriber-nal-cfg']";
      key "ip-sub";
      description
        "None";
      leaf enable {
        type empty;
        description
          "Enable None. Deletion of this object also
           causes deletion of all associated objects under
           CnbngNalIpSubscriber.";
      }
      leaf ip-sub {
        type xr:Cisco-ios-xr-string;
        description
          "Set string";
      }
      list cnbng-nal-ipv4-sub-enable {
        key "ipv4 ipv4l2-conn";
        description
          "None";
        leaf enable {
          type empty;
          description
            "Enable None. Deletion of this object also
             causes deletion of all associated objects
             under CnbngNalIpv4SubEnable.";
        }
        leaf cnbng-nal-ipv4-sub-init-dhcp {
          type empty;
          description
            "Enable";
        }
        leaf ipv4 {
          type xr:Cisco-ios-xr-string;
          description
            "Set string";
        }
        leaf ipv4l2-conn {
          type xr:Cisco-ios-xr-string;
          description
            "Set string";
        }
      }
      list cnbng-nal-ipv6-sub-enable {
        key "ipv6 ipv6l2-conn";
        description
          "None";
        leaf cnbng-nal-ipv6-sub-init-dhcp {
          type empty;
          description
            "Enable";
        }
        leaf enable {
          type empty;
          description
            "Enable None. Deletion of this object also
             causes deletion of all associated objects
             under CnbngNalIpv6SubEnable.";
        }
        leaf ipv6 {
          type xr:Cisco-ios-xr-string;
          description
            "Set string";
        }
        leaf ipv6l2-conn {
          type xr:Cisco-ios-xr-string;
          description
            "Set string";
        }
      }
    }
  }
  augment "/ncs:devices/ncs:template/ncs:ned-id/ncs:config/a1:interface-configurations/a1:interface-configuration" {
    description
      "This augment extends the configuration data of
       'Cisco-IOS-XR-ifmgr-cfg'";
    container cnbng-nal-pppoe-subscriber {
      description
        "None";
      leaf pppoe {
        type string;
        description
          "Set constant integer";
      }
      leaf bba-group {
        type string;
        description
          "The bba-group to use";
      }
    }
  }
  augment "/ncs:devices/ncs:device/ncs:live-status/a1:interface-configurations/a1:interface-configuration" {
    description
      "This augment extends the configuration data of
       'Cisco-IOS-XR-ifmgr-cfg'";
    container cnbng-nal-pppoe-subscriber {
      tailf:ncs-device-type "netconf";
      tailf:display-when "not(../../../../ncs:module) or ../../../../ncs:module[ncs:name='Cisco-IOS-XR-subscriber-nal-cfg'] or (../../../../ncs:live-status-protocol[not(ncs:capability)]) or (../../../../ncs:live-status-protocol/ncs:capability/ncs:module[.='Cisco-IOS-XR-subscriber-nal-cfg'])";
      description
        "None";
      leaf pppoe {
        type uint32;
        description
          "Set constant integer";
      }
      leaf bba-group {
        type string;
        description
          "The bba-group to use";
      }
    }
  }
  augment "/ncs:devices/ncs:device/ncs:config/a1:interface-configurations/a1:interface-configuration" {
    description
      "This augment extends the configuration data of
       'Cisco-IOS-XR-ifmgr-cfg'";
    container cnbng-nal-pppoe-subscriber {
      tailf:ncs-device-type "netconf";
      tailf:display-when "not(../../../../ncs:module) or ../../../../ncs:module[ncs:name='Cisco-IOS-XR-subscriber-nal-cfg']";
      description
        "None";
      leaf pppoe {
        type uint32;
        description
          "Set constant integer";
      }
      leaf bba-group {
        type string;
        description
          "The bba-group to use";
      }
    }
  }
}

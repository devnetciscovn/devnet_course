module Cisco-IOS-XR-osa-sp-cfg {
  // Generated by yanger -t ncs
  tailf:mount-id "cisco-iosxr-nc-7.3:cisco-iosxr-nc-7.3";
  tailf:ncs-device-type "netconf";

  namespace "http://cisco.com/ns/yang/Cisco-IOS-XR-osa-sp-cfg";
  prefix osa-sp-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR osa-sp package configuration.

     This module contains definitions
     for the following management objects:
       ains: AINS Soak Interval Value

     Copyright (c) 2013-2020 by Cisco Systems, Inc.
     All rights reserved.";

  revision 2020-03-09 {
    description
      "Initial Revision.";
    semver:module-version "1.0.0";
  }
  revision 2019-04-05 {
    description
      "Establish semantic version baseline.";
  }
  revision 2015-11-09 {
    description
      "IOS XR 6.0 revision.";
  }

  typedef ncs_template_Ains-soak-hrs-range {
    type string;
    description
      "Ains soak hrs range";
  }

  typedef ncs_template_Ains-soak-mins-range {
    type string;
    description
      "Ains soak mins range";
  }

  typedef ncs_rpc_notif_Ains-soak-hrs-range {
    type uint32 {
      range "0..48";
    }
    description
      "Ains soak hrs range";
  }

  typedef ncs_rpc_notif_Ains-soak-mins-range {
    type uint32 {
      range "0..59";
    }
    description
      "Ains soak mins range";
  }

  typedef live_ncs_Ains-soak-hrs-range {
    type uint32 {
      range "0..48";
    }
    description
      "Ains soak hrs range";
  }

  typedef live_ncs_Ains-soak-mins-range {
    type uint32 {
      range "0..59";
    }
    description
      "Ains soak mins range";
  }

  typedef Ains-soak-hrs-range {
    type uint32 {
      range "0..48";
    }
    description
      "Ains soak hrs range";
  }

  typedef Ains-soak-mins-range {
    type uint32 {
      range "0..59";
    }
    description
      "Ains soak mins range";
  }

  augment "/ncs:devices/ncs:device/ncs:config" {
    container ains {
      tailf:ncs-device-type "netconf";
      tailf:display-when "not(../../ncs:module) or ../../ncs:module[ncs:name='Cisco-IOS-XR-osa-sp-cfg']";
      description
        "AINS Soak Interval Value";
      leaf hours {
        type Ains-soak-hrs-range;
        units "hour";
        description
          "Hours";
      }
      leaf minutes {
        type Ains-soak-mins-range;
        units "minute";
        description
          "Minutes";
      }
    }
  }
  augment "/ncs:devices/ncs:device/ncs:live-status" {
    container ains {
      tailf:ncs-device-type "netconf";
      tailf:display-when "not(../../ncs:module) or ../../ncs:module[ncs:name='Cisco-IOS-XR-osa-sp-cfg'] or (../../ncs:live-status-protocol[not(ncs:capability)]) or (../../ncs:live-status-protocol/ncs:capability/ncs:module[.='Cisco-IOS-XR-osa-sp-cfg'])";
      description
        "AINS Soak Interval Value";
      leaf hours {
        type live_ncs_Ains-soak-hrs-range;
        units "hour";
        description
          "Hours";
      }
      leaf minutes {
        type live_ncs_Ains-soak-mins-range;
        units "minute";
        description
          "Minutes";
      }
    }
  }
  augment "/ncs:devices/ncs:template/ncs:ned-id/ncs:config" {
    container ains {
      description
        "AINS Soak Interval Value";
      leaf hours {
        type ncs_template_Ains-soak-hrs-range;
        units "hour";
        description
          "Hours";
      }
      leaf minutes {
        type ncs_template_Ains-soak-mins-range;
        units "minute";
        description
          "Minutes";
      }
    }
  }
}

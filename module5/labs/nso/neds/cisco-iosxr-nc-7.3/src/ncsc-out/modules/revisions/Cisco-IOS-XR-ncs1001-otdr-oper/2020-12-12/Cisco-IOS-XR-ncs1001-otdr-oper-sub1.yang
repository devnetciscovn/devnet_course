submodule Cisco-IOS-XR-ncs1001-otdr-oper-sub1 {
  // Generated by yanger -t ncs
  tailf:mount-id "cisco-iosxr-nc-7.3:cisco-iosxr-nc-7.3";

  belongs-to Cisco-IOS-XR-ncs1001-otdr-oper {
    prefix Cisco-IOS-XR-ncs1001-otdr-oper;
  }

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1001-otdr package operational data.

     Copyright (c) 2013-2020 by Cisco Systems, Inc.
     All rights reserved.";

  revision 2020-12-12 {
    description
      "XML query for CLI show hw-module ampli-trail-view/channel-trail-view does not return a response";
    semver:module-version "2.0.0";
  }
  revision 2019-05-28 {
    description
      "added OTDR periodic scan and event triggered auto scan";
    semver:module-version "1.1.0";
  }
  revision 2019-04-05 {
    description
      "Establish semantic version baseline.";
    semver:module-version "1.1.0";
  }
  revision 2018-03-15 {
    description
      "first release.";
  }
  revision 2015-11-09 {
    description
      "IOS XR 6.0 revision.";
  }

  typedef ncs_template_Otdr-status {
    type string;
    description
      "Otdr status";
  }

  typedef ncs_template_Otdr-event {
    type string;
    description
      "Otdr event";
  }

  typedef ncs_template_Otdr-scan-mode {
    type string;
    description
      "Otdr scan mode";
  }

  typedef ncs_template_Direction {
    type string;
    description
      "Direction";
  }

  typedef ncs_rpc_notif_Otdr-status {
    type enumeration {
      enum "otdr-status-unknown" {
        value 0;
        description
          "Unknown";
      }
      enum "otdr-status-ok" {
        value 1;
        description
          "Ok";
      }
      enum "otdr-status-orl-progress" {
        value 2;
        description
          "ORL Progress";
      }
      enum "otdr-status-otdr-progress" {
        value 3;
        description
          "OTDR Progress";
      }
      enum "otdr-status-progress" {
        value 4;
        description
          "Progress";
      }
      enum "otdr-status-failure" {
        value 5;
        description
          "Failure";
      }
      enum "otdr-status-aborted" {
        value 6;
        description
          "Aborted";
      }
    }
    description
      "Otdr status";
  }

  typedef ncs_rpc_notif_Otdr-event {
    type enumeration {
      enum "otdr-event-type-loss" {
        value 1;
        description
          "Loss";
      }
      enum "otdr-event-type-reflect-ion" {
        value 2;
        description
          "Reflection";
      }
      enum "otdr-event-type-loss-and-reflect-ion" {
        value 3;
        description
          "Loss and Reflection";
      }
      enum "otdr-event-type-end-of-fiber" {
        value 4;
        description
          "End Of Fiber";
      }
    }
    description
      "Otdr event";
  }

  typedef ncs_rpc_notif_Otdr-scan-mode {
    type enumeration {
      enum "otdr-scan-auto" {
        value 0;
        description
          "Auto";
      }
      enum "otdr-scan-expert" {
        value 1;
        description
          "Expert";
      }
    }
    description
      "Otdr scan mode";
  }

  typedef ncs_rpc_notif_Direction {
    type enumeration {
      enum "direction-tx" {
        value 0;
        description
          "Tx";
      }
      enum "direction-rx" {
        value 1;
        description
          "Rx";
      }
    }
    description
      "Direction";
  }

  typedef live_ncs_Otdr-status {
    type enumeration {
      enum "otdr-status-unknown" {
        value 0;
        description
          "Unknown";
      }
      enum "otdr-status-ok" {
        value 1;
        description
          "Ok";
      }
      enum "otdr-status-orl-progress" {
        value 2;
        description
          "ORL Progress";
      }
      enum "otdr-status-otdr-progress" {
        value 3;
        description
          "OTDR Progress";
      }
      enum "otdr-status-progress" {
        value 4;
        description
          "Progress";
      }
      enum "otdr-status-failure" {
        value 5;
        description
          "Failure";
      }
      enum "otdr-status-aborted" {
        value 6;
        description
          "Aborted";
      }
    }
    description
      "Otdr status";
  }

  typedef live_ncs_Otdr-event {
    type enumeration {
      enum "otdr-event-type-loss" {
        value 1;
        description
          "Loss";
      }
      enum "otdr-event-type-reflect-ion" {
        value 2;
        description
          "Reflection";
      }
      enum "otdr-event-type-loss-and-reflect-ion" {
        value 3;
        description
          "Loss and Reflection";
      }
      enum "otdr-event-type-end-of-fiber" {
        value 4;
        description
          "End Of Fiber";
      }
    }
    description
      "Otdr event";
  }

  typedef live_ncs_Otdr-scan-mode {
    type enumeration {
      enum "otdr-scan-auto" {
        value 0;
        description
          "Auto";
      }
      enum "otdr-scan-expert" {
        value 1;
        description
          "Expert";
      }
    }
    description
      "Otdr scan mode";
  }

  typedef live_ncs_Direction {
    type enumeration {
      enum "direction-tx" {
        value 0;
        description
          "Tx";
      }
      enum "direction-rx" {
        value 1;
        description
          "Rx";
      }
    }
    description
      "Direction";
  }

  typedef Otdr-status {
    type enumeration {
      enum "otdr-status-unknown" {
        value 0;
        description
          "Unknown";
      }
      enum "otdr-status-ok" {
        value 1;
        description
          "Ok";
      }
      enum "otdr-status-orl-progress" {
        value 2;
        description
          "ORL Progress";
      }
      enum "otdr-status-otdr-progress" {
        value 3;
        description
          "OTDR Progress";
      }
      enum "otdr-status-progress" {
        value 4;
        description
          "Progress";
      }
      enum "otdr-status-failure" {
        value 5;
        description
          "Failure";
      }
      enum "otdr-status-aborted" {
        value 6;
        description
          "Aborted";
      }
    }
    description
      "Otdr status";
  }

  typedef Otdr-event {
    type enumeration {
      enum "otdr-event-type-loss" {
        value 1;
        description
          "Loss";
      }
      enum "otdr-event-type-reflect-ion" {
        value 2;
        description
          "Reflection";
      }
      enum "otdr-event-type-loss-and-reflect-ion" {
        value 3;
        description
          "Loss and Reflection";
      }
      enum "otdr-event-type-end-of-fiber" {
        value 4;
        description
          "End Of Fiber";
      }
    }
    description
      "Otdr event";
  }

  typedef Otdr-scan-mode {
    type enumeration {
      enum "otdr-scan-auto" {
        value 0;
        description
          "Auto";
      }
      enum "otdr-scan-expert" {
        value 1;
        description
          "Expert";
      }
    }
    description
      "Otdr scan mode";
  }

  typedef Direction {
    type enumeration {
      enum "direction-tx" {
        value 0;
        description
          "Tx";
      }
      enum "direction-rx" {
        value 1;
        description
          "Rx";
      }
    }
    description
      "Direction";
  }

  grouping ncs_template_HWMOD-OTDR-STATUS-B {
    description
      "Otdr Status";
    leaf otdr-id {
      type string;
      description
        "Otdr Id";
    }
    leaf direction {
      type ncs_template_Direction;
      description
        "Direction";
    }
    leaf timestamp {
      type string;
      description
        "Timestamp";
    }
    leaf training-status {
      type ncs_template_Otdr-status;
      description
        "Training Status";
    }
    leaf measurement-status {
      type ncs_template_Otdr-status;
      description
        "Measurement Status";
    }
    leaf progress-pc {
      type string;
      description
        "Progress %";
    }
    leaf next-scan {
      type string;
      units "minute";
      description
        "Minutes from next scan";
    }
    leaf abort-status {
      type string;
      description
        "Abort status";
    }
  }

  grouping ncs_template_HWMOD-OTDR-ML-EVENT-DATA-B {
    description
      "Otdr ML Event Data";
    leaf event {
      type string;
      description
        "ML Event type";
    }
    leaf position {
      type string;
      description
        "Event Position in Km";
    }
    leaf enabled {
      type string;
      description
        "ML enabled flag";
    }
  }

  grouping ncs_template_HWMOD-OTDR-EVENT-DATA-B {
    description
      "Otdr Event Data";
    leaf event-id {
      type string;
      description
        "Event Id";
    }
    leaf type {
      type ncs_template_Otdr-event;
      description
        "Event Type";
    }
    leaf position {
      type string;
      description
        "Event Position in Km";
    }
    leaf accuracy {
      type string;
      description
        "Event accuracy in meters";
    }
    leaf magnitude {
      type string;
      description
        "Event Magnitude in dB";
    }
    leaf attenuation {
      type string;
      description
        "Event Attenuation in dB";
    }
    leaf eof-confidence {
      type string;
      description
        "Event End of Fiber Confidence";
    }
    leaf threshold-crossing {
      type string;
      description
        "Threshold Crossing";
    }
    leaf threshold-crossing-rel {
      type string;
      description
        "Trelative hreshold Crossing";
    }
  }

  grouping ncs_template_HWMOD-OTDR-ITEM-B {
    description
      "Otdr Item";
    leaf otdr-number {
      type string;
      description
        "Otdr Number";
    }
    leaf direction {
      type ncs_template_Direction;
      description
        "Scan Direction";
    }
    leaf timestamp {
      type string;
      description
        "Timestamp";
    }
    leaf sor-file {
      type string;
      description
        "Sor file name";
    }
    leaf sor-directory {
      type string;
      description
        "Sor file location";
    }
    leaf scan-mode {
      type ncs_template_Otdr-scan-mode;
      description
        "Scan Mode";
    }
    leaf distance {
      type string;
      description
        "Distance in Km";
    }
    leaf total-orl {
      type string;
      description
        "Total Orl in dB";
    }
    leaf high-reflection-location {
      type string;
      description
        "High Reflection Location in Km";
    }
    list otdr-event {
      // NCS patched for predictable order
      ordered-by user;
      description
        "Event list";
      uses ncs_template_HWMOD-OTDR-EVENT-DATA-B;
    }
    list otdr-ml-event {
      // NCS patched for predictable order
      ordered-by user;
      description
        "ML Event list";
      uses ncs_template_HWMOD-OTDR-ML-EVENT-DATA-B;
    }
  }

  grouping ncs_template_HWMOD-OTDR-SCAN-LIST-B {
    description
      "Otdr Scan Data";
    leaf index {
      type string;
      description
        "Index";
    }
    leaf otdr-number {
      type string;
      description
        "Otdr Number";
    }
    leaf direction {
      type ncs_template_Direction;
      description
        "Direction";
    }
    leaf scan-mode {
      type ncs_template_Otdr-scan-mode;
      description
        "Scan Mode";
    }
    leaf timestamp {
      type string;
      description
        "Timestamp";
    }
    leaf sor-file {
      type string;
      description
        "Sor File Name";
    }
  }

  grouping ncs_template_OTS-HWMOD-OTDR-OP {
    description
      "HwModule Otdr data";
    container otdr-item {
      description
        "Otdr Item";
      xr:event-telemetry "Subscribe Telemetry Event";
      uses ncs_template_HWMOD-OTDR-ITEM-B;
    }
    list otdr-scan {
      // NCS patched for predictable order
      ordered-by user;
      description
        "Otdr Scan list";
      uses ncs_template_HWMOD-OTDR-SCAN-LIST-B;
    }
    list otdr-status {
      // NCS patched for predictable order
      ordered-by user;
      description
        "Otdr Status List";
      uses ncs_template_HWMOD-OTDR-STATUS-B;
    }
  }

  grouping ncs_rpc_notif_HWMOD-OTDR-STATUS-B {
    description
      "Otdr Status";
    leaf otdr-id {
      type uint8;
      description
        "Otdr Id";
    }
    leaf direction {
      type ncs_rpc_notif_Direction;
      description
        "Direction";
    }
    leaf timestamp {
      type string {
        length "0..16";
      }
      description
        "Timestamp";
    }
    leaf training-status {
      type ncs_rpc_notif_Otdr-status;
      description
        "Training Status";
    }
    leaf measurement-status {
      type ncs_rpc_notif_Otdr-status;
      description
        "Measurement Status";
    }
    leaf progress-pc {
      type uint16;
      description
        "Progress %";
    }
    leaf next-scan {
      type uint32;
      units "minute";
      description
        "Minutes from next scan";
    }
    leaf abort-status {
      type uint32;
      description
        "Abort status";
    }
  }

  grouping ncs_rpc_notif_HWMOD-OTDR-ML-EVENT-DATA-B {
    description
      "Otdr ML Event Data";
    leaf event {
      type string {
        length "0..64";
      }
      description
        "ML Event type";
    }
    leaf position {
      type string {
        length "0..16";
      }
      description
        "Event Position in Km";
    }
    leaf enabled {
      type uint8;
      description
        "ML enabled flag";
    }
  }

  grouping ncs_rpc_notif_HWMOD-OTDR-EVENT-DATA-B {
    description
      "Otdr Event Data";
    leaf event-id {
      type uint16;
      description
        "Event Id";
    }
    leaf type {
      type ncs_rpc_notif_Otdr-event;
      description
        "Event Type";
    }
    leaf position {
      type string {
        length "0..16";
      }
      description
        "Event Position in Km";
    }
    leaf accuracy {
      type string {
        length "0..16";
      }
      description
        "Event accuracy in meters";
    }
    leaf magnitude {
      type string {
        length "0..16";
      }
      description
        "Event Magnitude in dB";
    }
    leaf attenuation {
      type string {
        length "0..16";
      }
      description
        "Event Attenuation in dB";
    }
    leaf eof-confidence {
      type uint32;
      description
        "Event End of Fiber Confidence";
    }
    leaf threshold-crossing {
      type uint8;
      description
        "Threshold Crossing";
    }
    leaf threshold-crossing-rel {
      type uint8;
      description
        "Trelative hreshold Crossing";
    }
  }

  grouping ncs_rpc_notif_HWMOD-OTDR-ITEM-B {
    description
      "Otdr Item";
    leaf otdr-number {
      type uint8;
      description
        "Otdr Number";
    }
    leaf direction {
      type ncs_rpc_notif_Direction;
      description
        "Scan Direction";
    }
    leaf timestamp {
      type string {
        length "0..16";
      }
      description
        "Timestamp";
    }
    leaf sor-file {
      type string {
        length "0..128";
      }
      description
        "Sor file name";
    }
    leaf sor-directory {
      type string {
        length "0..128";
      }
      description
        "Sor file location";
    }
    leaf scan-mode {
      type ncs_rpc_notif_Otdr-scan-mode;
      description
        "Scan Mode";
    }
    leaf distance {
      type string {
        length "0..16";
      }
      description
        "Distance in Km";
    }
    leaf total-orl {
      type string {
        length "0..16";
      }
      description
        "Total Orl in dB";
    }
    leaf high-reflection-location {
      type string {
        length "0..16";
      }
      description
        "High Reflection Location in Km";
    }
    list otdr-event {
      description
        "Event list";
      uses ncs_rpc_notif_HWMOD-OTDR-EVENT-DATA-B;
    }
    list otdr-ml-event {
      description
        "ML Event list";
      uses ncs_rpc_notif_HWMOD-OTDR-ML-EVENT-DATA-B;
    }
  }

  grouping ncs_rpc_notif_HWMOD-OTDR-SCAN-LIST-B {
    description
      "Otdr Scan Data";
    leaf index {
      type uint16;
      description
        "Index";
    }
    leaf otdr-number {
      type uint8;
      description
        "Otdr Number";
    }
    leaf direction {
      type ncs_rpc_notif_Direction;
      description
        "Direction";
    }
    leaf scan-mode {
      type ncs_rpc_notif_Otdr-scan-mode;
      description
        "Scan Mode";
    }
    leaf timestamp {
      type string {
        length "0..16";
      }
      description
        "Timestamp";
    }
    leaf sor-file {
      type string {
        length "0..128";
      }
      description
        "Sor File Name";
    }
  }

  grouping ncs_rpc_notif_OTS-HWMOD-OTDR-OP {
    description
      "HwModule Otdr data";
    container otdr-item {
      description
        "Otdr Item";
      xr:event-telemetry "Subscribe Telemetry Event";
      uses ncs_rpc_notif_HWMOD-OTDR-ITEM-B;
    }
    list otdr-scan {
      description
        "Otdr Scan list";
      uses ncs_rpc_notif_HWMOD-OTDR-SCAN-LIST-B;
    }
    list otdr-status {
      description
        "Otdr Status List";
      uses ncs_rpc_notif_HWMOD-OTDR-STATUS-B;
    }
  }

  grouping live_ncs_HWMOD-OTDR-STATUS-B {
    description
      "Otdr Status";
    leaf otdr-id {
      type uint8;
      description
        "Otdr Id";
    }
    leaf direction {
      type live_ncs_Direction;
      description
        "Direction";
    }
    leaf timestamp {
      type string {
        length "0..16";
      }
      description
        "Timestamp";
    }
    leaf training-status {
      type live_ncs_Otdr-status;
      description
        "Training Status";
    }
    leaf measurement-status {
      type live_ncs_Otdr-status;
      description
        "Measurement Status";
    }
    leaf progress-pc {
      type uint16;
      description
        "Progress %";
    }
    leaf next-scan {
      type uint32;
      units "minute";
      description
        "Minutes from next scan";
    }
    leaf abort-status {
      type uint32;
      description
        "Abort status";
    }
  }

  grouping live_ncs_HWMOD-OTDR-ML-EVENT-DATA-B {
    description
      "Otdr ML Event Data";
    leaf event {
      type string {
        length "0..64";
      }
      description
        "ML Event type";
    }
    leaf position {
      type string {
        length "0..16";
      }
      description
        "Event Position in Km";
    }
    leaf enabled {
      type uint8;
      description
        "ML enabled flag";
    }
  }

  grouping live_ncs_HWMOD-OTDR-EVENT-DATA-B {
    description
      "Otdr Event Data";
    leaf event-id {
      type uint16;
      description
        "Event Id";
    }
    leaf type {
      type live_ncs_Otdr-event;
      description
        "Event Type";
    }
    leaf position {
      type string {
        length "0..16";
      }
      description
        "Event Position in Km";
    }
    leaf accuracy {
      type string {
        length "0..16";
      }
      description
        "Event accuracy in meters";
    }
    leaf magnitude {
      type string {
        length "0..16";
      }
      description
        "Event Magnitude in dB";
    }
    leaf attenuation {
      type string {
        length "0..16";
      }
      description
        "Event Attenuation in dB";
    }
    leaf eof-confidence {
      type uint32;
      description
        "Event End of Fiber Confidence";
    }
    leaf threshold-crossing {
      type uint8;
      description
        "Threshold Crossing";
    }
    leaf threshold-crossing-rel {
      type uint8;
      description
        "Trelative hreshold Crossing";
    }
  }

  grouping live_ncs_HWMOD-OTDR-ITEM-B {
    description
      "Otdr Item";
    leaf otdr-number {
      type uint8;
      description
        "Otdr Number";
    }
    leaf direction {
      type live_ncs_Direction;
      description
        "Scan Direction";
    }
    leaf timestamp {
      type string {
        length "0..16";
      }
      description
        "Timestamp";
    }
    leaf sor-file {
      type string {
        length "0..128";
      }
      description
        "Sor file name";
    }
    leaf sor-directory {
      type string {
        length "0..128";
      }
      description
        "Sor file location";
    }
    leaf scan-mode {
      type live_ncs_Otdr-scan-mode;
      description
        "Scan Mode";
    }
    leaf distance {
      type string {
        length "0..16";
      }
      description
        "Distance in Km";
    }
    leaf total-orl {
      type string {
        length "0..16";
      }
      description
        "Total Orl in dB";
    }
    leaf high-reflection-location {
      type string {
        length "0..16";
      }
      description
        "High Reflection Location in Km";
    }
    list otdr-event {
      description
        "Event list";
      uses live_ncs_HWMOD-OTDR-EVENT-DATA-B;
    }
    list otdr-ml-event {
      description
        "ML Event list";
      uses live_ncs_HWMOD-OTDR-ML-EVENT-DATA-B;
    }
  }

  grouping live_ncs_HWMOD-OTDR-SCAN-LIST-B {
    description
      "Otdr Scan Data";
    leaf index {
      type uint16;
      description
        "Index";
    }
    leaf otdr-number {
      type uint8;
      description
        "Otdr Number";
    }
    leaf direction {
      type live_ncs_Direction;
      description
        "Direction";
    }
    leaf scan-mode {
      type live_ncs_Otdr-scan-mode;
      description
        "Scan Mode";
    }
    leaf timestamp {
      type string {
        length "0..16";
      }
      description
        "Timestamp";
    }
    leaf sor-file {
      type string {
        length "0..128";
      }
      description
        "Sor File Name";
    }
  }

  grouping live_ncs_OTS-HWMOD-OTDR-OP {
    description
      "HwModule Otdr data";
    container otdr-item {
      description
        "Otdr Item";
      xr:event-telemetry "Subscribe Telemetry Event";
      uses live_ncs_HWMOD-OTDR-ITEM-B;
    }
    list otdr-scan {
      description
        "Otdr Scan list";
      uses live_ncs_HWMOD-OTDR-SCAN-LIST-B;
    }
    list otdr-status {
      description
        "Otdr Status List";
      uses live_ncs_HWMOD-OTDR-STATUS-B;
    }
  }

  grouping HWMOD-OTDR-STATUS-B {
    description
      "Otdr Status";
    leaf otdr-id {
      type uint8;
      description
        "Otdr Id";
    }
    leaf direction {
      type Direction;
      description
        "Direction";
    }
    leaf timestamp {
      type string {
        length "0..16";
      }
      description
        "Timestamp";
    }
    leaf training-status {
      type Otdr-status;
      description
        "Training Status";
    }
    leaf measurement-status {
      type Otdr-status;
      description
        "Measurement Status";
    }
    leaf progress-pc {
      type uint16;
      description
        "Progress %";
    }
    leaf next-scan {
      type uint32;
      units "minute";
      description
        "Minutes from next scan";
    }
    leaf abort-status {
      type uint32;
      description
        "Abort status";
    }
  }

  grouping HWMOD-OTDR-ML-EVENT-DATA-B {
    description
      "Otdr ML Event Data";
    leaf event {
      type string {
        length "0..64";
      }
      description
        "ML Event type";
    }
    leaf position {
      type string {
        length "0..16";
      }
      description
        "Event Position in Km";
    }
    leaf enabled {
      type uint8;
      description
        "ML enabled flag";
    }
  }

  grouping HWMOD-OTDR-EVENT-DATA-B {
    description
      "Otdr Event Data";
    leaf event-id {
      type uint16;
      description
        "Event Id";
    }
    leaf type {
      type Otdr-event;
      description
        "Event Type";
    }
    leaf position {
      type string {
        length "0..16";
      }
      description
        "Event Position in Km";
    }
    leaf accuracy {
      type string {
        length "0..16";
      }
      description
        "Event accuracy in meters";
    }
    leaf magnitude {
      type string {
        length "0..16";
      }
      description
        "Event Magnitude in dB";
    }
    leaf attenuation {
      type string {
        length "0..16";
      }
      description
        "Event Attenuation in dB";
    }
    leaf eof-confidence {
      type uint32;
      description
        "Event End of Fiber Confidence";
    }
    leaf threshold-crossing {
      type uint8;
      description
        "Threshold Crossing";
    }
    leaf threshold-crossing-rel {
      type uint8;
      description
        "Trelative hreshold Crossing";
    }
  }

  grouping HWMOD-OTDR-ITEM-B {
    description
      "Otdr Item";
    leaf otdr-number {
      type uint8;
      description
        "Otdr Number";
    }
    leaf direction {
      type Direction;
      description
        "Scan Direction";
    }
    leaf timestamp {
      type string {
        length "0..16";
      }
      description
        "Timestamp";
    }
    leaf sor-file {
      type string {
        length "0..128";
      }
      description
        "Sor file name";
    }
    leaf sor-directory {
      type string {
        length "0..128";
      }
      description
        "Sor file location";
    }
    leaf scan-mode {
      type Otdr-scan-mode;
      description
        "Scan Mode";
    }
    leaf distance {
      type string {
        length "0..16";
      }
      description
        "Distance in Km";
    }
    leaf total-orl {
      type string {
        length "0..16";
      }
      description
        "Total Orl in dB";
    }
    leaf high-reflection-location {
      type string {
        length "0..16";
      }
      description
        "High Reflection Location in Km";
    }
    list otdr-event {
      description
        "Event list";
      uses HWMOD-OTDR-EVENT-DATA-B;
    }
    list otdr-ml-event {
      description
        "ML Event list";
      uses HWMOD-OTDR-ML-EVENT-DATA-B;
    }
  }

  grouping HWMOD-OTDR-SCAN-LIST-B {
    description
      "Otdr Scan Data";
    leaf index {
      type uint16;
      description
        "Index";
    }
    leaf otdr-number {
      type uint8;
      description
        "Otdr Number";
    }
    leaf direction {
      type Direction;
      description
        "Direction";
    }
    leaf scan-mode {
      type Otdr-scan-mode;
      description
        "Scan Mode";
    }
    leaf timestamp {
      type string {
        length "0..16";
      }
      description
        "Timestamp";
    }
    leaf sor-file {
      type string {
        length "0..128";
      }
      description
        "Sor File Name";
    }
  }

  grouping OTS-HWMOD-OTDR-OP {
    description
      "HwModule Otdr data";
    container otdr-item {
      description
        "Otdr Item";
      xr:event-telemetry "Subscribe Telemetry Event";
      uses HWMOD-OTDR-ITEM-B;
    }
    list otdr-scan {
      description
        "Otdr Scan list";
      uses HWMOD-OTDR-SCAN-LIST-B;
    }
    list otdr-status {
      description
        "Otdr Status List";
      uses HWMOD-OTDR-STATUS-B;
    }
  }
}

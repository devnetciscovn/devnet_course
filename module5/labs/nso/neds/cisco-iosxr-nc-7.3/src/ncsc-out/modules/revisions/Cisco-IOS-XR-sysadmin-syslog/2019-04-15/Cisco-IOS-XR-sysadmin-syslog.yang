module Cisco-IOS-XR-sysadmin-syslog {
  // Generated by yanger -t ncs
  tailf:mount-id "cisco-iosxr-nc-7.3:cisco-iosxr-nc-7.3";
  tailf:ncs-device-type "netconf";

  namespace "http://www.cisco.com/ns/yang/Cisco-IOS-XR-sysadmin-syslog";
  prefix syslog;

  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines configuration for
     sysadmin syslog infrastructure.

     Copyright (c) 2010-2020 by Cisco Systems, Inc.
     All rights reserved.";

  revision 2019-04-15 {
    description
      "Establish semantic version baseline.";
    semver:module-version "1.0.0";
  }
  revision 2017-05-09 {
    description
      "Namespace change to comply with Cisco guidelines";
  }
  revision 2016-09-16 {
    description
      "Added new type for show logging host";
  }

  typedef ncs_template_num-lines-type {
    type string;
  }

  typedef ncs_template_dir-or-file-path-type {
    type string;
  }

  typedef ncs_rpc_notif_num-lines-type {
    type uint32;
  }

  typedef ncs_rpc_notif_dir-or-file-path-type {
    type string;
  }

  typedef live_ncs_num-lines-type {
    type uint32;
  }

  typedef live_ncs_dir-or-file-path-type {
    type string;
  }

  typedef num-lines-type {
    type uint32;
  }

  typedef dir-or-file-path-type {
    type string;
  }

  grouping ncs_template_syslog-grp {
    container console {
      description
        "Syslog Infrastructure";
      choice disable_or_severity {
        // NCS drop mandatory statement
        case choice_emergency {
          leaf emergency {
            type empty;
          }
        }
        case choice_alert {
          leaf alert {
            type empty;
          }
        }
        case choice_critical {
          leaf critical {
            type empty;
          }
        }
        case choice_error {
          leaf error {
            type empty;
          }
        }
        case choice_warning {
          leaf warning {
            type empty;
          }
        }
        case choice_notice {
          leaf notice {
            type empty;
          }
        }
        case choice_informational {
          leaf informational {
            type empty;
          }
        }
        case choice_debug {
          leaf debug {
            type empty;
          }
        }
        case choice_disable {
          leaf disable {
            type empty;
          }
        }
      }
    }
  }

  grouping ncs_rpc_notif_syslog-grp {
    container console {
      description
        "Syslog Infrastructure";
      choice disable_or_severity {
        mandatory false;
        case choice_emergency {
          leaf emergency {
            type empty;
          }
        }
        case choice_alert {
          leaf alert {
            type empty;
          }
        }
        case choice_critical {
          leaf critical {
            type empty;
          }
        }
        case choice_error {
          leaf error {
            type empty;
          }
        }
        case choice_warning {
          leaf warning {
            type empty;
          }
        }
        case choice_notice {
          leaf notice {
            type empty;
          }
        }
        case choice_informational {
          leaf informational {
            type empty;
          }
        }
        case choice_debug {
          leaf debug {
            type empty;
          }
        }
        case choice_disable {
          leaf disable {
            type empty;
          }
        }
      }
    }
  }

  grouping live_ncs_syslog-grp {
    container console {
      description
        "Syslog Infrastructure";
      choice disable_or_severity {
        // NCS drop mandatory statement
        case choice_emergency {
          leaf emergency {
            type empty;
          }
        }
        case choice_alert {
          leaf alert {
            type empty;
          }
        }
        case choice_critical {
          leaf critical {
            type empty;
          }
        }
        case choice_error {
          leaf error {
            type empty;
          }
        }
        case choice_warning {
          leaf warning {
            type empty;
          }
        }
        case choice_notice {
          leaf notice {
            type empty;
          }
        }
        case choice_informational {
          leaf informational {
            type empty;
          }
        }
        case choice_debug {
          leaf debug {
            type empty;
          }
        }
        case choice_disable {
          leaf disable {
            type empty;
          }
        }
      }
    }
  }

  grouping syslog-grp {
    container console {
      description
        "Syslog Infrastructure";
      choice disable_or_severity {
        mandatory false;
        case choice_emergency {
          leaf emergency {
            type empty;
          }
        }
        case choice_alert {
          leaf alert {
            type empty;
          }
        }
        case choice_critical {
          leaf critical {
            type empty;
          }
        }
        case choice_error {
          leaf error {
            type empty;
          }
        }
        case choice_warning {
          leaf warning {
            type empty;
          }
        }
        case choice_notice {
          leaf notice {
            type empty;
          }
        }
        case choice_informational {
          leaf informational {
            type empty;
          }
        }
        case choice_debug {
          leaf debug {
            type empty;
          }
        }
        case choice_disable {
          leaf disable {
            type empty;
          }
        }
      }
    }
  }
}

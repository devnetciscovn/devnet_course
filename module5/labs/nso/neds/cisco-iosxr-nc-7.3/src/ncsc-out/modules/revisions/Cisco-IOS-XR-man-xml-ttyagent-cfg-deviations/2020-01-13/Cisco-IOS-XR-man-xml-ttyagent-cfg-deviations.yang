module Cisco-IOS-XR-man-xml-ttyagent-cfg-deviations {
  // Generated by yanger -t ncs
  tailf:mount-id "cisco-iosxr-nc-7.3:cisco-iosxr-nc-7.3";
  tailf:ncs-device-type "netconf";

  namespace "http://cisco.com/ns/yang/Cisco-IOS-XR-man-xml-ttyagent-cfg-deviations.yang";
  prefix cisco-ios-ttyagent-cfg-dev;

  import Cisco-IOS-XR-man-xml-ttyagent-cfg {
    prefix mxt-dev;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: 1 800 553-NETS

     E-mail: cs-yang@cisco.com";
  description
    "This module contains a set of deviations of leaf memory range data
     model set for Cisco IOS-XR.

     Copyright (c) 2016, 2020 by Cisco Systems, Inc.
     All rights reserved.";

  revision 2020-01-13 {
    description
      "Initial revision applicable to IOS-XR 6.1.2 and older releases";
  }

  deviation "/ncs:devices/ncs:template/ncs:ned-id/ncs:config/mxt-dev:xr-xml/mxt-dev:agent/mxt-dev:default/mxt-dev:throttle/mxt-dev:memory" {
    deviate replace {
      type string;
    }
  }
  deviation "/ncs:devices/ncs:device/ncs:live-status/mxt-dev:xr-xml/mxt-dev:agent/mxt-dev:default/mxt-dev:throttle/mxt-dev:memory" {
    deviate replace {
      type uint32 {
        range "100..1024";
      }
    }
  }
  deviation "/ncs:devices/ncs:device/ncs:config/mxt-dev:xr-xml/mxt-dev:agent/mxt-dev:default/mxt-dev:throttle/mxt-dev:memory" {
    deviate replace {
      type uint32 {
        range "100..1024";
      }
    }
  }
  deviation "/ncs:devices/ncs:template/ncs:ned-id/ncs:config/mxt-dev:xr-xml/mxt-dev:agent/mxt-dev:tty/mxt-dev:throttle/mxt-dev:memory" {
    deviate replace {
      type string;
    }
  }
  deviation "/ncs:devices/ncs:device/ncs:live-status/mxt-dev:xr-xml/mxt-dev:agent/mxt-dev:tty/mxt-dev:throttle/mxt-dev:memory" {
    deviate replace {
      type uint32 {
        range "100..1024";
      }
    }
  }
  deviation "/ncs:devices/ncs:device/ncs:config/mxt-dev:xr-xml/mxt-dev:agent/mxt-dev:tty/mxt-dev:throttle/mxt-dev:memory" {
    deviate replace {
      type uint32 {
        range "100..1024";
      }
    }
  }
  deviation "/ncs:devices/ncs:template/ncs:ned-id/ncs:config/mxt-dev:xr-xml/mxt-dev:agent/mxt-dev:ssl/mxt-dev:throttle/mxt-dev:memory" {
    deviate replace {
      type string;
    }
  }
  deviation "/ncs:devices/ncs:device/ncs:live-status/mxt-dev:xr-xml/mxt-dev:agent/mxt-dev:ssl/mxt-dev:throttle/mxt-dev:memory" {
    deviate replace {
      type uint32 {
        range "100..1024";
      }
    }
  }
  deviation "/ncs:devices/ncs:device/ncs:config/mxt-dev:xr-xml/mxt-dev:agent/mxt-dev:ssl/mxt-dev:throttle/mxt-dev:memory" {
    deviate replace {
      type uint32 {
        range "100..1024";
      }
    }
  }
}

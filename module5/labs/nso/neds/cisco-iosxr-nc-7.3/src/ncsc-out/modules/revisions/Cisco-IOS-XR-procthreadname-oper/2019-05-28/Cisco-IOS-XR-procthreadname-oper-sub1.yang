submodule Cisco-IOS-XR-procthreadname-oper-sub1 {
  // Generated by yanger -t ncs
  tailf:mount-id "cisco-iosxr-nc-7.3:cisco-iosxr-nc-7.3";

  belongs-to Cisco-IOS-XR-procthreadname-oper {
    prefix Cisco-IOS-XR-procthreadname-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR procthreadname package operational data.

     Copyright (c) 2013-2019 by Cisco Systems, Inc.
     All rights reserved.";

  revision 2019-05-28 {
    description
      "Initial version.";
    semver:module-version "1.0.0";
  }
  revision 2019-04-05 {
    description
      "Establish semantic version baseline.";
  }
  revision 2015-11-09 {
    description
      "IOS XR 6.0 revision.";
  }

  grouping ncs_template_PROCESSESTHREAD-ENTRY {
    description
      " Per Thread Information";
    leaf name {
      type string;
      description
        "Thread name";
    }
    leaf state {
      type string;
      description
        "Thread State";
    }
    leaf stack {
      type string;
      description
        "Stack";
    }
    leaf pri {
      type string;
      description
        "Priority";
    }
    leaf rtpri {
      type string;
      description
        "Rt pri";
    }
    leaf jid {
      type string;
      description
        "Job ID";
    }
    leaf tid {
      type string;
      description
        "Thread ID";
    }
  }

  grouping ncs_template_THREADLIST {
    description
      " Per node thread list";
    list thread {
      // NCS patched for predictable order
      ordered-by user;
      description
        "Thread list";
      uses ncs_template_PROCESSESTHREAD-ENTRY;
    }
  }

  grouping ncs_rpc_notif_PROCESSESTHREAD-ENTRY {
    description
      " Per Thread Information";
    leaf name {
      type string;
      description
        "Thread name";
    }
    leaf state {
      type string;
      description
        "Thread State";
    }
    leaf stack {
      type string;
      description
        "Stack";
    }
    leaf pri {
      type uint32;
      description
        "Priority";
    }
    leaf rtpri {
      type uint32;
      description
        "Rt pri";
    }
    leaf jid {
      type uint32;
      description
        "Job ID";
    }
    leaf tid {
      type uint32;
      description
        "Thread ID";
    }
  }

  grouping ncs_rpc_notif_THREADLIST {
    description
      " Per node thread list";
    list thread {
      description
        "Thread list";
      uses ncs_rpc_notif_PROCESSESTHREAD-ENTRY;
    }
  }

  grouping live_ncs_PROCESSESTHREAD-ENTRY {
    description
      " Per Thread Information";
    leaf name {
      type string;
      description
        "Thread name";
    }
    leaf state {
      type string;
      description
        "Thread State";
    }
    leaf stack {
      type string;
      description
        "Stack";
    }
    leaf pri {
      type uint32;
      description
        "Priority";
    }
    leaf rtpri {
      type uint32;
      description
        "Rt pri";
    }
    leaf jid {
      type uint32;
      description
        "Job ID";
    }
    leaf tid {
      type uint32;
      description
        "Thread ID";
    }
  }

  grouping live_ncs_THREADLIST {
    description
      " Per node thread list";
    list thread {
      description
        "Thread list";
      uses live_ncs_PROCESSESTHREAD-ENTRY;
    }
  }

  grouping PROCESSESTHREAD-ENTRY {
    description
      " Per Thread Information";
    leaf name {
      type string;
      description
        "Thread name";
    }
    leaf state {
      type string;
      description
        "Thread State";
    }
    leaf stack {
      type string;
      description
        "Stack";
    }
    leaf pri {
      type uint32;
      description
        "Priority";
    }
    leaf rtpri {
      type uint32;
      description
        "Rt pri";
    }
    leaf jid {
      type uint32;
      description
        "Job ID";
    }
    leaf tid {
      type uint32;
      description
        "Thread ID";
    }
  }

  grouping THREADLIST {
    description
      " Per node thread list";
    list thread {
      description
        "Thread list";
      uses PROCESSESTHREAD-ENTRY;
    }
  }
}

module Cisco-IOS-XR-freqsync-cfg {
  // Generated by yanger -t ncs
  tailf:mount-id "cisco-iosxr-nc-7.3:cisco-iosxr-nc-7.3";
  tailf:ncs-device-type "netconf";

  namespace "http://cisco.com/ns/yang/Cisco-IOS-XR-freqsync-cfg";
  prefix freqsync-cfg;

  import ietf-yang-types {
    prefix yang;
  }
  import Cisco-IOS-XR-config-mda-cfg {
    prefix node;
  }
  import cisco-semver {
    prefix semver;
  }
  import Cisco-IOS-XR-freqsync-datatypes {
    prefix dt1;
  }
  import Cisco-IOS-XR-snmp-agent-cfg {
    prefix a1;
  }
  import Cisco-IOS-XR-ifmgr-cfg {
    prefix a2;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR freqsync package configuration.

     This module contains definitions
     for the following management objects:
       frequency-synchronization: Frequency Synchronization global
         configuration

     This YANG module augments the
       Cisco-IOS-XR-snmp-agent-cfg,
       Cisco-IOS-XR-ifmgr-cfg
       Cisco-IOS-XR-config-mda-cfg
     modules with configuration data.

     Copyright (c) 2013-2020 by Cisco Systems, Inc.
     All rights reserved.";

  revision 2020-04-15 {
    description
      "Fixed must conditions bug.";
    semver:module-version "2.0.0";
  }
  revision 2019-04-05 {
    description
      "Establish semantic version baseline.";
    semver:module-version "1.0.0";
  }
  revision 2017-09-30 {
    description
      "Ensure propagation of MDA mandatory state to YANG model.";
  }
  revision 2017-09-07 {
    description
      "Fixed type translation error.";
  }
  revision 2015-11-09 {
    description
      "IOS XR 6.0 revision.";
  }

  typedef ncs_template_Fsync-system-timing-mode {
    type string;
    description
      "Fsync system timing mode";
  }

  typedef ncs_template_Fsync-clock-source {
    type string;
    description
      "Fsync clock source";
  }

  typedef ncs_template_Fsync-source-selection-logging {
    type string;
    description
      "Fsync source selection logging";
  }

  typedef ncs_template_Freq-sync-quality-level {
    type string;
    description
      "Freq sync quality level";
  }

  typedef ncs_rpc_notif_Fsync-system-timing-mode {
    type enumeration {
      enum "line-only" {
        value 2;
        description
          "Line-interfaces only";
      }
      enum "clock-only" {
        value 3;
        description
          "Clock-interfaces only";
      }
    }
    description
      "Fsync system timing mode";
  }

  typedef ncs_rpc_notif_Fsync-clock-source {
    type enumeration {
      enum "system" {
        value 1;
        description
          "System";
      }
      enum "independent" {
        value 3;
        description
          "Independent";
      }
    }
    description
      "Fsync clock source";
  }

  typedef ncs_rpc_notif_Fsync-source-selection-logging {
    type enumeration {
      enum "changes" {
        value 1;
        description
          "Log both selection changes and errors";
      }
      enum "errors" {
        value 2;
        description
          "Log selection errors";
      }
    }
    description
      "Fsync source selection logging";
  }

  typedef ncs_rpc_notif_Freq-sync-quality-level {
    type enumeration {
      enum "dnu" {
        value 1;
        description
          "DNU";
      }
      enum "prc" {
        value 2;
        description
          "PRC";
      }
      enum "sec" {
        value 3;
        description
          "SEC";
      }
      enum "ssua" {
        value 4;
        description
          "SSU A";
      }
      enum "ssub" {
        value 5;
        description
          "SSU B";
      }
    }
    description
      "Freq sync quality level";
  }

  typedef live_ncs_Fsync-system-timing-mode {
    type enumeration {
      enum "line-only" {
        value 2;
        description
          "Line-interfaces only";
      }
      enum "clock-only" {
        value 3;
        description
          "Clock-interfaces only";
      }
    }
    description
      "Fsync system timing mode";
  }

  typedef live_ncs_Fsync-clock-source {
    type enumeration {
      enum "system" {
        value 1;
        description
          "System";
      }
      enum "independent" {
        value 3;
        description
          "Independent";
      }
    }
    description
      "Fsync clock source";
  }

  typedef live_ncs_Fsync-source-selection-logging {
    type enumeration {
      enum "changes" {
        value 1;
        description
          "Log both selection changes and errors";
      }
      enum "errors" {
        value 2;
        description
          "Log selection errors";
      }
    }
    description
      "Fsync source selection logging";
  }

  typedef live_ncs_Freq-sync-quality-level {
    type enumeration {
      enum "dnu" {
        value 1;
        description
          "DNU";
      }
      enum "prc" {
        value 2;
        description
          "PRC";
      }
      enum "sec" {
        value 3;
        description
          "SEC";
      }
      enum "ssua" {
        value 4;
        description
          "SSU A";
      }
      enum "ssub" {
        value 5;
        description
          "SSU B";
      }
    }
    description
      "Freq sync quality level";
  }

  typedef Fsync-system-timing-mode {
    type enumeration {
      enum "line-only" {
        value 2;
        description
          "Line-interfaces only";
      }
      enum "clock-only" {
        value 3;
        description
          "Clock-interfaces only";
      }
    }
    description
      "Fsync system timing mode";
  }

  typedef Fsync-clock-source {
    type enumeration {
      enum "system" {
        value 1;
        description
          "System";
      }
      enum "independent" {
        value 3;
        description
          "Independent";
      }
    }
    description
      "Fsync clock source";
  }

  typedef Fsync-source-selection-logging {
    type enumeration {
      enum "changes" {
        value 1;
        description
          "Log both selection changes and errors";
      }
      enum "errors" {
        value 2;
        description
          "Log selection errors";
      }
    }
    description
      "Fsync source selection logging";
  }

  typedef Freq-sync-quality-level {
    type enumeration {
      enum "dnu" {
        value 1;
        description
          "DNU";
      }
      enum "prc" {
        value 2;
        description
          "PRC";
      }
      enum "sec" {
        value 3;
        description
          "SEC";
      }
      enum "ssua" {
        value 4;
        description
          "SSU A";
      }
      enum "ssub" {
        value 5;
        description
          "SSU B";
      }
    }
    description
      "Freq sync quality level";
  }

  grouping ncs_template_NODE-CFG {
    description
      "active/preconfigured nodes configuration";
    container clock-interface {
      description
        "Configuration for a clock interface";
      container clocks {
        description
          "Configuration for a clock interface";
        list clock {
          // NCS patched for predictable order
          ordered-by user;
          key "clock-type port";
          description
            "Configuration for a clock interface";
          container frequency-synchronization {
            description
              "Frequency Synchronization clock configuraiton";
            container output-quality-level {
              description
                "Set the output quality level";
              leaf quality-level-option {
                type dt1:ncs_template_Fsync-ql-option;
                // NCS drop must statement
                description
                  "Quality level option";
              }
              leaf exact-quality-level-value {
                type dt1:ncs_template_Fsync-ql-value;
                // NCS drop must statement
                description
                  "Exact quality level value";
              }
              leaf min-quality-level-value {
                type dt1:ncs_template_Fsync-ql-value;
                // NCS drop must statement
                description
                  "Minimum quality level value";
              }
              leaf max-quality-level-value {
                type dt1:ncs_template_Fsync-ql-value;
                // NCS drop must statement
                description
                  "Maximum quality level value";
              }
            }
            container input-quality-level {
              description
                "Set the input quality level";
              leaf quality-level-option {
                type dt1:ncs_template_Fsync-ql-option;
                // NCS drop must statement
                description
                  "Quality level option";
              }
              leaf exact-quality-level-value {
                type dt1:ncs_template_Fsync-ql-value;
                // NCS drop must statement
                description
                  "Exact quality level value";
              }
              leaf min-quality-level-value {
                type dt1:ncs_template_Fsync-ql-value;
                // NCS drop must statement
                description
                  "Minimum quality level value";
              }
              leaf max-quality-level-value {
                type dt1:ncs_template_Fsync-ql-value;
                // NCS drop must statement
                description
                  "Maximum quality level value";
              }
            }
            leaf wait-to-restore-time {
              type string;
              // NCS drop default statement
              description
                "Set the wait-to-restore time for this source";
            }
            leaf priority {
              type string;
              // NCS drop default statement
              description
                "Set the priority of this source";
            }
            leaf selection-input {
              type empty;
              description
                "Assign this source as a selection input";
            }
            leaf time-of-day-priority {
              type string;
              // NCS drop default statement
              description
                "Set the time-of-day priority of this source";
            }
            leaf ssm-disable {
              type empty;
              description
                "Disable SSM on this source";
            }
          }
          leaf clock-type {
            type dt1:ncs_template_Fsync-clock;
            description
              "Clock type";
          }
          leaf port {
            type string;
            description
              "Clock port";
          }
        }
      }
    }
  }

  grouping ncs_rpc_notif_NODE-CFG {
    description
      "active/preconfigured nodes configuration";
    container clock-interface {
      description
        "Configuration for a clock interface";
      container clocks {
        description
          "Configuration for a clock interface";
        list clock {
          key "clock-type port";
          description
            "Configuration for a clock interface";
          container frequency-synchronization {
            description
              "Frequency Synchronization clock configuraiton";
            container output-quality-level {
              description
                "Set the output quality level";
              leaf quality-level-option {
                type dt1:ncs_rpc_notif_Fsync-ql-option;
                must '../exact-quality-level-value or ../min-quality-level-value or ../max-quality-level-value or (../min-quality-level-value and ../max-quality-level-value)' {
                  tailf:xpath-root 3;
                }
                description
                  "Quality level option";
              }
              leaf exact-quality-level-value {
                type dt1:ncs_rpc_notif_Fsync-ql-value;
                must '../quality-level-option and not(../min-quality-level-value or ../max-quality-level-value)' {
                  tailf:xpath-root 3;
                }
                description
                  "Exact quality level value";
              }
              leaf min-quality-level-value {
                type dt1:ncs_rpc_notif_Fsync-ql-value;
                must '../quality-level-option and not(../exact-quality-level-value)' {
                  tailf:xpath-root 3;
                }
                description
                  "Minimum quality level value";
              }
              leaf max-quality-level-value {
                type dt1:ncs_rpc_notif_Fsync-ql-value;
                must '../quality-level-option and not(../exact-quality-level-value)' {
                  tailf:xpath-root 3;
                }
                description
                  "Maximum quality level value";
              }
            }
            container input-quality-level {
              description
                "Set the input quality level";
              leaf quality-level-option {
                type dt1:ncs_rpc_notif_Fsync-ql-option;
                must '../exact-quality-level-value or ../min-quality-level-value or ../max-quality-level-value or (../min-quality-level-value and ../max-quality-level-value)' {
                  tailf:xpath-root 3;
                }
                description
                  "Quality level option";
              }
              leaf exact-quality-level-value {
                type dt1:ncs_rpc_notif_Fsync-ql-value;
                must '../quality-level-option and not(../min-quality-level-value or ../max-quality-level-value)' {
                  tailf:xpath-root 3;
                }
                description
                  "Exact quality level value";
              }
              leaf min-quality-level-value {
                type dt1:ncs_rpc_notif_Fsync-ql-value;
                must '../quality-level-option and not(../exact-quality-level-value)' {
                  tailf:xpath-root 3;
                }
                description
                  "Minimum quality level value";
              }
              leaf max-quality-level-value {
                type dt1:ncs_rpc_notif_Fsync-ql-value;
                must '../quality-level-option and not(../exact-quality-level-value)' {
                  tailf:xpath-root 3;
                }
                description
                  "Maximum quality level value";
              }
            }
            leaf wait-to-restore-time {
              type uint32 {
                range "0..12";
              }
              default "5";
              description
                "Set the wait-to-restore time for this source";
            }
            leaf priority {
              type uint32 {
                range "1..254";
              }
              default "100";
              description
                "Set the priority of this source";
            }
            leaf selection-input {
              type empty;
              description
                "Assign this source as a selection input";
            }
            leaf time-of-day-priority {
              type uint32 {
                range "1..254";
              }
              default "100";
              description
                "Set the time-of-day priority of this source";
            }
            leaf ssm-disable {
              type empty;
              description
                "Disable SSM on this source";
            }
          }
          leaf clock-type {
            type dt1:ncs_rpc_notif_Fsync-clock;
            description
              "Clock type";
          }
          leaf port {
            type uint32;
            description
              "Clock port";
          }
        }
      }
    }
  }

  grouping live_ncs_NODE-CFG {
    description
      "active/preconfigured nodes configuration";
    container clock-interface {
      description
        "Configuration for a clock interface";
      container clocks {
        description
          "Configuration for a clock interface";
        list clock {
          key "clock-type port";
          description
            "Configuration for a clock interface";
          container frequency-synchronization {
            description
              "Frequency Synchronization clock configuraiton";
            container output-quality-level {
              description
                "Set the output quality level";
              leaf quality-level-option {
                type dt1:live_ncs_Fsync-ql-option;
                // NCS drop must statement
                description
                  "Quality level option";
              }
              leaf exact-quality-level-value {
                type dt1:live_ncs_Fsync-ql-value;
                // NCS drop must statement
                description
                  "Exact quality level value";
              }
              leaf min-quality-level-value {
                type dt1:live_ncs_Fsync-ql-value;
                // NCS drop must statement
                description
                  "Minimum quality level value";
              }
              leaf max-quality-level-value {
                type dt1:live_ncs_Fsync-ql-value;
                // NCS drop must statement
                description
                  "Maximum quality level value";
              }
            }
            container input-quality-level {
              description
                "Set the input quality level";
              leaf quality-level-option {
                type dt1:live_ncs_Fsync-ql-option;
                // NCS drop must statement
                description
                  "Quality level option";
              }
              leaf exact-quality-level-value {
                type dt1:live_ncs_Fsync-ql-value;
                // NCS drop must statement
                description
                  "Exact quality level value";
              }
              leaf min-quality-level-value {
                type dt1:live_ncs_Fsync-ql-value;
                // NCS drop must statement
                description
                  "Minimum quality level value";
              }
              leaf max-quality-level-value {
                type dt1:live_ncs_Fsync-ql-value;
                // NCS drop must statement
                description
                  "Maximum quality level value";
              }
            }
            leaf wait-to-restore-time {
              type uint32 {
                range "0..12";
              }
              // NCS drop default statement
              description
                "Set the wait-to-restore time for this source";
            }
            leaf priority {
              type uint32 {
                range "1..254";
              }
              // NCS drop default statement
              description
                "Set the priority of this source";
            }
            leaf selection-input {
              type empty;
              description
                "Assign this source as a selection input";
            }
            leaf time-of-day-priority {
              type uint32 {
                range "1..254";
              }
              // NCS drop default statement
              description
                "Set the time-of-day priority of this source";
            }
            leaf ssm-disable {
              type empty;
              description
                "Disable SSM on this source";
            }
          }
          leaf clock-type {
            type dt1:live_ncs_Fsync-clock;
            description
              "Clock type";
          }
          leaf port {
            type uint32;
            description
              "Clock port";
          }
        }
      }
    }
  }

  grouping NODE-CFG {
    description
      "active/preconfigured nodes configuration";
    container clock-interface {
      description
        "Configuration for a clock interface";
      container clocks {
        description
          "Configuration for a clock interface";
        list clock {
          key "clock-type port";
          description
            "Configuration for a clock interface";
          container frequency-synchronization {
            description
              "Frequency Synchronization clock configuraiton";
            container output-quality-level {
              description
                "Set the output quality level";
              leaf quality-level-option {
                type dt1:Fsync-ql-option;
                must '../exact-quality-level-value or ../min-quality-level-value or ../max-quality-level-value or (../min-quality-level-value and ../max-quality-level-value)' {
                  tailf:xpath-root 3;
                }
                description
                  "Quality level option";
              }
              leaf exact-quality-level-value {
                type dt1:Fsync-ql-value;
                must '../quality-level-option and not(../min-quality-level-value or ../max-quality-level-value)' {
                  tailf:xpath-root 3;
                }
                description
                  "Exact quality level value";
              }
              leaf min-quality-level-value {
                type dt1:Fsync-ql-value;
                must '../quality-level-option and not(../exact-quality-level-value)' {
                  tailf:xpath-root 3;
                }
                description
                  "Minimum quality level value";
              }
              leaf max-quality-level-value {
                type dt1:Fsync-ql-value;
                must '../quality-level-option and not(../exact-quality-level-value)' {
                  tailf:xpath-root 3;
                }
                description
                  "Maximum quality level value";
              }
            }
            container input-quality-level {
              description
                "Set the input quality level";
              leaf quality-level-option {
                type dt1:Fsync-ql-option;
                must '../exact-quality-level-value or ../min-quality-level-value or ../max-quality-level-value or (../min-quality-level-value and ../max-quality-level-value)' {
                  tailf:xpath-root 3;
                }
                description
                  "Quality level option";
              }
              leaf exact-quality-level-value {
                type dt1:Fsync-ql-value;
                must '../quality-level-option and not(../min-quality-level-value or ../max-quality-level-value)' {
                  tailf:xpath-root 3;
                }
                description
                  "Exact quality level value";
              }
              leaf min-quality-level-value {
                type dt1:Fsync-ql-value;
                must '../quality-level-option and not(../exact-quality-level-value)' {
                  tailf:xpath-root 3;
                }
                description
                  "Minimum quality level value";
              }
              leaf max-quality-level-value {
                type dt1:Fsync-ql-value;
                must '../quality-level-option and not(../exact-quality-level-value)' {
                  tailf:xpath-root 3;
                }
                description
                  "Maximum quality level value";
              }
            }
            leaf wait-to-restore-time {
              type uint32 {
                range "0..12";
              }
              default "5";
              description
                "Set the wait-to-restore time for this source";
            }
            leaf priority {
              type uint32 {
                range "1..254";
              }
              default "100";
              description
                "Set the priority of this source";
            }
            leaf selection-input {
              type empty;
              description
                "Assign this source as a selection input";
            }
            leaf time-of-day-priority {
              type uint32 {
                range "1..254";
              }
              default "100";
              description
                "Set the time-of-day priority of this source";
            }
            leaf ssm-disable {
              type empty;
              description
                "Disable SSM on this source";
            }
          }
          leaf clock-type {
            type dt1:Fsync-clock;
            description
              "Clock type";
          }
          leaf port {
            type uint32;
            description
              "Clock port";
          }
        }
      }
    }
  }

  augment "/ncs:devices/ncs:device/ncs:config" {
    container frequency-synchronization {
      tailf:ncs-device-type "netconf";
      tailf:display-when "not(../../ncs:module) or ../../ncs:module[ncs:name='Cisco-IOS-XR-freqsync-cfg']";
      presence "CLI submode compatibility.";
      description
        "Frequency Synchronization global configuration";
      leaf clock-identity {
        type yang:mac-address;
        description
          "Local clock ID";
      }
      leaf quality-level-option {
        type dt1:Fsync-ql-option;
        default "option-1";
        description
          "Quality level option";
      }
      leaf source-selection-logging {
        type Fsync-source-selection-logging;
        description
          "Source selection logging option";
      }
      leaf clock-interface-source-type {
        type Fsync-clock-source;
        description
          "Clock interface source type";
      }
      leaf system-timing-mode {
        type Fsync-system-timing-mode;
        description
          "System timing mode";
      }
    }
  }
  augment "/ncs:devices/ncs:device/ncs:live-status" {
    container frequency-synchronization {
      tailf:ncs-device-type "netconf";
      tailf:display-when "not(../../ncs:module) or ../../ncs:module[ncs:name='Cisco-IOS-XR-freqsync-cfg'] or (../../ncs:live-status-protocol[not(ncs:capability)]) or (../../ncs:live-status-protocol/ncs:capability/ncs:module[.='Cisco-IOS-XR-freqsync-cfg'])";
      presence "CLI submode compatibility.";
      description
        "Frequency Synchronization global configuration";
      leaf clock-identity {
        type yang:mac-address;
        description
          "Local clock ID";
      }
      leaf quality-level-option {
        type dt1:live_ncs_Fsync-ql-option;
        // NCS drop default statement
        description
          "Quality level option";
      }
      leaf source-selection-logging {
        type live_ncs_Fsync-source-selection-logging;
        description
          "Source selection logging option";
      }
      leaf clock-interface-source-type {
        type live_ncs_Fsync-clock-source;
        description
          "Clock interface source type";
      }
      leaf system-timing-mode {
        type live_ncs_Fsync-system-timing-mode;
        description
          "System timing mode";
      }
    }
  }
  augment "/ncs:devices/ncs:template/ncs:ned-id/ncs:config" {
    container frequency-synchronization {
      presence "CLI submode compatibility.";
      description
        "Frequency Synchronization global configuration";
      leaf clock-identity {
        type string;
        description
          "Local clock ID";
      }
      leaf quality-level-option {
        type dt1:ncs_template_Fsync-ql-option;
        // NCS drop default statement
        description
          "Quality level option";
      }
      leaf source-selection-logging {
        type ncs_template_Fsync-source-selection-logging;
        description
          "Source selection logging option";
      }
      leaf clock-interface-source-type {
        type ncs_template_Fsync-clock-source;
        description
          "Clock interface source type";
      }
      leaf system-timing-mode {
        type ncs_template_Fsync-system-timing-mode;
        description
          "System timing mode";
      }
    }
  }
  augment "/ncs:devices/ncs:template/ncs:ned-id/ncs:config/a2:interface-configurations/a2:interface-configuration" {
    description
      "This augment extends the configuration data of
       'Cisco-IOS-XR-ifmgr-cfg'";
    container frequency-synchronization {
      presence "CLI submode compatibility.";
      description
        "Frequency Synchronization interface
         configuration";
      container input-quality-level {
        description
          "Set the input quality level";
        leaf quality-level-option {
          type dt1:ncs_template_Fsync-ql-option;
          // NCS drop must statement
          description
            "Quality level option";
        }
        leaf exact-quality-level-value {
          type dt1:ncs_template_Fsync-ql-value;
          // NCS drop must statement
          description
            "Exact quality level value";
        }
        leaf min-quality-level-value {
          type dt1:ncs_template_Fsync-ql-value;
          // NCS drop must statement
          description
            "Minimum quality level value";
        }
        leaf max-quality-level-value {
          type dt1:ncs_template_Fsync-ql-value;
          // NCS drop must statement
          description
            "Maximum quality level value";
        }
      }
      container output-quality-level {
        description
          "Set the output quality level";
        leaf quality-level-option {
          type dt1:ncs_template_Fsync-ql-option;
          // NCS drop must statement
          description
            "Quality level option";
        }
        leaf exact-quality-level-value {
          type dt1:ncs_template_Fsync-ql-value;
          // NCS drop must statement
          description
            "Exact quality level value";
        }
        leaf min-quality-level-value {
          type dt1:ncs_template_Fsync-ql-value;
          // NCS drop must statement
          description
            "Minimum quality level value";
        }
        leaf max-quality-level-value {
          type dt1:ncs_template_Fsync-ql-value;
          // NCS drop must statement
          description
            "Maximum quality level value";
        }
      }
      leaf ssm-disable {
        type empty;
        description
          "Disable SSM on this source";
      }
      leaf time-of-day-priority {
        type string;
        // NCS drop default statement
        description
          "Set the time-of-day priority of this source";
      }
      leaf selection-input {
        type empty;
        description
          "Assign this source as a selection input";
      }
      leaf enable {
        type empty;
        description
          "Enable Frequency Synchronization";
      }
      leaf priority {
        type string;
        // NCS drop default statement
        description
          "Set the priority of this source";
      }
      leaf wait-to-restore-time {
        type string;
        // NCS drop default statement
        description
          "Set the wait-to-restore time for this source";
      }
    }
  }
  augment "/ncs:devices/ncs:device/ncs:live-status/a2:interface-configurations/a2:interface-configuration" {
    description
      "This augment extends the configuration data of
       'Cisco-IOS-XR-ifmgr-cfg'";
    container frequency-synchronization {
      tailf:ncs-device-type "netconf";
      tailf:display-when "not(../../../../ncs:module) or ../../../../ncs:module[ncs:name='Cisco-IOS-XR-freqsync-cfg'] or (../../../../ncs:live-status-protocol[not(ncs:capability)]) or (../../../../ncs:live-status-protocol/ncs:capability/ncs:module[.='Cisco-IOS-XR-freqsync-cfg'])";
      presence "CLI submode compatibility.";
      description
        "Frequency Synchronization interface
         configuration";
      container input-quality-level {
        description
          "Set the input quality level";
        leaf quality-level-option {
          type dt1:live_ncs_Fsync-ql-option;
          // NCS drop must statement
          description
            "Quality level option";
        }
        leaf exact-quality-level-value {
          type dt1:live_ncs_Fsync-ql-value;
          // NCS drop must statement
          description
            "Exact quality level value";
        }
        leaf min-quality-level-value {
          type dt1:live_ncs_Fsync-ql-value;
          // NCS drop must statement
          description
            "Minimum quality level value";
        }
        leaf max-quality-level-value {
          type dt1:live_ncs_Fsync-ql-value;
          // NCS drop must statement
          description
            "Maximum quality level value";
        }
      }
      container output-quality-level {
        description
          "Set the output quality level";
        leaf quality-level-option {
          type dt1:live_ncs_Fsync-ql-option;
          // NCS drop must statement
          description
            "Quality level option";
        }
        leaf exact-quality-level-value {
          type dt1:live_ncs_Fsync-ql-value;
          // NCS drop must statement
          description
            "Exact quality level value";
        }
        leaf min-quality-level-value {
          type dt1:live_ncs_Fsync-ql-value;
          // NCS drop must statement
          description
            "Minimum quality level value";
        }
        leaf max-quality-level-value {
          type dt1:live_ncs_Fsync-ql-value;
          // NCS drop must statement
          description
            "Maximum quality level value";
        }
      }
      leaf ssm-disable {
        type empty;
        description
          "Disable SSM on this source";
      }
      leaf time-of-day-priority {
        type uint32 {
          range "1..254";
        }
        // NCS drop default statement
        description
          "Set the time-of-day priority of this source";
      }
      leaf selection-input {
        type empty;
        description
          "Assign this source as a selection input";
      }
      leaf enable {
        type empty;
        description
          "Enable Frequency Synchronization";
      }
      leaf priority {
        type uint32 {
          range "1..254";
        }
        // NCS drop default statement
        description
          "Set the priority of this source";
      }
      leaf wait-to-restore-time {
        type uint32 {
          range "0..12";
        }
        // NCS drop default statement
        description
          "Set the wait-to-restore time for this source";
      }
    }
  }
  augment "/ncs:devices/ncs:device/ncs:config/a2:interface-configurations/a2:interface-configuration" {
    description
      "This augment extends the configuration data of
       'Cisco-IOS-XR-ifmgr-cfg'";
    container frequency-synchronization {
      tailf:ncs-device-type "netconf";
      tailf:display-when "not(../../../../ncs:module) or ../../../../ncs:module[ncs:name='Cisco-IOS-XR-freqsync-cfg']";
      presence "CLI submode compatibility.";
      description
        "Frequency Synchronization interface
         configuration";
      container input-quality-level {
        description
          "Set the input quality level";
        leaf quality-level-option {
          type dt1:Fsync-ql-option;
          must '../exact-quality-level-value or ../min-quality-level-value or ../max-quality-level-value or (../min-quality-level-value and ../max-quality-level-value)' {
            tailf:xpath-root 3;
          }
          description
            "Quality level option";
        }
        leaf exact-quality-level-value {
          type dt1:Fsync-ql-value;
          must '../quality-level-option and not(../min-quality-level-value or ../max-quality-level-value)' {
            tailf:xpath-root 3;
          }
          description
            "Exact quality level value";
        }
        leaf min-quality-level-value {
          type dt1:Fsync-ql-value;
          must '../quality-level-option and not(../exact-quality-level-value)' {
            tailf:xpath-root 3;
          }
          description
            "Minimum quality level value";
        }
        leaf max-quality-level-value {
          type dt1:Fsync-ql-value;
          must '../quality-level-option and not(../exact-quality-level-value)' {
            tailf:xpath-root 3;
          }
          description
            "Maximum quality level value";
        }
      }
      container output-quality-level {
        description
          "Set the output quality level";
        leaf quality-level-option {
          type dt1:Fsync-ql-option;
          must '../exact-quality-level-value or ../min-quality-level-value or ../max-quality-level-value or (../min-quality-level-value and ../max-quality-level-value)' {
            tailf:xpath-root 3;
          }
          description
            "Quality level option";
        }
        leaf exact-quality-level-value {
          type dt1:Fsync-ql-value;
          must '../quality-level-option and not(../min-quality-level-value or ../max-quality-level-value)' {
            tailf:xpath-root 3;
          }
          description
            "Exact quality level value";
        }
        leaf min-quality-level-value {
          type dt1:Fsync-ql-value;
          must '../quality-level-option and not(../exact-quality-level-value)' {
            tailf:xpath-root 3;
          }
          description
            "Minimum quality level value";
        }
        leaf max-quality-level-value {
          type dt1:Fsync-ql-value;
          must '../quality-level-option and not(../exact-quality-level-value)' {
            tailf:xpath-root 3;
          }
          description
            "Maximum quality level value";
        }
      }
      leaf ssm-disable {
        type empty;
        description
          "Disable SSM on this source";
      }
      leaf time-of-day-priority {
        type uint32 {
          range "1..254";
        }
        default "100";
        description
          "Set the time-of-day priority of this source";
      }
      leaf selection-input {
        type empty;
        description
          "Assign this source as a selection input";
      }
      leaf enable {
        type empty;
        description
          "Enable Frequency Synchronization";
      }
      leaf priority {
        type uint32 {
          range "1..254";
        }
        default "100";
        description
          "Set the priority of this source";
      }
      leaf wait-to-restore-time {
        type uint32 {
          range "0..12";
        }
        default "5";
        description
          "Set the wait-to-restore time for this source";
      }
    }
  }
  augment "/ncs:devices/ncs:template/ncs:ned-id/ncs:config/a1:snmp/a1:notification" {
    description
      "This augment extends the configuration data of
       'Cisco-IOS-XR-snmp-agent-cfg'";
    container frequency-synchronization {
      description
        "Frequency Synchronization trap configuration";
      leaf enable {
        type empty;
        description
          "Enable Frequency Synchronization traps";
      }
      leaf qlt {
        type ncs_template_Freq-sync-quality-level;
        description
          "Enable Frequency Synchronization QLT trap";
      }
    }
  }
  augment "/ncs:devices/ncs:device/ncs:live-status/a1:snmp/a1:notification" {
    description
      "This augment extends the configuration data of
       'Cisco-IOS-XR-snmp-agent-cfg'";
    container frequency-synchronization {
      tailf:ncs-device-type "netconf";
      tailf:display-when "not(../../../../ncs:module) or ../../../../ncs:module[ncs:name='Cisco-IOS-XR-freqsync-cfg'] or (../../../../ncs:live-status-protocol[not(ncs:capability)]) or (../../../../ncs:live-status-protocol/ncs:capability/ncs:module[.='Cisco-IOS-XR-freqsync-cfg'])";
      description
        "Frequency Synchronization trap configuration";
      leaf enable {
        type empty;
        description
          "Enable Frequency Synchronization traps";
      }
      leaf qlt {
        type live_ncs_Freq-sync-quality-level;
        description
          "Enable Frequency Synchronization QLT trap";
      }
    }
  }
  augment "/ncs:devices/ncs:device/ncs:config/a1:snmp/a1:notification" {
    description
      "This augment extends the configuration data of
       'Cisco-IOS-XR-snmp-agent-cfg'";
    container frequency-synchronization {
      tailf:ncs-device-type "netconf";
      tailf:display-when "not(../../../../ncs:module) or ../../../../ncs:module[ncs:name='Cisco-IOS-XR-freqsync-cfg']";
      description
        "Frequency Synchronization trap configuration";
      leaf enable {
        type empty;
        description
          "Enable Frequency Synchronization traps";
      }
      leaf qlt {
        type Freq-sync-quality-level;
        description
          "Enable Frequency Synchronization QLT trap";
      }
    }
  }
  augment "/ncs:devices/ncs:template/ncs:ned-id/ncs:config/node:active-nodes/node:active-node" {
    description
      "This augment extends active nodes configuration";
    uses ncs_template_NODE-CFG;
  }
  augment "/ncs:devices/ncs:device/ncs:live-status/node:active-nodes/node:active-node" {
    description
      "This augment extends active nodes configuration";
    uses live_ncs_NODE-CFG {
      refine clock-interface {
        tailf:ncs-device-type "netconf";
        tailf:display-when "not(../../../../ncs:module) or ../../../../ncs:module[ncs:name='Cisco-IOS-XR-freqsync-cfg'] or (../../../../ncs:live-status-protocol[not(ncs:capability)]) or (../../../../ncs:live-status-protocol/ncs:capability/ncs:module[.='Cisco-IOS-XR-freqsync-cfg'])";
      }
    }
  }
  augment "/ncs:devices/ncs:device/ncs:config/node:active-nodes/node:active-node" {
    description
      "This augment extends active nodes configuration";
    uses NODE-CFG {
      refine clock-interface {
        tailf:ncs-device-type "netconf";
        tailf:display-when "not(../../../../ncs:module) or ../../../../ncs:module[ncs:name='Cisco-IOS-XR-freqsync-cfg']";
      }
    }
  }
  augment "/ncs:devices/ncs:template/ncs:ned-id/ncs:config/node:preconfigured-nodes/node:preconfigured-node" {
    description
      "This augment extends preconfigured nodes
       configuration";
    uses ncs_template_NODE-CFG;
  }
  augment "/ncs:devices/ncs:device/ncs:live-status/node:preconfigured-nodes/node:preconfigured-node" {
    description
      "This augment extends preconfigured nodes
       configuration";
    uses live_ncs_NODE-CFG {
      refine clock-interface {
        tailf:ncs-device-type "netconf";
        tailf:display-when "not(../../../../ncs:module) or ../../../../ncs:module[ncs:name='Cisco-IOS-XR-freqsync-cfg'] or (../../../../ncs:live-status-protocol[not(ncs:capability)]) or (../../../../ncs:live-status-protocol/ncs:capability/ncs:module[.='Cisco-IOS-XR-freqsync-cfg'])";
      }
    }
  }
  augment "/ncs:devices/ncs:device/ncs:config/node:preconfigured-nodes/node:preconfigured-node" {
    description
      "This augment extends preconfigured nodes
       configuration";
    uses NODE-CFG {
      refine clock-interface {
        tailf:ncs-device-type "netconf";
        tailf:display-when "not(../../../../ncs:module) or ../../../../ncs:module[ncs:name='Cisco-IOS-XR-freqsync-cfg']";
      }
    }
  }
}

module Cisco-IOS-XR-lib-keychain-act {
  // Generated by yanger -t ncs
  tailf:mount-id "cisco-iosxr-nc-7.3:cisco-iosxr-nc-7.3";
  tailf:ncs-device-type "netconf";

  namespace "http://cisco.com/ns/yang/Cisco-IOS-XR-lib-keychain-act";
  prefix lib-keychain-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2017-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2017-04-17 {
    description
      "IOS XR 6.3.1 revision.";
  }

  grouping ncs_template_MASTER-KEY {
    description
      "Master Key";
    leaf old-key {
      type string;
      // NCS drop mandatory statement
      description
        "key already added/key to be replaced";
    }
    leaf new-key {
      type string;
      // NCS drop mandatory statement
      description
        "New master key to be added ";
    }
  }

  grouping ncs_rpc_notif_MASTER-KEY {
    description
      "Master Key";
    leaf old-key {
      type string;
      mandatory true;
      description
        "key already added/key to be replaced";
    }
    leaf new-key {
      type string;
      mandatory true;
      description
        "New master key to be added ";
    }
  }

  grouping live_ncs_MASTER-KEY {
    description
      "Master Key";
    leaf old-key {
      type string;
      // NCS drop mandatory statement
      description
        "key already added/key to be replaced";
    }
    leaf new-key {
      type string;
      // NCS drop mandatory statement
      description
        "New master key to be added ";
    }
  }

  grouping MASTER-KEY {
    description
      "Master Key";
    leaf old-key {
      type string;
      mandatory true;
      description
        "key already added/key to be replaced";
    }
    leaf new-key {
      type string;
      mandatory true;
      description
        "New master key to be added ";
    }
  }

  augment "/ncs:devices/ncs:device/ncs:rpc" {
    container rpc-master-key-update {
      tailf:ncs-device-type "netconf";
      tailf:display-when "not(../../ncs:module) or ../../ncs:module[ncs:name='Cisco-IOS-XR-lib-keychain-act']";
      tailf:action master-key-update {
        tailf:actionpoint ncsproxy {
          tailf:internal;
        }
        description
          "To update master key";
        input {
          uses ncs_rpc_notif_MASTER-KEY;
        }
      }
    }
  }
  augment "/ncs:devices/ncs:device-group/ncs:ned-id/ncs:rpc" {
    container rpc-master-key-update {
      tailf:ncs-device-type "netconf";
      tailf:display-when "/ncs:devices/ncs:device[ncs:name=current()/../../../ncs:member]/ncs:module[ncs:name='Cisco-IOS-XR-lib-keychain-act']";
      tailf:action master-key-update {
        tailf:actionpoint ncsproxy {
          tailf:internal;
        }
        description
          "To update master key";
        input {
          uses ncs_rpc_notif_MASTER-KEY;
        }
      }
    }
  }
  augment "/ncs:devices/ncs:device/ncs:rpc" {
    container rpc-master-key-delete {
      tailf:ncs-device-type "netconf";
      tailf:display-when "not(../../ncs:module) or ../../ncs:module[ncs:name='Cisco-IOS-XR-lib-keychain-act']";
      tailf:action master-key-delete {
        tailf:actionpoint ncsproxy {
          tailf:internal;
        }
        description
          "Remove Master key";
      }
    }
  }
  augment "/ncs:devices/ncs:device-group/ncs:ned-id/ncs:rpc" {
    container rpc-master-key-delete {
      tailf:ncs-device-type "netconf";
      tailf:display-when "/ncs:devices/ncs:device[ncs:name=current()/../../../ncs:member]/ncs:module[ncs:name='Cisco-IOS-XR-lib-keychain-act']";
      tailf:action master-key-delete {
        tailf:actionpoint ncsproxy {
          tailf:internal;
        }
        description
          "Remove Master key";
      }
    }
  }
  augment "/ncs:devices/ncs:device/ncs:rpc" {
    container rpc-master-key-add {
      tailf:ncs-device-type "netconf";
      tailf:display-when "not(../../ncs:module) or ../../ncs:module[ncs:name='Cisco-IOS-XR-lib-keychain-act']";
      tailf:action master-key-add {
        tailf:actionpoint ncsproxy {
          tailf:internal;
        }
        description
          "To add a new master key";
        input {
          leaf new-key {
            type string;
            description
              "New master key to be added";
          }
        }
      }
    }
  }
  augment "/ncs:devices/ncs:device-group/ncs:ned-id/ncs:rpc" {
    container rpc-master-key-add {
      tailf:ncs-device-type "netconf";
      tailf:display-when "/ncs:devices/ncs:device[ncs:name=current()/../../../ncs:member]/ncs:module[ncs:name='Cisco-IOS-XR-lib-keychain-act']";
      tailf:action master-key-add {
        tailf:actionpoint ncsproxy {
          tailf:internal;
        }
        description
          "To add a new master key";
        input {
          leaf new-key {
            type string;
            description
              "New master key to be added";
          }
        }
      }
    }
  }
}

module Cisco-IOS-XR-sysadmin-debug-trace {
  // Generated by yanger -t ncs
  tailf:mount-id "cisco-iosxr-nc-7.3:cisco-iosxr-nc-7.3";
  tailf:ncs-device-type "netconf";

  namespace "http://www.cisco.com/ns/yang/Cisco-IOS-XR-sysadmin-debug-trace";
  prefix debug_trace;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.
     This module contains definitions
     for the following management objects:
     debug_trace: Calvados debug trace.

     Copyright (c) 2015-2020, 2019-2020 by Cisco Systems, Inc.
     All rights reserved.";

  revision 2019-06-24 {
    description
      "PYANG error update with canonical order and revision update";
    semver:module-version "1.0.1";
  }
  revision 2019-04-15 {
    description
      "Establish semantic version baseline.";
    semver:module-version "1.0.1";
  }
  revision 2017-04-12 {
    description
      "Changed namespace and module name";
  }
  revision 2015-12-03 {
    description
      "Initial version.";
  }

  grouping ncs_template_config-debug-trace-group {
    container config {
      // NCS dropped explicit config true
      container debug {
        list trace {
          // NCS patched for predictable order
          ordered-by user;
          key "connection_type";
          // NCS drop max-elements statement
          leaf connection_type {
            type string;
          }
          choice trace-output {
            leaf enable {
              type empty;
            }
            leaf disable {
              type empty;
            }
          }
        }
      }
    }
  }

  grouping ncs_rpc_notif_config-debug-trace-group {
    container config {
      // NCS dropped explicit config true
      container debug {
        list trace {
          key "connection_type";
          max-elements 16;
          leaf connection_type {
            type string;
          }
          choice trace-output {
            leaf enable {
              type empty;
            }
            leaf disable {
              type empty;
            }
          }
        }
      }
    }
  }

  grouping live_ncs_config-debug-trace-group {
    container config {
      container debug {
        list trace {
          key "connection_type";
          // NCS drop max-elements statement
          leaf connection_type {
            type string;
          }
          choice trace-output {
            leaf enable {
              type empty;
            }
            leaf disable {
              type empty;
            }
          }
        }
      }
    }
  }

  grouping config-debug-trace-group {
    container config {
      // NCS dropped explicit config true
      container debug {
        list trace {
          key "connection_type";
          max-elements 16;
          leaf connection_type {
            type string;
          }
          choice trace-output {
            leaf enable {
              type empty;
            }
            leaf disable {
              type empty;
            }
          }
        }
      }
    }
  }

  augment "/ncs:devices/ncs:device/ncs:config" {
    uses config-debug-trace-group {
      refine config {
        tailf:ncs-device-type "netconf";
        tailf:display-when "not(../../ncs:module) or ../../ncs:module[ncs:name='Cisco-IOS-XR-sysadmin-debug-trace']";
      }
    }
  }
  augment "/ncs:devices/ncs:device/ncs:live-status" {
    uses live_ncs_config-debug-trace-group {
      refine config {
        tailf:ncs-device-type "netconf";
        tailf:display-when "not(../../ncs:module) or ../../ncs:module[ncs:name='Cisco-IOS-XR-sysadmin-debug-trace'] or (../../ncs:live-status-protocol[not(ncs:capability)]) or (../../ncs:live-status-protocol/ncs:capability/ncs:module[.='Cisco-IOS-XR-sysadmin-debug-trace'])";
      }
    }
  }
  augment "/ncs:devices/ncs:template/ncs:ned-id/ncs:config" {
    uses ncs_template_config-debug-trace-group;
  }
}

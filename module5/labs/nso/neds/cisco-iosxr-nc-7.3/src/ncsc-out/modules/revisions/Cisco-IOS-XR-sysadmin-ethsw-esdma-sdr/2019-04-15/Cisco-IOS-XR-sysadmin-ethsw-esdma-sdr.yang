module Cisco-IOS-XR-sysadmin-ethsw-esdma-sdr {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-sdr";
  prefix esdma_sdr;

  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch sdr' commands.

     Copyright (c) 2011-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2016-07-06 {
    description
      "Initial revision with content extracted from esdma_cli.yang.";
  }

  grouping ncs_template_sdr-detail-group {
    container sdr-detail {
      list sdr-id {
        // NCS patched for predictable order
        ordered-by user;
        key "sdr";
        leaf sdr {
          type esdma_types:ncs_template_esdma-sdr-id;
        }
        container port-statistics {
          list location {
            // NCS patched for predictable order
            ordered-by user;
            key "rack card switch-id";
            leaf rack {
              type esdma_types:ncs_template_esdma-rack-num-enum;
            }
            leaf card {
              type esdma_types:ncs_template_esdma-cpu;
              description
                "Card that owns a switch of interest";
            }
            leaf switch-id {
              type esdma_types:ncs_template_esdma-switch-type-enum;
              description
                "Switch type";
            }
            list port-iter {
              // NCS patched for predictable order
              ordered-by user;
              key "port";
              leaf port {
                type esdma_types:ncs_template_esdma-switch-port-type;
                description
                  "Switch port";
              }
              list traffic-type-id {
                // NCS patched for predictable order
                ordered-by user;
                key "traffic-type";
                leaf traffic-type {
                  type esdma_types:ncs_template_esdma-sdr-traffic-type;
                }
                list direction-id {
                  // NCS patched for predictable order
                  ordered-by user;
                  key "direction";
                  leaf direction {
                    type esdma_types:ncs_template_switch-data-direction-enum;
                    description
                      "Packet direction this rule applies to";
                  }
                  list traffic-class-id {
                    // NCS patched for predictable order
                    ordered-by user;
                    key "tc";
                    leaf tc {
                      type esdma_types:ncs_template_switch-traffic-class-enum;
                      description
                        "Traffic class (0->7) for these statistics.";
                    }
                    leaf green-packets {
                      type string;
                      description
                        "Counts packets within the committed information rate for a traffic class on this VLAN.";
                    }
                    leaf yellow-packets {
                      type string;
                      description
                        "Counts packets above the committed information rate, but within the excess information rate for a traffic class on this VLAN.";
                    }
                    leaf red-packets {
                      type string;
                      description
                        "Counts packets above the excess information rate for a traffic class on this VLAN. Generally, these packets are dropped.";
                    }
                  }
                }
              }
            }
          }
        }
      }
    }
  }

  grouping ncs_template_sdr-summary-port-stats {
    container port-statistics {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest to display the SDR configuration for";
        }
        leaf switch-id {
          type esdma_types:ncs_template_esdma-switch-type-enum;
          description
            "Switch type";
        }
        list port-iter {
          // NCS patched for predictable order
          ordered-by user;
          key "port";
          leaf port {
            type esdma_types:ncs_template_esdma-switch-port-type;
            description
              "Switch port";
          }
          list sdr-id {
            // NCS patched for predictable order
            ordered-by user;
            key "sdr";
            leaf sdr {
              type esdma_types:ncs_template_esdma-sdr-id;
            }
            leaf esd-sdr-name {
              type string;
            }
            list traffic-type-id {
              // NCS patched for predictable order
              ordered-by user;
              key "traffic-type";
              leaf traffic-type {
                type esdma_types:ncs_template_esdma-sdr-traffic-type;
              }
              list direction-id {
                // NCS patched for predictable order
                ordered-by user;
                key "direction";
                leaf direction {
                  type esdma_types:ncs_template_switch-data-direction-enum;
                  description
                    "Packet direction this rule applies to";
                }
                leaf green-packets {
                  type string;
                  description
                    "Counts packets within the committed information rate for all traffic classes on this SDR.";
                }
                leaf yellow-packets {
                  type string;
                  description
                    "Counts packets above the committed information rate, but within the excess information rate for all traffic classes on this SDR.";
                }
                leaf red-packets {
                  type string;
                  description
                    "Counts packets above the excess information rate for all traffic classes on this SDR. Generally, these packets are dropped.";
                }
              }
            }
          }
        }
      }
    }
  }

  grouping ncs_template_sdr-summary-global-stats {
    container global-statistics {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest to display the SDR configuration for";
        }
        leaf switch-id {
          type esdma_types:ncs_template_esdma-switch-type-enum;
          description
            "Switch type";
        }
        list sdr-id {
          // NCS patched for predictable order
          ordered-by user;
          key "sdr";
          leaf sdr {
            type esdma_types:ncs_template_esdma-sdr-id;
          }
          leaf esd-sdr-name {
            type string;
          }
          list traffic-type-id {
            // NCS patched for predictable order
            ordered-by user;
            key "traffic-type";
            leaf traffic-type {
              type esdma_types:ncs_template_esdma-sdr-traffic-type;
            }
            list traffic-class-id {
              // NCS patched for predictable order
              ordered-by user;
              key "tc";
              leaf tc {
                type esdma_types:ncs_template_switch-traffic-class-enum;
                description
                  "Traffic class (0->7) for these statistics.";
              }
              leaf green-packets {
                type string;
                description
                  "Counts packets within the committed information rate for a traffic class on this VLAN.";
              }
              leaf yellow-packets {
                type string;
                description
                  "Counts packets above the committed information rate, but within the excess information rate for a traffic class on this VLAN.";
              }
              leaf red-packets {
                type string;
                description
                  "Counts packets above the excess information rate for a traffic class on this VLAN. Generally, these packets are dropped.";
              }
            }
          }
        }
      }
    }
  }

  grouping ncs_template_sdr-summary-policers {
    container policers {
      list location {
        // NCS patched for predictable order
        ordered-by user;
        key "rack card switch-id";
        leaf rack {
          type esdma_types:ncs_template_esdma-rack-num-enum;
        }
        leaf card {
          type esdma_types:ncs_template_esdma-cpu;
        }
        leaf switch-id {
          type esdma_types:ncs_template_esdma-switch-type-enum;
        }
        container esd-policer-status {
          container indent-group {
            leaf esd-port-policing-enabled {
              type esdma_types:ncs_template_esdma-switch-yes-no-enum;
            }
            leaf esd-port-committed-burst-size {
              type string;
            }
            leaf esd-port-peak-burst-size {
              type string;
            }
            leaf esd-port-policer-mru {
              type string;
            }
            leaf esd-global-policing-enabled {
              type esdma_types:ncs_template_esdma-switch-yes-no-enum;
            }
            leaf esd-global-committed-burst-size {
              type string;
            }
            leaf esd-global-peak-burst-size {
              type string;
            }
            leaf esd-global-policer-mru {
              type string;
            }
          }
        }
        list sdr-id {
          // NCS patched for predictable order
          ordered-by user;
          key "sdr";
          leaf sdr {
            type esdma_types:ncs_template_esdma-sdr-id;
          }
          leaf esd-sdr-name {
            type string;
          }
          leaf esd-sdr-cir {
            type esdma_types:ncs_template_esd-percentage;
          }
          leaf esd-sdr-pir {
            type esdma_types:ncs_template_esd-percentage;
          }
          list esd-sdr-cos-type-iter {
            // NCS patched for predictable order
            ordered-by user;
            key "esd-sdr-cos-type";
            leaf esd-sdr-cos-type {
              type esdma_types:ncs_template_esd-cir-eir-type;
            }
            leaf esd-sdr-cos-0 {
              type esdma_types:ncs_template_esd-percentage;
            }
            leaf esd-sdr-cos-1 {
              type esdma_types:ncs_template_esd-percentage;
            }
            leaf esd-sdr-cos-2 {
              type esdma_types:ncs_template_esd-percentage;
            }
            leaf esd-sdr-cos-3 {
              type esdma_types:ncs_template_esd-percentage;
            }
            leaf esd-sdr-cos-4 {
              type esdma_types:ncs_template_esd-percentage;
            }
            leaf esd-sdr-cos-5 {
              type esdma_types:ncs_template_esd-percentage;
            }
            leaf esd-sdr-cos-6 {
              type esdma_types:ncs_template_esd-percentage;
            }
            leaf esd-sdr-cos-7 {
              type esdma_types:ncs_template_esd-percentage;
            }
          }
        }
      }
    }
  }

  grouping ncs_template_sdr-summary-group {
    uses ncs_template_sdr-summary-port-stats;
    uses ncs_template_sdr-summary-global-stats;
    uses ncs_template_sdr-summary-policers;
  }

  grouping ncs_template_switch-sdr-group {
    container sdr {
      uses ncs_template_sdr-detail-group;
      uses ncs_template_sdr-summary-group;
    }
  }

  grouping ncs_rpc_notif_sdr-detail-group {
    container sdr-detail {
      list sdr-id {
        key "sdr";
        leaf sdr {
          type esdma_types:ncs_rpc_notif_esdma-sdr-id;
        }
        container port-statistics {
          list location {
            key "rack card switch-id";
            leaf rack {
              type esdma_types:ncs_rpc_notif_esdma-rack-num-enum;
            }
            leaf card {
              type esdma_types:ncs_rpc_notif_esdma-cpu;
              description
                "Card that owns a switch of interest";
            }
            leaf switch-id {
              type esdma_types:ncs_rpc_notif_esdma-switch-type-enum;
              description
                "Switch type";
            }
            list port-iter {
              key "port";
              leaf port {
                type esdma_types:ncs_rpc_notif_esdma-switch-port-type;
                description
                  "Switch port";
              }
              list traffic-type-id {
                key "traffic-type";
                leaf traffic-type {
                  type esdma_types:ncs_rpc_notif_esdma-sdr-traffic-type;
                }
                list direction-id {
                  key "direction";
                  leaf direction {
                    type esdma_types:ncs_rpc_notif_switch-data-direction-enum;
                    description
                      "Packet direction this rule applies to";
                  }
                  list traffic-class-id {
                    key "tc";
                    leaf tc {
                      type esdma_types:ncs_rpc_notif_switch-traffic-class-enum;
                      description
                        "Traffic class (0->7) for these statistics.";
                    }
                    leaf green-packets {
                      type uint64;
                      description
                        "Counts packets within the committed information rate for a traffic class on this VLAN.";
                    }
                    leaf yellow-packets {
                      type uint64;
                      description
                        "Counts packets above the committed information rate, but within the excess information rate for a traffic class on this VLAN.";
                    }
                    leaf red-packets {
                      type uint64;
                      description
                        "Counts packets above the excess information rate for a traffic class on this VLAN. Generally, these packets are dropped.";
                    }
                  }
                }
              }
            }
          }
        }
      }
    }
  }

  grouping ncs_rpc_notif_sdr-summary-port-stats {
    container port-statistics {
      list location {
        key "rack card switch-id";
        leaf rack {
          type esdma_types:ncs_rpc_notif_esdma-rack-num-enum;
        }
        leaf card {
          type esdma_types:ncs_rpc_notif_esdma-cpu;
          description
            "Card that owns a switch of interest to display the SDR configuration for";
        }
        leaf switch-id {
          type esdma_types:ncs_rpc_notif_esdma-switch-type-enum;
          description
            "Switch type";
        }
        list port-iter {
          key "port";
          leaf port {
            type esdma_types:ncs_rpc_notif_esdma-switch-port-type;
            description
              "Switch port";
          }
          list sdr-id {
            key "sdr";
            leaf sdr {
              type esdma_types:ncs_rpc_notif_esdma-sdr-id;
            }
            leaf esd-sdr-name {
              type string;
            }
            list traffic-type-id {
              key "traffic-type";
              leaf traffic-type {
                type esdma_types:ncs_rpc_notif_esdma-sdr-traffic-type;
              }
              list direction-id {
                key "direction";
                leaf direction {
                  type esdma_types:ncs_rpc_notif_switch-data-direction-enum;
                  description
                    "Packet direction this rule applies to";
                }
                leaf green-packets {
                  type uint64;
                  description
                    "Counts packets within the committed information rate for all traffic classes on this SDR.";
                }
                leaf yellow-packets {
                  type uint64;
                  description
                    "Counts packets above the committed information rate, but within the excess information rate for all traffic classes on this SDR.";
                }
                leaf red-packets {
                  type uint64;
                  description
                    "Counts packets above the excess information rate for all traffic classes on this SDR. Generally, these packets are dropped.";
                }
              }
            }
          }
        }
      }
    }
  }

  grouping ncs_rpc_notif_sdr-summary-global-stats {
    container global-statistics {
      list location {
        key "rack card switch-id";
        leaf rack {
          type esdma_types:ncs_rpc_notif_esdma-rack-num-enum;
        }
        leaf card {
          type esdma_types:ncs_rpc_notif_esdma-cpu;
          description
            "Card that owns a switch of interest to display the SDR configuration for";
        }
        leaf switch-id {
          type esdma_types:ncs_rpc_notif_esdma-switch-type-enum;
          description
            "Switch type";
        }
        list sdr-id {
          key "sdr";
          leaf sdr {
            type esdma_types:ncs_rpc_notif_esdma-sdr-id;
          }
          leaf esd-sdr-name {
            type string;
          }
          list traffic-type-id {
            key "traffic-type";
            leaf traffic-type {
              type esdma_types:ncs_rpc_notif_esdma-sdr-traffic-type;
            }
            list traffic-class-id {
              key "tc";
              leaf tc {
                type esdma_types:ncs_rpc_notif_switch-traffic-class-enum;
                description
                  "Traffic class (0->7) for these statistics.";
              }
              leaf green-packets {
                type uint64;
                description
                  "Counts packets within the committed information rate for a traffic class on this VLAN.";
              }
              leaf yellow-packets {
                type uint64;
                description
                  "Counts packets above the committed information rate, but within the excess information rate for a traffic class on this VLAN.";
              }
              leaf red-packets {
                type uint64;
                description
                  "Counts packets above the excess information rate for a traffic class on this VLAN. Generally, these packets are dropped.";
              }
            }
          }
        }
      }
    }
  }

  grouping ncs_rpc_notif_sdr-summary-policers {
    container policers {
      list location {
        key "rack card switch-id";
        leaf rack {
          type esdma_types:ncs_rpc_notif_esdma-rack-num-enum;
        }
        leaf card {
          type esdma_types:ncs_rpc_notif_esdma-cpu;
        }
        leaf switch-id {
          type esdma_types:ncs_rpc_notif_esdma-switch-type-enum;
        }
        container esd-policer-status {
          container indent-group {
            leaf esd-port-policing-enabled {
              type esdma_types:ncs_rpc_notif_esdma-switch-yes-no-enum;
            }
            leaf esd-port-committed-burst-size {
              type uint32;
            }
            leaf esd-port-peak-burst-size {
              type uint32;
            }
            leaf esd-port-policer-mru {
              type uint32;
            }
            leaf esd-global-policing-enabled {
              type esdma_types:ncs_rpc_notif_esdma-switch-yes-no-enum;
            }
            leaf esd-global-committed-burst-size {
              type uint32;
            }
            leaf esd-global-peak-burst-size {
              type uint32;
            }
            leaf esd-global-policer-mru {
              type uint32;
            }
          }
        }
        list sdr-id {
          key "sdr";
          leaf sdr {
            type esdma_types:ncs_rpc_notif_esdma-sdr-id;
          }
          leaf esd-sdr-name {
            type string;
          }
          leaf esd-sdr-cir {
            type esdma_types:ncs_rpc_notif_esd-percentage;
          }
          leaf esd-sdr-pir {
            type esdma_types:ncs_rpc_notif_esd-percentage;
          }
          list esd-sdr-cos-type-iter {
            key "esd-sdr-cos-type";
            leaf esd-sdr-cos-type {
              type esdma_types:ncs_rpc_notif_esd-cir-eir-type;
            }
            leaf esd-sdr-cos-0 {
              type esdma_types:ncs_rpc_notif_esd-percentage;
            }
            leaf esd-sdr-cos-1 {
              type esdma_types:ncs_rpc_notif_esd-percentage;
            }
            leaf esd-sdr-cos-2 {
              type esdma_types:ncs_rpc_notif_esd-percentage;
            }
            leaf esd-sdr-cos-3 {
              type esdma_types:ncs_rpc_notif_esd-percentage;
            }
            leaf esd-sdr-cos-4 {
              type esdma_types:ncs_rpc_notif_esd-percentage;
            }
            leaf esd-sdr-cos-5 {
              type esdma_types:ncs_rpc_notif_esd-percentage;
            }
            leaf esd-sdr-cos-6 {
              type esdma_types:ncs_rpc_notif_esd-percentage;
            }
            leaf esd-sdr-cos-7 {
              type esdma_types:ncs_rpc_notif_esd-percentage;
            }
          }
        }
      }
    }
  }

  grouping ncs_rpc_notif_sdr-summary-group {
    uses ncs_rpc_notif_sdr-summary-port-stats;
    uses ncs_rpc_notif_sdr-summary-global-stats;
    uses ncs_rpc_notif_sdr-summary-policers;
  }

  grouping ncs_rpc_notif_switch-sdr-group {
    container sdr {
      uses ncs_rpc_notif_sdr-detail-group;
      uses ncs_rpc_notif_sdr-summary-group;
    }
  }

  grouping live_ncs_sdr-detail-group {
    container sdr-detail {
      list sdr-id {
        key "sdr";
        leaf sdr {
          type esdma_types:live_ncs_esdma-sdr-id;
        }
        container port-statistics {
          list location {
            key "rack card switch-id";
            leaf rack {
              type esdma_types:live_ncs_esdma-rack-num-enum;
            }
            leaf card {
              type esdma_types:live_ncs_esdma-cpu;
              description
                "Card that owns a switch of interest";
            }
            leaf switch-id {
              type esdma_types:live_ncs_esdma-switch-type-enum;
              description
                "Switch type";
            }
            list port-iter {
              key "port";
              leaf port {
                type esdma_types:live_ncs_esdma-switch-port-type;
                description
                  "Switch port";
              }
              list traffic-type-id {
                key "traffic-type";
                leaf traffic-type {
                  type esdma_types:live_ncs_esdma-sdr-traffic-type;
                }
                list direction-id {
                  key "direction";
                  leaf direction {
                    type esdma_types:live_ncs_switch-data-direction-enum;
                    description
                      "Packet direction this rule applies to";
                  }
                  list traffic-class-id {
                    key "tc";
                    leaf tc {
                      type esdma_types:live_ncs_switch-traffic-class-enum;
                      description
                        "Traffic class (0->7) for these statistics.";
                    }
                    leaf green-packets {
                      type uint64;
                      description
                        "Counts packets within the committed information rate for a traffic class on this VLAN.";
                    }
                    leaf yellow-packets {
                      type uint64;
                      description
                        "Counts packets above the committed information rate, but within the excess information rate for a traffic class on this VLAN.";
                    }
                    leaf red-packets {
                      type uint64;
                      description
                        "Counts packets above the excess information rate for a traffic class on this VLAN. Generally, these packets are dropped.";
                    }
                  }
                }
              }
            }
          }
        }
      }
    }
  }

  grouping live_ncs_sdr-summary-port-stats {
    container port-statistics {
      list location {
        key "rack card switch-id";
        leaf rack {
          type esdma_types:live_ncs_esdma-rack-num-enum;
        }
        leaf card {
          type esdma_types:live_ncs_esdma-cpu;
          description
            "Card that owns a switch of interest to display the SDR configuration for";
        }
        leaf switch-id {
          type esdma_types:live_ncs_esdma-switch-type-enum;
          description
            "Switch type";
        }
        list port-iter {
          key "port";
          leaf port {
            type esdma_types:live_ncs_esdma-switch-port-type;
            description
              "Switch port";
          }
          list sdr-id {
            key "sdr";
            leaf sdr {
              type esdma_types:live_ncs_esdma-sdr-id;
            }
            leaf esd-sdr-name {
              type string;
            }
            list traffic-type-id {
              key "traffic-type";
              leaf traffic-type {
                type esdma_types:live_ncs_esdma-sdr-traffic-type;
              }
              list direction-id {
                key "direction";
                leaf direction {
                  type esdma_types:live_ncs_switch-data-direction-enum;
                  description
                    "Packet direction this rule applies to";
                }
                leaf green-packets {
                  type uint64;
                  description
                    "Counts packets within the committed information rate for all traffic classes on this SDR.";
                }
                leaf yellow-packets {
                  type uint64;
                  description
                    "Counts packets above the committed information rate, but within the excess information rate for all traffic classes on this SDR.";
                }
                leaf red-packets {
                  type uint64;
                  description
                    "Counts packets above the excess information rate for all traffic classes on this SDR. Generally, these packets are dropped.";
                }
              }
            }
          }
        }
      }
    }
  }

  grouping live_ncs_sdr-summary-global-stats {
    container global-statistics {
      list location {
        key "rack card switch-id";
        leaf rack {
          type esdma_types:live_ncs_esdma-rack-num-enum;
        }
        leaf card {
          type esdma_types:live_ncs_esdma-cpu;
          description
            "Card that owns a switch of interest to display the SDR configuration for";
        }
        leaf switch-id {
          type esdma_types:live_ncs_esdma-switch-type-enum;
          description
            "Switch type";
        }
        list sdr-id {
          key "sdr";
          leaf sdr {
            type esdma_types:live_ncs_esdma-sdr-id;
          }
          leaf esd-sdr-name {
            type string;
          }
          list traffic-type-id {
            key "traffic-type";
            leaf traffic-type {
              type esdma_types:live_ncs_esdma-sdr-traffic-type;
            }
            list traffic-class-id {
              key "tc";
              leaf tc {
                type esdma_types:live_ncs_switch-traffic-class-enum;
                description
                  "Traffic class (0->7) for these statistics.";
              }
              leaf green-packets {
                type uint64;
                description
                  "Counts packets within the committed information rate for a traffic class on this VLAN.";
              }
              leaf yellow-packets {
                type uint64;
                description
                  "Counts packets above the committed information rate, but within the excess information rate for a traffic class on this VLAN.";
              }
              leaf red-packets {
                type uint64;
                description
                  "Counts packets above the excess information rate for a traffic class on this VLAN. Generally, these packets are dropped.";
              }
            }
          }
        }
      }
    }
  }

  grouping live_ncs_sdr-summary-policers {
    container policers {
      list location {
        key "rack card switch-id";
        leaf rack {
          type esdma_types:live_ncs_esdma-rack-num-enum;
        }
        leaf card {
          type esdma_types:live_ncs_esdma-cpu;
        }
        leaf switch-id {
          type esdma_types:live_ncs_esdma-switch-type-enum;
        }
        container esd-policer-status {
          container indent-group {
            leaf esd-port-policing-enabled {
              type esdma_types:live_ncs_esdma-switch-yes-no-enum;
            }
            leaf esd-port-committed-burst-size {
              type uint32;
            }
            leaf esd-port-peak-burst-size {
              type uint32;
            }
            leaf esd-port-policer-mru {
              type uint32;
            }
            leaf esd-global-policing-enabled {
              type esdma_types:live_ncs_esdma-switch-yes-no-enum;
            }
            leaf esd-global-committed-burst-size {
              type uint32;
            }
            leaf esd-global-peak-burst-size {
              type uint32;
            }
            leaf esd-global-policer-mru {
              type uint32;
            }
          }
        }
        list sdr-id {
          key "sdr";
          leaf sdr {
            type esdma_types:live_ncs_esdma-sdr-id;
          }
          leaf esd-sdr-name {
            type string;
          }
          leaf esd-sdr-cir {
            type esdma_types:live_ncs_esd-percentage;
          }
          leaf esd-sdr-pir {
            type esdma_types:live_ncs_esd-percentage;
          }
          list esd-sdr-cos-type-iter {
            key "esd-sdr-cos-type";
            leaf esd-sdr-cos-type {
              type esdma_types:live_ncs_esd-cir-eir-type;
            }
            leaf esd-sdr-cos-0 {
              type esdma_types:live_ncs_esd-percentage;
            }
            leaf esd-sdr-cos-1 {
              type esdma_types:live_ncs_esd-percentage;
            }
            leaf esd-sdr-cos-2 {
              type esdma_types:live_ncs_esd-percentage;
            }
            leaf esd-sdr-cos-3 {
              type esdma_types:live_ncs_esd-percentage;
            }
            leaf esd-sdr-cos-4 {
              type esdma_types:live_ncs_esd-percentage;
            }
            leaf esd-sdr-cos-5 {
              type esdma_types:live_ncs_esd-percentage;
            }
            leaf esd-sdr-cos-6 {
              type esdma_types:live_ncs_esd-percentage;
            }
            leaf esd-sdr-cos-7 {
              type esdma_types:live_ncs_esd-percentage;
            }
          }
        }
      }
    }
  }

  grouping live_ncs_sdr-summary-group {
    uses live_ncs_sdr-summary-port-stats;
    uses live_ncs_sdr-summary-global-stats;
    uses live_ncs_sdr-summary-policers;
  }

  grouping live_ncs_switch-sdr-group {
    container sdr {
      uses live_ncs_sdr-detail-group;
      uses live_ncs_sdr-summary-group;
    }
  }

  grouping sdr-detail-group {
    container sdr-detail {
      list sdr-id {
        key "sdr";
        leaf sdr {
          type esdma_types:esdma-sdr-id;
        }
        container port-statistics {
          list location {
            key "rack card switch-id";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              leaf port {
                type esdma_types:esdma-switch-port-type;
                description
                  "Switch port";
              }
              list traffic-type-id {
                key "traffic-type";
                leaf traffic-type {
                  type esdma_types:esdma-sdr-traffic-type;
                }
                list direction-id {
                  key "direction";
                  leaf direction {
                    type esdma_types:switch-data-direction-enum;
                    description
                      "Packet direction this rule applies to";
                  }
                  list traffic-class-id {
                    key "tc";
                    leaf tc {
                      type esdma_types:switch-traffic-class-enum;
                      description
                        "Traffic class (0->7) for these statistics.";
                    }
                    leaf green-packets {
                      type uint64;
                      description
                        "Counts packets within the committed information rate for a traffic class on this VLAN.";
                    }
                    leaf yellow-packets {
                      type uint64;
                      description
                        "Counts packets above the committed information rate, but within the excess information rate for a traffic class on this VLAN.";
                    }
                    leaf red-packets {
                      type uint64;
                      description
                        "Counts packets above the excess information rate for a traffic class on this VLAN. Generally, these packets are dropped.";
                    }
                  }
                }
              }
            }
          }
        }
      }
    }
  }

  grouping sdr-summary-port-stats {
    container port-statistics {
      list location {
        key "rack card switch-id";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list port-iter {
          key "port";
          leaf port {
            type esdma_types:esdma-switch-port-type;
            description
              "Switch port";
          }
          list sdr-id {
            key "sdr";
            leaf sdr {
              type esdma_types:esdma-sdr-id;
            }
            leaf esd-sdr-name {
              type string;
            }
            list traffic-type-id {
              key "traffic-type";
              leaf traffic-type {
                type esdma_types:esdma-sdr-traffic-type;
              }
              list direction-id {
                key "direction";
                leaf direction {
                  type esdma_types:switch-data-direction-enum;
                  description
                    "Packet direction this rule applies to";
                }
                leaf green-packets {
                  type uint64;
                  description
                    "Counts packets within the committed information rate for all traffic classes on this SDR.";
                }
                leaf yellow-packets {
                  type uint64;
                  description
                    "Counts packets above the committed information rate, but within the excess information rate for all traffic classes on this SDR.";
                }
                leaf red-packets {
                  type uint64;
                  description
                    "Counts packets above the excess information rate for all traffic classes on this SDR. Generally, these packets are dropped.";
                }
              }
            }
          }
        }
      }
    }
  }

  grouping sdr-summary-global-stats {
    container global-statistics {
      list location {
        key "rack card switch-id";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list sdr-id {
          key "sdr";
          leaf sdr {
            type esdma_types:esdma-sdr-id;
          }
          leaf esd-sdr-name {
            type string;
          }
          list traffic-type-id {
            key "traffic-type";
            leaf traffic-type {
              type esdma_types:esdma-sdr-traffic-type;
            }
            list traffic-class-id {
              key "tc";
              leaf tc {
                type esdma_types:switch-traffic-class-enum;
                description
                  "Traffic class (0->7) for these statistics.";
              }
              leaf green-packets {
                type uint64;
                description
                  "Counts packets within the committed information rate for a traffic class on this VLAN.";
              }
              leaf yellow-packets {
                type uint64;
                description
                  "Counts packets above the committed information rate, but within the excess information rate for a traffic class on this VLAN.";
              }
              leaf red-packets {
                type uint64;
                description
                  "Counts packets above the excess information rate for a traffic class on this VLAN. Generally, these packets are dropped.";
              }
            }
          }
        }
      }
    }
  }

  grouping sdr-summary-policers {
    container policers {
      list location {
        key "rack card switch-id";
        leaf rack {
          type esdma_types:esdma-rack-num-enum;
        }
        leaf card {
          type esdma_types:esdma-cpu;
        }
        leaf switch-id {
          type esdma_types:esdma-switch-type-enum;
        }
        container esd-policer-status {
          container indent-group {
            leaf esd-port-policing-enabled {
              type esdma_types:esdma-switch-yes-no-enum;
            }
            leaf esd-port-committed-burst-size {
              type uint32;
            }
            leaf esd-port-peak-burst-size {
              type uint32;
            }
            leaf esd-port-policer-mru {
              type uint32;
            }
            leaf esd-global-policing-enabled {
              type esdma_types:esdma-switch-yes-no-enum;
            }
            leaf esd-global-committed-burst-size {
              type uint32;
            }
            leaf esd-global-peak-burst-size {
              type uint32;
            }
            leaf esd-global-policer-mru {
              type uint32;
            }
          }
        }
        list sdr-id {
          key "sdr";
          leaf sdr {
            type esdma_types:esdma-sdr-id;
          }
          leaf esd-sdr-name {
            type string;
          }
          leaf esd-sdr-cir {
            type esdma_types:esd-percentage;
          }
          leaf esd-sdr-pir {
            type esdma_types:esd-percentage;
          }
          list esd-sdr-cos-type-iter {
            key "esd-sdr-cos-type";
            leaf esd-sdr-cos-type {
              type esdma_types:esd-cir-eir-type;
            }
            leaf esd-sdr-cos-0 {
              type esdma_types:esd-percentage;
            }
            leaf esd-sdr-cos-1 {
              type esdma_types:esd-percentage;
            }
            leaf esd-sdr-cos-2 {
              type esdma_types:esd-percentage;
            }
            leaf esd-sdr-cos-3 {
              type esdma_types:esd-percentage;
            }
            leaf esd-sdr-cos-4 {
              type esdma_types:esd-percentage;
            }
            leaf esd-sdr-cos-5 {
              type esdma_types:esd-percentage;
            }
            leaf esd-sdr-cos-6 {
              type esdma_types:esd-percentage;
            }
            leaf esd-sdr-cos-7 {
              type esdma_types:esd-percentage;
            }
          }
        }
      }
    }
  }

  grouping sdr-summary-group {
    uses sdr-summary-port-stats;
    uses sdr-summary-global-stats;
    uses sdr-summary-policers;
  }

  grouping switch-sdr-group {
    container sdr {
      uses sdr-detail-group;
      uses sdr-summary-group;
    }
  }
}

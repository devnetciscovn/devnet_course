module Cisco-IOS-XR-linux-xlnc-oper {
  // Generated by yanger -t ncs
  tailf:mount-id "cisco-iosxr-nc-7.3:cisco-iosxr-nc-7.3";
  tailf:ncs-device-type "netconf";

  namespace "http://cisco.com/ns/yang/Cisco-IOS-XR-linux-xlnc-oper";
  prefix linux-xlnc-oper;

  import Cisco-IOS-XR-types {
    prefix xr;
  }
  import cisco-semver {
    prefix semver;
  }
  include Cisco-IOS-XR-linux-xlnc-oper-sub1 {
    revision-date 2020-06-22;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-xlnc package operational data.

     This module contains definitions
     for the following management objects:
       linux-networking: Linux Networking operational data

     Copyright (c) 2013-2020 by Cisco Systems, Inc.
     All rights reserved.";

  revision 2020-06-22 {
    description
      "Added address-only interface types and corresponding inconsistencies";
    semver:module-version "1.2.0";
  }
  revision 2019-04-05 {
    description
      "Establish semantic version baseline.";
    semver:module-version "1.1.0";
  }
  revision 2015-11-09 {
    description
      "IOS XR 6.0 revision.";
  }

  augment "/ncs:devices/ncs:device/ncs:config" {
    // NCS drop config false container 'linux-networking'
  }
  augment "/ncs:devices/ncs:device/ncs:live-status" {
    container linux-networking {
      tailf:ncs-device-type "netconf";
      tailf:display-when "not(../../ncs:module) or ../../ncs:module[ncs:name='Cisco-IOS-XR-linux-xlnc-oper'] or (../../ncs:live-status-protocol[not(ncs:capability)]) or (../../ncs:live-status-protocol/ncs:capability/ncs:module[.='Cisco-IOS-XR-linux-xlnc-oper'])";
      description
        "Linux Networking operational data";
      container global {
        description
          "Global operational data";
        container interfaces {
          description
            "Linux Networking interface information";
          container address-only-interfaces {
            description
              "Interfaces with addresses addeded to a Linux
               Loopback";
            list address-only-interface {
              key "vrf-name interface-name";
              description
                "Interface with an IP address added to a Linux
                 Loopback";
              leaf vrf-name {
                type xr:live_ncs_Cisco-ios-xr-string;
                description
                  "VRF name";
              }
              leaf interface-name {
                type xr:live_ncs_Interface-name;
                description
                  "Interface name";
              }
              uses live_ncs_XLNC-BAG-INTERFACE-ADDRESS-ONLY;
            }
          }
        }
        container status {
          description
            "Linux Networking operational status";
          container inconsistencies-per-vrfs {
            description
              "Global inconsistencies table";
            list inconsistencies-per-vrf {
              key "vrf-name";
              description
                "Inconsistencies observed for a particular VRF
                 .";
              leaf vrf-name {
                type xr:live_ncs_Cisco-ios-xr-string;
                description
                  "VRF name";
              }
              uses live_ncs_XLNC-BAG-VRF-INCONSISTENCIES;
            }
          }
          container inconsistencies-per-interfaces {
            description
              "Global inconsistencies table";
            list inconsistencies-per-interface {
              key "interface-name";
              description
                "Inconsistencies observed for a particular
                 interface.";
              leaf interface-name {
                type xr:live_ncs_Interface-name;
                description
                  "Interface name";
              }
              uses live_ncs_XLNC-BAG-INTERFACE-INCONSISTENCIES;
            }
          }
        }
      }
    }
  }
  augment "/ncs:devices/ncs:template/ncs:ned-id/ncs:config" {
    // NCS drop config false container 'linux-networking'
  }
}

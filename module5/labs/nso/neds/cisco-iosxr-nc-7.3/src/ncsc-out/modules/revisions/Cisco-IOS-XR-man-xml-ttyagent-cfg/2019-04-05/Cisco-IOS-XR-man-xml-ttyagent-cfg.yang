module Cisco-IOS-XR-man-xml-ttyagent-cfg {
  // Generated by yanger -t ncs
  tailf:mount-id "cisco-iosxr-nc-7.3:cisco-iosxr-nc-7.3";
  tailf:ncs-device-type "netconf";

  namespace "http://cisco.com/ns/yang/Cisco-IOS-XR-man-xml-ttyagent-cfg";
  prefix man-xml-ttyagent-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-xml-ttyagent package configuration.

     This module contains definitions
     for the following management objects:
       xr-xml: XML
       netconf: NETCONF

     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-07-30 {
    description
      "Descriptions updated.";
  }
  revision 2015-01-07 {
    description
      "IOS XR 5.3.1 revision.";
  }

  grouping ncs_template_SESSION {
    description
      "Common node of default, ssl, tty";
    container session {
      description
        "Session attributes";
      leaf timeout {
        type string;
        units "minute";
        description
          "Timeout in minutes";
      }
    }
  }

  grouping ncs_template_VRF-TABLE {
    description
      "Common node of default, ssl";
    container vrfs {
      description
        "List of VRFs";
      list vrf {
        // NCS patched for predictable order
        ordered-by user;
        key "vrf-name";
        description
          "A specific VRF";
        leaf ipv6-access-list {
          type xr:ncs_template_Cisco-ios-xr-string;
          description
            "IPv6 Transport Access list for VRF";
        }
        leaf ipv4-access-list {
          type xr:ncs_template_Cisco-ios-xr-string;
          description
            "IPv4 Transport Access list for VRF";
        }
        leaf access-list {
          type xr:ncs_template_Cisco-ios-xr-string;
          description
            "Access list for XML agent";
        }
        leaf shutdown {
          type empty;
          description
            "Shutdown default VRF. This is applicable only
             for VRF default.";
        }
        leaf vrf-name {
          type xr:ncs_template_Cisco-ios-xr-string;
          description
            "VRF name";
        }
      }
    }
  }

  grouping ncs_template_ITERATION-SIZE {
    description
      "Common node of default, ssl, tty";
    leaf iteration-size {
      type string;
      units "kilobyte";
      // NCS drop default statement
      description
        "Iterator size, in KBytes, of the XML response.
         Specify 0 to turn off the XML response iterator.";
    }
  }

  grouping ncs_template_STREAMING-SIZE {
    description
      "Common node of default, ssl, tty";
    leaf streaming-size {
      type string;
      units "kilobyte";
      description
        "Streaming size, in KBytes, of the XML response.";
    }
  }

  grouping ncs_template_THROTTLE {
    description
      "Common node of default, ssl, tty";
    container throttle {
      description
        "XML agent throttling";
      leaf process-rate {
        type string;
        description
          "Process rate in number of XML tags per second";
      }
      leaf memory {
        type string;
        units "megabyte";
        // NCS drop default statement
        description
          "Size of memory usage, in MBytes, per session.";
      }
    }
  }

  grouping ncs_template_ENABLE {
    description
      "Common node of default, ssl, tty";
    leaf enable {
      type empty;
      description
        "Enable specified XML agent";
    }
  }

  grouping ncs_rpc_notif_SESSION {
    description
      "Common node of default, ssl, tty";
    container session {
      description
        "Session attributes";
      leaf timeout {
        type uint32 {
          range "1..1440";
        }
        units "minute";
        description
          "Timeout in minutes";
      }
    }
  }

  grouping ncs_rpc_notif_VRF-TABLE {
    description
      "Common node of default, ssl";
    container vrfs {
      description
        "List of VRFs";
      list vrf {
        key "vrf-name";
        description
          "A specific VRF";
        leaf ipv6-access-list {
          type xr:ncs_rpc_notif_Cisco-ios-xr-string;
          description
            "IPv6 Transport Access list for VRF";
        }
        leaf ipv4-access-list {
          type xr:ncs_rpc_notif_Cisco-ios-xr-string;
          description
            "IPv4 Transport Access list for VRF";
        }
        leaf access-list {
          type xr:ncs_rpc_notif_Cisco-ios-xr-string;
          description
            "Access list for XML agent";
        }
        leaf shutdown {
          type empty;
          description
            "Shutdown default VRF. This is applicable only
             for VRF default.";
        }
        leaf vrf-name {
          type xr:ncs_rpc_notif_Cisco-ios-xr-string;
          description
            "VRF name";
        }
      }
    }
  }

  grouping ncs_rpc_notif_ITERATION-SIZE {
    description
      "Common node of default, ssl, tty";
    leaf iteration-size {
      type uint32 {
        range "0..100000";
      }
      units "kilobyte";
      default "48";
      description
        "Iterator size, in KBytes, of the XML response.
         Specify 0 to turn off the XML response iterator.";
    }
  }

  grouping ncs_rpc_notif_STREAMING-SIZE {
    description
      "Common node of default, ssl, tty";
    leaf streaming-size {
      type uint32 {
        range "1..100000";
      }
      units "kilobyte";
      description
        "Streaming size, in KBytes, of the XML response.";
    }
  }

  grouping ncs_rpc_notif_THROTTLE {
    description
      "Common node of default, ssl, tty";
    container throttle {
      description
        "XML agent throttling";
      leaf process-rate {
        type uint32 {
          range "1000..30000";
        }
        description
          "Process rate in number of XML tags per second";
      }
      leaf memory {
        type uint32 {
          range "100..1024";
        }
        units "megabyte";
        default "300";
        description
          "Size of memory usage, in MBytes, per session.";
      }
    }
  }

  grouping ncs_rpc_notif_ENABLE {
    description
      "Common node of default, ssl, tty";
    leaf enable {
      type empty;
      description
        "Enable specified XML agent";
    }
  }

  grouping live_ncs_SESSION {
    description
      "Common node of default, ssl, tty";
    container session {
      description
        "Session attributes";
      leaf timeout {
        type uint32 {
          range "1..1440";
        }
        units "minute";
        description
          "Timeout in minutes";
      }
    }
  }

  grouping live_ncs_VRF-TABLE {
    description
      "Common node of default, ssl";
    container vrfs {
      description
        "List of VRFs";
      list vrf {
        key "vrf-name";
        description
          "A specific VRF";
        leaf ipv6-access-list {
          type xr:live_ncs_Cisco-ios-xr-string;
          description
            "IPv6 Transport Access list for VRF";
        }
        leaf ipv4-access-list {
          type xr:live_ncs_Cisco-ios-xr-string;
          description
            "IPv4 Transport Access list for VRF";
        }
        leaf access-list {
          type xr:live_ncs_Cisco-ios-xr-string;
          description
            "Access list for XML agent";
        }
        leaf shutdown {
          type empty;
          description
            "Shutdown default VRF. This is applicable only
             for VRF default.";
        }
        leaf vrf-name {
          type xr:live_ncs_Cisco-ios-xr-string;
          description
            "VRF name";
        }
      }
    }
  }

  grouping live_ncs_ITERATION-SIZE {
    description
      "Common node of default, ssl, tty";
    leaf iteration-size {
      type uint32 {
        range "0..100000";
      }
      units "kilobyte";
      // NCS drop default statement
      description
        "Iterator size, in KBytes, of the XML response.
         Specify 0 to turn off the XML response iterator.";
    }
  }

  grouping live_ncs_STREAMING-SIZE {
    description
      "Common node of default, ssl, tty";
    leaf streaming-size {
      type uint32 {
        range "1..100000";
      }
      units "kilobyte";
      description
        "Streaming size, in KBytes, of the XML response.";
    }
  }

  grouping live_ncs_THROTTLE {
    description
      "Common node of default, ssl, tty";
    container throttle {
      description
        "XML agent throttling";
      leaf process-rate {
        type uint32 {
          range "1000..30000";
        }
        description
          "Process rate in number of XML tags per second";
      }
      leaf memory {
        type uint32 {
          range "100..1024";
        }
        units "megabyte";
        // NCS drop default statement
        description
          "Size of memory usage, in MBytes, per session.";
      }
    }
  }

  grouping live_ncs_ENABLE {
    description
      "Common node of default, ssl, tty";
    leaf enable {
      type empty;
      description
        "Enable specified XML agent";
    }
  }

  grouping SESSION {
    description
      "Common node of default, ssl, tty";
    container session {
      description
        "Session attributes";
      leaf timeout {
        type uint32 {
          range "1..1440";
        }
        units "minute";
        description
          "Timeout in minutes";
      }
    }
  }

  grouping VRF-TABLE {
    description
      "Common node of default, ssl";
    container vrfs {
      description
        "List of VRFs";
      list vrf {
        key "vrf-name";
        description
          "A specific VRF";
        leaf ipv6-access-list {
          type xr:Cisco-ios-xr-string {
            length "1..32";
          }
          description
            "IPv6 Transport Access list for VRF";
        }
        leaf ipv4-access-list {
          type xr:Cisco-ios-xr-string {
            length "1..32";
          }
          description
            "IPv4 Transport Access list for VRF";
        }
        leaf access-list {
          type xr:Cisco-ios-xr-string {
            length "1..32";
          }
          description
            "Access list for XML agent";
        }
        leaf shutdown {
          type empty;
          description
            "Shutdown default VRF. This is applicable only
             for VRF default.";
        }
        leaf vrf-name {
          type xr:Cisco-ios-xr-string {
            length "1..32";
          }
          description
            "VRF name";
        }
      }
    }
  }

  grouping ITERATION-SIZE {
    description
      "Common node of default, ssl, tty";
    leaf iteration-size {
      type uint32 {
        range "0..100000";
      }
      units "kilobyte";
      default "48";
      description
        "Iterator size, in KBytes, of the XML response.
         Specify 0 to turn off the XML response iterator.";
    }
  }

  grouping STREAMING-SIZE {
    description
      "Common node of default, ssl, tty";
    leaf streaming-size {
      type uint32 {
        range "1..100000";
      }
      units "kilobyte";
      description
        "Streaming size, in KBytes, of the XML response.";
    }
  }

  grouping THROTTLE {
    description
      "Common node of default, ssl, tty";
    container throttle {
      description
        "XML agent throttling";
      leaf process-rate {
        type uint32 {
          range "1000..30000";
        }
        description
          "Process rate in number of XML tags per second";
      }
      leaf memory {
        type uint32 {
          range "100..1024";
        }
        units "megabyte";
        default "300";
        description
          "Size of memory usage, in MBytes, per session.";
      }
    }
  }

  grouping ENABLE {
    description
      "Common node of default, ssl, tty";
    leaf enable {
      type empty;
      description
        "Enable specified XML agent";
    }
  }

  augment "/ncs:devices/ncs:device/ncs:config" {
    container xr-xml {
      tailf:ncs-device-type "netconf";
      tailf:display-when "not(../../ncs:module) or ../../ncs:module[ncs:name='Cisco-IOS-XR-man-xml-ttyagent-cfg']";
      description
        "XML";
      container agent {
        description
          "XML agent";
        container default {
          description
            "XML default dedicated agent";
          leaf ipv6-enable {
            type boolean;
            description
              "IPv6 Transport State";
          }
          leaf ipv4-disable {
            type boolean;
            description
              "TRUE to disable IPV4";
          }
          uses SESSION;
          uses ITERATION-SIZE;
          uses THROTTLE;
          uses ENABLE;
          uses STREAMING-SIZE;
          uses VRF-TABLE;
        }
        container tty {
          description
            "XML TTY agent";
          uses SESSION;
          uses ITERATION-SIZE;
          uses THROTTLE;
          uses ENABLE;
          uses STREAMING-SIZE;
        }
        container ssl {
          description
            "XML SSL agent";
          uses SESSION;
          uses ITERATION-SIZE;
          uses THROTTLE;
          uses ENABLE;
          uses STREAMING-SIZE;
          uses VRF-TABLE;
        }
      }
    }
    container netconf {
      tailf:ncs-device-type "netconf";
      tailf:display-when "not(../../ncs:module) or ../../ncs:module[ncs:name='Cisco-IOS-XR-man-xml-ttyagent-cfg']";
      description
        "NETCONF";
      container agent {
        description
          "XML agent";
        container tty {
          description
            "NETCONF agent over TTY";
          container throttle {
            description
              "NETCONF agent throttling";
            leaf memory {
              type uint32 {
                range "100..1024";
              }
              units "megabyte";
              default "300";
              description
                "Size of memory usage, in MBytes, per session.";
            }
            leaf offload-memory {
              type uint32 {
                range "0..12000";
              }
              units "megabyte";
              default "0";
              description
                "Size of memory usage, in MBytes, per session.";
            }
            leaf process-rate {
              type uint32 {
                range "1000..30000";
              }
              description
                "Process rate in number of XML tags per second";
            }
          }
          container session {
            description
              "Session attributes";
            leaf timeout {
              type uint32 {
                range "1..1440";
              }
              units "minute";
              description
                "Timeout in minutes";
            }
          }
          leaf enable {
            type empty;
            description
              "Enable specified NETCONF agent";
          }
        }
      }
    }
  }
  augment "/ncs:devices/ncs:device/ncs:live-status" {
    container xr-xml {
      tailf:ncs-device-type "netconf";
      tailf:display-when "not(../../ncs:module) or ../../ncs:module[ncs:name='Cisco-IOS-XR-man-xml-ttyagent-cfg'] or (../../ncs:live-status-protocol[not(ncs:capability)]) or (../../ncs:live-status-protocol/ncs:capability/ncs:module[.='Cisco-IOS-XR-man-xml-ttyagent-cfg'])";
      description
        "XML";
      container agent {
        description
          "XML agent";
        container default {
          description
            "XML default dedicated agent";
          leaf ipv6-enable {
            type boolean;
            description
              "IPv6 Transport State";
          }
          leaf ipv4-disable {
            type boolean;
            description
              "TRUE to disable IPV4";
          }
          uses live_ncs_SESSION;
          uses live_ncs_ITERATION-SIZE;
          uses live_ncs_THROTTLE;
          uses live_ncs_ENABLE;
          uses live_ncs_STREAMING-SIZE;
          uses live_ncs_VRF-TABLE;
        }
        container tty {
          description
            "XML TTY agent";
          uses live_ncs_SESSION;
          uses live_ncs_ITERATION-SIZE;
          uses live_ncs_THROTTLE;
          uses live_ncs_ENABLE;
          uses live_ncs_STREAMING-SIZE;
        }
        container ssl {
          description
            "XML SSL agent";
          uses live_ncs_SESSION;
          uses live_ncs_ITERATION-SIZE;
          uses live_ncs_THROTTLE;
          uses live_ncs_ENABLE;
          uses live_ncs_STREAMING-SIZE;
          uses live_ncs_VRF-TABLE;
        }
      }
    }
    container netconf {
      tailf:ncs-device-type "netconf";
      tailf:display-when "not(../../ncs:module) or ../../ncs:module[ncs:name='Cisco-IOS-XR-man-xml-ttyagent-cfg'] or (../../ncs:live-status-protocol[not(ncs:capability)]) or (../../ncs:live-status-protocol/ncs:capability/ncs:module[.='Cisco-IOS-XR-man-xml-ttyagent-cfg'])";
      description
        "NETCONF";
      container agent {
        description
          "XML agent";
        container tty {
          description
            "NETCONF agent over TTY";
          container throttle {
            description
              "NETCONF agent throttling";
            leaf memory {
              type uint32 {
                range "100..1024";
              }
              units "megabyte";
              // NCS drop default statement
              description
                "Size of memory usage, in MBytes, per session.";
            }
            leaf offload-memory {
              type uint32 {
                range "0..12000";
              }
              units "megabyte";
              // NCS drop default statement
              description
                "Size of memory usage, in MBytes, per session.";
            }
            leaf process-rate {
              type uint32 {
                range "1000..30000";
              }
              description
                "Process rate in number of XML tags per second";
            }
          }
          container session {
            description
              "Session attributes";
            leaf timeout {
              type uint32 {
                range "1..1440";
              }
              units "minute";
              description
                "Timeout in minutes";
            }
          }
          leaf enable {
            type empty;
            description
              "Enable specified NETCONF agent";
          }
        }
      }
    }
  }
  augment "/ncs:devices/ncs:template/ncs:ned-id/ncs:config" {
    container xr-xml {
      description
        "XML";
      container agent {
        description
          "XML agent";
        container default {
          description
            "XML default dedicated agent";
          leaf ipv6-enable {
            type string;
            description
              "IPv6 Transport State";
          }
          leaf ipv4-disable {
            type string;
            description
              "TRUE to disable IPV4";
          }
          uses ncs_template_SESSION;
          uses ncs_template_ITERATION-SIZE;
          uses ncs_template_THROTTLE;
          uses ncs_template_ENABLE;
          uses ncs_template_STREAMING-SIZE;
          uses ncs_template_VRF-TABLE;
        }
        container tty {
          description
            "XML TTY agent";
          uses ncs_template_SESSION;
          uses ncs_template_ITERATION-SIZE;
          uses ncs_template_THROTTLE;
          uses ncs_template_ENABLE;
          uses ncs_template_STREAMING-SIZE;
        }
        container ssl {
          description
            "XML SSL agent";
          uses ncs_template_SESSION;
          uses ncs_template_ITERATION-SIZE;
          uses ncs_template_THROTTLE;
          uses ncs_template_ENABLE;
          uses ncs_template_STREAMING-SIZE;
          uses ncs_template_VRF-TABLE;
        }
      }
    }
    container netconf {
      description
        "NETCONF";
      container agent {
        description
          "XML agent";
        container tty {
          description
            "NETCONF agent over TTY";
          container throttle {
            description
              "NETCONF agent throttling";
            leaf memory {
              type string;
              units "megabyte";
              // NCS drop default statement
              description
                "Size of memory usage, in MBytes, per session.";
            }
            leaf offload-memory {
              type string;
              units "megabyte";
              // NCS drop default statement
              description
                "Size of memory usage, in MBytes, per session.";
            }
            leaf process-rate {
              type string;
              description
                "Process rate in number of XML tags per second";
            }
          }
          container session {
            description
              "Session attributes";
            leaf timeout {
              type string;
              units "minute";
              description
                "Timeout in minutes";
            }
          }
          leaf enable {
            type empty;
            description
              "Enable specified NETCONF agent";
          }
        }
      }
    }
  }
}

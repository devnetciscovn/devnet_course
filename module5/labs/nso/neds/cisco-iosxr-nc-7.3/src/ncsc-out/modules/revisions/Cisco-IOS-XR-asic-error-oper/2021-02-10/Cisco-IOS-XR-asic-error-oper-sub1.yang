submodule Cisco-IOS-XR-asic-error-oper-sub1 {
  // Generated by yanger -t ncs
  tailf:mount-id "cisco-iosxr-nc-7.3:cisco-iosxr-nc-7.3";

  belongs-to Cisco-IOS-XR-asic-error-oper {
    prefix Cisco-IOS-XR-asic-error-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-error package operational data.

     Copyright (c) 2013-2021 by Cisco Systems, Inc.
     All rights reserved.";

  revision 2021-02-10 {
    description
      "Introduced working oper model for asic-errors.";
    semver:module-version "1.1.0";
  }
  revision 2019-09-27 {
    description
      "Introduced working oper model for asic-errors.";
    semver:module-version "1.0.0";
  }
  revision 2019-09-24 {
    description
      "Introduced working oper model for asic-errors.";
    semver:module-version "1.0.0";
  }
  revision 2019-04-05 {
    description
      "Establish semantic version baseline.";
  }
  revision 2015-11-09 {
    description
      "IOS XR 6.0 revision.";
  }

  grouping ncs_template_ASIC-SUMMARY-BG {
    description
      "ASIC SUMMARY BG";
    leaf legacy-client {
      type string;
      description
        "boolean field for legacy client";
    }
    leaf cih-client {
      type string;
      description
        "boolean field for cih client";
    }
    leaf pac-client {
      type string;
      description
        "boolean field for pac client";
    }
    list sum-data {
      // NCS patched for predictable order
      ordered-by user;
      description
        "summary data for asic error";
      uses ncs_template_SUMMARY-DATA-BG;
    }
  }

  grouping ncs_template_COUNT-INFO-BG {
    description
      "COUNT INFO BG";
    leaf name {
      type string;
      description
        "Name of asic error";
    }
    leaf count {
      type string;
      description
        "Number of occurrence";
    }
  }

  grouping ncs_template_SUMMARY-DATA-BG {
    description
      "SUMMARY DATA BG";
    leaf num-nodes {
      type string;
      description
        "Number of nodes";
    }
    leaf crc-err-count {
      type string;
      description
        "CRC Error Count";
    }
    leaf sbe-err-count {
      type string;
      description
        "Single Bit Error Count";
    }
    leaf mbe-err-count {
      type string;
      description
        "Multi-Bit Error Count";
    }
    leaf par-err-count {
      type string;
      description
        "Parity Error Count";
    }
    leaf gen-err-count {
      type string;
      description
        "General Error Count";
    }
    leaf reset-err-count {
      type string;
      description
        "Reset Error Count";
    }
    list err-count {
      // NCS patched for predictable order
      ordered-by user;
      description
        "Error Count";
      uses ncs_template_COUNT-INFO-BG;
    }
    list pcie-err-count {
      // NCS patched for predictable order
      ordered-by user;
      description
        "PCIE Error Count";
      uses ncs_template_COUNT-INFO-BG;
    }
    list pacerr-count {
      // NCS patched for predictable order
      ordered-by user;
      description
        "Pac Error Count";
      uses ncs_template_COUNT-INFO-BG;
    }
    list node-key {
      // NCS patched for predictable order
      ordered-by user;
      description
        "Keys to the node";
      leaf entry {
        type string;
        description
          "Keys to the node";
      }
    }
  }

  grouping ncs_rpc_notif_ASIC-SUMMARY-BG {
    description
      "ASIC SUMMARY BG";
    leaf legacy-client {
      type boolean;
      description
        "boolean field for legacy client";
    }
    leaf cih-client {
      type boolean;
      description
        "boolean field for cih client";
    }
    leaf pac-client {
      type boolean;
      description
        "boolean field for pac client";
    }
    list sum-data {
      description
        "summary data for asic error";
      uses ncs_rpc_notif_SUMMARY-DATA-BG;
    }
  }

  grouping ncs_rpc_notif_COUNT-INFO-BG {
    description
      "COUNT INFO BG";
    leaf name {
      type string;
      description
        "Name of asic error";
    }
    leaf count {
      type uint32;
      description
        "Number of occurrence";
    }
  }

  grouping ncs_rpc_notif_SUMMARY-DATA-BG {
    description
      "SUMMARY DATA BG";
    leaf num-nodes {
      type uint32;
      description
        "Number of nodes";
    }
    leaf crc-err-count {
      type uint32;
      description
        "CRC Error Count";
    }
    leaf sbe-err-count {
      type uint32;
      description
        "Single Bit Error Count";
    }
    leaf mbe-err-count {
      type uint32;
      description
        "Multi-Bit Error Count";
    }
    leaf par-err-count {
      type uint32;
      description
        "Parity Error Count";
    }
    leaf gen-err-count {
      type uint32;
      description
        "General Error Count";
    }
    leaf reset-err-count {
      type uint32;
      description
        "Reset Error Count";
    }
    list err-count {
      description
        "Error Count";
      uses ncs_rpc_notif_COUNT-INFO-BG;
    }
    list pcie-err-count {
      description
        "PCIE Error Count";
      uses ncs_rpc_notif_COUNT-INFO-BG;
    }
    list pacerr-count {
      description
        "Pac Error Count";
      uses ncs_rpc_notif_COUNT-INFO-BG;
    }
    list node-key {
      description
        "Keys to the node";
      leaf entry {
        type uint32;
        description
          "Keys to the node";
      }
    }
  }

  grouping live_ncs_ASIC-SUMMARY-BG {
    description
      "ASIC SUMMARY BG";
    leaf legacy-client {
      type boolean;
      description
        "boolean field for legacy client";
    }
    leaf cih-client {
      type boolean;
      description
        "boolean field for cih client";
    }
    leaf pac-client {
      type boolean;
      description
        "boolean field for pac client";
    }
    list sum-data {
      description
        "summary data for asic error";
      uses live_ncs_SUMMARY-DATA-BG;
    }
  }

  grouping live_ncs_COUNT-INFO-BG {
    description
      "COUNT INFO BG";
    leaf name {
      type string;
      description
        "Name of asic error";
    }
    leaf count {
      type uint32;
      description
        "Number of occurrence";
    }
  }

  grouping live_ncs_SUMMARY-DATA-BG {
    description
      "SUMMARY DATA BG";
    leaf num-nodes {
      type uint32;
      description
        "Number of nodes";
    }
    leaf crc-err-count {
      type uint32;
      description
        "CRC Error Count";
    }
    leaf sbe-err-count {
      type uint32;
      description
        "Single Bit Error Count";
    }
    leaf mbe-err-count {
      type uint32;
      description
        "Multi-Bit Error Count";
    }
    leaf par-err-count {
      type uint32;
      description
        "Parity Error Count";
    }
    leaf gen-err-count {
      type uint32;
      description
        "General Error Count";
    }
    leaf reset-err-count {
      type uint32;
      description
        "Reset Error Count";
    }
    list err-count {
      description
        "Error Count";
      uses live_ncs_COUNT-INFO-BG;
    }
    list pcie-err-count {
      description
        "PCIE Error Count";
      uses live_ncs_COUNT-INFO-BG;
    }
    list pacerr-count {
      description
        "Pac Error Count";
      uses live_ncs_COUNT-INFO-BG;
    }
    list node-key {
      description
        "Keys to the node";
      leaf entry {
        type uint32;
        description
          "Keys to the node";
      }
    }
  }

  grouping ASIC-SUMMARY-BG {
    description
      "ASIC SUMMARY BG";
    leaf legacy-client {
      type boolean;
      description
        "boolean field for legacy client";
    }
    leaf cih-client {
      type boolean;
      description
        "boolean field for cih client";
    }
    leaf pac-client {
      type boolean;
      description
        "boolean field for pac client";
    }
    list sum-data {
      description
        "summary data for asic error";
      uses SUMMARY-DATA-BG;
    }
  }

  grouping COUNT-INFO-BG {
    description
      "COUNT INFO BG";
    leaf name {
      type string;
      description
        "Name of asic error";
    }
    leaf count {
      type uint32;
      description
        "Number of occurrence";
    }
  }

  grouping SUMMARY-DATA-BG {
    description
      "SUMMARY DATA BG";
    leaf num-nodes {
      type uint32;
      description
        "Number of nodes";
    }
    leaf crc-err-count {
      type uint32;
      description
        "CRC Error Count";
    }
    leaf sbe-err-count {
      type uint32;
      description
        "Single Bit Error Count";
    }
    leaf mbe-err-count {
      type uint32;
      description
        "Multi-Bit Error Count";
    }
    leaf par-err-count {
      type uint32;
      description
        "Parity Error Count";
    }
    leaf gen-err-count {
      type uint32;
      description
        "General Error Count";
    }
    leaf reset-err-count {
      type uint32;
      description
        "Reset Error Count";
    }
    list err-count {
      description
        "Error Count";
      uses COUNT-INFO-BG;
    }
    list pcie-err-count {
      description
        "PCIE Error Count";
      uses COUNT-INFO-BG;
    }
    list pacerr-count {
      description
        "Pac Error Count";
      uses COUNT-INFO-BG;
    }
    list node-key {
      description
        "Keys to the node";
      leaf entry {
        type uint32;
        description
          "Keys to the node";
      }
    }
  }
}

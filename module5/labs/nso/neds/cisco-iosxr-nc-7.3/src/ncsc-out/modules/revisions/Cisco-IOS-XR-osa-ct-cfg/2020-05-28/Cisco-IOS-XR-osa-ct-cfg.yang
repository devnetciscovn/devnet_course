module Cisco-IOS-XR-osa-ct-cfg {
  // Generated by yanger -t ncs
  tailf:mount-id "cisco-iosxr-nc-7.3:cisco-iosxr-nc-7.3";
  tailf:ncs-device-type "netconf";

  namespace "http://cisco.com/ns/yang/Cisco-IOS-XR-osa-ct-cfg";
  prefix osa-ct-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR osa-ct package configuration.

     This module contains definitions
     for the following management objects:
       resrv-cli: Reserve Slot Cli Configuration

     Copyright (c) 2013-2020 by Cisco Systems, Inc.
     All rights reserved.";

  revision 2020-05-28 {
    description
      "Initial Revision.";
    semver:module-version "1.0.0";
  }
  revision 2019-04-05 {
    description
      "Establish semantic version baseline.";
  }
  revision 2015-11-09 {
    description
      "IOS XR 6.0 revision.";
  }

  typedef ncs_template_Card {
    type string;
    description
      "Card";
  }

  typedef ncs_rpc_notif_Card {
    type enumeration {
      enum "ncs1k4-1.2t-k9" {
        value 1;
        description
          "C Band Card";
      }
      enum "ncs1k4-1.2t-l-k9" {
        value 2;
        description
          "Licensed Card";
      }
      enum "ncs1k4-1.2tl-k9" {
        value 3;
        description
          "L Band Card";
      }
      enum "ncs1k4-otn-xp" {
        value 4;
        description
          "BO Card";
      }
      enum "ncs1k4-otn-xpl" {
        value 5;
        description
          "BO Licensed Card";
      }
      enum "ncs1k4-2-qdd-c-k9" {
        value 6;
        description
          "BELLATRIX C Band Card";
      }
      enum "ncs1k4-lc-filler" {
        value 7;
        description
          "Filler Card";
      }
    }
    description
      "Card";
  }

  typedef live_ncs_Card {
    type enumeration {
      enum "ncs1k4-1.2t-k9" {
        value 1;
        description
          "C Band Card";
      }
      enum "ncs1k4-1.2t-l-k9" {
        value 2;
        description
          "Licensed Card";
      }
      enum "ncs1k4-1.2tl-k9" {
        value 3;
        description
          "L Band Card";
      }
      enum "ncs1k4-otn-xp" {
        value 4;
        description
          "BO Card";
      }
      enum "ncs1k4-otn-xpl" {
        value 5;
        description
          "BO Licensed Card";
      }
      enum "ncs1k4-2-qdd-c-k9" {
        value 6;
        description
          "BELLATRIX C Band Card";
      }
      enum "ncs1k4-lc-filler" {
        value 7;
        description
          "Filler Card";
      }
    }
    description
      "Card";
  }

  typedef Card {
    type enumeration {
      enum "ncs1k4-1.2t-k9" {
        value 1;
        description
          "C Band Card";
      }
      enum "ncs1k4-1.2t-l-k9" {
        value 2;
        description
          "Licensed Card";
      }
      enum "ncs1k4-1.2tl-k9" {
        value 3;
        description
          "L Band Card";
      }
      enum "ncs1k4-otn-xp" {
        value 4;
        description
          "BO Card";
      }
      enum "ncs1k4-otn-xpl" {
        value 5;
        description
          "BO Licensed Card";
      }
      enum "ncs1k4-2-qdd-c-k9" {
        value 6;
        description
          "BELLATRIX C Band Card";
      }
      enum "ncs1k4-lc-filler" {
        value 7;
        description
          "Filler Card";
      }
    }
    description
      "Card";
  }

  augment "/ncs:devices/ncs:device/ncs:config" {
    container resrv-cli {
      tailf:ncs-device-type "netconf";
      tailf:display-when "not(../../ncs:module) or ../../ncs:module[ncs:name='Cisco-IOS-XR-osa-ct-cfg']";
      description
        "Reserve Slot Cli Configuration";
      list slot-info-cli {
        key "lc-slot";
        description
          "location of LC";
        leaf card-type-cli {
          type Card;
          description
            "CardType config type";
        }
        leaf lc-slot {
          type xr:Cisco-ios-xr-string;
          description
            "LC location";
        }
      }
    }
  }
  augment "/ncs:devices/ncs:device/ncs:live-status" {
    container resrv-cli {
      tailf:ncs-device-type "netconf";
      tailf:display-when "not(../../ncs:module) or ../../ncs:module[ncs:name='Cisco-IOS-XR-osa-ct-cfg'] or (../../ncs:live-status-protocol[not(ncs:capability)]) or (../../ncs:live-status-protocol/ncs:capability/ncs:module[.='Cisco-IOS-XR-osa-ct-cfg'])";
      description
        "Reserve Slot Cli Configuration";
      list slot-info-cli {
        key "lc-slot";
        description
          "location of LC";
        leaf card-type-cli {
          type live_ncs_Card;
          description
            "CardType config type";
        }
        leaf lc-slot {
          type xr:live_ncs_Cisco-ios-xr-string;
          description
            "LC location";
        }
      }
    }
  }
  augment "/ncs:devices/ncs:template/ncs:ned-id/ncs:config" {
    container resrv-cli {
      description
        "Reserve Slot Cli Configuration";
      list slot-info-cli {
        // NCS patched for predictable order
        ordered-by user;
        key "lc-slot";
        description
          "location of LC";
        leaf card-type-cli {
          type ncs_template_Card;
          description
            "CardType config type";
        }
        leaf lc-slot {
          type xr:ncs_template_Cisco-ios-xr-string;
          description
            "LC location";
        }
      }
    }
  }
}

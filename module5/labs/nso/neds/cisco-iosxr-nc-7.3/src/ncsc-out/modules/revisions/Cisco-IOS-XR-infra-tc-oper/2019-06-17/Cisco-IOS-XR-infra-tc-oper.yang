module Cisco-IOS-XR-infra-tc-oper {
  // Generated by yanger -t ncs
  tailf:mount-id "cisco-iosxr-nc-7.3:cisco-iosxr-nc-7.3";
  tailf:ncs-device-type "netconf";

  namespace "http://cisco.com/ns/yang/Cisco-IOS-XR-infra-tc-oper";
  prefix infra-tc-oper;

  import Cisco-IOS-XR-types {
    prefix xr;
  }
  import cisco-semver {
    prefix semver;
  }
  include Cisco-IOS-XR-infra-tc-oper-sub1 {
    revision-date 2019-06-17;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-tc package operational data.

     This module contains definitions
     for the following management objects:
       traffic-collector: Global Traffic Collector configuration
         commands

     Copyright (c) 2013-2019 by Cisco Systems, Inc.
     All rights reserved.";

  revision 2019-06-17 {
    description
      "Change type of tunnel interface name to string";
    semver:module-version "1.0.0";
  }
  revision 2019-05-30 {
    description
      "Fix to extend range of valid OC-AFT Labels";
  }
  revision 2019-04-05 {
    description
      "Establish semantic version baseline.";
  }
  revision 2019-01-01 {
    description
      "Yang evaluator: updates to schema descriptions.";
  }
  revision 2018-11-30 {
    description
      "Adding label data and total count stats for OC-AFT.";
  }
  revision 2018-10-05 {
    description
      "Removed stat collection message statistics. LDP label is provided in prefix info if present.";
  }
  revision 2015-11-09 {
    description
      "IOS XR 6.0 revision.";
  }

  typedef ncs_template_Tc-oper-af-name {
    type string;
    description
      "Tc oper af name";
  }

  typedef ncs_template_Tc-oper-ocaft-label {
    type string;
    description
      "Tc oper ocaft label";
  }

  typedef ncs_template_Tc-oper-local-label {
    type string;
    description
      "Tc oper local label";
  }

  typedef ncs_rpc_notif_Tc-oper-af-name {
    type enumeration {
      enum "ipv4" {
        value 0;
        description
          "IPv4";
      }
      enum "ipv6" {
        value 1;
        description
          "IPv6";
      }
    }
    description
      "Tc oper af name";
  }

  typedef ncs_rpc_notif_Tc-oper-ocaft-label {
    type uint32 {
      range "0..1048575";
    }
    description
      "Tc oper ocaft label";
  }

  typedef ncs_rpc_notif_Tc-oper-local-label {
    type uint32 {
      range "16..1048575";
    }
    description
      "Tc oper local label";
  }

  typedef live_ncs_Tc-oper-af-name {
    type enumeration {
      enum "ipv4" {
        value 0;
        description
          "IPv4";
      }
      enum "ipv6" {
        value 1;
        description
          "IPv6";
      }
    }
    description
      "Tc oper af name";
  }

  typedef live_ncs_Tc-oper-ocaft-label {
    type uint32 {
      range "0..1048575";
    }
    description
      "Tc oper ocaft label";
  }

  typedef live_ncs_Tc-oper-local-label {
    type uint32 {
      range "16..1048575";
    }
    description
      "Tc oper local label";
  }

  typedef Tc-oper-af-name {
    type enumeration {
      enum "ipv4" {
        value 0;
        description
          "IPv4";
      }
      enum "ipv6" {
        value 1;
        description
          "IPv6";
      }
    }
    description
      "Tc oper af name";
  }

  typedef Tc-oper-ocaft-label {
    type uint32 {
      range "0..1048575";
    }
    description
      "Tc oper ocaft label";
  }

  typedef Tc-oper-local-label {
    type uint32 {
      range "16..1048575";
    }
    description
      "Tc oper local label";
  }

  grouping ncs_template_AF-TABLE {
    description
      "Common node of default-vrf, traffic-collector";
    container afs {
      description
        "Address Family specific operational data";
      list af {
        // NCS patched for predictable order
        ordered-by user;
        key "af-name";
        description
          "Operational data for given Address Family";
        container counters {
          description
            "Show Counters";
          container labels {
            description
              "Label Database";
            list label {
              // NCS patched for predictable order
              ordered-by user;
              key "label";
              description
                "Show Label Counter";
              leaf label {
                type ncs_template_Tc-oper-ocaft-label;
                description
                  "Local Label";
              }
              uses ncs_template_TC-MGMT-LABEL-DATA;
            }
          }
          container prefixes {
            description
              "Prefix Database";
            list prefix {
              // NCS patched for predictable order
              ordered-by user;
              description
                "Show Prefix Counter";
              leaf ipaddr {
                type xr:ncs_template_Cisco-ios-xr-string;
                description
                  "IP Address";
              }
              leaf mask {
                type xr:ncs_template_Cisco-ios-xr-string;
                description
                  "Prefix Mask";
              }
              leaf label {
                type ncs_template_Tc-oper-local-label;
                description
                  "Local Label";
              }
              uses ncs_template_TC-MGMT-PREFIX-DATA;
            }
          }
          container tunnels {
            description
              "List of tunnels in the traffic collector
               tunnel database";
            list tunnel {
              // NCS patched for predictable order
              ordered-by user;
              key "interface-name";
              description
                "Information about a specific tunnel";
              leaf interface-name {
                type xr:ncs_template_Cisco-ios-xr-string;
                description
                  "The Interface Name";
              }
              uses ncs_template_TC-MGMT-TUNNEL-DATA;
            }
          }
        }
        leaf af-name {
          type ncs_template_Tc-oper-af-name;
          description
            "Address Family name";
        }
      }
    }
  }

  grouping ncs_rpc_notif_AF-TABLE {
    description
      "Common node of default-vrf, traffic-collector";
    container afs {
      description
        "Address Family specific operational data";
      list af {
        key "af-name";
        description
          "Operational data for given Address Family";
        container counters {
          description
            "Show Counters";
          container labels {
            description
              "Label Database";
            list label {
              key "label";
              description
                "Show Label Counter";
              leaf label {
                type ncs_rpc_notif_Tc-oper-ocaft-label;
                description
                  "Local Label";
              }
              uses ncs_rpc_notif_TC-MGMT-LABEL-DATA;
            }
          }
          container prefixes {
            description
              "Prefix Database";
            list prefix {
              description
                "Show Prefix Counter";
              leaf ipaddr {
                type xr:ncs_rpc_notif_Cisco-ios-xr-string;
                description
                  "IP Address";
              }
              leaf mask {
                type xr:ncs_rpc_notif_Cisco-ios-xr-string;
                description
                  "Prefix Mask";
              }
              leaf label {
                type ncs_rpc_notif_Tc-oper-local-label;
                description
                  "Local Label";
              }
              uses ncs_rpc_notif_TC-MGMT-PREFIX-DATA;
            }
          }
          container tunnels {
            description
              "List of tunnels in the traffic collector
               tunnel database";
            list tunnel {
              key "interface-name";
              description
                "Information about a specific tunnel";
              leaf interface-name {
                type xr:ncs_rpc_notif_Cisco-ios-xr-string;
                description
                  "The Interface Name";
              }
              uses ncs_rpc_notif_TC-MGMT-TUNNEL-DATA;
            }
          }
        }
        leaf af-name {
          type ncs_rpc_notif_Tc-oper-af-name;
          description
            "Address Family name";
        }
      }
    }
  }

  grouping live_ncs_AF-TABLE {
    description
      "Common node of default-vrf, traffic-collector";
    container afs {
      description
        "Address Family specific operational data";
      list af {
        key "af-name";
        description
          "Operational data for given Address Family";
        container counters {
          description
            "Show Counters";
          container labels {
            description
              "Label Database";
            list label {
              key "label";
              description
                "Show Label Counter";
              leaf label {
                type live_ncs_Tc-oper-ocaft-label;
                description
                  "Local Label";
              }
              uses live_ncs_TC-MGMT-LABEL-DATA;
            }
          }
          container prefixes {
            description
              "Prefix Database";
            list prefix {
              description
                "Show Prefix Counter";
              leaf ipaddr {
                type xr:live_ncs_Cisco-ios-xr-string;
                description
                  "IP Address";
              }
              leaf mask {
                type xr:live_ncs_Cisco-ios-xr-string;
                description
                  "Prefix Mask";
              }
              leaf label {
                type live_ncs_Tc-oper-local-label;
                description
                  "Local Label";
              }
              uses live_ncs_TC-MGMT-PREFIX-DATA;
            }
          }
          container tunnels {
            description
              "List of tunnels in the traffic collector
               tunnel database";
            list tunnel {
              key "interface-name";
              description
                "Information about a specific tunnel";
              leaf interface-name {
                type xr:live_ncs_Cisco-ios-xr-string;
                description
                  "The Interface Name";
              }
              uses live_ncs_TC-MGMT-TUNNEL-DATA;
            }
          }
        }
        leaf af-name {
          type live_ncs_Tc-oper-af-name;
          description
            "Address Family name";
        }
      }
    }
  }

  grouping AF-TABLE {
    description
      "Common node of default-vrf, traffic-collector";
    container afs {
      description
        "Address Family specific operational data";
      list af {
        key "af-name";
        description
          "Operational data for given Address Family";
        container counters {
          description
            "Show Counters";
          container labels {
            description
              "Label Database";
            list label {
              key "label";
              description
                "Show Label Counter";
              leaf label {
                type Tc-oper-ocaft-label;
                description
                  "Local Label";
              }
              uses TC-MGMT-LABEL-DATA;
            }
          }
          container prefixes {
            description
              "Prefix Database";
            list prefix {
              description
                "Show Prefix Counter";
              leaf ipaddr {
                type xr:Cisco-ios-xr-string;
                description
                  "IP Address";
              }
              leaf mask {
                type xr:Cisco-ios-xr-string;
                description
                  "Prefix Mask";
              }
              leaf label {
                type Tc-oper-local-label;
                description
                  "Local Label";
              }
              uses TC-MGMT-PREFIX-DATA;
            }
          }
          container tunnels {
            description
              "List of tunnels in the traffic collector
               tunnel database";
            list tunnel {
              key "interface-name";
              description
                "Information about a specific tunnel";
              leaf interface-name {
                type xr:Cisco-ios-xr-string;
                description
                  "The Interface Name";
              }
              uses TC-MGMT-TUNNEL-DATA;
            }
          }
        }
        leaf af-name {
          type Tc-oper-af-name;
          description
            "Address Family name";
        }
      }
    }
  }

  augment "/ncs:devices/ncs:device/ncs:config" {
    // NCS drop config false container 'traffic-collector'
  }
  augment "/ncs:devices/ncs:device/ncs:live-status" {
    container traffic-collector {
      tailf:ncs-device-type "netconf";
      tailf:display-when "not(../../ncs:module) or ../../ncs:module[ncs:name='Cisco-IOS-XR-infra-tc-oper'] or (../../ncs:live-status-protocol[not(ncs:capability)]) or (../../ncs:live-status-protocol/ncs:capability/ncs:module[.='Cisco-IOS-XR-infra-tc-oper'])";
      description
        "Global Traffic Collector configuration commands";
      container summary-oc-aft {
        description
          "Traffic Collector summary for oc-aft";
        uses live_ncs_TC-MGMT-OCAFT-SUMMARY;
      }
      container external-interfaces {
        description
          "List of interfaces in the traffic collector
           external interface database";
        list external-interface {
          key "interface-name";
          description
            "Information about a specific external interface";
          leaf interface-name {
            type xr:live_ncs_Interface-name;
            description
              "The Interface Name";
          }
          uses live_ncs_TC-MGMT-EXT-IF-DATA;
        }
      }
      container summary {
        description
          "Traffic Collector summary";
        uses live_ncs_TC-MGMT-SUMMARY;
      }
      container vrf-table {
        description
          "VRF specific operational data";
        container default-vrf {
          description
            "DefaultVRF specific operational data";
          uses live_ncs_AF-TABLE;
        }
      }
      uses live_ncs_AF-TABLE;
    }
  }
  augment "/ncs:devices/ncs:template/ncs:ned-id/ncs:config" {
    // NCS drop config false container 'traffic-collector'
  }
}

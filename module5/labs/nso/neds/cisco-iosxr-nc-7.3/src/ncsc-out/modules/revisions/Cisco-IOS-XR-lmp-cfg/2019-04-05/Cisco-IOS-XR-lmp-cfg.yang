module Cisco-IOS-XR-lmp-cfg {
  // Generated by yanger -t ncs
  tailf:mount-id "cisco-iosxr-nc-7.3:cisco-iosxr-nc-7.3";
  tailf:ncs-device-type "netconf";

  namespace "http://cisco.com/ns/yang/Cisco-IOS-XR-lmp-cfg";
  prefix lmp-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lmp package configuration.

     This module contains definitions
     for the following management objects:
       lmp: Main common OLM/LMP configuration container

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Olm-addr {
    type string;
    description
      "Olm addr";
  }

  typedef ncs_template_Olm-switching-cap {
    type string;
    description
      "Olm switching cap";
  }

  typedef ncs_rpc_notif_Olm-addr {
    type enumeration {
      enum "ipv4" {
        value 101;
        description
          "IPv4 address";
      }
      enum "ipv6" {
        value 102;
        description
          "IPv6 address";
      }
      enum "unnumbered" {
        value 103;
        description
          "Unnumbered address";
      }
      enum "nsap" {
        value 104;
        description
          "NSAP address";
      }
    }
    description
      "Olm addr";
  }

  typedef ncs_rpc_notif_Olm-switching-cap {
    type enumeration {
      enum "lsc" {
        value 150;
        description
          "Lambda switch capable";
      }
      enum "fsc" {
        value 200;
        description
          "Fiber switch capable";
      }
    }
    description
      "Olm switching cap";
  }

  typedef live_ncs_Olm-addr {
    type enumeration {
      enum "ipv4" {
        value 101;
        description
          "IPv4 address";
      }
      enum "ipv6" {
        value 102;
        description
          "IPv6 address";
      }
      enum "unnumbered" {
        value 103;
        description
          "Unnumbered address";
      }
      enum "nsap" {
        value 104;
        description
          "NSAP address";
      }
    }
    description
      "Olm addr";
  }

  typedef live_ncs_Olm-switching-cap {
    type enumeration {
      enum "lsc" {
        value 150;
        description
          "Lambda switch capable";
      }
      enum "fsc" {
        value 200;
        description
          "Fiber switch capable";
      }
    }
    description
      "Olm switching cap";
  }

  typedef Olm-addr {
    type enumeration {
      enum "ipv4" {
        value 101;
        description
          "IPv4 address";
      }
      enum "ipv6" {
        value 102;
        description
          "IPv6 address";
      }
      enum "unnumbered" {
        value 103;
        description
          "Unnumbered address";
      }
      enum "nsap" {
        value 104;
        description
          "NSAP address";
      }
    }
    description
      "Olm addr";
  }

  typedef Olm-switching-cap {
    type enumeration {
      enum "lsc" {
        value 150;
        description
          "Lambda switch capable";
      }
      enum "fsc" {
        value 200;
        description
          "Fiber switch capable";
      }
    }
    description
      "Olm switching cap";
  }

  augment "/ncs:devices/ncs:device/ncs:config" {
    container lmp {
      tailf:ncs-device-type "netconf";
      tailf:display-when "not(../../ncs:module) or ../../ncs:module[ncs:name='Cisco-IOS-XR-lmp-cfg']";
      description
        "Main common OLM/LMP configuration container";
      container gmpls-uni {
        description
          "GMPLS UNI specific OLM/LMP configuration";
        container neighbors {
          description
            "Neighbor configuration";
          list neighbor {
            key "neighbor-name";
            description
              "Neighbor configuration";
            container ipcc {
              description
                "IPCC configuration";
              container routed {
                description
                  "Routed IPCC configuration";
                leaf enable {
                  type empty;
                  description
                    "Routed IPCC creation";
                }
              }
            }
            leaf enable {
              type empty;
              description
                "Neighbor creation";
            }
            leaf neighbor-router-id {
              type inet:ipv4-address-no-zone;
              description
                "Neighbor router ID (IPv4 Address)";
            }
            leaf neighbor-name {
              type xr:Cisco-ios-xr-string {
                length "1..64";
              }
              description
                "Neighbor name";
            }
          }
        }
        container router-id {
          presence "enable router-id";
          description
            "Local GMPLS UNI router ID";
          leaf interface-name {
            type xr:Interface-name;
            description
              "Name of interface";
          }
          leaf address {
            type inet:ipv4-address-no-zone;
            description
              "Local router ID (IPv4 Address)";
          }
        }
        container controllers {
          description
            "Configure GMPLS UNI OLM/LMP controllers";
          list controller {
            key "controller-name";
            description
              "Configure an GMPLS UNI OLM/LMP contoller";
            container local-link-id {
              description
                "Local Link ID configuration";
              leaf address-type {
                type Olm-addr;
                description
                  "Local link ID address type";
              }
              leaf unnumbered {
                when "../address-type = 'unnumbered'" {
                  tailf:xpath-root 3;
                  description
                    "../AddressType = Unnumbered";
                }
                type uint32;
                description
                  "Local address unnumbered ";
              }
              leaf address {
                when "../address-type = 'ipv4'" {
                  tailf:xpath-root 3;
                  description
                    "../AddressType = IPv4";
                }
                type inet:ipv4-address-no-zone;
                description
                  "Local link ID address IPv4";
              }
            }
            container adjacency {
              description
                "Neighbor controller adjacency configuration";
              container remote-neighbor {
                description
                  "Neighbor data";
                container interface-id {
                  description
                    "Neighbor Interface ID configuration";
                  leaf address-type {
                    type Olm-addr;
                    description
                      "Local link ID address type";
                  }
                  leaf unnumbered {
                    when "../address-type = 'unnumbered'" {
                      tailf:xpath-root 3;
                      description
                        "../AddressType = Unnumbered";
                    }
                    type uint32;
                    description
                      "Local address unnumbered ";
                  }
                  leaf address {
                    when "../address-type = 'ipv4'" {
                      tailf:xpath-root 3;
                      description
                        "../AddressType = IPv4";
                    }
                    type inet:ipv4-address-no-zone;
                    description
                      "Local link ID address IPv4";
                  }
                }
                container link-id {
                  description
                    "Neighbor Link ID configuration";
                  leaf address-type {
                    type Olm-addr;
                    description
                      "Neighbor link ID address type";
                  }
                  leaf unnumbered {
                    when "../address-type = 'unnumbered'" {
                      tailf:xpath-root 3;
                      description
                        "../AddressType = Unnumbered";
                    }
                    type uint32;
                    description
                      "Neighbor address unnumbered [Not
                       supported]";
                  }
                  leaf address {
                    when "../address-type = 'ipv4'" {
                      tailf:xpath-root 3;
                      description
                        "../AddressType = IPv4";
                    }
                    type inet:ipv4-address-no-zone;
                    description
                      "Neighbor ID address IPv4";
                  }
                }
                leaf neighbor-association {
                  type xr:Cisco-ios-xr-string {
                    length "1..64";
                  }
                  description
                    "Create LMP controller to neighbor
                     association";
                }
                leaf link-switching-capability {
                  type Olm-switching-cap;
                  default "lsc";
                  description
                    "Neighbor link switching capability
                     configuration";
                }
                leaf flexi-grid-capable {
                  type uint32;
                  description
                    "Remote node flexi grid capability ";
                }
              }
            }
            leaf enable {
              type empty;
              description
                "Enable the OLM/LMP application on this
                 controller";
            }
            leaf controller-name {
              type xr:Interface-name;
              description
                "Controller name";
            }
          }
        }
      }
      leaf enable {
        type empty;
        description
          "Enable the OLM/LMP application";
      }
    }
  }
  augment "/ncs:devices/ncs:device/ncs:live-status" {
    container lmp {
      tailf:ncs-device-type "netconf";
      tailf:display-when "not(../../ncs:module) or ../../ncs:module[ncs:name='Cisco-IOS-XR-lmp-cfg'] or (../../ncs:live-status-protocol[not(ncs:capability)]) or (../../ncs:live-status-protocol/ncs:capability/ncs:module[.='Cisco-IOS-XR-lmp-cfg'])";
      description
        "Main common OLM/LMP configuration container";
      container gmpls-uni {
        description
          "GMPLS UNI specific OLM/LMP configuration";
        container neighbors {
          description
            "Neighbor configuration";
          list neighbor {
            key "neighbor-name";
            description
              "Neighbor configuration";
            container ipcc {
              description
                "IPCC configuration";
              container routed {
                description
                  "Routed IPCC configuration";
                leaf enable {
                  type empty;
                  description
                    "Routed IPCC creation";
                }
              }
            }
            leaf enable {
              type empty;
              description
                "Neighbor creation";
            }
            leaf neighbor-router-id {
              type inet:ipv4-address-no-zone;
              description
                "Neighbor router ID (IPv4 Address)";
            }
            leaf neighbor-name {
              type xr:live_ncs_Cisco-ios-xr-string;
              description
                "Neighbor name";
            }
          }
        }
        container router-id {
          presence "enable router-id";
          description
            "Local GMPLS UNI router ID";
          leaf interface-name {
            type xr:live_ncs_Interface-name;
            description
              "Name of interface";
          }
          leaf address {
            type inet:ipv4-address-no-zone;
            description
              "Local router ID (IPv4 Address)";
          }
        }
        container controllers {
          description
            "Configure GMPLS UNI OLM/LMP controllers";
          list controller {
            key "controller-name";
            description
              "Configure an GMPLS UNI OLM/LMP contoller";
            container local-link-id {
              description
                "Local Link ID configuration";
              leaf address-type {
                type live_ncs_Olm-addr;
                description
                  "Local link ID address type";
              }
              leaf unnumbered {
                // NCS drop when statement
                type uint32;
                description
                  "Local address unnumbered ";
              }
              leaf address {
                // NCS drop when statement
                type inet:ipv4-address-no-zone;
                description
                  "Local link ID address IPv4";
              }
            }
            container adjacency {
              description
                "Neighbor controller adjacency configuration";
              container remote-neighbor {
                description
                  "Neighbor data";
                container interface-id {
                  description
                    "Neighbor Interface ID configuration";
                  leaf address-type {
                    type live_ncs_Olm-addr;
                    description
                      "Local link ID address type";
                  }
                  leaf unnumbered {
                    // NCS drop when statement
                    type uint32;
                    description
                      "Local address unnumbered ";
                  }
                  leaf address {
                    // NCS drop when statement
                    type inet:ipv4-address-no-zone;
                    description
                      "Local link ID address IPv4";
                  }
                }
                container link-id {
                  description
                    "Neighbor Link ID configuration";
                  leaf address-type {
                    type live_ncs_Olm-addr;
                    description
                      "Neighbor link ID address type";
                  }
                  leaf unnumbered {
                    // NCS drop when statement
                    type uint32;
                    description
                      "Neighbor address unnumbered [Not
                       supported]";
                  }
                  leaf address {
                    // NCS drop when statement
                    type inet:ipv4-address-no-zone;
                    description
                      "Neighbor ID address IPv4";
                  }
                }
                leaf neighbor-association {
                  type xr:live_ncs_Cisco-ios-xr-string;
                  description
                    "Create LMP controller to neighbor
                     association";
                }
                leaf link-switching-capability {
                  type live_ncs_Olm-switching-cap;
                  // NCS drop default statement
                  description
                    "Neighbor link switching capability
                     configuration";
                }
                leaf flexi-grid-capable {
                  type uint32;
                  description
                    "Remote node flexi grid capability ";
                }
              }
            }
            leaf enable {
              type empty;
              description
                "Enable the OLM/LMP application on this
                 controller";
            }
            leaf controller-name {
              type xr:live_ncs_Interface-name;
              description
                "Controller name";
            }
          }
        }
      }
      leaf enable {
        type empty;
        description
          "Enable the OLM/LMP application";
      }
    }
  }
  augment "/ncs:devices/ncs:template/ncs:ned-id/ncs:config" {
    container lmp {
      description
        "Main common OLM/LMP configuration container";
      container gmpls-uni {
        description
          "GMPLS UNI specific OLM/LMP configuration";
        container neighbors {
          description
            "Neighbor configuration";
          list neighbor {
            // NCS patched for predictable order
            ordered-by user;
            key "neighbor-name";
            description
              "Neighbor configuration";
            container ipcc {
              description
                "IPCC configuration";
              container routed {
                description
                  "Routed IPCC configuration";
                leaf enable {
                  type empty;
                  description
                    "Routed IPCC creation";
                }
              }
            }
            leaf enable {
              type empty;
              description
                "Neighbor creation";
            }
            leaf neighbor-router-id {
              type string;
              description
                "Neighbor router ID (IPv4 Address)";
            }
            leaf neighbor-name {
              type xr:ncs_template_Cisco-ios-xr-string;
              description
                "Neighbor name";
            }
          }
        }
        container router-id {
          presence "enable router-id";
          description
            "Local GMPLS UNI router ID";
          leaf interface-name {
            type xr:ncs_template_Interface-name;
            description
              "Name of interface";
          }
          leaf address {
            type string;
            description
              "Local router ID (IPv4 Address)";
          }
        }
        container controllers {
          description
            "Configure GMPLS UNI OLM/LMP controllers";
          list controller {
            // NCS patched for predictable order
            ordered-by user;
            key "controller-name";
            description
              "Configure an GMPLS UNI OLM/LMP contoller";
            container local-link-id {
              description
                "Local Link ID configuration";
              leaf address-type {
                type ncs_template_Olm-addr;
                description
                  "Local link ID address type";
              }
              leaf unnumbered {
                // NCS drop when statement
                type string;
                description
                  "Local address unnumbered ";
              }
              leaf address {
                // NCS drop when statement
                type string;
                description
                  "Local link ID address IPv4";
              }
            }
            container adjacency {
              description
                "Neighbor controller adjacency configuration";
              container remote-neighbor {
                description
                  "Neighbor data";
                container interface-id {
                  description
                    "Neighbor Interface ID configuration";
                  leaf address-type {
                    type ncs_template_Olm-addr;
                    description
                      "Local link ID address type";
                  }
                  leaf unnumbered {
                    // NCS drop when statement
                    type string;
                    description
                      "Local address unnumbered ";
                  }
                  leaf address {
                    // NCS drop when statement
                    type string;
                    description
                      "Local link ID address IPv4";
                  }
                }
                container link-id {
                  description
                    "Neighbor Link ID configuration";
                  leaf address-type {
                    type ncs_template_Olm-addr;
                    description
                      "Neighbor link ID address type";
                  }
                  leaf unnumbered {
                    // NCS drop when statement
                    type string;
                    description
                      "Neighbor address unnumbered [Not
                       supported]";
                  }
                  leaf address {
                    // NCS drop when statement
                    type string;
                    description
                      "Neighbor ID address IPv4";
                  }
                }
                leaf neighbor-association {
                  type xr:ncs_template_Cisco-ios-xr-string;
                  description
                    "Create LMP controller to neighbor
                     association";
                }
                leaf link-switching-capability {
                  type ncs_template_Olm-switching-cap;
                  // NCS drop default statement
                  description
                    "Neighbor link switching capability
                     configuration";
                }
                leaf flexi-grid-capable {
                  type string;
                  description
                    "Remote node flexi grid capability ";
                }
              }
            }
            leaf enable {
              type empty;
              description
                "Enable the OLM/LMP application on this
                 controller";
            }
            leaf controller-name {
              type xr:ncs_template_Interface-name;
              description
                "Controller name";
            }
          }
        }
      }
      leaf enable {
        type empty;
        description
          "Enable the OLM/LMP application";
      }
    }
  }
}

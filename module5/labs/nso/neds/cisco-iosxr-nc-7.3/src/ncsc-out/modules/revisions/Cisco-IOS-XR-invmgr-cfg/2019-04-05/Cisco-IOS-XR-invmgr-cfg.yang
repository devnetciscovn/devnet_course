module Cisco-IOS-XR-invmgr-cfg {
  // Generated by yanger -t ncs
  tailf:mount-id "cisco-iosxr-nc-7.3:cisco-iosxr-nc-7.3";
  tailf:ncs-device-type "netconf";

  namespace "http://cisco.com/ns/yang/Cisco-IOS-XR-invmgr-cfg";
  prefix invmgr-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR invmgr package configuration.

     This module contains definitions
     for the following management objects:
       inventory-configurations: Configuration for inventory entities

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    container inventory-configurations {
      tailf:ncs-device-type "netconf";
      tailf:display-when "not(../../ncs:module) or ../../ncs:module[ncs:name='Cisco-IOS-XR-invmgr-cfg']";
      description
        "Configuration for inventory entities";
      list entity {
        key "name";
        description
          "Entity name";
        leaf name {
          type string;
          description
            "Entity name";
        }
        leaf name-xr {
          type string;
          mandatory true;
          description
            "Entity name";
        }
      }
    }
  }
  augment "/ncs:devices/ncs:device/ncs:live-status" {
    container inventory-configurations {
      tailf:ncs-device-type "netconf";
      tailf:display-when "not(../../ncs:module) or ../../ncs:module[ncs:name='Cisco-IOS-XR-invmgr-cfg'] or (../../ncs:live-status-protocol[not(ncs:capability)]) or (../../ncs:live-status-protocol/ncs:capability/ncs:module[.='Cisco-IOS-XR-invmgr-cfg'])";
      description
        "Configuration for inventory entities";
      list entity {
        key "name";
        description
          "Entity name";
        leaf name {
          type string;
          description
            "Entity name";
        }
        leaf name-xr {
          type string;
          // NCS drop mandatory statement
          description
            "Entity name";
        }
      }
    }
  }
  augment "/ncs:devices/ncs:template/ncs:ned-id/ncs:config" {
    container inventory-configurations {
      description
        "Configuration for inventory entities";
      list entity {
        // NCS patched for predictable order
        ordered-by user;
        key "name";
        description
          "Entity name";
        leaf name {
          type string;
          description
            "Entity name";
        }
        leaf name-xr {
          type string;
          // NCS drop mandatory statement
          description
            "Entity name";
        }
      }
    }
  }
}

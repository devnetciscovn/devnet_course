module Cisco-IOS-XR-sysadmin-entity-sensor-mib {
  // Generated by yanger -t ncs
  tailf:mount-id "cisco-iosxr-nc-7.3:cisco-iosxr-nc-7.3";
  tailf:ncs-device-type "netconf";

  namespace "http://www.cisco.com/ns/yang/Cisco-IOS-XR-sysadmin-entity-sensor-mib";
  prefix CISCO_ENTITY_SENSOR_MIB;

  import ietf-yang-types {
    prefix yang;
  }
  import SNMPv2-TC {
    prefix SNMPv2-TC;
  }
  import Cisco-IOS-XR-sysadmin-entity-mib {
    prefix ENTITY-MIB;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright (c) 2015-2020 by Cisco Systems, Inc.
     All rights reserved.";

  revision 2019-04-15 {
    description
      "Establish semantic version baseline.";
    semver:module-version "1.0.0";
  }
  revision 2017-04-12 {
    description
      "Changed namespace and module name";
  }
  revision 2002-10-16 {
    description
      "";
  }

  typedef ncs_template_SensorDataType {
    type string;
  }

  typedef ncs_template_SensorDataScale {
    type string;
  }

  typedef ncs_template_SensorPrecision {
    type string;
  }

  typedef ncs_template_SensorValue {
    type string;
  }

  typedef ncs_template_SensorStatus {
    type string;
  }

  typedef ncs_template_SensorValueUpdateRate {
    type string;
  }

  typedef ncs_template_SensorThresholdSeverity {
    type string;
  }

  typedef ncs_template_SensorThresholdRelation {
    type string;
  }

  typedef ncs_template_entSensorMeasuredEntityType {
    type string;
  }

  typedef ncs_template_entSensorThresholdIndexType {
    type string;
  }

  typedef ncs_rpc_notif_SensorDataType {
    type enumeration {
      enum "other" {
        value 1;
      }
      enum "unknown" {
        value 2;
      }
      enum "voltsAC" {
        value 3;
      }
      enum "voltsDC" {
        value 4;
      }
      enum "amperes" {
        value 5;
      }
      enum "watts" {
        value 6;
      }
      enum "hertz" {
        value 7;
      }
      enum "celsius" {
        value 8;
      }
      enum "percentRH" {
        value 9;
      }
      enum "rpm" {
        value 10;
      }
      enum "cmm" {
        value 11;
      }
      enum "truthvalue" {
        value 12;
      }
      enum "specialEnum" {
        value 13;
      }
    }
  }

  typedef ncs_rpc_notif_SensorDataScale {
    type enumeration {
      enum "yocto" {
        value 1;
      }
      enum "zepto" {
        value 2;
      }
      enum "atto" {
        value 3;
      }
      enum "femto" {
        value 4;
      }
      enum "pico" {
        value 5;
      }
      enum "nano" {
        value 6;
      }
      enum "micro" {
        value 7;
      }
      enum "milli" {
        value 8;
      }
      enum "units" {
        value 9;
      }
      enum "kilo" {
        value 10;
      }
      enum "mega" {
        value 11;
      }
      enum "giga" {
        value 12;
      }
      enum "tera" {
        value 13;
      }
      enum "exa" {
        value 14;
      }
      enum "peta" {
        value 15;
      }
      enum "zetta" {
        value 16;
      }
      enum "yotta" {
        value 17;
      }
    }
  }

  typedef ncs_rpc_notif_SensorPrecision {
    type int32 {
      range "-8 .. 9";
    }
  }

  typedef ncs_rpc_notif_SensorValue {
    type int32 {
      range "-1000000000 .. 1000000000";
    }
  }

  typedef ncs_rpc_notif_SensorStatus {
    type enumeration {
      enum "ok" {
        value 1;
      }
      enum "unavailable" {
        value 2;
      }
      enum "nonoperational" {
        value 3;
      }
    }
  }

  typedef ncs_rpc_notif_SensorValueUpdateRate {
    type int32 {
      range "0 .. 999999999";
    }
  }

  typedef ncs_rpc_notif_SensorThresholdSeverity {
    type enumeration {
      enum "other" {
        value 1;
      }
      enum "minor" {
        value 10;
      }
      enum "major" {
        value 20;
      }
      enum "critical" {
        value 30;
      }
    }
  }

  typedef ncs_rpc_notif_SensorThresholdRelation {
    type enumeration {
      enum "lessThan" {
        value 1;
      }
      enum "lessOrEqual" {
        value 2;
      }
      enum "greaterThan" {
        value 3;
      }
      enum "greaterOrEqual" {
        value 4;
      }
      enum "equalTo" {
        value 5;
      }
      enum "notEqualTo" {
        value 6;
      }
    }
  }

  typedef ncs_rpc_notif_entSensorMeasuredEntityType {
    type int32 {
      range "0 .. 2147483647";
    }
  }

  typedef ncs_rpc_notif_entSensorThresholdIndexType {
    type int32 {
      range "1 .. 99999999";
    }
  }

  typedef live_ncs_SensorDataType {
    type enumeration {
      enum "other" {
        value 1;
      }
      enum "unknown" {
        value 2;
      }
      enum "voltsAC" {
        value 3;
      }
      enum "voltsDC" {
        value 4;
      }
      enum "amperes" {
        value 5;
      }
      enum "watts" {
        value 6;
      }
      enum "hertz" {
        value 7;
      }
      enum "celsius" {
        value 8;
      }
      enum "percentRH" {
        value 9;
      }
      enum "rpm" {
        value 10;
      }
      enum "cmm" {
        value 11;
      }
      enum "truthvalue" {
        value 12;
      }
      enum "specialEnum" {
        value 13;
      }
    }
  }

  typedef live_ncs_SensorDataScale {
    type enumeration {
      enum "yocto" {
        value 1;
      }
      enum "zepto" {
        value 2;
      }
      enum "atto" {
        value 3;
      }
      enum "femto" {
        value 4;
      }
      enum "pico" {
        value 5;
      }
      enum "nano" {
        value 6;
      }
      enum "micro" {
        value 7;
      }
      enum "milli" {
        value 8;
      }
      enum "units" {
        value 9;
      }
      enum "kilo" {
        value 10;
      }
      enum "mega" {
        value 11;
      }
      enum "giga" {
        value 12;
      }
      enum "tera" {
        value 13;
      }
      enum "exa" {
        value 14;
      }
      enum "peta" {
        value 15;
      }
      enum "zetta" {
        value 16;
      }
      enum "yotta" {
        value 17;
      }
    }
  }

  typedef live_ncs_SensorPrecision {
    type int32 {
      range "-8 .. 9";
    }
  }

  typedef live_ncs_SensorValue {
    type int32 {
      range "-1000000000 .. 1000000000";
    }
  }

  typedef live_ncs_SensorStatus {
    type enumeration {
      enum "ok" {
        value 1;
      }
      enum "unavailable" {
        value 2;
      }
      enum "nonoperational" {
        value 3;
      }
    }
  }

  typedef live_ncs_SensorValueUpdateRate {
    type int32 {
      range "0 .. 999999999";
    }
  }

  typedef live_ncs_SensorThresholdSeverity {
    type enumeration {
      enum "other" {
        value 1;
      }
      enum "minor" {
        value 10;
      }
      enum "major" {
        value 20;
      }
      enum "critical" {
        value 30;
      }
    }
  }

  typedef live_ncs_SensorThresholdRelation {
    type enumeration {
      enum "lessThan" {
        value 1;
      }
      enum "lessOrEqual" {
        value 2;
      }
      enum "greaterThan" {
        value 3;
      }
      enum "greaterOrEqual" {
        value 4;
      }
      enum "equalTo" {
        value 5;
      }
      enum "notEqualTo" {
        value 6;
      }
    }
  }

  typedef live_ncs_entSensorMeasuredEntityType {
    type int32 {
      range "0 .. 2147483647";
    }
  }

  typedef live_ncs_entSensorThresholdIndexType {
    type int32 {
      range "1 .. 99999999";
    }
  }

  typedef SensorDataType {
    type enumeration {
      enum "other" {
        value 1;
      }
      enum "unknown" {
        value 2;
      }
      enum "voltsAC" {
        value 3;
      }
      enum "voltsDC" {
        value 4;
      }
      enum "amperes" {
        value 5;
      }
      enum "watts" {
        value 6;
      }
      enum "hertz" {
        value 7;
      }
      enum "celsius" {
        value 8;
      }
      enum "percentRH" {
        value 9;
      }
      enum "rpm" {
        value 10;
      }
      enum "cmm" {
        value 11;
      }
      enum "truthvalue" {
        value 12;
      }
      enum "specialEnum" {
        value 13;
      }
    }
  }

  typedef SensorDataScale {
    type enumeration {
      enum "yocto" {
        value 1;
      }
      enum "zepto" {
        value 2;
      }
      enum "atto" {
        value 3;
      }
      enum "femto" {
        value 4;
      }
      enum "pico" {
        value 5;
      }
      enum "nano" {
        value 6;
      }
      enum "micro" {
        value 7;
      }
      enum "milli" {
        value 8;
      }
      enum "units" {
        value 9;
      }
      enum "kilo" {
        value 10;
      }
      enum "mega" {
        value 11;
      }
      enum "giga" {
        value 12;
      }
      enum "tera" {
        value 13;
      }
      enum "exa" {
        value 14;
      }
      enum "peta" {
        value 15;
      }
      enum "zetta" {
        value 16;
      }
      enum "yotta" {
        value 17;
      }
    }
  }

  typedef SensorPrecision {
    type int32 {
      range "-8 .. 9";
    }
  }

  typedef SensorValue {
    type int32 {
      range "-1000000000 .. 1000000000";
    }
  }

  typedef SensorStatus {
    type enumeration {
      enum "ok" {
        value 1;
      }
      enum "unavailable" {
        value 2;
      }
      enum "nonoperational" {
        value 3;
      }
    }
  }

  typedef SensorValueUpdateRate {
    type int32 {
      range "0 .. 999999999";
    }
  }

  typedef SensorThresholdSeverity {
    type enumeration {
      enum "other" {
        value 1;
      }
      enum "minor" {
        value 10;
      }
      enum "major" {
        value 20;
      }
      enum "critical" {
        value 30;
      }
    }
  }

  typedef SensorThresholdRelation {
    type enumeration {
      enum "lessThan" {
        value 1;
      }
      enum "lessOrEqual" {
        value 2;
      }
      enum "greaterThan" {
        value 3;
      }
      enum "greaterOrEqual" {
        value 4;
      }
      enum "equalTo" {
        value 5;
      }
      enum "notEqualTo" {
        value 6;
      }
    }
  }

  typedef entSensorMeasuredEntityType {
    type int32 {
      range "0 .. 2147483647";
    }
  }

  typedef entSensorThresholdIndexType {
    type int32 {
      range "1 .. 99999999";
    }
  }

  augment "/ncs:devices/ncs:device/ncs:config" {
    container CISCO-ENTITY-SENSOR-MIB {
      tailf:ncs-device-type "netconf";
      tailf:display-when "not(../../ncs:module) or ../../ncs:module[ncs:name='Cisco-IOS-XR-sysadmin-entity-sensor-mib']";
      // NCS drop config false container entSensorValueTable
      // NCS drop config false container entSensorThresholdTable
    }
  }
  augment "/ncs:devices/ncs:device/ncs:live-status" {
    container CISCO-ENTITY-SENSOR-MIB {
      tailf:ncs-device-type "netconf";
      tailf:display-when "not(../../ncs:module) or ../../ncs:module[ncs:name='Cisco-IOS-XR-sysadmin-entity-sensor-mib'] or (../../ncs:live-status-protocol[not(ncs:capability)]) or (../../ncs:live-status-protocol/ncs:capability/ncs:module[.='Cisco-IOS-XR-sysadmin-entity-sensor-mib'])";
      container entSensorValueTable {
        list entSensorValueEntry {
          key "entPhysicalIndex";
          leaf entPhysicalIndex {
            type ENTITY-MIB:live_ncs_PhysicalIndex;
          }
          leaf entSensorType {
            type live_ncs_SensorDataType;
          }
          leaf entSensorScale {
            type live_ncs_SensorDataScale;
          }
          leaf entSensorPrecision {
            type live_ncs_SensorPrecision;
          }
          leaf entSensorValue {
            type live_ncs_SensorValue;
          }
          leaf entSensorStatus {
            type live_ncs_SensorStatus;
          }
          leaf entSensorValueTimeStamp {
            type yang:timestamp;
          }
          leaf entSensorValueUpdateRate {
            type live_ncs_SensorValueUpdateRate;
          }
          leaf entSensorMeasuredEntity {
            type live_ncs_entSensorMeasuredEntityType;
          }
        }
      }
      container entSensorThresholdTable {
        list entSensorThresholdEntry {
          key "entPhysicalIndex entSensorThresholdIndex";
          leaf entPhysicalIndex {
            type ENTITY-MIB:live_ncs_PhysicalIndex;
          }
          leaf entSensorThresholdIndex {
            type live_ncs_entSensorThresholdIndexType;
          }
          leaf entSensorThresholdSeverity {
            type live_ncs_SensorThresholdSeverity;
          }
          leaf entSensorThresholdRelation {
            type live_ncs_SensorThresholdRelation;
          }
          leaf entSensorThresholdValue {
            type live_ncs_SensorValue;
          }
          leaf entSensorThresholdEvaluation {
            type SNMPv2-TC:live_ncs_TruthValue;
          }
          leaf entSensorThresholdNotificationEnable {
            type SNMPv2-TC:live_ncs_TruthValue;
          }
        }
      }
    }
  }
  augment "/ncs:devices/ncs:template/ncs:ned-id/ncs:config" {
    container CISCO-ENTITY-SENSOR-MIB {
      // NCS drop config false container entSensorValueTable
      // NCS drop config false container entSensorThresholdTable
    }
  }
}

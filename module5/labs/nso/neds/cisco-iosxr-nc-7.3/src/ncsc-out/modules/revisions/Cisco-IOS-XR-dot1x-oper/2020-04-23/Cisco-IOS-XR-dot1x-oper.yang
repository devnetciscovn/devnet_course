module Cisco-IOS-XR-dot1x-oper {
  // Generated by yanger -t ncs
  tailf:mount-id "cisco-iosxr-nc-7.3:cisco-iosxr-nc-7.3";
  tailf:ncs-device-type "netconf";

  namespace "http://cisco.com/ns/yang/Cisco-IOS-XR-dot1x-oper";
  prefix dot1x-oper;

  import Cisco-IOS-XR-types {
    prefix xr;
  }
  import cisco-semver {
    prefix semver;
  }
  include Cisco-IOS-XR-dot1x-oper-sub1 {
    revision-date 2020-04-23;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dot1x package operational data.

     This module contains definitions
     for the following management objects:
       dot1x: Dot1x operational data

     Copyright (c) 2013-2020 by Cisco Systems, Inc.
     All rights reserved.";

  revision 2020-04-23 {
    description
      "Dot1x Port Status";
    semver:module-version "2.1.0";
  }
  revision 2019-08-23 {
    description
      "Host Mode";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    // NCS drop config false container dot1x
  }
  augment "/ncs:devices/ncs:device/ncs:live-status" {
    container dot1x {
      tailf:ncs-device-type "netconf";
      tailf:display-when "not(../../ncs:module) or ../../ncs:module[ncs:name='Cisco-IOS-XR-dot1x-oper'] or (../../ncs:live-status-protocol[not(ncs:capability)]) or (../../ncs:live-status-protocol/ncs:capability/ncs:module[.='Cisco-IOS-XR-dot1x-oper'])";
      description
        "Dot1x operational data";
      container statistics {
        description
          "Dot1x operational data";
        container interface-statistics {
          description
            "Interfaces with Dot1x";
          list interface-statistic {
            key "name";
            description
              "Dot1x Data for that Interface";
            leaf name {
              type xr:live_ncs_Interface-name;
              description
                "Interface Name";
            }
            uses live_ncs_DOT1X-IF-STATISTICS;
          }
        }
      }
      container nodes {
        description
          "Node-specific Dot1x operational data";
        list node {
          key "node-name";
          description
            "Dot1x operational data for a particular node";
          container interface-summaries {
            description
              "Dot1x Summary";
            list interface-summary {
              key "name";
              description
                "Dot1x Summary for that Interface";
              leaf name {
                type xr:live_ncs_Interface-name;
                description
                  "Interface Name";
              }
              uses live_ncs_DOT1X-INTERFACE;
            }
          }
          container dot1x-defaults {
            description
              "Dot1x Default Values";
            uses live_ncs_DOT1X-DEFAULT;
          }
          container statistics {
            description
              "Dot1x Default Values";
            uses live_ncs_DOT1X-STATISTICS;
          }
          leaf node-name {
            type xr:live_ncs_Node-id;
            description
              "The node name";
          }
        }
      }
      container session {
        description
          "Dot1x operational data";
        container interface-sessions {
          description
            "Interfaces with Dot1x";
          list interface-session {
            key "name";
            description
              "Dot1x Data for that Interface";
            leaf name {
              type xr:live_ncs_Interface-name;
              description
                "Interface Name";
            }
            uses live_ncs_DOT1X-INTERFACE-DETAIL;
          }
        }
      }
    }
  }
  augment "/ncs:devices/ncs:template/ncs:ned-id/ncs:config" {
    // NCS drop config false container dot1x
  }
}

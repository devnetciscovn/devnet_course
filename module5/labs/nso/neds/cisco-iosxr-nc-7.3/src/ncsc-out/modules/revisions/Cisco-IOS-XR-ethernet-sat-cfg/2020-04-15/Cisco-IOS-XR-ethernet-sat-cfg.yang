module Cisco-IOS-XR-ethernet-sat-cfg {
  // Generated by yanger -t ncs
  tailf:mount-id "cisco-iosxr-nc-7.3:cisco-iosxr-nc-7.3";
  tailf:ncs-device-type "netconf";

  namespace "http://cisco.com/ns/yang/Cisco-IOS-XR-ethernet-sat-cfg";
  prefix ethernet-sat-cfg;

  import Cisco-IOS-XR-types {
    prefix xr;
  }
  import cisco-semver {
    prefix semver;
  }
  import Cisco-IOS-XR-ethernet-sat-datatypes {
    prefix dt1;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-sat package configuration.

     This module contains definitions
     for the following management objects:
       service-activation-test: Service Activation Testing global
         configuration

     This YANG module augments the
       Cisco-IOS-XR-ifmgr-cfg
     module with configuration data.

     Copyright (c) 2013-2020 by Cisco Systems, Inc.
     All rights reserved.";

  revision 2020-04-15 {
    description
      "Fixed must conditions bug.";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    container service-activation-test {
      tailf:ncs-device-type "netconf";
      tailf:display-when "not(../../ncs:module) or ../../ncs:module[ncs:name='Cisco-IOS-XR-ethernet-sat-cfg']";
      description
        "Service Activation Testing global configuration";
      container profiles {
        description
          "Table for profile configuration";
        list profile {
          key "profile-name";
          description
            "Profile configuration";
          container color-aware {
            description
              "Set the SAT color aware config";
            leaf cir-value {
              type uint32 {
                range "1..4294967295";
              }
              must '(../cir-units and ../set-dei) or (../cir-units and ../eir-cos) or (../cir-units and ../set-dei and ../eir-cos)' {
                tailf:xpath-root 3;
              }
              description
                "CIR value";
            }
            leaf cir-units {
              type dt1:Sat-inf-rate-units;
              must '(../cir-value and ../set-dei) or (../cir-value and ../eir-cos) or (../cir-value and ../set-dei and ../eir-cos)' {
                tailf:xpath-root 3;
              }
              description
                "CIR units";
            }
            leaf set-dei {
              type boolean;
              must '../cir-value and ../cir-units' {
                tailf:xpath-root 3;
              }
              description
                "Set DEI in EIR packets";
            }
            leaf eir-cos {
              type uint32 {
                range "0..7";
              }
              must '../cir-value and ../cir-units' {
                tailf:xpath-root 3;
              }
              description
                "CoS value in EIR packets";
            }
          }
          container cos {
            presence "Indicates a cos node is configured.";
            description
              "Set the SAT CoS config";
            leaf outer-cos {
              type uint32 {
                range "0..7";
              }
              mandatory true;
              description
                "Outer CoS value";
            }
            leaf inner-cos {
              type uint32 {
                range "0..7";
              }
              description
                "Inner CoS value";
            }
          }
          container duration {
            presence "Indicates a duration node is configured.";
            description
              "Set the SAT duration config";
            leaf value {
              type uint32 {
                range "1..1440";
              }
              mandatory true;
              description
                "Duration value";
            }
            leaf units {
              type dt1:Sat-duration-units;
              mandatory true;
              description
                "Duration units";
            }
            leaf per-step {
              type boolean;
              description
                "Per-step flag";
            }
          }
          container information-rate {
            description
              "Set the SAT information rate config";
            leaf fixed-value {
              type uint32 {
                range "1..4294967295";
              }
              must '../units and not(../minimum or ../step or ../maximum)' {
                tailf:xpath-root 3;
              }
              description
                "Fixed information rate value";
            }
            leaf minimum {
              type uint32 {
                range "1..4294967295";
              }
              must '../step and ../maximum and ../units and not(../fixed-value)' {
                tailf:xpath-root 3;
              }
              description
                "Minimum information rate";
            }
            leaf step {
              type uint32 {
                range "1..4294967295";
              }
              must '../minimum and ../maximum and ../units and not(../fixed-value)' {
                tailf:xpath-root 3;
              }
              description
                "Information rate step";
            }
            leaf maximum {
              type uint32 {
                range "1..4294967295";
              }
              must '../minimum and ../step and ../units and not(../fixed-value)' {
                tailf:xpath-root 3;
              }
              description
                "Maximum information rate";
            }
            leaf units {
              type dt1:Sat-inf-rate-units;
              must '../fixed-value or (../minimum and ../step and ../maximum)' {
                tailf:xpath-root 3;
              }
              description
                "Information rate units";
            }
          }
          container packet-size {
            description
              "Set the SAT packet size config";
            leaf emix {
              type empty;
              must 'not(../size)' {
                tailf:xpath-root 3;
              }
              description
                "Use EMIX profile flag";
            }
            leaf sequence {
              type string;
              must '../emix and not(../size)' {
                tailf:xpath-root 3;
              }
              description
                "EMIX Sequence";
            }
            leaf user-defined-frame-size {
              type uint32 {
                range "64..10236";
              }
              must '../emix and ../sequence and not(../size)' {
                tailf:xpath-root 3;
              }
              description
                "User Defined Frame Size";
            }
            leaf size {
              type uint32 {
                range "1..10236";
              }
              units "byte";
              must 'not(../emix or ../sequence or ../user-defined-frame-size)' {
                tailf:xpath-root 3;
              }
              description
                "Packet size in bytes";
            }
            leaf pseudo-random {
              type empty;
              must '../emix or ../size and not(../hex-pattern)' {
                tailf:xpath-root 3;
              }
              description
                "Use pseudo-random data for packet contents";
            }
            leaf hex-pattern {
              type uint32 {
                range "0..255";
              }
              must '../emix or ../size and not(../pseudo-random)' {
                tailf:xpath-root 3;
              }
              description
                "Hex pattern used as packet contents";
            }
          }
          leaf enable {
            type empty;
            description
              "Enable the profile";
          }
          leaf description {
            type string {
              length "1..63";
            }
            description
              "Set the SAT description config";
          }
          leaf mode {
            type dt1:Sat-mode;
            description
              "Set the SAT mode config";
          }
          leaf profile-name {
            type xr:Cisco-ios-xr-string {
              length "1..63";
            }
            description
              "Profile";
          }
        }
      }
    }
  }
  augment "/ncs:devices/ncs:device/ncs:live-status" {
    container service-activation-test {
      tailf:ncs-device-type "netconf";
      tailf:display-when "not(../../ncs:module) or ../../ncs:module[ncs:name='Cisco-IOS-XR-ethernet-sat-cfg'] or (../../ncs:live-status-protocol[not(ncs:capability)]) or (../../ncs:live-status-protocol/ncs:capability/ncs:module[.='Cisco-IOS-XR-ethernet-sat-cfg'])";
      description
        "Service Activation Testing global configuration";
      container profiles {
        description
          "Table for profile configuration";
        list profile {
          key "profile-name";
          description
            "Profile configuration";
          container color-aware {
            description
              "Set the SAT color aware config";
            leaf cir-value {
              type uint32 {
                range "1..4294967295";
              }
              // NCS drop must statement
              description
                "CIR value";
            }
            leaf cir-units {
              type dt1:live_ncs_Sat-inf-rate-units;
              // NCS drop must statement
              description
                "CIR units";
            }
            leaf set-dei {
              type boolean;
              // NCS drop must statement
              description
                "Set DEI in EIR packets";
            }
            leaf eir-cos {
              type uint32 {
                range "0..7";
              }
              // NCS drop must statement
              description
                "CoS value in EIR packets";
            }
          }
          container cos {
            presence "Indicates a cos node is configured.";
            description
              "Set the SAT CoS config";
            leaf outer-cos {
              type uint32 {
                range "0..7";
              }
              // NCS drop mandatory statement
              description
                "Outer CoS value";
            }
            leaf inner-cos {
              type uint32 {
                range "0..7";
              }
              description
                "Inner CoS value";
            }
          }
          container duration {
            presence "Indicates a duration node is configured.";
            description
              "Set the SAT duration config";
            leaf value {
              type uint32 {
                range "1..1440";
              }
              // NCS drop mandatory statement
              description
                "Duration value";
            }
            leaf units {
              type dt1:live_ncs_Sat-duration-units;
              // NCS drop mandatory statement
              description
                "Duration units";
            }
            leaf per-step {
              type boolean;
              description
                "Per-step flag";
            }
          }
          container information-rate {
            description
              "Set the SAT information rate config";
            leaf fixed-value {
              type uint32 {
                range "1..4294967295";
              }
              // NCS drop must statement
              description
                "Fixed information rate value";
            }
            leaf minimum {
              type uint32 {
                range "1..4294967295";
              }
              // NCS drop must statement
              description
                "Minimum information rate";
            }
            leaf step {
              type uint32 {
                range "1..4294967295";
              }
              // NCS drop must statement
              description
                "Information rate step";
            }
            leaf maximum {
              type uint32 {
                range "1..4294967295";
              }
              // NCS drop must statement
              description
                "Maximum information rate";
            }
            leaf units {
              type dt1:live_ncs_Sat-inf-rate-units;
              // NCS drop must statement
              description
                "Information rate units";
            }
          }
          container packet-size {
            description
              "Set the SAT packet size config";
            leaf emix {
              type empty;
              // NCS drop must statement
              description
                "Use EMIX profile flag";
            }
            leaf sequence {
              type string;
              // NCS drop must statement
              description
                "EMIX Sequence";
            }
            leaf user-defined-frame-size {
              type uint32 {
                range "64..10236";
              }
              // NCS drop must statement
              description
                "User Defined Frame Size";
            }
            leaf size {
              type uint32 {
                range "1..10236";
              }
              units "byte";
              // NCS drop must statement
              description
                "Packet size in bytes";
            }
            leaf pseudo-random {
              type empty;
              // NCS drop must statement
              description
                "Use pseudo-random data for packet contents";
            }
            leaf hex-pattern {
              type uint32 {
                range "0..255";
              }
              // NCS drop must statement
              description
                "Hex pattern used as packet contents";
            }
          }
          leaf enable {
            type empty;
            description
              "Enable the profile";
          }
          leaf description {
            type string {
              length "1..63";
            }
            description
              "Set the SAT description config";
          }
          leaf mode {
            type dt1:live_ncs_Sat-mode;
            description
              "Set the SAT mode config";
          }
          leaf profile-name {
            type xr:live_ncs_Cisco-ios-xr-string;
            description
              "Profile";
          }
        }
      }
    }
  }
  augment "/ncs:devices/ncs:template/ncs:ned-id/ncs:config" {
    container service-activation-test {
      description
        "Service Activation Testing global configuration";
      container profiles {
        description
          "Table for profile configuration";
        list profile {
          // NCS patched for predictable order
          ordered-by user;
          key "profile-name";
          description
            "Profile configuration";
          container color-aware {
            description
              "Set the SAT color aware config";
            leaf cir-value {
              type string;
              // NCS drop must statement
              description
                "CIR value";
            }
            leaf cir-units {
              type dt1:ncs_template_Sat-inf-rate-units;
              // NCS drop must statement
              description
                "CIR units";
            }
            leaf set-dei {
              type string;
              // NCS drop must statement
              description
                "Set DEI in EIR packets";
            }
            leaf eir-cos {
              type string;
              // NCS drop must statement
              description
                "CoS value in EIR packets";
            }
          }
          container cos {
            presence "Indicates a cos node is configured.";
            description
              "Set the SAT CoS config";
            leaf outer-cos {
              type string;
              // NCS drop mandatory statement
              description
                "Outer CoS value";
            }
            leaf inner-cos {
              type string;
              description
                "Inner CoS value";
            }
          }
          container duration {
            presence "Indicates a duration node is configured.";
            description
              "Set the SAT duration config";
            leaf value {
              type string;
              // NCS drop mandatory statement
              description
                "Duration value";
            }
            leaf units {
              type dt1:ncs_template_Sat-duration-units;
              // NCS drop mandatory statement
              description
                "Duration units";
            }
            leaf per-step {
              type string;
              description
                "Per-step flag";
            }
          }
          container information-rate {
            description
              "Set the SAT information rate config";
            leaf fixed-value {
              type string;
              // NCS drop must statement
              description
                "Fixed information rate value";
            }
            leaf minimum {
              type string;
              // NCS drop must statement
              description
                "Minimum information rate";
            }
            leaf step {
              type string;
              // NCS drop must statement
              description
                "Information rate step";
            }
            leaf maximum {
              type string;
              // NCS drop must statement
              description
                "Maximum information rate";
            }
            leaf units {
              type dt1:ncs_template_Sat-inf-rate-units;
              // NCS drop must statement
              description
                "Information rate units";
            }
          }
          container packet-size {
            description
              "Set the SAT packet size config";
            leaf emix {
              type empty;
              // NCS drop must statement
              description
                "Use EMIX profile flag";
            }
            leaf sequence {
              type string;
              // NCS drop must statement
              description
                "EMIX Sequence";
            }
            leaf user-defined-frame-size {
              type string;
              // NCS drop must statement
              description
                "User Defined Frame Size";
            }
            leaf size {
              type string;
              units "byte";
              // NCS drop must statement
              description
                "Packet size in bytes";
            }
            leaf pseudo-random {
              type empty;
              // NCS drop must statement
              description
                "Use pseudo-random data for packet contents";
            }
            leaf hex-pattern {
              type string;
              // NCS drop must statement
              description
                "Hex pattern used as packet contents";
            }
          }
          leaf enable {
            type empty;
            description
              "Enable the profile";
          }
          leaf description {
            type string;
            description
              "Set the SAT description config";
          }
          leaf mode {
            type dt1:ncs_template_Sat-mode;
            description
              "Set the SAT mode config";
          }
          leaf profile-name {
            type xr:ncs_template_Cisco-ios-xr-string;
            description
              "Profile";
          }
        }
      }
    }
  }
  augment "/ncs:devices/ncs:template/ncs:ned-id/ncs:config/a1:interface-configurations/a1:interface-configuration" {
    description
      "This augment extends the configuration data of
       'Cisco-IOS-XR-ifmgr-cfg'";
    container service-activation-test {
      description
        "Service Activation Testing interface
         configuration";
      leaf permit {
        type dt1:ncs_template_Sat-permit;
        description
          "Set SAT permission on the interface";
      }
    }
  }
  augment "/ncs:devices/ncs:device/ncs:live-status/a1:interface-configurations/a1:interface-configuration" {
    description
      "This augment extends the configuration data of
       'Cisco-IOS-XR-ifmgr-cfg'";
    container service-activation-test {
      tailf:ncs-device-type "netconf";
      tailf:display-when "not(../../../../ncs:module) or ../../../../ncs:module[ncs:name='Cisco-IOS-XR-ethernet-sat-cfg'] or (../../../../ncs:live-status-protocol[not(ncs:capability)]) or (../../../../ncs:live-status-protocol/ncs:capability/ncs:module[.='Cisco-IOS-XR-ethernet-sat-cfg'])";
      description
        "Service Activation Testing interface
         configuration";
      leaf permit {
        type dt1:live_ncs_Sat-permit;
        description
          "Set SAT permission on the interface";
      }
    }
  }
  augment "/ncs:devices/ncs:device/ncs:config/a1:interface-configurations/a1:interface-configuration" {
    description
      "This augment extends the configuration data of
       'Cisco-IOS-XR-ifmgr-cfg'";
    container service-activation-test {
      tailf:ncs-device-type "netconf";
      tailf:display-when "not(../../../../ncs:module) or ../../../../ncs:module[ncs:name='Cisco-IOS-XR-ethernet-sat-cfg']";
      description
        "Service Activation Testing interface
         configuration";
      leaf permit {
        type dt1:Sat-permit;
        description
          "Set SAT permission on the interface";
      }
    }
  }
}

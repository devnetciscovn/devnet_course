submodule Cisco-IOS-XR-icpe-infra-oper-sub1 {
  // Generated by yanger -t ncs
  tailf:mount-id "cisco-iosxr-nc-7.3:cisco-iosxr-nc-7.3";

  belongs-to Cisco-IOS-XR-icpe-infra-oper {
    prefix Cisco-IOS-XR-icpe-infra-oper;
  }

  import cisco-semver {
    prefix semver;
  }
  include Cisco-IOS-XR-icpe-infra-oper-sub4 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR icpe-infra package operational data.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ncs_template_ICPE-OPER-INSTALL-IMAGE-REF-INFO-TYPE {
    description
      "Install Reference Information";
    leaf reference-name-xr {
      type ncs_template_Xr-yang-string;
      description
        "Reference name";
    }
    leaf-list reference-file {
      // NCS patched for predictable order
      ordered-by user;
      type ncs_template_Xr-yang-string;
      description
        "Reference files";
    }
  }

  grouping ncs_rpc_notif_ICPE-OPER-INSTALL-IMAGE-REF-INFO-TYPE {
    description
      "Install Reference Information";
    leaf reference-name-xr {
      type ncs_rpc_notif_Xr-yang-string;
      description
        "Reference name";
    }
    leaf-list reference-file {
      type ncs_rpc_notif_Xr-yang-string;
      description
        "Reference files";
    }
  }

  grouping live_ncs_ICPE-OPER-INSTALL-IMAGE-REF-INFO-TYPE {
    description
      "Install Reference Information";
    leaf reference-name-xr {
      type live_ncs_Xr-yang-string;
      description
        "Reference name";
    }
    leaf-list reference-file {
      type live_ncs_Xr-yang-string;
      description
        "Reference files";
    }
  }

  grouping ICPE-OPER-INSTALL-IMAGE-REF-INFO-TYPE {
    description
      "Install Reference Information";
    leaf reference-name-xr {
      type Xr-yang-string;
      description
        "Reference name";
    }
    leaf-list reference-file {
      type Xr-yang-string;
      description
        "Reference files";
    }
  }
}

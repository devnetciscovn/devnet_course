submodule Cisco-IOS-XR-attestation-agent-ima-oper-sub1 {
  // Generated by yanger -t ncs
  tailf:mount-id "cisco-iosxr-nc-7.3:cisco-iosxr-nc-7.3";

  belongs-to Cisco-IOS-XR-attestation-agent-ima-oper {
    prefix Cisco-IOS-XR-attestation-agent-ima-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR attestation-agent-ima package operational data.

     Copyright (c) 2013-2020 by Cisco Systems, Inc.
     All rights reserved.";

  revision 2020-09-21 {
    description
      "Fixed bag mismatch issue for dossier stat.";
    semver:module-version "1.0.0";
  }
  revision 2020-09-15 {
    description
      "Added task for netconf support.";
  }
  revision 2019-04-05 {
    description
      "Establish semantic version baseline.";
  }
  revision 2015-11-09 {
    description
      "IOS XR 6.0 revision.";
  }

  grouping ncs_template_CACHE-BLOCK-SUMMARY {
    description
      "CACHE BLOCK SUMMARY";
    leaf block-start {
      type string;
      description
        "block start event number";
    }
    leaf block-end {
      type string;
      description
        "block end event number";
    }
    leaf block-size {
      type string;
      description
        "block size in MB";
    }
    leaf duplicate-events {
      type string;
      description
        "total no. of duplicate events in block";
    }
    leaf unique-events {
      type string;
      description
        "total no. of unique events in block";
    }
    leaf block-name {
      type string;
      description
        "block name";
    }
    leaf timestamp {
      type string;
      description
        "last modified";
    }
    leaf create-time {
      type string;
      description
        "timestamp when block was created";
    }
    leaf block-exists {
      type string;
      description
        "TRUE if block is present FALSE if block is
         deleted";
    }
  }

  grouping ncs_template_NODE-BLOCK-SUMMARY {
    description
      "NODE BLOCK SUMMARY";
    leaf node-name {
      type string;
      description
        "node name";
    }
    list block {
      // NCS patched for predictable order
      ordered-by user;
      description
        "list of blocks for this node";
      uses ncs_template_CACHE-BLOCK-SUMMARY;
    }
  }

  grouping ncs_template_BLOCK-DET {
    description
      "BLOCK DET";
    list node-block {
      // NCS patched for predictable order
      ordered-by user;
      description
        "node block";
      uses ncs_template_NODE-BLOCK-SUMMARY;
    }
  }

  grouping ncs_template_CACHE-SUMMARY {
    description
      "CACHE SUMMARY";
    leaf total-blocks {
      type string;
      description
        "total blocks in cache";
    }
    leaf cache-size {
      type string;
      description
        "total cache size in MB";
    }
    leaf total-events {
      type string;
      description
        "total no. of events in cache";
    }
    leaf duplicate-events {
      type string;
      description
        "total no. of duplicate events in cache";
    }
    leaf unique-events {
      type string;
      description
        "total no. of unique events in cache";
    }
    leaf node-name {
      type string;
      description
        "node name";
    }
    leaf timestamp {
      type string;
      description
        "last modified";
    }
  }

  grouping ncs_template_CACHE-DET {
    description
      "CACHE DET";
    list cache {
      // NCS patched for predictable order
      ordered-by user;
      description
        "cache";
      uses ncs_template_CACHE-SUMMARY;
    }
  }

  grouping ncs_template_CRON-STAT {
    description
      "CRON STAT";
    leaf run-time {
      type string;
      units "second";
      description
        "average run time in secs";
    }
    leaf averag-blocks-read {
      type string;
      description
        "average no of IMA signed blocks read";
    }
    leaf success-count {
      type string;
      description
        "successful run count";
    }
    leaf failure-count {
      type string;
      description
        "failure count";
    }
    leaf periodicity {
      type string;
      description
        "Periodicity of cron job";
    }
    leaf no-update-count {
      type string;
      description
        "No. of times cron-job ran without reading any
         data";
    }
    leaf timestamp {
      type string;
      description
        "last instant ran";
    }
    leaf node-name {
      type string;
      description
        "node name";
    }
  }

  grouping ncs_template_CRON-DET {
    description
      "CRON DET";
    list cron {
      // NCS patched for predictable order
      ordered-by user;
      description
        "cron";
      uses ncs_template_CRON-STAT;
    }
  }

  grouping ncs_template_DOSSIER-STAT {
    description
      "DOSSIER STAT";
    leaf success-count {
      type string;
      description
        "dossier successfull execution count";
    }
    leaf fail-count {
      type string;
      description
        "dossier failure count";
    }
    leaf avg-time {
      type string;
      description
        "avg time taken for dossier execution";
    }
  }

  grouping ncs_template_BLOCK-VALIDITY {
    description
      "BLOCK VALIDITY";
    leaf chunk-start-event {
      type string;
      description
        "Corrupted chunk start number";
    }
    leaf chunk-end-event {
      type string;
      description
        "Corrupted chunk end event";
    }
  }

  grouping ncs_template_BLOCK-VALIDITY-SUMMARY {
    description
      "BLOCK VALIDITY SUMMARY";
    leaf node-name {
      type string;
      description
        "node name";
    }
    list chunk {
      // NCS patched for predictable order
      ordered-by user;
      description
        "list of starting event of corrupted chunk";
      uses ncs_template_BLOCK-VALIDITY;
    }
  }

  grouping ncs_template_BLOCK-VALID-DET {
    description
      "BLOCK VALID DET";
    list node {
      // NCS patched for predictable order
      ordered-by user;
      description
        "node";
      uses ncs_template_BLOCK-VALIDITY-SUMMARY;
    }
  }

  grouping ncs_rpc_notif_CACHE-BLOCK-SUMMARY {
    description
      "CACHE BLOCK SUMMARY";
    leaf block-start {
      type uint32;
      description
        "block start event number";
    }
    leaf block-end {
      type uint32;
      description
        "block end event number";
    }
    leaf block-size {
      type uint32;
      description
        "block size in MB";
    }
    leaf duplicate-events {
      type uint32;
      description
        "total no. of duplicate events in block";
    }
    leaf unique-events {
      type uint32;
      description
        "total no. of unique events in block";
    }
    leaf block-name {
      type string {
        length "0..256";
      }
      description
        "block name";
    }
    leaf timestamp {
      type string {
        length "0..256";
      }
      description
        "last modified";
    }
    leaf create-time {
      type string {
        length "0..256";
      }
      description
        "timestamp when block was created";
    }
    leaf block-exists {
      type string {
        length "0..50";
      }
      description
        "TRUE if block is present FALSE if block is
         deleted";
    }
  }

  grouping ncs_rpc_notif_NODE-BLOCK-SUMMARY {
    description
      "NODE BLOCK SUMMARY";
    leaf node-name {
      type string {
        length "0..256";
      }
      description
        "node name";
    }
    list block {
      description
        "list of blocks for this node";
      uses ncs_rpc_notif_CACHE-BLOCK-SUMMARY;
    }
  }

  grouping ncs_rpc_notif_BLOCK-DET {
    description
      "BLOCK DET";
    list node-block {
      description
        "node block";
      uses ncs_rpc_notif_NODE-BLOCK-SUMMARY;
    }
  }

  grouping ncs_rpc_notif_CACHE-SUMMARY {
    description
      "CACHE SUMMARY";
    leaf total-blocks {
      type uint32;
      description
        "total blocks in cache";
    }
    leaf cache-size {
      type uint32;
      description
        "total cache size in MB";
    }
    leaf total-events {
      type uint32;
      description
        "total no. of events in cache";
    }
    leaf duplicate-events {
      type uint32;
      description
        "total no. of duplicate events in cache";
    }
    leaf unique-events {
      type uint32;
      description
        "total no. of unique events in cache";
    }
    leaf node-name {
      type string {
        length "0..256";
      }
      description
        "node name";
    }
    leaf timestamp {
      type string {
        length "0..256";
      }
      description
        "last modified";
    }
  }

  grouping ncs_rpc_notif_CACHE-DET {
    description
      "CACHE DET";
    list cache {
      description
        "cache";
      uses ncs_rpc_notif_CACHE-SUMMARY;
    }
  }

  grouping ncs_rpc_notif_CRON-STAT {
    description
      "CRON STAT";
    leaf run-time {
      type uint32;
      units "second";
      description
        "average run time in secs";
    }
    leaf averag-blocks-read {
      type uint32;
      description
        "average no of IMA signed blocks read";
    }
    leaf success-count {
      type uint32;
      description
        "successful run count";
    }
    leaf failure-count {
      type uint32;
      description
        "failure count";
    }
    leaf periodicity {
      type uint32;
      description
        "Periodicity of cron job";
    }
    leaf no-update-count {
      type uint32;
      description
        "No. of times cron-job ran without reading any
         data";
    }
    leaf timestamp {
      type string {
        length "0..256";
      }
      description
        "last instant ran";
    }
    leaf node-name {
      type string {
        length "0..256";
      }
      description
        "node name";
    }
  }

  grouping ncs_rpc_notif_CRON-DET {
    description
      "CRON DET";
    list cron {
      description
        "cron";
      uses ncs_rpc_notif_CRON-STAT;
    }
  }

  grouping ncs_rpc_notif_DOSSIER-STAT {
    description
      "DOSSIER STAT";
    leaf success-count {
      type uint32;
      description
        "dossier successfull execution count";
    }
    leaf fail-count {
      type uint32;
      description
        "dossier failure count";
    }
    leaf avg-time {
      type uint32;
      description
        "avg time taken for dossier execution";
    }
  }

  grouping ncs_rpc_notif_BLOCK-VALIDITY {
    description
      "BLOCK VALIDITY";
    leaf chunk-start-event {
      type uint32;
      description
        "Corrupted chunk start number";
    }
    leaf chunk-end-event {
      type uint32;
      description
        "Corrupted chunk end event";
    }
  }

  grouping ncs_rpc_notif_BLOCK-VALIDITY-SUMMARY {
    description
      "BLOCK VALIDITY SUMMARY";
    leaf node-name {
      type string {
        length "0..256";
      }
      description
        "node name";
    }
    list chunk {
      description
        "list of starting event of corrupted chunk";
      uses ncs_rpc_notif_BLOCK-VALIDITY;
    }
  }

  grouping ncs_rpc_notif_BLOCK-VALID-DET {
    description
      "BLOCK VALID DET";
    list node {
      description
        "node";
      uses ncs_rpc_notif_BLOCK-VALIDITY-SUMMARY;
    }
  }

  grouping live_ncs_CACHE-BLOCK-SUMMARY {
    description
      "CACHE BLOCK SUMMARY";
    leaf block-start {
      type uint32;
      description
        "block start event number";
    }
    leaf block-end {
      type uint32;
      description
        "block end event number";
    }
    leaf block-size {
      type uint32;
      description
        "block size in MB";
    }
    leaf duplicate-events {
      type uint32;
      description
        "total no. of duplicate events in block";
    }
    leaf unique-events {
      type uint32;
      description
        "total no. of unique events in block";
    }
    leaf block-name {
      type string {
        length "0..256";
      }
      description
        "block name";
    }
    leaf timestamp {
      type string {
        length "0..256";
      }
      description
        "last modified";
    }
    leaf create-time {
      type string {
        length "0..256";
      }
      description
        "timestamp when block was created";
    }
    leaf block-exists {
      type string {
        length "0..50";
      }
      description
        "TRUE if block is present FALSE if block is
         deleted";
    }
  }

  grouping live_ncs_NODE-BLOCK-SUMMARY {
    description
      "NODE BLOCK SUMMARY";
    leaf node-name {
      type string {
        length "0..256";
      }
      description
        "node name";
    }
    list block {
      description
        "list of blocks for this node";
      uses live_ncs_CACHE-BLOCK-SUMMARY;
    }
  }

  grouping live_ncs_BLOCK-DET {
    description
      "BLOCK DET";
    list node-block {
      description
        "node block";
      uses live_ncs_NODE-BLOCK-SUMMARY;
    }
  }

  grouping live_ncs_CACHE-SUMMARY {
    description
      "CACHE SUMMARY";
    leaf total-blocks {
      type uint32;
      description
        "total blocks in cache";
    }
    leaf cache-size {
      type uint32;
      description
        "total cache size in MB";
    }
    leaf total-events {
      type uint32;
      description
        "total no. of events in cache";
    }
    leaf duplicate-events {
      type uint32;
      description
        "total no. of duplicate events in cache";
    }
    leaf unique-events {
      type uint32;
      description
        "total no. of unique events in cache";
    }
    leaf node-name {
      type string {
        length "0..256";
      }
      description
        "node name";
    }
    leaf timestamp {
      type string {
        length "0..256";
      }
      description
        "last modified";
    }
  }

  grouping live_ncs_CACHE-DET {
    description
      "CACHE DET";
    list cache {
      description
        "cache";
      uses live_ncs_CACHE-SUMMARY;
    }
  }

  grouping live_ncs_CRON-STAT {
    description
      "CRON STAT";
    leaf run-time {
      type uint32;
      units "second";
      description
        "average run time in secs";
    }
    leaf averag-blocks-read {
      type uint32;
      description
        "average no of IMA signed blocks read";
    }
    leaf success-count {
      type uint32;
      description
        "successful run count";
    }
    leaf failure-count {
      type uint32;
      description
        "failure count";
    }
    leaf periodicity {
      type uint32;
      description
        "Periodicity of cron job";
    }
    leaf no-update-count {
      type uint32;
      description
        "No. of times cron-job ran without reading any
         data";
    }
    leaf timestamp {
      type string {
        length "0..256";
      }
      description
        "last instant ran";
    }
    leaf node-name {
      type string {
        length "0..256";
      }
      description
        "node name";
    }
  }

  grouping live_ncs_CRON-DET {
    description
      "CRON DET";
    list cron {
      description
        "cron";
      uses live_ncs_CRON-STAT;
    }
  }

  grouping live_ncs_DOSSIER-STAT {
    description
      "DOSSIER STAT";
    leaf success-count {
      type uint32;
      description
        "dossier successfull execution count";
    }
    leaf fail-count {
      type uint32;
      description
        "dossier failure count";
    }
    leaf avg-time {
      type uint32;
      description
        "avg time taken for dossier execution";
    }
  }

  grouping live_ncs_BLOCK-VALIDITY {
    description
      "BLOCK VALIDITY";
    leaf chunk-start-event {
      type uint32;
      description
        "Corrupted chunk start number";
    }
    leaf chunk-end-event {
      type uint32;
      description
        "Corrupted chunk end event";
    }
  }

  grouping live_ncs_BLOCK-VALIDITY-SUMMARY {
    description
      "BLOCK VALIDITY SUMMARY";
    leaf node-name {
      type string {
        length "0..256";
      }
      description
        "node name";
    }
    list chunk {
      description
        "list of starting event of corrupted chunk";
      uses live_ncs_BLOCK-VALIDITY;
    }
  }

  grouping live_ncs_BLOCK-VALID-DET {
    description
      "BLOCK VALID DET";
    list node {
      description
        "node";
      uses live_ncs_BLOCK-VALIDITY-SUMMARY;
    }
  }

  grouping CACHE-BLOCK-SUMMARY {
    description
      "CACHE BLOCK SUMMARY";
    leaf block-start {
      type uint32;
      description
        "block start event number";
    }
    leaf block-end {
      type uint32;
      description
        "block end event number";
    }
    leaf block-size {
      type uint32;
      description
        "block size in MB";
    }
    leaf duplicate-events {
      type uint32;
      description
        "total no. of duplicate events in block";
    }
    leaf unique-events {
      type uint32;
      description
        "total no. of unique events in block";
    }
    leaf block-name {
      type string {
        length "0..256";
      }
      description
        "block name";
    }
    leaf timestamp {
      type string {
        length "0..256";
      }
      description
        "last modified";
    }
    leaf create-time {
      type string {
        length "0..256";
      }
      description
        "timestamp when block was created";
    }
    leaf block-exists {
      type string {
        length "0..50";
      }
      description
        "TRUE if block is present FALSE if block is
         deleted";
    }
  }

  grouping NODE-BLOCK-SUMMARY {
    description
      "NODE BLOCK SUMMARY";
    leaf node-name {
      type string {
        length "0..256";
      }
      description
        "node name";
    }
    list block {
      description
        "list of blocks for this node";
      uses CACHE-BLOCK-SUMMARY;
    }
  }

  grouping BLOCK-DET {
    description
      "BLOCK DET";
    list node-block {
      description
        "node block";
      uses NODE-BLOCK-SUMMARY;
    }
  }

  grouping CACHE-SUMMARY {
    description
      "CACHE SUMMARY";
    leaf total-blocks {
      type uint32;
      description
        "total blocks in cache";
    }
    leaf cache-size {
      type uint32;
      description
        "total cache size in MB";
    }
    leaf total-events {
      type uint32;
      description
        "total no. of events in cache";
    }
    leaf duplicate-events {
      type uint32;
      description
        "total no. of duplicate events in cache";
    }
    leaf unique-events {
      type uint32;
      description
        "total no. of unique events in cache";
    }
    leaf node-name {
      type string {
        length "0..256";
      }
      description
        "node name";
    }
    leaf timestamp {
      type string {
        length "0..256";
      }
      description
        "last modified";
    }
  }

  grouping CACHE-DET {
    description
      "CACHE DET";
    list cache {
      description
        "cache";
      uses CACHE-SUMMARY;
    }
  }

  grouping CRON-STAT {
    description
      "CRON STAT";
    leaf run-time {
      type uint32;
      units "second";
      description
        "average run time in secs";
    }
    leaf averag-blocks-read {
      type uint32;
      description
        "average no of IMA signed blocks read";
    }
    leaf success-count {
      type uint32;
      description
        "successful run count";
    }
    leaf failure-count {
      type uint32;
      description
        "failure count";
    }
    leaf periodicity {
      type uint32;
      description
        "Periodicity of cron job";
    }
    leaf no-update-count {
      type uint32;
      description
        "No. of times cron-job ran without reading any
         data";
    }
    leaf timestamp {
      type string {
        length "0..256";
      }
      description
        "last instant ran";
    }
    leaf node-name {
      type string {
        length "0..256";
      }
      description
        "node name";
    }
  }

  grouping CRON-DET {
    description
      "CRON DET";
    list cron {
      description
        "cron";
      uses CRON-STAT;
    }
  }

  grouping DOSSIER-STAT {
    description
      "DOSSIER STAT";
    leaf success-count {
      type uint32;
      description
        "dossier successfull execution count";
    }
    leaf fail-count {
      type uint32;
      description
        "dossier failure count";
    }
    leaf avg-time {
      type uint32;
      description
        "avg time taken for dossier execution";
    }
  }

  grouping BLOCK-VALIDITY {
    description
      "BLOCK VALIDITY";
    leaf chunk-start-event {
      type uint32;
      description
        "Corrupted chunk start number";
    }
    leaf chunk-end-event {
      type uint32;
      description
        "Corrupted chunk end event";
    }
  }

  grouping BLOCK-VALIDITY-SUMMARY {
    description
      "BLOCK VALIDITY SUMMARY";
    leaf node-name {
      type string {
        length "0..256";
      }
      description
        "node name";
    }
    list chunk {
      description
        "list of starting event of corrupted chunk";
      uses BLOCK-VALIDITY;
    }
  }

  grouping BLOCK-VALID-DET {
    description
      "BLOCK VALID DET";
    list node {
      description
        "node";
      uses BLOCK-VALIDITY-SUMMARY;
    }
  }
}

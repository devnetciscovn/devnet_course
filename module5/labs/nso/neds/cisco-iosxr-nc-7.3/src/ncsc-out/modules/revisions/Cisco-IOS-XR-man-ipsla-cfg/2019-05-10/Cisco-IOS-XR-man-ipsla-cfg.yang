module Cisco-IOS-XR-man-ipsla-cfg {
  // Generated by yanger -t ncs
  tailf:mount-id "cisco-iosxr-nc-7.3:cisco-iosxr-nc-7.3";
  tailf:ncs-device-type "netconf";

  namespace "http://cisco.com/ns/yang/Cisco-IOS-XR-man-ipsla-cfg";
  prefix man-ipsla-cfg;

  import ietf-inet-types {
    prefix inet;
  }
  import Cisco-IOS-XR-types {
    prefix xr;
  }
  import cisco-semver {
    prefix semver;
  }
  import Cisco-IOS-XR-snmp-agent-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-ipsla package configuration.

     This module contains definitions
     for the following management objects:
       ipsla: IPSLA configuration

     This YANG module augments the
       Cisco-IOS-XR-snmp-agent-cfg
     module with configuration data.

     Copyright (c) 2013-2019 by Cisco Systems, Inc.
     All rights reserved.";

  revision 2019-05-10 {
    description
      "Change in default value of lsp-selector.";
    semver:module-version "1.1.0";
  }
  revision 2019-04-05 {
    description
      "Establish semantic version baseline.";
    semver:module-version "1.0.0";
  }
  revision 2015-11-09 {
    description
      "IOS XR 6.0 revision.";
  }

  typedef ncs_template_Ipsla-secondary-frequency {
    type string;
    description
      "Ipsla secondary frequency";
  }

  typedef ncs_template_Ipsla-month {
    type string;
    description
      "Ipsla month";
  }

  typedef ncs_template_Ipsla-lsp-ping-reply-mode {
    type string;
    description
      "Ipsla lsp ping reply mode";
  }

  typedef ncs_template_Ipsla-lsp-trace-reply-mode {
    type string;
    description
      "Ipsla lsp trace reply mode";
  }

  typedef ncs_template_Ipsla-lsp-monitor-reply-mode {
    type string;
    description
      "Ipsla lsp monitor reply mode";
  }

  typedef ncs_template_Ipsla-sched {
    type string;
    description
      "Ipsla sched";
  }

  typedef ncs_template_Ipsla-lsp-reply-dscp {
    type string;
    description
      "Ipsla lsp reply dscp";
  }

  typedef ncs_template_Ipsla-life {
    type string;
    description
      "Ipsla life";
  }

  typedef ncs_template_Ipsla-threshold-types {
    type string;
    description
      "Ipsla threshold types";
  }

  typedef ncs_template_Ipsla-lsp-monitor-threshold-types {
    type string;
    description
      "Ipsla lsp monitor threshold types";
  }

  typedef ncs_template_Ipsla-history-filter {
    type string;
    description
      "Ipsla history filter";
  }

  typedef ncs_rpc_notif_Ipsla-secondary-frequency {
    type enumeration {
      enum "connection-loss" {
        value 1;
        description
          "Enable secondary frequency for connection loss";
      }
      enum "timeout" {
        value 2;
        description
          "Enable secondary frequency for timeout";
      }
      enum "both" {
        value 3;
        description
          "Enable secondary frequency for timeout and
           connection loss";
      }
    }
    description
      "Ipsla secondary frequency";
  }

  typedef ncs_rpc_notif_Ipsla-month {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Ipsla month";
  }

  typedef ncs_rpc_notif_Ipsla-lsp-ping-reply-mode {
    type enumeration {
      enum "ipv4-udp-router-alert" {
        value 3;
        description
          "Send replies via IPv4 UDP packets with Router
           Alert option";
      }
      enum "control-channel" {
        value 4;
        description
          "Send replies via a Control Channel option";
      }
    }
    description
      "Ipsla lsp ping reply mode";
  }

  typedef ncs_rpc_notif_Ipsla-lsp-trace-reply-mode {
    type enumeration {
      enum "ipv4-udp-router-alert" {
        value 3;
        description
          "Send replies via IPv4 UDP packets with Router
           Alert option";
      }
    }
    description
      "Ipsla lsp trace reply mode";
  }

  typedef ncs_rpc_notif_Ipsla-lsp-monitor-reply-mode {
    type enumeration {
      enum "ipv4-udp-router-alert" {
        value 3;
        description
          "Send replies via IPv4 UDP packets with Router
           Alert option";
      }
    }
    description
      "Ipsla lsp monitor reply mode";
  }

  typedef ncs_rpc_notif_Ipsla-sched {
    type enumeration {
      enum "pending" {
        value 1;
        description
          "Schedule pending for later time";
      }
      enum "now" {
        value 2;
        description
          "Schedule operation now";
      }
      enum "after" {
        value 3;
        description
          "Schedule operation after specifed duration";
      }
      enum "at" {
        value 4;
        description
          "Schedule operation at specified time";
      }
    }
    description
      "Ipsla sched";
  }

  typedef ncs_rpc_notif_Ipsla-lsp-reply-dscp {
    type union {
      type enumeration {
        enum "default" {
          value 0;
          description
            "Match packets with default dscp (000000)";
        }
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp
             (001000)";
        }
        enum "cs2" {
          value 16;
          description
            "Match packets with CS2(precedence 2) dscp
             (010000)";
        }
        enum "cs3" {
          value 24;
          description
            "Match packets with CS3(precedence 3) dscp
             (011000)";
        }
        enum "cs4" {
          value 32;
          description
            "Match packets with CS4(precedence 4) dscp
             (100000)";
        }
        enum "cs5" {
          value 40;
          description
            "Match packets with CS5(precedence 5) dscp
             (101000)";
        }
        enum "cs6" {
          value 48;
          description
            "Match packets with CS6(precedence 6) dscp
             (110000)";
        }
        enum "cs7" {
          value 56;
          description
            "Match packets with CS7(precedence 7) dscp
             (111000)";
        }
        enum "ef" {
          value 46;
          description
            "Match packets with EF dscp (101110)";
        }
      }
      type uint32 {
        range "0..63";
      }
    }
    description
      "Ipsla lsp reply dscp";
  }

  typedef ncs_rpc_notif_Ipsla-life {
    type union {
      type enumeration {
        enum "forever" {
          value 0;
          description
            "Schedule operation to run forever";
        }
      }
      type uint32 {
        range "0..2147483647";
      }
    }
    description
      "Ipsla life";
  }

  typedef ncs_rpc_notif_Ipsla-threshold-types {
    type enumeration {
      enum "immediate" {
        value 2;
        description
          "Take action immediately after threshold is
           violated";
      }
      enum "consecutive" {
        value 3;
        description
          "Take action after N consecutive threshold
           violations";
      }
      enum "xof-y" {
        value 4;
        description
          "Take action after X violations in Y probes";
      }
      enum "average" {
        value 5;
        description
          "Take action if average of N probes violates the
           threshold";
      }
    }
    description
      "Ipsla threshold types";
  }

  typedef ncs_rpc_notif_Ipsla-lsp-monitor-threshold-types {
    type enumeration {
      enum "immediate" {
        value 2;
        description
          "Take action immediately after threshold is
           violated";
      }
      enum "consecutive" {
        value 3;
        description
          "Take action after N consecutive threshold
           violations";
      }
    }
    description
      "Ipsla lsp monitor threshold types";
  }

  typedef ncs_rpc_notif_Ipsla-history-filter {
    type enumeration {
      enum "failed" {
        value 2;
        description
          "Store data for failed operations";
      }
      enum "all" {
        value 255;
        description
          "Store data for all operations";
      }
    }
    description
      "Ipsla history filter";
  }

  typedef live_ncs_Ipsla-secondary-frequency {
    type enumeration {
      enum "connection-loss" {
        value 1;
        description
          "Enable secondary frequency for connection loss";
      }
      enum "timeout" {
        value 2;
        description
          "Enable secondary frequency for timeout";
      }
      enum "both" {
        value 3;
        description
          "Enable secondary frequency for timeout and
           connection loss";
      }
    }
    description
      "Ipsla secondary frequency";
  }

  typedef live_ncs_Ipsla-month {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Ipsla month";
  }

  typedef live_ncs_Ipsla-lsp-ping-reply-mode {
    type enumeration {
      enum "ipv4-udp-router-alert" {
        value 3;
        description
          "Send replies via IPv4 UDP packets with Router
           Alert option";
      }
      enum "control-channel" {
        value 4;
        description
          "Send replies via a Control Channel option";
      }
    }
    description
      "Ipsla lsp ping reply mode";
  }

  typedef live_ncs_Ipsla-lsp-trace-reply-mode {
    type enumeration {
      enum "ipv4-udp-router-alert" {
        value 3;
        description
          "Send replies via IPv4 UDP packets with Router
           Alert option";
      }
    }
    description
      "Ipsla lsp trace reply mode";
  }

  typedef live_ncs_Ipsla-lsp-monitor-reply-mode {
    type enumeration {
      enum "ipv4-udp-router-alert" {
        value 3;
        description
          "Send replies via IPv4 UDP packets with Router
           Alert option";
      }
    }
    description
      "Ipsla lsp monitor reply mode";
  }

  typedef live_ncs_Ipsla-sched {
    type enumeration {
      enum "pending" {
        value 1;
        description
          "Schedule pending for later time";
      }
      enum "now" {
        value 2;
        description
          "Schedule operation now";
      }
      enum "after" {
        value 3;
        description
          "Schedule operation after specifed duration";
      }
      enum "at" {
        value 4;
        description
          "Schedule operation at specified time";
      }
    }
    description
      "Ipsla sched";
  }

  typedef live_ncs_Ipsla-lsp-reply-dscp {
    type union {
      type enumeration {
        enum "default" {
          value 0;
          description
            "Match packets with default dscp (000000)";
        }
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp
             (001000)";
        }
        enum "cs2" {
          value 16;
          description
            "Match packets with CS2(precedence 2) dscp
             (010000)";
        }
        enum "cs3" {
          value 24;
          description
            "Match packets with CS3(precedence 3) dscp
             (011000)";
        }
        enum "cs4" {
          value 32;
          description
            "Match packets with CS4(precedence 4) dscp
             (100000)";
        }
        enum "cs5" {
          value 40;
          description
            "Match packets with CS5(precedence 5) dscp
             (101000)";
        }
        enum "cs6" {
          value 48;
          description
            "Match packets with CS6(precedence 6) dscp
             (110000)";
        }
        enum "cs7" {
          value 56;
          description
            "Match packets with CS7(precedence 7) dscp
             (111000)";
        }
        enum "ef" {
          value 46;
          description
            "Match packets with EF dscp (101110)";
        }
      }
      type uint32 {
        range "0..63";
      }
    }
    description
      "Ipsla lsp reply dscp";
  }

  typedef live_ncs_Ipsla-life {
    type union {
      type enumeration {
        enum "forever" {
          value 0;
          description
            "Schedule operation to run forever";
        }
      }
      type uint32 {
        range "0..2147483647";
      }
    }
    description
      "Ipsla life";
  }

  typedef live_ncs_Ipsla-threshold-types {
    type enumeration {
      enum "immediate" {
        value 2;
        description
          "Take action immediately after threshold is
           violated";
      }
      enum "consecutive" {
        value 3;
        description
          "Take action after N consecutive threshold
           violations";
      }
      enum "xof-y" {
        value 4;
        description
          "Take action after X violations in Y probes";
      }
      enum "average" {
        value 5;
        description
          "Take action if average of N probes violates the
           threshold";
      }
    }
    description
      "Ipsla threshold types";
  }

  typedef live_ncs_Ipsla-lsp-monitor-threshold-types {
    type enumeration {
      enum "immediate" {
        value 2;
        description
          "Take action immediately after threshold is
           violated";
      }
      enum "consecutive" {
        value 3;
        description
          "Take action after N consecutive threshold
           violations";
      }
    }
    description
      "Ipsla lsp monitor threshold types";
  }

  typedef live_ncs_Ipsla-history-filter {
    type enumeration {
      enum "failed" {
        value 2;
        description
          "Store data for failed operations";
      }
      enum "all" {
        value 255;
        description
          "Store data for all operations";
      }
    }
    description
      "Ipsla history filter";
  }

  typedef Ipsla-secondary-frequency {
    type enumeration {
      enum "connection-loss" {
        value 1;
        description
          "Enable secondary frequency for connection loss";
      }
      enum "timeout" {
        value 2;
        description
          "Enable secondary frequency for timeout";
      }
      enum "both" {
        value 3;
        description
          "Enable secondary frequency for timeout and
           connection loss";
      }
    }
    description
      "Ipsla secondary frequency";
  }

  typedef Ipsla-month {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Ipsla month";
  }

  typedef Ipsla-lsp-ping-reply-mode {
    type enumeration {
      enum "ipv4-udp-router-alert" {
        value 3;
        description
          "Send replies via IPv4 UDP packets with Router
           Alert option";
      }
      enum "control-channel" {
        value 4;
        description
          "Send replies via a Control Channel option";
      }
    }
    description
      "Ipsla lsp ping reply mode";
  }

  typedef Ipsla-lsp-trace-reply-mode {
    type enumeration {
      enum "ipv4-udp-router-alert" {
        value 3;
        description
          "Send replies via IPv4 UDP packets with Router
           Alert option";
      }
    }
    description
      "Ipsla lsp trace reply mode";
  }

  typedef Ipsla-lsp-monitor-reply-mode {
    type enumeration {
      enum "ipv4-udp-router-alert" {
        value 3;
        description
          "Send replies via IPv4 UDP packets with Router
           Alert option";
      }
    }
    description
      "Ipsla lsp monitor reply mode";
  }

  typedef Ipsla-sched {
    type enumeration {
      enum "pending" {
        value 1;
        description
          "Schedule pending for later time";
      }
      enum "now" {
        value 2;
        description
          "Schedule operation now";
      }
      enum "after" {
        value 3;
        description
          "Schedule operation after specifed duration";
      }
      enum "at" {
        value 4;
        description
          "Schedule operation at specified time";
      }
    }
    description
      "Ipsla sched";
  }

  typedef Ipsla-lsp-reply-dscp {
    type union {
      type enumeration {
        enum "default" {
          value 0;
          description
            "Match packets with default dscp (000000)";
        }
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp
             (001000)";
        }
        enum "cs2" {
          value 16;
          description
            "Match packets with CS2(precedence 2) dscp
             (010000)";
        }
        enum "cs3" {
          value 24;
          description
            "Match packets with CS3(precedence 3) dscp
             (011000)";
        }
        enum "cs4" {
          value 32;
          description
            "Match packets with CS4(precedence 4) dscp
             (100000)";
        }
        enum "cs5" {
          value 40;
          description
            "Match packets with CS5(precedence 5) dscp
             (101000)";
        }
        enum "cs6" {
          value 48;
          description
            "Match packets with CS6(precedence 6) dscp
             (110000)";
        }
        enum "cs7" {
          value 56;
          description
            "Match packets with CS7(precedence 7) dscp
             (111000)";
        }
        enum "ef" {
          value 46;
          description
            "Match packets with EF dscp (101110)";
        }
      }
      type uint32 {
        range "0..63";
      }
    }
    description
      "Ipsla lsp reply dscp";
  }

  typedef Ipsla-life {
    type union {
      type enumeration {
        enum "forever" {
          value 0;
          description
            "Schedule operation to run forever";
        }
      }
      type uint32 {
        range "0..2147483647";
      }
    }
    description
      "Ipsla life";
  }

  typedef Ipsla-threshold-types {
    type enumeration {
      enum "immediate" {
        value 2;
        description
          "Take action immediately after threshold is
           violated";
      }
      enum "consecutive" {
        value 3;
        description
          "Take action after N consecutive threshold
           violations";
      }
      enum "xof-y" {
        value 4;
        description
          "Take action after X violations in Y probes";
      }
      enum "average" {
        value 5;
        description
          "Take action if average of N probes violates the
           threshold";
      }
    }
    description
      "Ipsla threshold types";
  }

  typedef Ipsla-lsp-monitor-threshold-types {
    type enumeration {
      enum "immediate" {
        value 2;
        description
          "Take action immediately after threshold is
           violated";
      }
      enum "consecutive" {
        value 3;
        description
          "Take action after N consecutive threshold
           violations";
      }
    }
    description
      "Ipsla lsp monitor threshold types";
  }

  typedef Ipsla-history-filter {
    type enumeration {
      enum "failed" {
        value 2;
        description
          "Store data for failed operations";
      }
      enum "all" {
        value 255;
        description
          "Store data for all operations";
      }
    }
    description
      "Ipsla history filter";
  }

  grouping ncs_template_TAG {
    description
      "Common node of mpls-lsp-ping, mpls-lsp-trace";
    leaf tag {
      type string;
      description
        "Add a tag for this MPLSLM instance";
    }
  }

  grouping ncs_template_IPSLA-OP-DEF-COMMON-CFG-TAG {
    description
      "Common node of mpls-lsp-ping,
       mpls-lsp-traceCommon node of icmp-echo,
       icmp-path-echo, icmp-path-jitter, udp-echo,
       udp-jitter, mpls-lsp-ping, mpls-lsp-trace";
    leaf tag {
      type string;
      description
        "Add a tag for this operation";
    }
  }

  grouping ncs_template_LSR-PATH {
    description
      "Common node of icmp-path-echo, icmp-path-jitter";
    container lsr-path {
      presence "Indicates a lsr-path node is configured.";
      description
        "Loose source routing path (up to 8 intermediate
         nodes)";
      leaf node1 {
        type string;
        // NCS drop mandatory statement
        description
          "IPv4 address of the intermediate node";
      }
      leaf node2 {
        type string;
        description
          "IPv4 address of the intermediate node";
      }
      leaf node3 {
        type string;
        description
          "IPv4 address of the intermediate node";
      }
      leaf node4 {
        type string;
        description
          "IPv4 address of the intermediate node";
      }
      leaf node5 {
        type string;
        description
          "IPv4 address of the intermediate node";
      }
      leaf node6 {
        type string;
        description
          "IPv4 address of the intermediate node";
      }
      leaf node7 {
        type string;
        description
          "IPv4 address of the intermediate node";
      }
      leaf node8 {
        type string;
        description
          "IPv4 address of the intermediate node";
      }
    }
  }

  grouping ncs_template_VERIFY-DATA {
    description
      "Common node of udp-echo, udp-jitter";
    leaf verify-data {
      type empty;
      description
        "Check each IPSLA response for corruption";
    }
  }

  grouping ncs_template_SOURCE-ADDRESS {
    description
      "Common node of icmp-echo, icmp-path-echo,
       icmp-path-jitter, udp-echo, udp-jitter,
       mpls-lsp-ping, mpls-lsp-trace";
    leaf source-address {
      type string;
      description
        "Enter IPv4 address of the source device";
    }
  }

  grouping ncs_template_FREQUENCY {
    description
      "Common node of icmp-echo, icmp-path-echo,
       icmp-path-jitter, udp-echo, udp-jitter,
       mpls-lsp-ping, mpls-lsp-trace";
    leaf frequency {
      type string;
      units "second";
      // NCS drop default statement
      description
        "Probe interval in seconds";
    }
  }

  grouping ncs_template_DEST-ADDRESS {
    description
      "Common node of icmp-echo, icmp-path-echo,
       icmp-path-jitter, udp-echo, udp-jitter";
    leaf dest-address {
      type string;
      description
        "Enter IPv4 address of the destination device";
    }
  }

  grouping ncs_template_SCAN {
    description
      "Common node of mpls-lsp-ping, mpls-lsp-trace";
    container scan {
      description
        "Scanning parameters configuration";
      leaf interval {
        type string;
        units "minute";
        // NCS drop default statement
        description
          "Time interval for automatic discovery";
      }
      leaf delete-factor {
        type string;
        // NCS drop default statement
        description
          "Number of times for automatic deletion";
      }
    }
  }

  grouping ncs_template_DSCP-BITS {
    description
      "Common node of reply, reply";
    leaf dscp-bits {
      type ncs_template_Ipsla-lsp-reply-dscp;
      description
        "DSCP bits in the reply IP header";
    }
  }

  grouping ncs_template_THRESHOLD-TYPE {
    description
      "Common node of timeout, connection-loss";
    container threshold-type {
      description
        "Type of thresholding to perform on the monitored
         element";
      leaf thresh-type {
        type ncs_template_Ipsla-lsp-monitor-threshold-types;
        description
          "Type of thresholding to perform";
      }
      leaf count1 {
        // NCS drop when statement
        type string;
        description
          "Probe count for consecutive";
      }
      leaf count2 {
        // NCS drop when statement
        type string;
        description
          "Y value, when threshold type is XofY";
      }
    }
  }

  grouping ncs_template_IPSLA-OP-REACT-CFG-THRESHOLD-TYPE {
    description
      "Common node of timeout, connection-lossCommon
       node of timeout, verify-error, connection-loss,
       jitter-average-sd, jitter-average-ds,
       jitter-average, packet-loss-ds, packet-loss-sd,
       rtt";
    container threshold-type {
      description
        "Type of thresholding to perform on the monitored
         element";
      leaf thresh-type {
        type ncs_template_Ipsla-threshold-types;
        description
          "Type of thresholding to perform";
      }
      leaf count1 {
        // NCS drop when statement
        type string;
        description
          "Probe count for avarage, consecutive case or X
           value for XofY case";
      }
      leaf count2 {
        // NCS drop when statement
        type string;
        description
          "Y value, when threshold type is XofY";
      }
    }
  }

  grouping ncs_template_STATISTICS {
    description
      "Common node of icmp-echo, udp-echo, udp-jitter,
       mpls-lsp-ping, mpls-lsp-trace";
    container statistics {
      description
        "Statistics collection aggregated over an hour";
      leaf hours {
        type string;
        units "hour";
        // NCS drop default statement
        description
          "Number of hours for which hourly statistics are
           kept";
      }
      leaf dist-interval {
        type string;
        units "millisecond";
        // NCS drop default statement
        description
          "Specify distribution interval in milliseconds";
      }
      leaf dist-count {
        type string;
        // NCS drop default statement
        description
          "Count of distribution intervals maintained";
      }
    }
  }

  grouping ncs_template_IPSLA-MPLSLM-DEF-CFG-STATISTICS {
    description
      "Common node of icmp-echo, udp-echo, udp-jitter,
       mpls-lsp-ping, mpls-lsp-traceCommon node of
       mpls-lsp-ping, mpls-lsp-trace";
    container statistics {
      description
        "Statistics collection aggregated over an hour";
      leaf hours {
        type string;
        units "hour";
        // NCS drop default statement
        description
          "Number of hours for which hourly statistics are
           kept";
      }
    }
  }

  grouping ncs_template_TIMEOUT {
    description
      "Common node of mpls-lsp-ping, mpls-lsp-trace";
    leaf timeout {
      type string;
      units "millisecond";
      // NCS drop default statement
      description
        "Probe/Control timeout in milliseconds";
    }
  }

  grouping ncs_template_IPSLA-OP-DEF-COMMON-CFG-TIMEOUT {
    description
      "Common node of mpls-lsp-ping,
       mpls-lsp-traceCommon node of icmp-echo,
       icmp-path-echo, icmp-path-jitter, udp-echo,
       udp-jitter, mpls-lsp-ping, mpls-lsp-trace";
    leaf timeout {
      type string;
      units "millisecond";
      // NCS drop default statement
      description
        "Probe/Control timeout in milliseconds";
    }
  }

  grouping ncs_template_CONTROL-DISABLE {
    description
      "Common node of udp-echo, udp-jitter";
    leaf control-disable {
      type empty;
      description
        "Disable control packets";
    }
  }

  grouping ncs_template_FORCE-EXPLICIT-NULL {
    description
      "Common node of mpls-lsp-ping, mpls-lsp-trace";
    leaf force-explicit-null {
      type empty;
      description
        "Forced option for the MPLS LSP operation";
    }
  }

  grouping ncs_template_IPSLA-MPLSLM-DEF-CFG-FORCE-EXPLICIT-NULL {
    description
      "Common node of mpls-lsp-ping,
       mpls-lsp-traceCommon node of mpls-lsp-ping,
       mpls-lsp-trace";
    leaf force-explicit-null {
      type empty;
      description
        "Forced option for the MPLS LSP operation";
    }
  }

  grouping ncs_template_REMOTE-PORT {
    description
      "Common node of remote-ipv4-address,
       remote-ipv6-address";
    container remote-port-numbers {
      description
        "Configuration of remote port";
      list remote-port-number {
        // NCS patched for predictable order
        ordered-by user;
        key "remote-port";
        description
          "Enter value of remote port";
        container vrf-names {
          description
            "Configuration of vrf";
          list vrf-name {
            // NCS patched for predictable order
            ordered-by user;
            key "vrf-name";
            description
              "Configure vrf name value";
            leaf vrf-name {
              type xr:ncs_template_Cisco-ios-xr-string;
              description
                "VRF Name";
            }
          }
        }
        leaf remote-port {
          type string;
          description
            "Remote port";
        }
      }
    }
  }

  grouping ncs_template_ENHANCED-STATS-TABLE {
    description
      "Common node of icmp-echo, udp-echo, udp-jitter,
       mpls-lsp-ping";
    container enhanced-stats {
      description
        "Table of statistics collection intervals";
      list enhanced-stat {
        // NCS patched for predictable order
        ordered-by user;
        key "interval";
        description
          "Statistics for a specified time interval";
        leaf buckets {
          type string;
          // NCS drop default statement
          description
            "Buckets of enhanced statistics kept";
        }
        leaf interval {
          type string;
          units "second";
          description
            "Interval in seconds";
        }
      }
    }
  }

  grouping ncs_template_LSP-SELECTOR {
    description
      "Common node of mpls-lsp-ping, mpls-lsp-trace";
    leaf lsp-selector {
      type string;
      // NCS drop default statement
      description
        "Attributes used for path selection during LSP
         load balancing";
    }
  }

  grouping ncs_template_IPSLA-MPLSLM-DEF-CFG-LSP-SELECTOR {
    description
      "Common node of mpls-lsp-ping,
       mpls-lsp-traceCommon node of mpls-lsp-ping,
       mpls-lsp-trace";
    leaf lsp-selector {
      type string;
      // NCS drop default statement
      description
        "Attributes used for path selection during LSP
         load balancing";
    }
  }

  grouping ncs_template_ACTION-TYPE {
    description
      "Common node of timeout, verify-error,
       connection-loss, jitter-average-sd,
       jitter-average-ds, jitter-average, packet-loss-ds
       , packet-loss-sd, rtt";
    container action-type {
      description
        "Type of action to be taken on threshold
         violation(s)";
      leaf logging {
        type empty;
        description
          "Generate a syslog alarm on threshold violation";
      }
      leaf trigger {
        type empty;
        description
          "Generate trigger to active reaction triggered
           operation(s)";
      }
    }
  }

  grouping ncs_template_IPSLA-MPLSLM-REACT-CFG-ACTION-TYPE {
    description
      "Common node of timeout, verify-error,
       connection-loss, jitter-average-sd,
       jitter-average-ds, jitter-average, packet-loss-ds
       , packet-loss-sd, rttCommon node of timeout,
       connection-loss, lpd-tree-trace, lpd-group";
    container action-type {
      description
        "Type of action to be taken on threshold
         violation(s)";
      leaf logging {
        type empty;
        description
          "Generate a syslog alarm on threshold violation";
      }
    }
  }

  grouping ncs_template_REPLY {
    description
      "Common node of mpls-lsp-ping, mpls-lsp-trace";
    container reply {
      description
        "Echo reply options for the MPLS LSP operation";
      leaf dscp-bits {
        type ncs_template_Ipsla-lsp-reply-dscp;
        description
          "DSCP bits in the reply IP header";
      }
      leaf mode {
        type ncs_template_Ipsla-lsp-monitor-reply-mode;
        description
          "Enables use of router alert in echo reply
           packets";
      }
    }
  }

  grouping ncs_template_IPSLA-MPLSLM-DEF-CFG-CREATE {
    description
      "Common node of icmp-echo, icmp-path-echo,
       icmp-path-jitter, udp-echo, udp-jitter,
       mpls-lsp-ping, mpls-lsp-traceCommon node of
       mpls-lsp-ping, mpls-lsp-trace";
    leaf create {
      type empty;
      description
        "Create MPLSLM instance with specified type";
    }
  }

  grouping ncs_template_IPSLA-MPLSLM-REACT-CFG-CREATE {
    description
      "Common node of icmp-echo, icmp-path-echo,
       icmp-path-jitter, udp-echo, udp-jitter,
       mpls-lsp-ping, mpls-lsp-traceCommon node of
       mpls-lsp-ping, mpls-lsp-traceCommon node of
       timeout, verify-error, connection-loss,
       jitter-average, jitter-average-sd,
       jitter-average-ds, packet-loss-sd, packet-loss-ds
       , rttCommon node of timeout, connection-loss,
       lpd-tree-trace, lpd-group";
    leaf create {
      type empty;
      description
        "Create reaction condition for a particular
         MPLSLM";
    }
  }

  grouping ncs_template_TOS {
    description
      "Common node of icmp-echo, icmp-path-echo,
       icmp-path-jitter, udp-echo, udp-jitter";
    leaf tos {
      type string;
      // NCS drop default statement
      description
        "Type of service setting in probe packet";
    }
  }

  grouping ncs_template_SOURCE-PORT {
    description
      "Common node of udp-echo, udp-jitter";
    leaf source-port {
      type string;
      description
        "Port number on source device";
    }
  }

  grouping ncs_template_OUTPUT-NEXTHOP {
    description
      "Common node of mpls-lsp-ping, mpls-lsp-trace";
    leaf output-nexthop {
      type string;
      description
        "Echo request output nexthop";
    }
  }

  grouping ncs_template_IPSLA-MPLSLM-DEF-CFG-OUTPUT-NEXTHOP {
    description
      "Common node of mpls-lsp-ping,
       mpls-lsp-traceCommon node of mpls-lsp-ping,
       mpls-lsp-trace";
    leaf output-nexthop {
      type string;
      description
        "Echo request output nexthop";
    }
  }

  grouping ncs_template_ACCESSLIST {
    description
      "Common node of mpls-lsp-ping, mpls-lsp-trace";
    leaf accesslist {
      type xr:ncs_template_Cisco-ios-xr-string;
      description
        "Apply access list to filter PE addresses";
    }
  }

  grouping ncs_template_OUTPUT-INTERFACE {
    description
      "Common node of mpls-lsp-ping, mpls-lsp-trace";
    leaf output-interface {
      type xr:ncs_template_Interface-name;
      description
        "Echo request output interface";
    }
  }

  grouping ncs_template_IPSLA-OP-DEF-MPLS-LSP-CFG-OUTPUT-INTERFACE {
    description
      "Common node of mpls-lsp-ping,
       mpls-lsp-traceCommon node of mpls-lsp-ping,
       mpls-lsp-trace";
    leaf output-interface {
      type xr:ncs_template_Interface-name;
      description
        "Echo request output interface";
    }
  }

  grouping ncs_template_EXP-BITS {
    description
      "Common node of mpls-lsp-ping, mpls-lsp-trace";
    leaf exp-bits {
      type string;
      // NCS drop default statement
      description
        "EXP bits in MPLS LSP echo request header";
    }
  }

  grouping ncs_template_IPSLA-OP-DEF-MPLS-LSP-CFG-EXP-BITS {
    description
      "Common node of mpls-lsp-ping,
       mpls-lsp-traceCommon node of mpls-lsp-ping,
       mpls-lsp-trace";
    leaf exp-bits {
      type string;
      // NCS drop default statement
      description
        "EXP bits in MPLS LSP echo reply header";
    }
  }

  grouping ncs_template_VRF {
    description
      "Common node of icmp-echo, icmp-path-echo,
       icmp-path-jitter, udp-echo, udp-jitter";
    leaf vrf {
      type xr:ncs_template_Cisco-ios-xr-string;
      description
        "Configure IPSLA for a VPN Routing/Forwarding
         instance)";
    }
  }

  grouping ncs_template_IPSLA-MPLSLM-DEF-CFG-VRF {
    description
      "Common node of icmp-echo, icmp-path-echo,
       icmp-path-jitter, udp-echo, udp-jitterCommon node
       of mpls-lsp-ping, mpls-lsp-trace";
    leaf vrf {
      type xr:ncs_template_Cisco-ios-xr-string;
      description
        "Specify a VRF instance to be monitored";
    }
  }

  grouping ncs_template_HISTORY {
    description
      "Common node of icmp-echo, udp-echo, mpls-lsp-ping
       , mpls-lsp-trace";
    container history {
      description
        "Configure the history parameters for this
         operation";
      leaf lives {
        type string;
        // NCS drop default statement
        description
          "Specify number of lives to be kept";
      }
      leaf history-filter {
        type ncs_template_Ipsla-history-filter;
        description
          "Choose type of data to be stored in history
           buffer";
      }
      leaf buckets {
        type string;
        // NCS drop default statement
        description
          "Specify number of history buckets";
      }
    }
  }

  grouping ncs_template_THRESHOLD-LIMITS {
    description
      "Common node of jitter-average-sd,
       jitter-average-ds, jitter-average, packet-loss-ds
       , packet-loss-sd, rtt";
    container threshold-limits {
      presence "Indicates a threshold-limits node is configured.";
      description
        "Specify threshold limits for the monitored
         element";
      leaf lower-limit {
        type string;
        // NCS drop mandatory statement
        description
          "Threshold lower limit value";
      }
      leaf upper-limit {
        type string;
        // NCS drop mandatory statement
        description
          "Threshold upper limit value";
      }
    }
  }

  grouping ncs_template_DEST-PORT {
    description
      "Common node of udp-echo, udp-jitter";
    leaf dest-port {
      type string;
      description
        "Port number on target device";
    }
  }

  grouping ncs_template_LOCAL-PORT {
    description
      "Common node of local-ipv4-address,
       local-ipv6-address";
    container local-port-numbers {
      description
        "Configuration of local port";
      list local-port-number {
        // NCS patched for predictable order
        ordered-by user;
        key "local-port";
        description
          "Enter value of local port";
        container remote-ip {
          description
            "Configure remote ip address";
          container remote-ipv4-addresses {
            description
              "Configure IPV4 address";
            list remote-ipv4-address {
              // NCS patched for predictable order
              ordered-by user;
              key "remotev4-address";
              description
                "Enter value of remote ipv4 address";
              leaf remotev4-address {
                type xr:ncs_template_Cisco-ios-xr-string;
                description
                  "Remote IPv4 address";
              }
              uses ncs_template_REMOTE-PORT;
            }
          }
          container remote-ipv6-addresses {
            description
              "Configure IPV6 address";
            list remote-ipv6-address {
              // NCS patched for predictable order
              ordered-by user;
              key "remotev6-address";
              description
                "Enter value of remote ipv6 address";
              leaf remotev6-address {
                type xr:ncs_template_Cisco-ios-xr-string;
                description
                  "Remote IPv6 address";
              }
              uses ncs_template_REMOTE-PORT;
            }
          }
        }
        leaf local-port {
          type string;
          description
            "Local port";
        }
      }
    }
  }

  grouping ncs_rpc_notif_TAG {
    description
      "Common node of mpls-lsp-ping, mpls-lsp-trace";
    leaf tag {
      type string {
        length "1..128";
      }
      description
        "Add a tag for this MPLSLM instance";
    }
  }

  grouping ncs_rpc_notif_IPSLA-OP-DEF-COMMON-CFG-TAG {
    description
      "Common node of mpls-lsp-ping,
       mpls-lsp-traceCommon node of icmp-echo,
       icmp-path-echo, icmp-path-jitter, udp-echo,
       udp-jitter, mpls-lsp-ping, mpls-lsp-trace";
    leaf tag {
      type string {
        length "1..128";
      }
      description
        "Add a tag for this operation";
    }
  }

  grouping ncs_rpc_notif_LSR-PATH {
    description
      "Common node of icmp-path-echo, icmp-path-jitter";
    container lsr-path {
      presence "Indicates a lsr-path node is configured.";
      description
        "Loose source routing path (up to 8 intermediate
         nodes)";
      leaf node1 {
        type inet:ipv4-address-no-zone;
        mandatory true;
        description
          "IPv4 address of the intermediate node";
      }
      leaf node2 {
        type inet:ipv4-address-no-zone;
        description
          "IPv4 address of the intermediate node";
      }
      leaf node3 {
        type inet:ipv4-address-no-zone;
        description
          "IPv4 address of the intermediate node";
      }
      leaf node4 {
        type inet:ipv4-address-no-zone;
        description
          "IPv4 address of the intermediate node";
      }
      leaf node5 {
        type inet:ipv4-address-no-zone;
        description
          "IPv4 address of the intermediate node";
      }
      leaf node6 {
        type inet:ipv4-address-no-zone;
        description
          "IPv4 address of the intermediate node";
      }
      leaf node7 {
        type inet:ipv4-address-no-zone;
        description
          "IPv4 address of the intermediate node";
      }
      leaf node8 {
        type inet:ipv4-address-no-zone;
        description
          "IPv4 address of the intermediate node";
      }
    }
  }

  grouping ncs_rpc_notif_VERIFY-DATA {
    description
      "Common node of udp-echo, udp-jitter";
    leaf verify-data {
      type empty;
      description
        "Check each IPSLA response for corruption";
    }
  }

  grouping ncs_rpc_notif_SOURCE-ADDRESS {
    description
      "Common node of icmp-echo, icmp-path-echo,
       icmp-path-jitter, udp-echo, udp-jitter,
       mpls-lsp-ping, mpls-lsp-trace";
    leaf source-address {
      type string;
      description
        "Enter IPv4 address of the source device";
    }
  }

  grouping ncs_rpc_notif_FREQUENCY {
    description
      "Common node of icmp-echo, icmp-path-echo,
       icmp-path-jitter, udp-echo, udp-jitter,
       mpls-lsp-ping, mpls-lsp-trace";
    leaf frequency {
      type uint32 {
        range "1..604800";
      }
      units "second";
      default "60";
      description
        "Probe interval in seconds";
    }
  }

  grouping ncs_rpc_notif_DEST-ADDRESS {
    description
      "Common node of icmp-echo, icmp-path-echo,
       icmp-path-jitter, udp-echo, udp-jitter";
    leaf dest-address {
      type string;
      description
        "Enter IPv4 address of the destination device";
    }
  }

  grouping ncs_rpc_notif_SCAN {
    description
      "Common node of mpls-lsp-ping, mpls-lsp-trace";
    container scan {
      description
        "Scanning parameters configuration";
      leaf interval {
        type uint32 {
          range "1..70560";
        }
        units "minute";
        default "240";
        description
          "Time interval for automatic discovery";
      }
      leaf delete-factor {
        type uint32 {
          range "0..2147483647";
        }
        default "1";
        description
          "Number of times for automatic deletion";
      }
    }
  }

  grouping ncs_rpc_notif_DSCP-BITS {
    description
      "Common node of reply, reply";
    leaf dscp-bits {
      type ncs_rpc_notif_Ipsla-lsp-reply-dscp;
      description
        "DSCP bits in the reply IP header";
    }
  }

  grouping ncs_rpc_notif_THRESHOLD-TYPE {
    description
      "Common node of timeout, connection-loss";
    container threshold-type {
      description
        "Type of thresholding to perform on the monitored
         element";
      leaf thresh-type {
        type ncs_rpc_notif_Ipsla-lsp-monitor-threshold-types;
        description
          "Type of thresholding to perform";
      }
      leaf count1 {
        when "../thresh-type != 'immediate'" {
          tailf:xpath-root 3;
          description
            "../ThreshType != Immediate";
        }
        type uint32 {
          range "1..16";
        }
        description
          "Probe count for consecutive";
      }
      leaf count2 {
        when "../thresh-type != 'immediate' and ../thresh-type != 'consecutive'" {
          tailf:xpath-root 3;
          description
            "../ThreshType != Immediate and ../ThreshType
             != Consecutive";
        }
        type uint32 {
          range "1..16";
        }
        description
          "Y value, when threshold type is XofY";
      }
    }
  }

  grouping ncs_rpc_notif_IPSLA-OP-REACT-CFG-THRESHOLD-TYPE {
    description
      "Common node of timeout, connection-lossCommon
       node of timeout, verify-error, connection-loss,
       jitter-average-sd, jitter-average-ds,
       jitter-average, packet-loss-ds, packet-loss-sd,
       rtt";
    container threshold-type {
      description
        "Type of thresholding to perform on the monitored
         element";
      leaf thresh-type {
        type ncs_rpc_notif_Ipsla-threshold-types;
        description
          "Type of thresholding to perform";
      }
      leaf count1 {
        when "../thresh-type != 'immediate'" {
          tailf:xpath-root 3;
          description
            "../ThreshType != Immediate";
        }
        type uint32 {
          range "1..16";
        }
        description
          "Probe count for avarage, consecutive case or X
           value for XofY case";
      }
      leaf count2 {
        when "../thresh-type != 'immediate' and ../thresh-type != 'consecutive' and ../thresh-type != 'average'" {
          tailf:xpath-root 3;
          description
            "../ThreshType != Immediate and ../ThreshType
             != Consecutive and ../ThreshType != Average";
        }
        type uint32 {
          range "1..16";
        }
        description
          "Y value, when threshold type is XofY";
      }
    }
  }

  grouping ncs_rpc_notif_STATISTICS {
    description
      "Common node of icmp-echo, udp-echo, udp-jitter,
       mpls-lsp-ping, mpls-lsp-trace";
    container statistics {
      description
        "Statistics collection aggregated over an hour";
      leaf hours {
        type uint32 {
          range "0..25";
        }
        units "hour";
        default "2";
        description
          "Number of hours for which hourly statistics are
           kept";
      }
      leaf dist-interval {
        type uint32 {
          range "1..100";
        }
        units "millisecond";
        default "20";
        description
          "Specify distribution interval in milliseconds";
      }
      leaf dist-count {
        type uint32 {
          range "1..20";
        }
        default "1";
        description
          "Count of distribution intervals maintained";
      }
    }
  }

  grouping ncs_rpc_notif_IPSLA-MPLSLM-DEF-CFG-STATISTICS {
    description
      "Common node of icmp-echo, udp-echo, udp-jitter,
       mpls-lsp-ping, mpls-lsp-traceCommon node of
       mpls-lsp-ping, mpls-lsp-trace";
    container statistics {
      description
        "Statistics collection aggregated over an hour";
      leaf hours {
        type uint32 {
          range "0..2";
        }
        units "hour";
        default "2";
        description
          "Number of hours for which hourly statistics are
           kept";
      }
    }
  }

  grouping ncs_rpc_notif_TIMEOUT {
    description
      "Common node of mpls-lsp-ping, mpls-lsp-trace";
    leaf timeout {
      type uint32 {
        range "1..604800000";
      }
      units "millisecond";
      default "5000";
      description
        "Probe/Control timeout in milliseconds";
    }
  }

  grouping ncs_rpc_notif_IPSLA-OP-DEF-COMMON-CFG-TIMEOUT {
    description
      "Common node of mpls-lsp-ping,
       mpls-lsp-traceCommon node of icmp-echo,
       icmp-path-echo, icmp-path-jitter, udp-echo,
       udp-jitter, mpls-lsp-ping, mpls-lsp-trace";
    leaf timeout {
      type uint32 {
        range "1..604800000";
      }
      units "millisecond";
      default "5000";
      description
        "Probe/Control timeout in milliseconds";
    }
  }

  grouping ncs_rpc_notif_CONTROL-DISABLE {
    description
      "Common node of udp-echo, udp-jitter";
    leaf control-disable {
      type empty;
      description
        "Disable control packets";
    }
  }

  grouping ncs_rpc_notif_FORCE-EXPLICIT-NULL {
    description
      "Common node of mpls-lsp-ping, mpls-lsp-trace";
    leaf force-explicit-null {
      type empty;
      description
        "Forced option for the MPLS LSP operation";
    }
  }

  grouping ncs_rpc_notif_IPSLA-MPLSLM-DEF-CFG-FORCE-EXPLICIT-NULL {
    description
      "Common node of mpls-lsp-ping,
       mpls-lsp-traceCommon node of mpls-lsp-ping,
       mpls-lsp-trace";
    leaf force-explicit-null {
      type empty;
      description
        "Forced option for the MPLS LSP operation";
    }
  }

  grouping ncs_rpc_notif_REMOTE-PORT {
    description
      "Common node of remote-ipv4-address,
       remote-ipv6-address";
    container remote-port-numbers {
      description
        "Configuration of remote port";
      list remote-port-number {
        key "remote-port";
        description
          "Enter value of remote port";
        container vrf-names {
          description
            "Configuration of vrf";
          list vrf-name {
            key "vrf-name";
            description
              "Configure vrf name value";
            leaf vrf-name {
              type xr:ncs_rpc_notif_Cisco-ios-xr-string;
              description
                "VRF Name";
            }
          }
        }
        leaf remote-port {
          type inet:port-number;
          description
            "Remote port";
        }
      }
    }
  }

  grouping ncs_rpc_notif_ENHANCED-STATS-TABLE {
    description
      "Common node of icmp-echo, udp-echo, udp-jitter,
       mpls-lsp-ping";
    container enhanced-stats {
      description
        "Table of statistics collection intervals";
      list enhanced-stat {
        key "interval";
        description
          "Statistics for a specified time interval";
        leaf buckets {
          type uint32 {
            range "1..100";
          }
          default "15";
          description
            "Buckets of enhanced statistics kept";
        }
        leaf interval {
          type uint32 {
            range "1..3600";
          }
          units "second";
          description
            "Interval in seconds";
        }
      }
    }
  }

  grouping ncs_rpc_notif_LSP-SELECTOR {
    description
      "Common node of mpls-lsp-ping, mpls-lsp-trace";
    leaf lsp-selector {
      type inet:ipv4-address-no-zone;
      default "1.0.0.127";
      description
        "Attributes used for path selection during LSP
         load balancing";
    }
  }

  grouping ncs_rpc_notif_IPSLA-MPLSLM-DEF-CFG-LSP-SELECTOR {
    description
      "Common node of mpls-lsp-ping,
       mpls-lsp-traceCommon node of mpls-lsp-ping,
       mpls-lsp-trace";
    leaf lsp-selector {
      type inet:ipv4-address-no-zone;
      default "1.0.0.127";
      description
        "Attributes used for path selection during LSP
         load balancing";
    }
  }

  grouping ncs_rpc_notif_ACTION-TYPE {
    description
      "Common node of timeout, verify-error,
       connection-loss, jitter-average-sd,
       jitter-average-ds, jitter-average, packet-loss-ds
       , packet-loss-sd, rtt";
    container action-type {
      description
        "Type of action to be taken on threshold
         violation(s)";
      leaf logging {
        type empty;
        description
          "Generate a syslog alarm on threshold violation";
      }
      leaf trigger {
        type empty;
        description
          "Generate trigger to active reaction triggered
           operation(s)";
      }
    }
  }

  grouping ncs_rpc_notif_IPSLA-MPLSLM-REACT-CFG-ACTION-TYPE {
    description
      "Common node of timeout, verify-error,
       connection-loss, jitter-average-sd,
       jitter-average-ds, jitter-average, packet-loss-ds
       , packet-loss-sd, rttCommon node of timeout,
       connection-loss, lpd-tree-trace, lpd-group";
    container action-type {
      description
        "Type of action to be taken on threshold
         violation(s)";
      leaf logging {
        type empty;
        description
          "Generate a syslog alarm on threshold violation";
      }
    }
  }

  grouping ncs_rpc_notif_REPLY {
    description
      "Common node of mpls-lsp-ping, mpls-lsp-trace";
    container reply {
      description
        "Echo reply options for the MPLS LSP operation";
      leaf dscp-bits {
        type ncs_rpc_notif_Ipsla-lsp-reply-dscp;
        description
          "DSCP bits in the reply IP header";
      }
      leaf mode {
        type ncs_rpc_notif_Ipsla-lsp-monitor-reply-mode;
        description
          "Enables use of router alert in echo reply
           packets";
      }
    }
  }

  grouping ncs_rpc_notif_IPSLA-MPLSLM-DEF-CFG-CREATE {
    description
      "Common node of icmp-echo, icmp-path-echo,
       icmp-path-jitter, udp-echo, udp-jitter,
       mpls-lsp-ping, mpls-lsp-traceCommon node of
       mpls-lsp-ping, mpls-lsp-trace";
    leaf create {
      type empty;
      description
        "Create MPLSLM instance with specified type";
    }
  }

  grouping ncs_rpc_notif_IPSLA-MPLSLM-REACT-CFG-CREATE {
    description
      "Common node of icmp-echo, icmp-path-echo,
       icmp-path-jitter, udp-echo, udp-jitter,
       mpls-lsp-ping, mpls-lsp-traceCommon node of
       mpls-lsp-ping, mpls-lsp-traceCommon node of
       timeout, verify-error, connection-loss,
       jitter-average, jitter-average-sd,
       jitter-average-ds, packet-loss-sd, packet-loss-ds
       , rttCommon node of timeout, connection-loss,
       lpd-tree-trace, lpd-group";
    leaf create {
      type empty;
      description
        "Create reaction condition for a particular
         MPLSLM";
    }
  }

  grouping ncs_rpc_notif_TOS {
    description
      "Common node of icmp-echo, icmp-path-echo,
       icmp-path-jitter, udp-echo, udp-jitter";
    leaf tos {
      type uint32 {
        range "0..255";
      }
      default "0";
      description
        "Type of service setting in probe packet";
    }
  }

  grouping ncs_rpc_notif_SOURCE-PORT {
    description
      "Common node of udp-echo, udp-jitter";
    leaf source-port {
      type inet:port-number;
      description
        "Port number on source device";
    }
  }

  grouping ncs_rpc_notif_OUTPUT-NEXTHOP {
    description
      "Common node of mpls-lsp-ping, mpls-lsp-trace";
    leaf output-nexthop {
      type inet:ipv4-address-no-zone;
      description
        "Echo request output nexthop";
    }
  }

  grouping ncs_rpc_notif_IPSLA-MPLSLM-DEF-CFG-OUTPUT-NEXTHOP {
    description
      "Common node of mpls-lsp-ping,
       mpls-lsp-traceCommon node of mpls-lsp-ping,
       mpls-lsp-trace";
    leaf output-nexthop {
      type inet:ipv4-address-no-zone;
      description
        "Echo request output nexthop";
    }
  }

  grouping ncs_rpc_notif_ACCESSLIST {
    description
      "Common node of mpls-lsp-ping, mpls-lsp-trace";
    leaf accesslist {
      type xr:ncs_rpc_notif_Cisco-ios-xr-string;
      description
        "Apply access list to filter PE addresses";
    }
  }

  grouping ncs_rpc_notif_OUTPUT-INTERFACE {
    description
      "Common node of mpls-lsp-ping, mpls-lsp-trace";
    leaf output-interface {
      type xr:ncs_rpc_notif_Interface-name;
      description
        "Echo request output interface";
    }
  }

  grouping ncs_rpc_notif_IPSLA-OP-DEF-MPLS-LSP-CFG-OUTPUT-INTERFACE {
    description
      "Common node of mpls-lsp-ping,
       mpls-lsp-traceCommon node of mpls-lsp-ping,
       mpls-lsp-trace";
    leaf output-interface {
      type xr:ncs_rpc_notif_Interface-name;
      description
        "Echo request output interface";
    }
  }

  grouping ncs_rpc_notif_EXP-BITS {
    description
      "Common node of mpls-lsp-ping, mpls-lsp-trace";
    leaf exp-bits {
      type uint32 {
        range "0..7";
      }
      default "0";
      description
        "EXP bits in MPLS LSP echo request header";
    }
  }

  grouping ncs_rpc_notif_IPSLA-OP-DEF-MPLS-LSP-CFG-EXP-BITS {
    description
      "Common node of mpls-lsp-ping,
       mpls-lsp-traceCommon node of mpls-lsp-ping,
       mpls-lsp-trace";
    leaf exp-bits {
      type uint32 {
        range "0..7";
      }
      default "0";
      description
        "EXP bits in MPLS LSP echo reply header";
    }
  }

  grouping ncs_rpc_notif_VRF {
    description
      "Common node of icmp-echo, icmp-path-echo,
       icmp-path-jitter, udp-echo, udp-jitter";
    leaf vrf {
      type xr:ncs_rpc_notif_Cisco-ios-xr-string;
      description
        "Configure IPSLA for a VPN Routing/Forwarding
         instance)";
    }
  }

  grouping ncs_rpc_notif_IPSLA-MPLSLM-DEF-CFG-VRF {
    description
      "Common node of icmp-echo, icmp-path-echo,
       icmp-path-jitter, udp-echo, udp-jitterCommon node
       of mpls-lsp-ping, mpls-lsp-trace";
    leaf vrf {
      type xr:ncs_rpc_notif_Cisco-ios-xr-string;
      description
        "Specify a VRF instance to be monitored";
    }
  }

  grouping ncs_rpc_notif_HISTORY {
    description
      "Common node of icmp-echo, udp-echo, mpls-lsp-ping
       , mpls-lsp-trace";
    container history {
      description
        "Configure the history parameters for this
         operation";
      leaf lives {
        type uint32 {
          range "0..2";
        }
        default "0";
        description
          "Specify number of lives to be kept";
      }
      leaf history-filter {
        type ncs_rpc_notif_Ipsla-history-filter;
        description
          "Choose type of data to be stored in history
           buffer";
      }
      leaf buckets {
        type uint32 {
          range "1..60";
        }
        default "15";
        description
          "Specify number of history buckets";
      }
    }
  }

  grouping ncs_rpc_notif_THRESHOLD-LIMITS {
    description
      "Common node of jitter-average-sd,
       jitter-average-ds, jitter-average, packet-loss-ds
       , packet-loss-sd, rtt";
    container threshold-limits {
      presence "Indicates a threshold-limits node is configured.";
      description
        "Specify threshold limits for the monitored
         element";
      leaf lower-limit {
        type uint32 {
          range "1..4294967295";
        }
        mandatory true;
        description
          "Threshold lower limit value";
      }
      leaf upper-limit {
        type uint32 {
          range "1..4294967295";
        }
        mandatory true;
        description
          "Threshold upper limit value";
      }
    }
  }

  grouping ncs_rpc_notif_DEST-PORT {
    description
      "Common node of udp-echo, udp-jitter";
    leaf dest-port {
      type inet:port-number;
      description
        "Port number on target device";
    }
  }

  grouping ncs_rpc_notif_LOCAL-PORT {
    description
      "Common node of local-ipv4-address,
       local-ipv6-address";
    container local-port-numbers {
      description
        "Configuration of local port";
      list local-port-number {
        key "local-port";
        description
          "Enter value of local port";
        container remote-ip {
          description
            "Configure remote ip address";
          container remote-ipv4-addresses {
            description
              "Configure IPV4 address";
            list remote-ipv4-address {
              key "remotev4-address";
              description
                "Enter value of remote ipv4 address";
              leaf remotev4-address {
                type xr:ncs_rpc_notif_Cisco-ios-xr-string;
                description
                  "Remote IPv4 address";
              }
              uses ncs_rpc_notif_REMOTE-PORT;
            }
          }
          container remote-ipv6-addresses {
            description
              "Configure IPV6 address";
            list remote-ipv6-address {
              key "remotev6-address";
              description
                "Enter value of remote ipv6 address";
              leaf remotev6-address {
                type xr:ncs_rpc_notif_Cisco-ios-xr-string;
                description
                  "Remote IPv6 address";
              }
              uses ncs_rpc_notif_REMOTE-PORT;
            }
          }
        }
        leaf local-port {
          type inet:port-number;
          description
            "Local port";
        }
      }
    }
  }

  grouping live_ncs_TAG {
    description
      "Common node of mpls-lsp-ping, mpls-lsp-trace";
    leaf tag {
      type string {
        length "1..128";
      }
      description
        "Add a tag for this MPLSLM instance";
    }
  }

  grouping live_ncs_IPSLA-OP-DEF-COMMON-CFG-TAG {
    description
      "Common node of mpls-lsp-ping,
       mpls-lsp-traceCommon node of icmp-echo,
       icmp-path-echo, icmp-path-jitter, udp-echo,
       udp-jitter, mpls-lsp-ping, mpls-lsp-trace";
    leaf tag {
      type string {
        length "1..128";
      }
      description
        "Add a tag for this operation";
    }
  }

  grouping live_ncs_LSR-PATH {
    description
      "Common node of icmp-path-echo, icmp-path-jitter";
    container lsr-path {
      presence "Indicates a lsr-path node is configured.";
      description
        "Loose source routing path (up to 8 intermediate
         nodes)";
      leaf node1 {
        type inet:ipv4-address-no-zone;
        // NCS drop mandatory statement
        description
          "IPv4 address of the intermediate node";
      }
      leaf node2 {
        type inet:ipv4-address-no-zone;
        description
          "IPv4 address of the intermediate node";
      }
      leaf node3 {
        type inet:ipv4-address-no-zone;
        description
          "IPv4 address of the intermediate node";
      }
      leaf node4 {
        type inet:ipv4-address-no-zone;
        description
          "IPv4 address of the intermediate node";
      }
      leaf node5 {
        type inet:ipv4-address-no-zone;
        description
          "IPv4 address of the intermediate node";
      }
      leaf node6 {
        type inet:ipv4-address-no-zone;
        description
          "IPv4 address of the intermediate node";
      }
      leaf node7 {
        type inet:ipv4-address-no-zone;
        description
          "IPv4 address of the intermediate node";
      }
      leaf node8 {
        type inet:ipv4-address-no-zone;
        description
          "IPv4 address of the intermediate node";
      }
    }
  }

  grouping live_ncs_VERIFY-DATA {
    description
      "Common node of udp-echo, udp-jitter";
    leaf verify-data {
      type empty;
      description
        "Check each IPSLA response for corruption";
    }
  }

  grouping live_ncs_SOURCE-ADDRESS {
    description
      "Common node of icmp-echo, icmp-path-echo,
       icmp-path-jitter, udp-echo, udp-jitter,
       mpls-lsp-ping, mpls-lsp-trace";
    leaf source-address {
      type string;
      description
        "Enter IPv4 address of the source device";
    }
  }

  grouping live_ncs_FREQUENCY {
    description
      "Common node of icmp-echo, icmp-path-echo,
       icmp-path-jitter, udp-echo, udp-jitter,
       mpls-lsp-ping, mpls-lsp-trace";
    leaf frequency {
      type uint32 {
        range "1..604800";
      }
      units "second";
      // NCS drop default statement
      description
        "Probe interval in seconds";
    }
  }

  grouping live_ncs_DEST-ADDRESS {
    description
      "Common node of icmp-echo, icmp-path-echo,
       icmp-path-jitter, udp-echo, udp-jitter";
    leaf dest-address {
      type string;
      description
        "Enter IPv4 address of the destination device";
    }
  }

  grouping live_ncs_SCAN {
    description
      "Common node of mpls-lsp-ping, mpls-lsp-trace";
    container scan {
      description
        "Scanning parameters configuration";
      leaf interval {
        type uint32 {
          range "1..70560";
        }
        units "minute";
        // NCS drop default statement
        description
          "Time interval for automatic discovery";
      }
      leaf delete-factor {
        type uint32 {
          range "0..2147483647";
        }
        // NCS drop default statement
        description
          "Number of times for automatic deletion";
      }
    }
  }

  grouping live_ncs_DSCP-BITS {
    description
      "Common node of reply, reply";
    leaf dscp-bits {
      type live_ncs_Ipsla-lsp-reply-dscp;
      description
        "DSCP bits in the reply IP header";
    }
  }

  grouping live_ncs_THRESHOLD-TYPE {
    description
      "Common node of timeout, connection-loss";
    container threshold-type {
      description
        "Type of thresholding to perform on the monitored
         element";
      leaf thresh-type {
        type live_ncs_Ipsla-lsp-monitor-threshold-types;
        description
          "Type of thresholding to perform";
      }
      leaf count1 {
        // NCS drop when statement
        type uint32 {
          range "1..16";
        }
        description
          "Probe count for consecutive";
      }
      leaf count2 {
        // NCS drop when statement
        type uint32 {
          range "1..16";
        }
        description
          "Y value, when threshold type is XofY";
      }
    }
  }

  grouping live_ncs_IPSLA-OP-REACT-CFG-THRESHOLD-TYPE {
    description
      "Common node of timeout, connection-lossCommon
       node of timeout, verify-error, connection-loss,
       jitter-average-sd, jitter-average-ds,
       jitter-average, packet-loss-ds, packet-loss-sd,
       rtt";
    container threshold-type {
      description
        "Type of thresholding to perform on the monitored
         element";
      leaf thresh-type {
        type live_ncs_Ipsla-threshold-types;
        description
          "Type of thresholding to perform";
      }
      leaf count1 {
        // NCS drop when statement
        type uint32 {
          range "1..16";
        }
        description
          "Probe count for avarage, consecutive case or X
           value for XofY case";
      }
      leaf count2 {
        // NCS drop when statement
        type uint32 {
          range "1..16";
        }
        description
          "Y value, when threshold type is XofY";
      }
    }
  }

  grouping live_ncs_STATISTICS {
    description
      "Common node of icmp-echo, udp-echo, udp-jitter,
       mpls-lsp-ping, mpls-lsp-trace";
    container statistics {
      description
        "Statistics collection aggregated over an hour";
      leaf hours {
        type uint32 {
          range "0..25";
        }
        units "hour";
        // NCS drop default statement
        description
          "Number of hours for which hourly statistics are
           kept";
      }
      leaf dist-interval {
        type uint32 {
          range "1..100";
        }
        units "millisecond";
        // NCS drop default statement
        description
          "Specify distribution interval in milliseconds";
      }
      leaf dist-count {
        type uint32 {
          range "1..20";
        }
        // NCS drop default statement
        description
          "Count of distribution intervals maintained";
      }
    }
  }

  grouping live_ncs_IPSLA-MPLSLM-DEF-CFG-STATISTICS {
    description
      "Common node of icmp-echo, udp-echo, udp-jitter,
       mpls-lsp-ping, mpls-lsp-traceCommon node of
       mpls-lsp-ping, mpls-lsp-trace";
    container statistics {
      description
        "Statistics collection aggregated over an hour";
      leaf hours {
        type uint32 {
          range "0..2";
        }
        units "hour";
        // NCS drop default statement
        description
          "Number of hours for which hourly statistics are
           kept";
      }
    }
  }

  grouping live_ncs_TIMEOUT {
    description
      "Common node of mpls-lsp-ping, mpls-lsp-trace";
    leaf timeout {
      type uint32 {
        range "1..604800000";
      }
      units "millisecond";
      // NCS drop default statement
      description
        "Probe/Control timeout in milliseconds";
    }
  }

  grouping live_ncs_IPSLA-OP-DEF-COMMON-CFG-TIMEOUT {
    description
      "Common node of mpls-lsp-ping,
       mpls-lsp-traceCommon node of icmp-echo,
       icmp-path-echo, icmp-path-jitter, udp-echo,
       udp-jitter, mpls-lsp-ping, mpls-lsp-trace";
    leaf timeout {
      type uint32 {
        range "1..604800000";
      }
      units "millisecond";
      // NCS drop default statement
      description
        "Probe/Control timeout in milliseconds";
    }
  }

  grouping live_ncs_CONTROL-DISABLE {
    description
      "Common node of udp-echo, udp-jitter";
    leaf control-disable {
      type empty;
      description
        "Disable control packets";
    }
  }

  grouping live_ncs_FORCE-EXPLICIT-NULL {
    description
      "Common node of mpls-lsp-ping, mpls-lsp-trace";
    leaf force-explicit-null {
      type empty;
      description
        "Forced option for the MPLS LSP operation";
    }
  }

  grouping live_ncs_IPSLA-MPLSLM-DEF-CFG-FORCE-EXPLICIT-NULL {
    description
      "Common node of mpls-lsp-ping,
       mpls-lsp-traceCommon node of mpls-lsp-ping,
       mpls-lsp-trace";
    leaf force-explicit-null {
      type empty;
      description
        "Forced option for the MPLS LSP operation";
    }
  }

  grouping live_ncs_REMOTE-PORT {
    description
      "Common node of remote-ipv4-address,
       remote-ipv6-address";
    container remote-port-numbers {
      description
        "Configuration of remote port";
      list remote-port-number {
        key "remote-port";
        description
          "Enter value of remote port";
        container vrf-names {
          description
            "Configuration of vrf";
          list vrf-name {
            key "vrf-name";
            description
              "Configure vrf name value";
            leaf vrf-name {
              type xr:live_ncs_Cisco-ios-xr-string;
              description
                "VRF Name";
            }
          }
        }
        leaf remote-port {
          type inet:port-number;
          description
            "Remote port";
        }
      }
    }
  }

  grouping live_ncs_ENHANCED-STATS-TABLE {
    description
      "Common node of icmp-echo, udp-echo, udp-jitter,
       mpls-lsp-ping";
    container enhanced-stats {
      description
        "Table of statistics collection intervals";
      list enhanced-stat {
        key "interval";
        description
          "Statistics for a specified time interval";
        leaf buckets {
          type uint32 {
            range "1..100";
          }
          // NCS drop default statement
          description
            "Buckets of enhanced statistics kept";
        }
        leaf interval {
          type uint32 {
            range "1..3600";
          }
          units "second";
          description
            "Interval in seconds";
        }
      }
    }
  }

  grouping live_ncs_LSP-SELECTOR {
    description
      "Common node of mpls-lsp-ping, mpls-lsp-trace";
    leaf lsp-selector {
      type inet:ipv4-address-no-zone;
      // NCS drop default statement
      description
        "Attributes used for path selection during LSP
         load balancing";
    }
  }

  grouping live_ncs_IPSLA-MPLSLM-DEF-CFG-LSP-SELECTOR {
    description
      "Common node of mpls-lsp-ping,
       mpls-lsp-traceCommon node of mpls-lsp-ping,
       mpls-lsp-trace";
    leaf lsp-selector {
      type inet:ipv4-address-no-zone;
      // NCS drop default statement
      description
        "Attributes used for path selection during LSP
         load balancing";
    }
  }

  grouping live_ncs_ACTION-TYPE {
    description
      "Common node of timeout, verify-error,
       connection-loss, jitter-average-sd,
       jitter-average-ds, jitter-average, packet-loss-ds
       , packet-loss-sd, rtt";
    container action-type {
      description
        "Type of action to be taken on threshold
         violation(s)";
      leaf logging {
        type empty;
        description
          "Generate a syslog alarm on threshold violation";
      }
      leaf trigger {
        type empty;
        description
          "Generate trigger to active reaction triggered
           operation(s)";
      }
    }
  }

  grouping live_ncs_IPSLA-MPLSLM-REACT-CFG-ACTION-TYPE {
    description
      "Common node of timeout, verify-error,
       connection-loss, jitter-average-sd,
       jitter-average-ds, jitter-average, packet-loss-ds
       , packet-loss-sd, rttCommon node of timeout,
       connection-loss, lpd-tree-trace, lpd-group";
    container action-type {
      description
        "Type of action to be taken on threshold
         violation(s)";
      leaf logging {
        type empty;
        description
          "Generate a syslog alarm on threshold violation";
      }
    }
  }

  grouping live_ncs_REPLY {
    description
      "Common node of mpls-lsp-ping, mpls-lsp-trace";
    container reply {
      description
        "Echo reply options for the MPLS LSP operation";
      leaf dscp-bits {
        type live_ncs_Ipsla-lsp-reply-dscp;
        description
          "DSCP bits in the reply IP header";
      }
      leaf mode {
        type live_ncs_Ipsla-lsp-monitor-reply-mode;
        description
          "Enables use of router alert in echo reply
           packets";
      }
    }
  }

  grouping live_ncs_IPSLA-MPLSLM-DEF-CFG-CREATE {
    description
      "Common node of icmp-echo, icmp-path-echo,
       icmp-path-jitter, udp-echo, udp-jitter,
       mpls-lsp-ping, mpls-lsp-traceCommon node of
       mpls-lsp-ping, mpls-lsp-trace";
    leaf create {
      type empty;
      description
        "Create MPLSLM instance with specified type";
    }
  }

  grouping live_ncs_IPSLA-MPLSLM-REACT-CFG-CREATE {
    description
      "Common node of icmp-echo, icmp-path-echo,
       icmp-path-jitter, udp-echo, udp-jitter,
       mpls-lsp-ping, mpls-lsp-traceCommon node of
       mpls-lsp-ping, mpls-lsp-traceCommon node of
       timeout, verify-error, connection-loss,
       jitter-average, jitter-average-sd,
       jitter-average-ds, packet-loss-sd, packet-loss-ds
       , rttCommon node of timeout, connection-loss,
       lpd-tree-trace, lpd-group";
    leaf create {
      type empty;
      description
        "Create reaction condition for a particular
         MPLSLM";
    }
  }

  grouping live_ncs_TOS {
    description
      "Common node of icmp-echo, icmp-path-echo,
       icmp-path-jitter, udp-echo, udp-jitter";
    leaf tos {
      type uint32 {
        range "0..255";
      }
      // NCS drop default statement
      description
        "Type of service setting in probe packet";
    }
  }

  grouping live_ncs_SOURCE-PORT {
    description
      "Common node of udp-echo, udp-jitter";
    leaf source-port {
      type inet:port-number;
      description
        "Port number on source device";
    }
  }

  grouping live_ncs_OUTPUT-NEXTHOP {
    description
      "Common node of mpls-lsp-ping, mpls-lsp-trace";
    leaf output-nexthop {
      type inet:ipv4-address-no-zone;
      description
        "Echo request output nexthop";
    }
  }

  grouping live_ncs_IPSLA-MPLSLM-DEF-CFG-OUTPUT-NEXTHOP {
    description
      "Common node of mpls-lsp-ping,
       mpls-lsp-traceCommon node of mpls-lsp-ping,
       mpls-lsp-trace";
    leaf output-nexthop {
      type inet:ipv4-address-no-zone;
      description
        "Echo request output nexthop";
    }
  }

  grouping live_ncs_ACCESSLIST {
    description
      "Common node of mpls-lsp-ping, mpls-lsp-trace";
    leaf accesslist {
      type xr:live_ncs_Cisco-ios-xr-string;
      description
        "Apply access list to filter PE addresses";
    }
  }

  grouping live_ncs_OUTPUT-INTERFACE {
    description
      "Common node of mpls-lsp-ping, mpls-lsp-trace";
    leaf output-interface {
      type xr:live_ncs_Interface-name;
      description
        "Echo request output interface";
    }
  }

  grouping live_ncs_IPSLA-OP-DEF-MPLS-LSP-CFG-OUTPUT-INTERFACE {
    description
      "Common node of mpls-lsp-ping,
       mpls-lsp-traceCommon node of mpls-lsp-ping,
       mpls-lsp-trace";
    leaf output-interface {
      type xr:live_ncs_Interface-name;
      description
        "Echo request output interface";
    }
  }

  grouping live_ncs_EXP-BITS {
    description
      "Common node of mpls-lsp-ping, mpls-lsp-trace";
    leaf exp-bits {
      type uint32 {
        range "0..7";
      }
      // NCS drop default statement
      description
        "EXP bits in MPLS LSP echo request header";
    }
  }

  grouping live_ncs_IPSLA-OP-DEF-MPLS-LSP-CFG-EXP-BITS {
    description
      "Common node of mpls-lsp-ping,
       mpls-lsp-traceCommon node of mpls-lsp-ping,
       mpls-lsp-trace";
    leaf exp-bits {
      type uint32 {
        range "0..7";
      }
      // NCS drop default statement
      description
        "EXP bits in MPLS LSP echo reply header";
    }
  }

  grouping live_ncs_VRF {
    description
      "Common node of icmp-echo, icmp-path-echo,
       icmp-path-jitter, udp-echo, udp-jitter";
    leaf vrf {
      type xr:live_ncs_Cisco-ios-xr-string;
      description
        "Configure IPSLA for a VPN Routing/Forwarding
         instance)";
    }
  }

  grouping live_ncs_IPSLA-MPLSLM-DEF-CFG-VRF {
    description
      "Common node of icmp-echo, icmp-path-echo,
       icmp-path-jitter, udp-echo, udp-jitterCommon node
       of mpls-lsp-ping, mpls-lsp-trace";
    leaf vrf {
      type xr:live_ncs_Cisco-ios-xr-string;
      description
        "Specify a VRF instance to be monitored";
    }
  }

  grouping live_ncs_HISTORY {
    description
      "Common node of icmp-echo, udp-echo, mpls-lsp-ping
       , mpls-lsp-trace";
    container history {
      description
        "Configure the history parameters for this
         operation";
      leaf lives {
        type uint32 {
          range "0..2";
        }
        // NCS drop default statement
        description
          "Specify number of lives to be kept";
      }
      leaf history-filter {
        type live_ncs_Ipsla-history-filter;
        description
          "Choose type of data to be stored in history
           buffer";
      }
      leaf buckets {
        type uint32 {
          range "1..60";
        }
        // NCS drop default statement
        description
          "Specify number of history buckets";
      }
    }
  }

  grouping live_ncs_THRESHOLD-LIMITS {
    description
      "Common node of jitter-average-sd,
       jitter-average-ds, jitter-average, packet-loss-ds
       , packet-loss-sd, rtt";
    container threshold-limits {
      presence "Indicates a threshold-limits node is configured.";
      description
        "Specify threshold limits for the monitored
         element";
      leaf lower-limit {
        type uint32 {
          range "1..4294967295";
        }
        // NCS drop mandatory statement
        description
          "Threshold lower limit value";
      }
      leaf upper-limit {
        type uint32 {
          range "1..4294967295";
        }
        // NCS drop mandatory statement
        description
          "Threshold upper limit value";
      }
    }
  }

  grouping live_ncs_DEST-PORT {
    description
      "Common node of udp-echo, udp-jitter";
    leaf dest-port {
      type inet:port-number;
      description
        "Port number on target device";
    }
  }

  grouping live_ncs_LOCAL-PORT {
    description
      "Common node of local-ipv4-address,
       local-ipv6-address";
    container local-port-numbers {
      description
        "Configuration of local port";
      list local-port-number {
        key "local-port";
        description
          "Enter value of local port";
        container remote-ip {
          description
            "Configure remote ip address";
          container remote-ipv4-addresses {
            description
              "Configure IPV4 address";
            list remote-ipv4-address {
              key "remotev4-address";
              description
                "Enter value of remote ipv4 address";
              leaf remotev4-address {
                type xr:live_ncs_Cisco-ios-xr-string;
                description
                  "Remote IPv4 address";
              }
              uses live_ncs_REMOTE-PORT;
            }
          }
          container remote-ipv6-addresses {
            description
              "Configure IPV6 address";
            list remote-ipv6-address {
              key "remotev6-address";
              description
                "Enter value of remote ipv6 address";
              leaf remotev6-address {
                type xr:live_ncs_Cisco-ios-xr-string;
                description
                  "Remote IPv6 address";
              }
              uses live_ncs_REMOTE-PORT;
            }
          }
        }
        leaf local-port {
          type inet:port-number;
          description
            "Local port";
        }
      }
    }
  }

  grouping TAG {
    description
      "Common node of mpls-lsp-ping, mpls-lsp-trace";
    leaf tag {
      type string {
        length "1..128";
      }
      description
        "Add a tag for this MPLSLM instance";
    }
  }

  grouping IPSLA-OP-DEF-COMMON-CFG-TAG {
    description
      "Common node of mpls-lsp-ping,
       mpls-lsp-traceCommon node of icmp-echo,
       icmp-path-echo, icmp-path-jitter, udp-echo,
       udp-jitter, mpls-lsp-ping, mpls-lsp-trace";
    leaf tag {
      type string {
        length "1..128";
      }
      description
        "Add a tag for this operation";
    }
  }

  grouping LSR-PATH {
    description
      "Common node of icmp-path-echo, icmp-path-jitter";
    container lsr-path {
      presence "Indicates a lsr-path node is configured.";
      description
        "Loose source routing path (up to 8 intermediate
         nodes)";
      leaf node1 {
        type inet:ipv4-address-no-zone;
        mandatory true;
        description
          "IPv4 address of the intermediate node";
      }
      leaf node2 {
        type inet:ipv4-address-no-zone;
        description
          "IPv4 address of the intermediate node";
      }
      leaf node3 {
        type inet:ipv4-address-no-zone;
        description
          "IPv4 address of the intermediate node";
      }
      leaf node4 {
        type inet:ipv4-address-no-zone;
        description
          "IPv4 address of the intermediate node";
      }
      leaf node5 {
        type inet:ipv4-address-no-zone;
        description
          "IPv4 address of the intermediate node";
      }
      leaf node6 {
        type inet:ipv4-address-no-zone;
        description
          "IPv4 address of the intermediate node";
      }
      leaf node7 {
        type inet:ipv4-address-no-zone;
        description
          "IPv4 address of the intermediate node";
      }
      leaf node8 {
        type inet:ipv4-address-no-zone;
        description
          "IPv4 address of the intermediate node";
      }
    }
  }

  grouping VERIFY-DATA {
    description
      "Common node of udp-echo, udp-jitter";
    leaf verify-data {
      type empty;
      description
        "Check each IPSLA response for corruption";
    }
  }

  grouping SOURCE-ADDRESS {
    description
      "Common node of icmp-echo, icmp-path-echo,
       icmp-path-jitter, udp-echo, udp-jitter,
       mpls-lsp-ping, mpls-lsp-trace";
    leaf source-address {
      type string;
      description
        "Enter IPv4 address of the source device";
    }
  }

  grouping FREQUENCY {
    description
      "Common node of icmp-echo, icmp-path-echo,
       icmp-path-jitter, udp-echo, udp-jitter,
       mpls-lsp-ping, mpls-lsp-trace";
    leaf frequency {
      type uint32 {
        range "1..604800";
      }
      units "second";
      default "60";
      description
        "Probe interval in seconds";
    }
  }

  grouping DEST-ADDRESS {
    description
      "Common node of icmp-echo, icmp-path-echo,
       icmp-path-jitter, udp-echo, udp-jitter";
    leaf dest-address {
      type string;
      description
        "Enter IPv4 address of the destination device";
    }
  }

  grouping SCAN {
    description
      "Common node of mpls-lsp-ping, mpls-lsp-trace";
    container scan {
      description
        "Scanning parameters configuration";
      leaf interval {
        type uint32 {
          range "1..70560";
        }
        units "minute";
        default "240";
        description
          "Time interval for automatic discovery";
      }
      leaf delete-factor {
        type uint32 {
          range "0..2147483647";
        }
        default "1";
        description
          "Number of times for automatic deletion";
      }
    }
  }

  grouping DSCP-BITS {
    description
      "Common node of reply, reply";
    leaf dscp-bits {
      type Ipsla-lsp-reply-dscp;
      description
        "DSCP bits in the reply IP header";
    }
  }

  grouping THRESHOLD-TYPE {
    description
      "Common node of timeout, connection-loss";
    container threshold-type {
      description
        "Type of thresholding to perform on the monitored
         element";
      leaf thresh-type {
        type Ipsla-lsp-monitor-threshold-types;
        description
          "Type of thresholding to perform";
      }
      leaf count1 {
        when "../thresh-type != 'immediate'" {
          tailf:xpath-root 3;
          description
            "../ThreshType != Immediate";
        }
        type uint32 {
          range "1..16";
        }
        description
          "Probe count for consecutive";
      }
      leaf count2 {
        when "../thresh-type != 'immediate' and ../thresh-type != 'consecutive'" {
          tailf:xpath-root 3;
          description
            "../ThreshType != Immediate and ../ThreshType
             != Consecutive";
        }
        type uint32 {
          range "1..16";
        }
        description
          "Y value, when threshold type is XofY";
      }
    }
  }

  grouping IPSLA-OP-REACT-CFG-THRESHOLD-TYPE {
    description
      "Common node of timeout, connection-lossCommon
       node of timeout, verify-error, connection-loss,
       jitter-average-sd, jitter-average-ds,
       jitter-average, packet-loss-ds, packet-loss-sd,
       rtt";
    container threshold-type {
      description
        "Type of thresholding to perform on the monitored
         element";
      leaf thresh-type {
        type Ipsla-threshold-types;
        description
          "Type of thresholding to perform";
      }
      leaf count1 {
        when "../thresh-type != 'immediate'" {
          tailf:xpath-root 3;
          description
            "../ThreshType != Immediate";
        }
        type uint32 {
          range "1..16";
        }
        description
          "Probe count for avarage, consecutive case or X
           value for XofY case";
      }
      leaf count2 {
        when "../thresh-type != 'immediate' and ../thresh-type != 'consecutive' and ../thresh-type != 'average'" {
          tailf:xpath-root 3;
          description
            "../ThreshType != Immediate and ../ThreshType
             != Consecutive and ../ThreshType != Average";
        }
        type uint32 {
          range "1..16";
        }
        description
          "Y value, when threshold type is XofY";
      }
    }
  }

  grouping STATISTICS {
    description
      "Common node of icmp-echo, udp-echo, udp-jitter,
       mpls-lsp-ping, mpls-lsp-trace";
    container statistics {
      description
        "Statistics collection aggregated over an hour";
      leaf hours {
        type uint32 {
          range "0..25";
        }
        units "hour";
        default "2";
        description
          "Number of hours for which hourly statistics are
           kept";
      }
      leaf dist-interval {
        type uint32 {
          range "1..100";
        }
        units "millisecond";
        default "20";
        description
          "Specify distribution interval in milliseconds";
      }
      leaf dist-count {
        type uint32 {
          range "1..20";
        }
        default "1";
        description
          "Count of distribution intervals maintained";
      }
    }
  }

  grouping IPSLA-MPLSLM-DEF-CFG-STATISTICS {
    description
      "Common node of icmp-echo, udp-echo, udp-jitter,
       mpls-lsp-ping, mpls-lsp-traceCommon node of
       mpls-lsp-ping, mpls-lsp-trace";
    container statistics {
      description
        "Statistics collection aggregated over an hour";
      leaf hours {
        type uint32 {
          range "0..2";
        }
        units "hour";
        default "2";
        description
          "Number of hours for which hourly statistics are
           kept";
      }
    }
  }

  grouping TIMEOUT {
    description
      "Common node of mpls-lsp-ping, mpls-lsp-trace";
    leaf timeout {
      type uint32 {
        range "1..604800000";
      }
      units "millisecond";
      default "5000";
      description
        "Probe/Control timeout in milliseconds";
    }
  }

  grouping IPSLA-OP-DEF-COMMON-CFG-TIMEOUT {
    description
      "Common node of mpls-lsp-ping,
       mpls-lsp-traceCommon node of icmp-echo,
       icmp-path-echo, icmp-path-jitter, udp-echo,
       udp-jitter, mpls-lsp-ping, mpls-lsp-trace";
    leaf timeout {
      type uint32 {
        range "1..604800000";
      }
      units "millisecond";
      default "5000";
      description
        "Probe/Control timeout in milliseconds";
    }
  }

  grouping CONTROL-DISABLE {
    description
      "Common node of udp-echo, udp-jitter";
    leaf control-disable {
      type empty;
      description
        "Disable control packets";
    }
  }

  grouping FORCE-EXPLICIT-NULL {
    description
      "Common node of mpls-lsp-ping, mpls-lsp-trace";
    leaf force-explicit-null {
      type empty;
      description
        "Forced option for the MPLS LSP operation";
    }
  }

  grouping IPSLA-MPLSLM-DEF-CFG-FORCE-EXPLICIT-NULL {
    description
      "Common node of mpls-lsp-ping,
       mpls-lsp-traceCommon node of mpls-lsp-ping,
       mpls-lsp-trace";
    leaf force-explicit-null {
      type empty;
      description
        "Forced option for the MPLS LSP operation";
    }
  }

  grouping REMOTE-PORT {
    description
      "Common node of remote-ipv4-address,
       remote-ipv6-address";
    container remote-port-numbers {
      description
        "Configuration of remote port";
      list remote-port-number {
        key "remote-port";
        description
          "Enter value of remote port";
        container vrf-names {
          description
            "Configuration of vrf";
          list vrf-name {
            key "vrf-name";
            description
              "Configure vrf name value";
            leaf vrf-name {
              type xr:Cisco-ios-xr-string {
                length "1..32";
              }
              description
                "VRF Name";
            }
          }
        }
        leaf remote-port {
          type inet:port-number;
          description
            "Remote port";
        }
      }
    }
  }

  grouping ENHANCED-STATS-TABLE {
    description
      "Common node of icmp-echo, udp-echo, udp-jitter,
       mpls-lsp-ping";
    container enhanced-stats {
      description
        "Table of statistics collection intervals";
      list enhanced-stat {
        key "interval";
        description
          "Statistics for a specified time interval";
        leaf buckets {
          type uint32 {
            range "1..100";
          }
          default "15";
          description
            "Buckets of enhanced statistics kept";
        }
        leaf interval {
          type uint32 {
            range "1..3600";
          }
          units "second";
          description
            "Interval in seconds";
        }
      }
    }
  }

  grouping LSP-SELECTOR {
    description
      "Common node of mpls-lsp-ping, mpls-lsp-trace";
    leaf lsp-selector {
      type inet:ipv4-address-no-zone;
      default "1.0.0.127";
      description
        "Attributes used for path selection during LSP
         load balancing";
    }
  }

  grouping IPSLA-MPLSLM-DEF-CFG-LSP-SELECTOR {
    description
      "Common node of mpls-lsp-ping,
       mpls-lsp-traceCommon node of mpls-lsp-ping,
       mpls-lsp-trace";
    leaf lsp-selector {
      type inet:ipv4-address-no-zone;
      default "1.0.0.127";
      description
        "Attributes used for path selection during LSP
         load balancing";
    }
  }

  grouping ACTION-TYPE {
    description
      "Common node of timeout, verify-error,
       connection-loss, jitter-average-sd,
       jitter-average-ds, jitter-average, packet-loss-ds
       , packet-loss-sd, rtt";
    container action-type {
      description
        "Type of action to be taken on threshold
         violation(s)";
      leaf logging {
        type empty;
        description
          "Generate a syslog alarm on threshold violation";
      }
      leaf trigger {
        type empty;
        description
          "Generate trigger to active reaction triggered
           operation(s)";
      }
    }
  }

  grouping IPSLA-MPLSLM-REACT-CFG-ACTION-TYPE {
    description
      "Common node of timeout, verify-error,
       connection-loss, jitter-average-sd,
       jitter-average-ds, jitter-average, packet-loss-ds
       , packet-loss-sd, rttCommon node of timeout,
       connection-loss, lpd-tree-trace, lpd-group";
    container action-type {
      description
        "Type of action to be taken on threshold
         violation(s)";
      leaf logging {
        type empty;
        description
          "Generate a syslog alarm on threshold violation";
      }
    }
  }

  grouping REPLY {
    description
      "Common node of mpls-lsp-ping, mpls-lsp-trace";
    container reply {
      description
        "Echo reply options for the MPLS LSP operation";
      leaf dscp-bits {
        type Ipsla-lsp-reply-dscp;
        description
          "DSCP bits in the reply IP header";
      }
      leaf mode {
        type Ipsla-lsp-monitor-reply-mode;
        description
          "Enables use of router alert in echo reply
           packets";
      }
    }
  }

  grouping IPSLA-MPLSLM-DEF-CFG-CREATE {
    description
      "Common node of icmp-echo, icmp-path-echo,
       icmp-path-jitter, udp-echo, udp-jitter,
       mpls-lsp-ping, mpls-lsp-traceCommon node of
       mpls-lsp-ping, mpls-lsp-trace";
    leaf create {
      type empty;
      description
        "Create MPLSLM instance with specified type";
    }
  }

  grouping IPSLA-MPLSLM-REACT-CFG-CREATE {
    description
      "Common node of icmp-echo, icmp-path-echo,
       icmp-path-jitter, udp-echo, udp-jitter,
       mpls-lsp-ping, mpls-lsp-traceCommon node of
       mpls-lsp-ping, mpls-lsp-traceCommon node of
       timeout, verify-error, connection-loss,
       jitter-average, jitter-average-sd,
       jitter-average-ds, packet-loss-sd, packet-loss-ds
       , rttCommon node of timeout, connection-loss,
       lpd-tree-trace, lpd-group";
    leaf create {
      type empty;
      description
        "Create reaction condition for a particular
         MPLSLM";
    }
  }

  grouping TOS {
    description
      "Common node of icmp-echo, icmp-path-echo,
       icmp-path-jitter, udp-echo, udp-jitter";
    leaf tos {
      type uint32 {
        range "0..255";
      }
      default "0";
      description
        "Type of service setting in probe packet";
    }
  }

  grouping SOURCE-PORT {
    description
      "Common node of udp-echo, udp-jitter";
    leaf source-port {
      type inet:port-number;
      description
        "Port number on source device";
    }
  }

  grouping OUTPUT-NEXTHOP {
    description
      "Common node of mpls-lsp-ping, mpls-lsp-trace";
    leaf output-nexthop {
      type inet:ipv4-address-no-zone;
      description
        "Echo request output nexthop";
    }
  }

  grouping IPSLA-MPLSLM-DEF-CFG-OUTPUT-NEXTHOP {
    description
      "Common node of mpls-lsp-ping,
       mpls-lsp-traceCommon node of mpls-lsp-ping,
       mpls-lsp-trace";
    leaf output-nexthop {
      type inet:ipv4-address-no-zone;
      description
        "Echo request output nexthop";
    }
  }

  grouping ACCESSLIST {
    description
      "Common node of mpls-lsp-ping, mpls-lsp-trace";
    leaf accesslist {
      type xr:Cisco-ios-xr-string {
        length "1..32";
      }
      description
        "Apply access list to filter PE addresses";
    }
  }

  grouping OUTPUT-INTERFACE {
    description
      "Common node of mpls-lsp-ping, mpls-lsp-trace";
    leaf output-interface {
      type xr:Interface-name;
      description
        "Echo request output interface";
    }
  }

  grouping IPSLA-OP-DEF-MPLS-LSP-CFG-OUTPUT-INTERFACE {
    description
      "Common node of mpls-lsp-ping,
       mpls-lsp-traceCommon node of mpls-lsp-ping,
       mpls-lsp-trace";
    leaf output-interface {
      type xr:Interface-name;
      description
        "Echo request output interface";
    }
  }

  grouping EXP-BITS {
    description
      "Common node of mpls-lsp-ping, mpls-lsp-trace";
    leaf exp-bits {
      type uint32 {
        range "0..7";
      }
      default "0";
      description
        "EXP bits in MPLS LSP echo request header";
    }
  }

  grouping IPSLA-OP-DEF-MPLS-LSP-CFG-EXP-BITS {
    description
      "Common node of mpls-lsp-ping,
       mpls-lsp-traceCommon node of mpls-lsp-ping,
       mpls-lsp-trace";
    leaf exp-bits {
      type uint32 {
        range "0..7";
      }
      default "0";
      description
        "EXP bits in MPLS LSP echo reply header";
    }
  }

  grouping VRF {
    description
      "Common node of icmp-echo, icmp-path-echo,
       icmp-path-jitter, udp-echo, udp-jitter";
    leaf vrf {
      type xr:Cisco-ios-xr-string {
        length "1..32";
      }
      description
        "Configure IPSLA for a VPN Routing/Forwarding
         instance)";
    }
  }

  grouping IPSLA-MPLSLM-DEF-CFG-VRF {
    description
      "Common node of icmp-echo, icmp-path-echo,
       icmp-path-jitter, udp-echo, udp-jitterCommon node
       of mpls-lsp-ping, mpls-lsp-trace";
    leaf vrf {
      type xr:Cisco-ios-xr-string {
        length "1..32";
      }
      description
        "Specify a VRF instance to be monitored";
    }
  }

  grouping HISTORY {
    description
      "Common node of icmp-echo, udp-echo, mpls-lsp-ping
       , mpls-lsp-trace";
    container history {
      description
        "Configure the history parameters for this
         operation";
      leaf lives {
        type uint32 {
          range "0..2";
        }
        default "0";
        description
          "Specify number of lives to be kept";
      }
      leaf history-filter {
        type Ipsla-history-filter;
        description
          "Choose type of data to be stored in history
           buffer";
      }
      leaf buckets {
        type uint32 {
          range "1..60";
        }
        default "15";
        description
          "Specify number of history buckets";
      }
    }
  }

  grouping THRESHOLD-LIMITS {
    description
      "Common node of jitter-average-sd,
       jitter-average-ds, jitter-average, packet-loss-ds
       , packet-loss-sd, rtt";
    container threshold-limits {
      presence "Indicates a threshold-limits node is configured.";
      description
        "Specify threshold limits for the monitored
         element";
      leaf lower-limit {
        type uint32 {
          range "1..4294967295";
        }
        mandatory true;
        description
          "Threshold lower limit value";
      }
      leaf upper-limit {
        type uint32 {
          range "1..4294967295";
        }
        mandatory true;
        description
          "Threshold upper limit value";
      }
    }
  }

  grouping DEST-PORT {
    description
      "Common node of udp-echo, udp-jitter";
    leaf dest-port {
      type inet:port-number;
      description
        "Port number on target device";
    }
  }

  grouping LOCAL-PORT {
    description
      "Common node of local-ipv4-address,
       local-ipv6-address";
    container local-port-numbers {
      description
        "Configuration of local port";
      list local-port-number {
        key "local-port";
        description
          "Enter value of local port";
        container remote-ip {
          description
            "Configure remote ip address";
          container remote-ipv4-addresses {
            description
              "Configure IPV4 address";
            list remote-ipv4-address {
              key "remotev4-address";
              description
                "Enter value of remote ipv4 address";
              leaf remotev4-address {
                type xr:Cisco-ios-xr-string;
                description
                  "Remote IPv4 address";
              }
              uses REMOTE-PORT;
            }
          }
          container remote-ipv6-addresses {
            description
              "Configure IPV6 address";
            list remote-ipv6-address {
              key "remotev6-address";
              description
                "Enter value of remote ipv6 address";
              leaf remotev6-address {
                type xr:Cisco-ios-xr-string;
                description
                  "Remote IPv6 address";
              }
              uses REMOTE-PORT;
            }
          }
        }
        leaf local-port {
          type inet:port-number;
          description
            "Local port";
        }
      }
    }
  }

  augment "/ncs:devices/ncs:device/ncs:config" {
    container ipsla {
      tailf:ncs-device-type "netconf";
      tailf:display-when "not(../../ncs:module) or ../../ncs:module[ncs:name='Cisco-IOS-XR-man-ipsla-cfg']";
      description
        "IPSLA configuration";
      container common {
        description
          "IPSLA application common configuration";
        container hardware-timestamp {
          description
            "Hardware Timestamp configuration";
          leaf disable {
            type empty;
            description
              "states true if hw-timestamp is disabled";
          }
        }
        container authentication {
          description
            "Authenticaion configuration";
          leaf key-chain {
            type string {
              length "1..32";
            }
            description
              "Use MD5 authentication for IPSLA control
               message";
          }
        }
        leaf low-memory {
          type uint32 {
            range "0..4294967295";
          }
          default "20480";
          description
            "Configure low memory water mark (default 20M)";
        }
      }
      container mpls-lsp-monitor {
        description
          "MPLS LSP Monitor(MPLSLM) configuration";
        container reactions {
          description
            "MPLSLM Reaction configuration";
          list reaction {
            key "monitor-id";
            description
              "Reaction configuration for an MPLSLM instance";
            container condition {
              description
                "Reaction condition specification";
              container lpd-tree-trace {
                presence "CLI submode compatibility.";
                description
                  "React on LPD Tree Trace violation for a
                   monitored MPLSLM";
                uses IPSLA-MPLSLM-REACT-CFG-ACTION-TYPE;
              }
              container timeout {
                presence "CLI submode compatibility.";
                description
                  "React on probe timeout";
                uses IPSLA-MPLSLM-REACT-CFG-ACTION-TYPE;
                uses THRESHOLD-TYPE;
              }
              container lpd-group {
                presence "CLI submode compatibility.";
                description
                  "React on LPD Group violation for a monitored
                   MPLSLM";
                uses IPSLA-MPLSLM-REACT-CFG-ACTION-TYPE;
              }
              container connection-loss {
                presence "CLI submode compatibility.";
                description
                  "React on connection loss for a monitored
                   MPLSLM";
                uses IPSLA-MPLSLM-REACT-CFG-ACTION-TYPE;
                uses THRESHOLD-TYPE;
              }
            }
            leaf monitor-id {
              type uint32 {
                range "1..2048";
              }
              description
                "Monitor identifier";
            }
          }
        }
        container schedules {
          description
            "MPLSLM schedule configuration";
          list schedule {
            key "monitor-id";
            description
              "Schedule an MPLSLM instance";
            container start-time {
              description
                "Start time of MPLSLM instance";
              leaf schedule-type {
                type Ipsla-sched;
                description
                  "Type of schedule";
              }
              leaf hour {
                when "../schedule-type != 'now' and ../schedule-type != 'pending'" {
                  tailf:xpath-root 3;
                  description
                    "../ScheduleType != Now and ../ScheduleType
                     != Pending";
                }
                type uint32 {
                  range "0..23";
                }
                description
                  "Hour value(hh) in hh:mm:ss specification";
              }
              leaf minute {
                when "../schedule-type != 'now' and ../schedule-type != 'pending'" {
                  tailf:xpath-root 3;
                  description
                    "../ScheduleType != Now and ../ScheduleType
                     != Pending";
                }
                type uint32 {
                  range "0..59";
                }
                description
                  "Minute value(mm) in hh:mm:ss specification";
              }
              leaf second {
                when "../schedule-type != 'now' and ../schedule-type != 'pending'" {
                  tailf:xpath-root 3;
                  description
                    "../ScheduleType != Now and ../ScheduleType
                     != Pending";
                }
                type uint32 {
                  range "0..59";
                }
                description
                  "Second value(ss) in hh:mm:ss specification";
              }
              leaf month {
                when "../schedule-type != 'now' and ../schedule-type != 'pending' and ../schedule-type != 'after'" {
                  tailf:xpath-root 3;
                  description
                    "../ScheduleType != Now and ../ScheduleType
                     != Pending and ../ScheduleType != After";
                }
                type Ipsla-month;
                description
                  "Month of the year (optional. Default current
                   month)";
              }
              leaf day {
                when "../schedule-type != 'now' and ../schedule-type != 'pending' and ../schedule-type != 'after'" {
                  tailf:xpath-root 3;
                  description
                    "../ScheduleType != Now and ../ScheduleType
                     != Pending and ../ScheduleType != After";
                }
                type uint32 {
                  range "1..31";
                }
                description
                  "Day of the month(optional. Default today)";
              }
              leaf year {
                when "../schedule-type != 'now' and ../schedule-type != 'pending' and ../schedule-type != 'after'" {
                  tailf:xpath-root 3;
                  description
                    "../ScheduleType != Now and ../ScheduleType
                     != Pending and ../ScheduleType != After";
                }
                type uint32 {
                  range "1993..2035";
                }
                description
                  "Year (optional. Default current year)";
              }
            }
            leaf frequency {
              type uint32 {
                range "1..604800";
              }
              units "second";
              description
                "Group schedule frequency of the probing";
            }
            leaf period {
              type uint32 {
                range "1..604800";
              }
              units "second";
              description
                "Group schedule period range";
            }
            leaf monitor-id {
              type uint32 {
                range "1..2048";
              }
              description
                "Monitor indentifier";
            }
          }
        }
        container definitions {
          description
            "MPLS LSP Monitor definition table";
          list definition {
            key "monitor-id";
            description
              "MPLS LSP Monitor definition";
            container operation-type {
              description
                "Operation type specification";
              container mpls-lsp-trace {
                presence "CLI submode compatibility.";
                description
                  "Perform MPLS LSP Trace operation";
                leaf ttl {
                  type uint32 {
                    range "1..255";
                  }
                  default "30";
                  description
                    "Time to live value";
                }
                uses EXP-BITS;
                uses REPLY;
                uses TAG;
                uses IPSLA-MPLSLM-DEF-CFG-LSP-SELECTOR;
                uses OUTPUT-INTERFACE;
                uses ACCESSLIST;
                uses IPSLA-MPLSLM-DEF-CFG-OUTPUT-NEXTHOP;
                uses IPSLA-MPLSLM-DEF-CFG-STATISTICS;
                uses TIMEOUT;
                uses IPSLA-MPLSLM-DEF-CFG-FORCE-EXPLICIT-NULL;
                uses SCAN;
                uses IPSLA-MPLSLM-DEF-CFG-VRF;
              }
              container mpls-lsp-ping {
                presence "CLI submode compatibility.";
                description
                  "Perform MPLS LSP Ping operation";
                container data-size {
                  description
                    "Protocol data size in payload of probe
                     packets";
                  leaf request {
                    type uint32 {
                      range "100..17986";
                    }
                    units "byte";
                    default "100";
                    description
                      "Payload size in request probe packet";
                  }
                }
                container path-discover {
                  presence "CLI submode compatibility.";
                  description
                    "Path discover configuration";
                  container session {
                    description
                      "Session parameters configuration";
                    leaf timeout {
                      type uint32 {
                        range "1..900";
                      }
                      units "second";
                      default "120";
                      description
                        "Timeout value for path discovery request";
                    }
                    leaf limit {
                      type uint32 {
                        range "1..15";
                      }
                      default "1";
                      description
                        "Number of concurrent active path
                         discovery requests at one time";
                    }
                  }
                  container path {
                    description
                      "Path parameters configuration";
                    container secondary-frequency {
                      presence "Indicates a secondary-frequency node is configured.";
                      description
                        "Frequency to be used if path failure
                         condition is detected";
                      leaf type {
                        type Ipsla-secondary-frequency;
                        mandatory true;
                        description
                          "Condition type of path failure";
                      }
                      leaf frequency {
                        type uint32 {
                          range "1..604800";
                        }
                        units "second";
                        mandatory true;
                        description
                          "Frequency value in seconds";
                      }
                    }
                    leaf retry {
                      type uint32 {
                        range "1..16";
                      }
                      default "1";
                      description
                        "Number of attempts before declaring the
                         path as down";
                    }
                  }
                  container echo {
                    description
                      "Echo parameters configuration";
                    container multipath {
                      description
                        "Downstream map multipath settings";
                      leaf bitmap-size {
                        type uint32 {
                          range "1..256";
                        }
                        default "32";
                        description
                          "Multipath bit size";
                      }
                    }
                    leaf interval {
                      type uint32 {
                        range "0..3600000";
                      }
                      units "millisecond";
                      default "0";
                      description
                        "Send interval between echo requests
                         during path discovery";
                    }
                    leaf timeout {
                      type uint32 {
                        range "1..3600";
                      }
                      units "second";
                      default "5";
                      description
                        "Timeout value for echo requests during
                         path discovery";
                    }
                    leaf retry {
                      type uint32 {
                        range "0..10";
                      }
                      default "3";
                      description
                        "Number of timeout retry attempts during
                         path discovery";
                    }
                    leaf maximum-lsp-selector {
                      type inet:ipv4-address-no-zone;
                      default "127.255.255.255";
                      description
                        "Maximum IPv4 address used as destination
                         in echo request";
                    }
                  }
                  leaf scan-period {
                    type uint32 {
                      range "0..7200";
                    }
                    units "minute";
                    default "0";
                    description
                      "Time period for finishing path discovery";
                  }
                }
                leaf ttl {
                  type uint32 {
                    range "1..255";
                  }
                  default "255";
                  description
                    "Time to live value";
                }
                uses EXP-BITS;
                uses REPLY;
                uses TAG;
                uses IPSLA-MPLSLM-DEF-CFG-LSP-SELECTOR;
                uses OUTPUT-INTERFACE;
                uses ACCESSLIST;
                uses IPSLA-MPLSLM-DEF-CFG-OUTPUT-NEXTHOP;
                uses IPSLA-MPLSLM-DEF-CFG-STATISTICS;
                uses TIMEOUT;
                uses IPSLA-MPLSLM-DEF-CFG-FORCE-EXPLICIT-NULL;
                uses SCAN;
                uses IPSLA-MPLSLM-DEF-CFG-VRF;
              }
            }
            leaf monitor-id {
              type uint32 {
                range "1..2048";
              }
              description
                "Monitor identifier";
            }
          }
        }
      }
      container operation {
        description
          "IPSLA Operation configuration";
        container schedules {
          description
            "Schedule an operation";
          list schedule {
            key "operation-id";
            description
              "Operation schedule configuration";
            container start-time {
              description
                "Start time of the operation";
              leaf schedule-type {
                type Ipsla-sched;
                description
                  "Type of schedule";
              }
              leaf hour {
                when "../schedule-type != 'now' and ../schedule-type != 'pending'" {
                  tailf:xpath-root 3;
                  description
                    "../ScheduleType != Now and ../ScheduleType
                     != Pending";
                }
                type uint32 {
                  range "0..23";
                }
                description
                  "Hour value(hh) in hh:mm:ss specification";
              }
              leaf minute {
                when "../schedule-type != 'now' and ../schedule-type != 'pending'" {
                  tailf:xpath-root 3;
                  description
                    "../ScheduleType != Now and ../ScheduleType
                     != Pending";
                }
                type uint32 {
                  range "0..59";
                }
                description
                  "Minute value(mm) in hh:mm:ss specification";
              }
              leaf second {
                when "../schedule-type != 'now' and ../schedule-type != 'pending'" {
                  tailf:xpath-root 3;
                  description
                    "../ScheduleType != Now and ../ScheduleType
                     != Pending";
                }
                type uint32 {
                  range "0..59";
                }
                description
                  "Second value(ss) in hh:mm:ss specification";
              }
              leaf month {
                when "../schedule-type != 'now' and ../schedule-type != 'pending' and ../schedule-type != 'after'" {
                  tailf:xpath-root 3;
                  description
                    "../ScheduleType != Now and ../ScheduleType
                     != Pending and ../ScheduleType != After";
                }
                type Ipsla-month;
                description
                  "Month of the year (optional. Default current
                   month)";
              }
              leaf day {
                when "../schedule-type != 'now' and ../schedule-type != 'pending' and ../schedule-type != 'after'" {
                  tailf:xpath-root 3;
                  description
                    "../ScheduleType != Now and ../ScheduleType
                     != Pending and ../ScheduleType != After";
                }
                type uint32 {
                  range "1..31";
                }
                description
                  "Day of the month(optional. Default today)";
              }
              leaf year {
                when "../schedule-type != 'now' and ../schedule-type != 'pending' and ../schedule-type != 'after'" {
                  tailf:xpath-root 3;
                  description
                    "../ScheduleType != Now and ../ScheduleType
                     != Pending and ../ScheduleType != After";
                }
                type uint32 {
                  range "1993..2035";
                }
                description
                  "Year(optional. Default current year)";
              }
            }
            leaf life {
              type Ipsla-life;
              units "second";
              description
                "Length of the time to execute (default 3600
                 seconds)";
            }
            leaf ageout {
              type uint32 {
                range "0..2073600";
              }
              units "second";
              description
                "How long to keep this entry after it becomes
                 inactive";
            }
            leaf recurring {
              type empty;
              description
                "probe to be scheduled automatically every day";
            }
            leaf operation-id {
              type uint32 {
                range "1..2048";
              }
              description
                "Operation number";
            }
          }
        }
        container reactions {
          description
            "Reaction configuration";
          list reaction {
            key "operation-id";
            description
              "Reaction configuration for an operation";
            container condition {
              description
                "Reaction condition specification";
              container jitter-average-ds {
                presence "CLI submode compatibility.";
                description
                  "React on destination to source jitter
                   threshold violation";
                uses THRESHOLD-LIMITS;
                uses ACTION-TYPE;
                uses IPSLA-OP-REACT-CFG-THRESHOLD-TYPE;
              }
              container timeout {
                presence "CLI submode compatibility.";
                description
                  "React on probe timeout";
                uses ACTION-TYPE;
                uses IPSLA-OP-REACT-CFG-THRESHOLD-TYPE;
              }
              container jitter-average {
                presence "CLI submode compatibility.";
                description
                  "React on average round trip jitter threshold
                   violation";
                uses THRESHOLD-LIMITS;
                uses ACTION-TYPE;
                uses IPSLA-OP-REACT-CFG-THRESHOLD-TYPE;
              }
              container verify-error {
                presence "CLI submode compatibility.";
                description
                  "React on error verfication violation";
                uses ACTION-TYPE;
                uses IPSLA-OP-REACT-CFG-THRESHOLD-TYPE;
              }
              container rtt {
                presence "CLI submode compatibility.";
                description
                  "React on round trip time threshold violation";
                uses THRESHOLD-LIMITS;
                uses ACTION-TYPE;
                uses IPSLA-OP-REACT-CFG-THRESHOLD-TYPE;
              }
              container packet-loss-sd {
                presence "CLI submode compatibility.";
                description
                  "React on destination to source packet loss
                   threshold violation";
                uses THRESHOLD-LIMITS;
                uses ACTION-TYPE;
                uses IPSLA-OP-REACT-CFG-THRESHOLD-TYPE;
              }
              container jitter-average-sd {
                presence "CLI submode compatibility.";
                description
                  "React on average source to destination
                   jitter threshold violation";
                uses THRESHOLD-LIMITS;
                uses ACTION-TYPE;
                uses IPSLA-OP-REACT-CFG-THRESHOLD-TYPE;
              }
              container connection-loss {
                presence "CLI submode compatibility.";
                description
                  "React on connection loss for a monitored
                   operation";
                uses ACTION-TYPE;
                uses IPSLA-OP-REACT-CFG-THRESHOLD-TYPE;
              }
              container packet-loss-ds {
                presence "CLI submode compatibility.";
                description
                  "React on source to destination packet loss
                   threshold violation";
                uses THRESHOLD-LIMITS;
                uses ACTION-TYPE;
                uses IPSLA-OP-REACT-CFG-THRESHOLD-TYPE;
              }
            }
            leaf operation-id {
              type uint32 {
                range "1..2048";
              }
              description
                "Operation number";
            }
          }
        }
        container reaction-triggers {
          description
            "Reaction trigger configuration";
          list reaction-trigger {
            key "operation-id";
            description
              "Reaction trigger for an operation";
            leaf triggered-op-id {
              type uint32 {
                range "1..2048";
              }
              description
                "Operation number of the operation to be
                 triggered";
            }
            leaf operation-id {
              type uint32 {
                range "1..2048";
              }
              description
                "Operation number of the operation generating
                 a trigger";
            }
          }
        }
        container definitions {
          description
            "Operation definition table";
          list definition {
            key "operation-id";
            description
              "Operation definition";
            container operation-type {
              description
                "Operation type specification";
              container icmp-echo {
                presence "CLI submode compatibility.";
                description
                  "ICMPEcho Operation type";
                container data-size {
                  description
                    "Protocol data size in payload of probe
                     packets";
                  leaf request {
                    type uint32 {
                      range "0..16384";
                    }
                    units "byte";
                    default "36";
                    description
                      "Payload size in request probe packet";
                  }
                }
                leaf source-address-v6 {
                  type string;
                  description
                    "Enter IPv6 address of the source device";
                }
                leaf dest-address-v6 {
                  type string;
                  description
                    "Enter IPv6 address of the destination
                     device";
                }
                uses SOURCE-ADDRESS;
                uses TOS;
                uses STATISTICS;
                uses VRF;
                uses HISTORY;
                uses IPSLA-OP-DEF-COMMON-CFG-TIMEOUT;
                uses FREQUENCY;
                uses DEST-ADDRESS;
                uses ENHANCED-STATS-TABLE;
                uses IPSLA-OP-DEF-COMMON-CFG-TAG;
              }
              container mpls-lsp-ping {
                presence "CLI submode compatibility.";
                description
                  "MPLS LSP Ping Operation type";
                container data-size {
                  description
                    "Protocol data size in payload of probe
                     packets";
                  leaf request {
                    type uint32 {
                      range "100..17986";
                    }
                    default "100";
                    description
                      "Payload size in request probe packet";
                  }
                }
                container reply {
                  description
                    "Echo reply options for the MPLS LSP
                     operation";
                  leaf mode {
                    type Ipsla-lsp-ping-reply-mode;
                    description
                      "Enables use of router alert in echo reply
                       packets";
                  }
                  uses DSCP-BITS;
                }
                container target {
                  description
                    "Target for the MPLS LSP operation";
                  container traffic-engineering {
                    description
                      "Traffic engineering target";
                    leaf tunnel {
                      type uint32 {
                        range "0..65535";
                      }
                      description
                        "Tunnel interface number";
                    }
                  }
                  container ipv4 {
                    description
                      "Target specified as an IPv4 address";
                    container fec-address {
                      presence "Indicates a fec-address node is configured.";
                      description
                        "Target FEC address with mask";
                      leaf address {
                        type inet:ipv4-address-no-zone;
                        mandatory true;
                        description
                          "IP address for target";
                      }
                      leaf mask {
                        type inet:ipv4-address-no-zone;
                        mandatory true;
                        description
                          "IP netmask for target";
                      }
                    }
                  }
                  container pseudowire {
                    description
                      "Pseudowire target";
                    container target-address {
                      presence "Indicates a target-address node is configured.";
                      description
                        "Target address";
                      leaf address {
                        type inet:ipv4-address-no-zone;
                        mandatory true;
                        description
                          "Target address";
                      }
                      leaf vc-id {
                        type uint32 {
                          range "1..4294967295";
                        }
                        mandatory true;
                        description
                          "Virtual circuit ID";
                      }
                    }
                  }
                }
                leaf ttl {
                  type uint32 {
                    range "1..255";
                  }
                  default "255";
                  description
                    "Time to live value";
                }
                uses SOURCE-ADDRESS;
                uses OUTPUT-NEXTHOP;
                uses LSP-SELECTOR;
                uses STATISTICS;
                uses IPSLA-OP-DEF-MPLS-LSP-CFG-EXP-BITS;
                uses FORCE-EXPLICIT-NULL;
                uses HISTORY;
                uses IPSLA-OP-DEF-COMMON-CFG-TIMEOUT;
                uses IPSLA-OP-DEF-MPLS-LSP-CFG-OUTPUT-INTERFACE;
                uses FREQUENCY;
                uses ENHANCED-STATS-TABLE;
                uses IPSLA-OP-DEF-COMMON-CFG-TAG;
              }
              container udp-echo {
                presence "CLI submode compatibility.";
                description
                  "UDPEcho Operation type";
                container data-size {
                  description
                    "Protocol data size in payload of probe
                     packets";
                  leaf request {
                    type uint32 {
                      range "16..1500";
                    }
                    units "byte";
                    default "16";
                    description
                      "Payload size in request probe packet";
                  }
                }
                uses SOURCE-ADDRESS;
                uses TOS;
                uses CONTROL-DISABLE;
                uses SOURCE-PORT;
                uses STATISTICS;
                uses VRF;
                uses HISTORY;
                uses IPSLA-OP-DEF-COMMON-CFG-TIMEOUT;
                uses FREQUENCY;
                uses DEST-PORT;
                uses VERIFY-DATA;
                uses DEST-ADDRESS;
                uses ENHANCED-STATS-TABLE;
                uses IPSLA-OP-DEF-COMMON-CFG-TAG;
              }
              container mpls-lsp-trace {
                presence "CLI submode compatibility.";
                description
                  "MPLS LSP Trace Operation type";
                container target {
                  description
                    "Target for the MPLS LSP operation";
                  container traffic-engineering {
                    description
                      "Traffic engineering target";
                    leaf tunnel {
                      type uint32 {
                        range "0..65535";
                      }
                      description
                        "Tunnel interface number";
                    }
                  }
                  container ipv4 {
                    description
                      "Target specified as an IPv4 address";
                    container fec-address {
                      presence "Indicates a fec-address node is configured.";
                      description
                        "Target FEC address with mask";
                      leaf address {
                        type inet:ipv4-address-no-zone;
                        mandatory true;
                        description
                          "IP address for target";
                      }
                      leaf mask {
                        type inet:ipv4-address-no-zone;
                        mandatory true;
                        description
                          "IP netmask for target";
                      }
                    }
                  }
                }
                container reply {
                  description
                    "Echo reply options for the MPLS LSP
                     operation";
                  leaf mode {
                    type Ipsla-lsp-trace-reply-mode;
                    description
                      "Enables use of router alert in echo reply
                       packets";
                  }
                  uses DSCP-BITS;
                }
                leaf ttl {
                  type uint32 {
                    range "1..255";
                  }
                  default "30";
                  description
                    "Time to live value";
                }
                uses SOURCE-ADDRESS;
                uses OUTPUT-NEXTHOP;
                uses LSP-SELECTOR;
                uses STATISTICS;
                uses IPSLA-OP-DEF-MPLS-LSP-CFG-EXP-BITS;
                uses FORCE-EXPLICIT-NULL;
                uses HISTORY;
                uses IPSLA-OP-DEF-COMMON-CFG-TIMEOUT;
                uses IPSLA-OP-DEF-MPLS-LSP-CFG-OUTPUT-INTERFACE;
                uses FREQUENCY;
                uses IPSLA-OP-DEF-COMMON-CFG-TAG;
              }
              container udp-jitter {
                presence "CLI submode compatibility.";
                description
                  "UDPJitter Operation type";
                container data-size {
                  description
                    "Protocol data size in payload of probe
                     packets";
                  leaf request {
                    type uint32 {
                      range "28..1500";
                    }
                    units "byte";
                    default "32";
                    description
                      "Payload size in request probe packet";
                  }
                }
                container packet {
                  description
                    "Probe packet stream configuration
                     parameters";
                  leaf count {
                    type uint32 {
                      range "1..60000";
                    }
                    default "10";
                    description
                      "Number of packets to be transmitted during
                       a probe";
                  }
                  leaf interval {
                    type uint32 {
                      range "1..60000";
                    }
                    units "millisecond";
                    default "20";
                    description
                      "Packet interval in milliseconds";
                  }
                }
                uses SOURCE-ADDRESS;
                uses TOS;
                uses CONTROL-DISABLE;
                uses SOURCE-PORT;
                uses STATISTICS;
                uses VRF;
                uses IPSLA-OP-DEF-COMMON-CFG-TIMEOUT;
                uses FREQUENCY;
                uses DEST-PORT;
                uses VERIFY-DATA;
                uses DEST-ADDRESS;
                uses ENHANCED-STATS-TABLE;
                uses IPSLA-OP-DEF-COMMON-CFG-TAG;
              }
              container icmp-path-echo {
                presence "CLI submode compatibility.";
                description
                  "ICMPPathEcho Operation type";
                container history {
                  description
                    "Configure the history parameters for this
                     operation";
                  leaf samples {
                    type uint32 {
                      range "1..30";
                    }
                    default "16";
                    description
                      "Specify number of samples to keep";
                  }
                  leaf buckets {
                    type uint32 {
                      range "1..60";
                    }
                    default "15";
                    description
                      "Specify number of history buckets";
                  }
                  leaf history-filter {
                    type Ipsla-history-filter;
                    description
                      "Choose type of data to be stored in
                       history buffer";
                  }
                  leaf lives {
                    type uint32 {
                      range "0..2";
                    }
                    default "0";
                    description
                      "Specify number of lives to be kept";
                  }
                }
                container data-size {
                  description
                    "Protocol data size in payload of probe
                     packets";
                  leaf request {
                    type uint32 {
                      range "0..16384";
                    }
                    units "byte";
                    default "36";
                    description
                      "Payload size in request probe packet";
                  }
                }
                container statistics {
                  description
                    "Statistics collection aggregated over an
                     hour";
                  leaf paths {
                    type uint32 {
                      range "1..128";
                    }
                    default "5";
                    description
                      "Maximum number of paths for which
                       statistics are kept";
                  }
                  leaf dist-interval {
                    type uint32 {
                      range "1..100";
                    }
                    units "millisecond";
                    default "20";
                    description
                      "Specify distribution interval in
                       milliseconds";
                  }
                  leaf dist-count {
                    type uint32 {
                      range "1..20";
                    }
                    default "1";
                    description
                      "Count of distribution intervals maintained";
                  }
                  leaf hours {
                    type uint32 {
                      range "0..25";
                    }
                    units "hour";
                    default "2";
                    description
                      "Number of hours for which hourly
                       statistics are kept";
                  }
                  leaf hops {
                    type uint32 {
                      range "1..30";
                    }
                    default "16";
                    description
                      "Maximum hops per path for which statistics
                       are kept";
                  }
                }
                uses SOURCE-ADDRESS;
                uses TOS;
                uses LSR-PATH;
                uses VRF;
                uses IPSLA-OP-DEF-COMMON-CFG-TIMEOUT;
                uses FREQUENCY;
                uses DEST-ADDRESS;
                uses IPSLA-OP-DEF-COMMON-CFG-TAG;
              }
              container icmp-path-jitter {
                presence "CLI submode compatibility.";
                description
                  "ICMPPathJitter Operation type";
                container data-size {
                  description
                    "Protocol data size in payload of probe
                     packets";
                  leaf request {
                    type uint32 {
                      range "0..16384";
                    }
                    units "byte";
                    default "36";
                    description
                      "Payload size in request probe packet";
                  }
                }
                container packet {
                  description
                    "Probe packet stream configuration
                     parameters";
                  leaf count {
                    type uint32 {
                      range "1..100";
                    }
                    default "10";
                    description
                      "Number of packets to be transmitted during
                       a probe";
                  }
                  leaf interval {
                    type uint32 {
                      range "1..60000";
                    }
                    units "millisecond";
                    default "20";
                    description
                      "Packet interval in milliseconds";
                  }
                }
                uses SOURCE-ADDRESS;
                uses TOS;
                uses LSR-PATH;
                uses VRF;
                uses IPSLA-OP-DEF-COMMON-CFG-TIMEOUT;
                uses FREQUENCY;
                uses DEST-ADDRESS;
                uses IPSLA-OP-DEF-COMMON-CFG-TAG;
              }
            }
            leaf operation-id {
              type uint32 {
                range "1..2048";
              }
              description
                "Operation number";
            }
          }
        }
      }
      container responder {
        presence "CLI submode compatibility.";
        description
          "Responder configuration";
        container twamp {
          presence "CLI submode compatibility.";
          description
            "Responder TWAMP configuration";
          leaf timeout {
            type uint32 {
              range "1..604800";
            }
            units "second";
            default "900";
            description
              "Configure responder timeout value in seconds";
          }
        }
        container type {
          description
            "Configure IPSLA Responder port type";
          container udp {
            description
              "Configure IPSLA Responder UDP address and port";
            container addresses {
              description
                "Configure IP address";
              list address {
                key "local-address";
                description
                  "Configure IP address for the permanent port";
                container ports {
                  description
                    "Configure port";
                  list port {
                    key "port";
                    description
                      "Configure port number for the permanent
                       port";
                    leaf port {
                      type inet:port-number;
                      description
                        "Port number to be enabled";
                    }
                  }
                }
                leaf local-address {
                  type inet:ipv4-address-no-zone;
                  description
                    "IP address of the Responder";
                }
              }
            }
          }
        }
        container twamp-light {
          description
            "Enter twamp-light session details";
          container session-ids {
            description
              "Create twamp-light session";
            list session-id {
              key "session-id";
              description
                "Configure session ID";
              container local-ip {
                description
                  "Configure local ip address";
                container local-ipv6-addresses {
                  description
                    "Configure IPV6 address";
                  list local-ipv6-address {
                    key "localv6-address";
                    description
                      "Enter value of local ip address";
                    leaf localv6-address {
                      type xr:Cisco-ios-xr-string;
                      description
                        "Local IPv6 address";
                    }
                    uses LOCAL-PORT;
                  }
                }
                container local-ipv4-addresses {
                  description
                    "Configure IPV4 address";
                  list local-ipv4-address {
                    key "localv4-address";
                    description
                      "Enter value of local ipv4 address";
                    leaf localv4-address {
                      type xr:Cisco-ios-xr-string;
                      description
                        "Local IPv4 address";
                    }
                    uses LOCAL-PORT;
                  }
                }
              }
              leaf twamp-light-timeout {
                type uint32 {
                  range "60..86400";
                }
                units "second";
                description
                  "Configure session timeout";
              }
              leaf session-id {
                type uint32 {
                  range "1..65535";
                }
                description
                  "SessionID";
              }
            }
          }
        }
      }
      container mpls-discovery {
        description
          "Provider Edge(PE) discovery configuration";
        container vpn {
          description
            "Layer 3 VPN PE discovery configuration";
          leaf interval {
            type uint32 {
              range "30..70560";
            }
            units "minute";
            default "300";
            description
              "Specify a discovery refresh interval";
          }
        }
      }
      container server-twamp {
        presence "CLI submode compatibility.";
        description
          "IPPM Server configuration";
        leaf inactivity-timer {
          type uint32 {
            range "1..6000";
          }
          units "second";
          default "900";
          description
            "Configure ippmserver inactivity timer value in
             seconds";
        }
        leaf port {
          type xr:Cisco-ios-xr-port-number;
          default "862";
          description
            "Configure port number for ippmserver listening
             port";
        }
      }
    }
  }
  augment "/ncs:devices/ncs:device/ncs:live-status" {
    container ipsla {
      tailf:ncs-device-type "netconf";
      tailf:display-when "not(../../ncs:module) or ../../ncs:module[ncs:name='Cisco-IOS-XR-man-ipsla-cfg'] or (../../ncs:live-status-protocol[not(ncs:capability)]) or (../../ncs:live-status-protocol/ncs:capability/ncs:module[.='Cisco-IOS-XR-man-ipsla-cfg'])";
      description
        "IPSLA configuration";
      container common {
        description
          "IPSLA application common configuration";
        container hardware-timestamp {
          description
            "Hardware Timestamp configuration";
          leaf disable {
            type empty;
            description
              "states true if hw-timestamp is disabled";
          }
        }
        container authentication {
          description
            "Authenticaion configuration";
          leaf key-chain {
            type string {
              length "1..32";
            }
            description
              "Use MD5 authentication for IPSLA control
               message";
          }
        }
        leaf low-memory {
          type uint32 {
            range "0..4294967295";
          }
          // NCS drop default statement
          description
            "Configure low memory water mark (default 20M)";
        }
      }
      container mpls-lsp-monitor {
        description
          "MPLS LSP Monitor(MPLSLM) configuration";
        container reactions {
          description
            "MPLSLM Reaction configuration";
          list reaction {
            key "monitor-id";
            description
              "Reaction configuration for an MPLSLM instance";
            container condition {
              description
                "Reaction condition specification";
              container lpd-tree-trace {
                presence "CLI submode compatibility.";
                description
                  "React on LPD Tree Trace violation for a
                   monitored MPLSLM";
                uses live_ncs_IPSLA-MPLSLM-REACT-CFG-ACTION-TYPE;
              }
              container timeout {
                presence "CLI submode compatibility.";
                description
                  "React on probe timeout";
                uses live_ncs_IPSLA-MPLSLM-REACT-CFG-ACTION-TYPE;
                uses live_ncs_THRESHOLD-TYPE;
              }
              container lpd-group {
                presence "CLI submode compatibility.";
                description
                  "React on LPD Group violation for a monitored
                   MPLSLM";
                uses live_ncs_IPSLA-MPLSLM-REACT-CFG-ACTION-TYPE;
              }
              container connection-loss {
                presence "CLI submode compatibility.";
                description
                  "React on connection loss for a monitored
                   MPLSLM";
                uses live_ncs_IPSLA-MPLSLM-REACT-CFG-ACTION-TYPE;
                uses live_ncs_THRESHOLD-TYPE;
              }
            }
            leaf monitor-id {
              type uint32 {
                range "1..2048";
              }
              description
                "Monitor identifier";
            }
          }
        }
        container schedules {
          description
            "MPLSLM schedule configuration";
          list schedule {
            key "monitor-id";
            description
              "Schedule an MPLSLM instance";
            container start-time {
              description
                "Start time of MPLSLM instance";
              leaf schedule-type {
                type live_ncs_Ipsla-sched;
                description
                  "Type of schedule";
              }
              leaf hour {
                // NCS drop when statement
                type uint32 {
                  range "0..23";
                }
                description
                  "Hour value(hh) in hh:mm:ss specification";
              }
              leaf minute {
                // NCS drop when statement
                type uint32 {
                  range "0..59";
                }
                description
                  "Minute value(mm) in hh:mm:ss specification";
              }
              leaf second {
                // NCS drop when statement
                type uint32 {
                  range "0..59";
                }
                description
                  "Second value(ss) in hh:mm:ss specification";
              }
              leaf month {
                // NCS drop when statement
                type live_ncs_Ipsla-month;
                description
                  "Month of the year (optional. Default current
                   month)";
              }
              leaf day {
                // NCS drop when statement
                type uint32 {
                  range "1..31";
                }
                description
                  "Day of the month(optional. Default today)";
              }
              leaf year {
                // NCS drop when statement
                type uint32 {
                  range "1993..2035";
                }
                description
                  "Year (optional. Default current year)";
              }
            }
            leaf frequency {
              type uint32 {
                range "1..604800";
              }
              units "second";
              description
                "Group schedule frequency of the probing";
            }
            leaf period {
              type uint32 {
                range "1..604800";
              }
              units "second";
              description
                "Group schedule period range";
            }
            leaf monitor-id {
              type uint32 {
                range "1..2048";
              }
              description
                "Monitor indentifier";
            }
          }
        }
        container definitions {
          description
            "MPLS LSP Monitor definition table";
          list definition {
            key "monitor-id";
            description
              "MPLS LSP Monitor definition";
            container operation-type {
              description
                "Operation type specification";
              container mpls-lsp-trace {
                presence "CLI submode compatibility.";
                description
                  "Perform MPLS LSP Trace operation";
                leaf ttl {
                  type uint32 {
                    range "1..255";
                  }
                  // NCS drop default statement
                  description
                    "Time to live value";
                }
                uses live_ncs_EXP-BITS;
                uses live_ncs_REPLY;
                uses live_ncs_TAG;
                uses live_ncs_IPSLA-MPLSLM-DEF-CFG-LSP-SELECTOR;
                uses live_ncs_OUTPUT-INTERFACE;
                uses live_ncs_ACCESSLIST;
                uses live_ncs_IPSLA-MPLSLM-DEF-CFG-OUTPUT-NEXTHOP;
                uses live_ncs_IPSLA-MPLSLM-DEF-CFG-STATISTICS;
                uses live_ncs_TIMEOUT;
                uses live_ncs_IPSLA-MPLSLM-DEF-CFG-FORCE-EXPLICIT-NULL;
                uses live_ncs_SCAN;
                uses live_ncs_IPSLA-MPLSLM-DEF-CFG-VRF;
              }
              container mpls-lsp-ping {
                presence "CLI submode compatibility.";
                description
                  "Perform MPLS LSP Ping operation";
                container data-size {
                  description
                    "Protocol data size in payload of probe
                     packets";
                  leaf request {
                    type uint32 {
                      range "100..17986";
                    }
                    units "byte";
                    // NCS drop default statement
                    description
                      "Payload size in request probe packet";
                  }
                }
                container path-discover {
                  presence "CLI submode compatibility.";
                  description
                    "Path discover configuration";
                  container session {
                    description
                      "Session parameters configuration";
                    leaf timeout {
                      type uint32 {
                        range "1..900";
                      }
                      units "second";
                      // NCS drop default statement
                      description
                        "Timeout value for path discovery request";
                    }
                    leaf limit {
                      type uint32 {
                        range "1..15";
                      }
                      // NCS drop default statement
                      description
                        "Number of concurrent active path
                         discovery requests at one time";
                    }
                  }
                  container path {
                    description
                      "Path parameters configuration";
                    container secondary-frequency {
                      presence "Indicates a secondary-frequency node is configured.";
                      description
                        "Frequency to be used if path failure
                         condition is detected";
                      leaf type {
                        type live_ncs_Ipsla-secondary-frequency;
                        // NCS drop mandatory statement
                        description
                          "Condition type of path failure";
                      }
                      leaf frequency {
                        type uint32 {
                          range "1..604800";
                        }
                        units "second";
                        // NCS drop mandatory statement
                        description
                          "Frequency value in seconds";
                      }
                    }
                    leaf retry {
                      type uint32 {
                        range "1..16";
                      }
                      // NCS drop default statement
                      description
                        "Number of attempts before declaring the
                         path as down";
                    }
                  }
                  container echo {
                    description
                      "Echo parameters configuration";
                    container multipath {
                      description
                        "Downstream map multipath settings";
                      leaf bitmap-size {
                        type uint32 {
                          range "1..256";
                        }
                        // NCS drop default statement
                        description
                          "Multipath bit size";
                      }
                    }
                    leaf interval {
                      type uint32 {
                        range "0..3600000";
                      }
                      units "millisecond";
                      // NCS drop default statement
                      description
                        "Send interval between echo requests
                         during path discovery";
                    }
                    leaf timeout {
                      type uint32 {
                        range "1..3600";
                      }
                      units "second";
                      // NCS drop default statement
                      description
                        "Timeout value for echo requests during
                         path discovery";
                    }
                    leaf retry {
                      type uint32 {
                        range "0..10";
                      }
                      // NCS drop default statement
                      description
                        "Number of timeout retry attempts during
                         path discovery";
                    }
                    leaf maximum-lsp-selector {
                      type inet:ipv4-address-no-zone;
                      // NCS drop default statement
                      description
                        "Maximum IPv4 address used as destination
                         in echo request";
                    }
                  }
                  leaf scan-period {
                    type uint32 {
                      range "0..7200";
                    }
                    units "minute";
                    // NCS drop default statement
                    description
                      "Time period for finishing path discovery";
                  }
                }
                leaf ttl {
                  type uint32 {
                    range "1..255";
                  }
                  // NCS drop default statement
                  description
                    "Time to live value";
                }
                uses live_ncs_EXP-BITS;
                uses live_ncs_REPLY;
                uses live_ncs_TAG;
                uses live_ncs_IPSLA-MPLSLM-DEF-CFG-LSP-SELECTOR;
                uses live_ncs_OUTPUT-INTERFACE;
                uses live_ncs_ACCESSLIST;
                uses live_ncs_IPSLA-MPLSLM-DEF-CFG-OUTPUT-NEXTHOP;
                uses live_ncs_IPSLA-MPLSLM-DEF-CFG-STATISTICS;
                uses live_ncs_TIMEOUT;
                uses live_ncs_IPSLA-MPLSLM-DEF-CFG-FORCE-EXPLICIT-NULL;
                uses live_ncs_SCAN;
                uses live_ncs_IPSLA-MPLSLM-DEF-CFG-VRF;
              }
            }
            leaf monitor-id {
              type uint32 {
                range "1..2048";
              }
              description
                "Monitor identifier";
            }
          }
        }
      }
      container operation {
        description
          "IPSLA Operation configuration";
        container schedules {
          description
            "Schedule an operation";
          list schedule {
            key "operation-id";
            description
              "Operation schedule configuration";
            container start-time {
              description
                "Start time of the operation";
              leaf schedule-type {
                type live_ncs_Ipsla-sched;
                description
                  "Type of schedule";
              }
              leaf hour {
                // NCS drop when statement
                type uint32 {
                  range "0..23";
                }
                description
                  "Hour value(hh) in hh:mm:ss specification";
              }
              leaf minute {
                // NCS drop when statement
                type uint32 {
                  range "0..59";
                }
                description
                  "Minute value(mm) in hh:mm:ss specification";
              }
              leaf second {
                // NCS drop when statement
                type uint32 {
                  range "0..59";
                }
                description
                  "Second value(ss) in hh:mm:ss specification";
              }
              leaf month {
                // NCS drop when statement
                type live_ncs_Ipsla-month;
                description
                  "Month of the year (optional. Default current
                   month)";
              }
              leaf day {
                // NCS drop when statement
                type uint32 {
                  range "1..31";
                }
                description
                  "Day of the month(optional. Default today)";
              }
              leaf year {
                // NCS drop when statement
                type uint32 {
                  range "1993..2035";
                }
                description
                  "Year(optional. Default current year)";
              }
            }
            leaf life {
              type live_ncs_Ipsla-life;
              units "second";
              description
                "Length of the time to execute (default 3600
                 seconds)";
            }
            leaf ageout {
              type uint32 {
                range "0..2073600";
              }
              units "second";
              description
                "How long to keep this entry after it becomes
                 inactive";
            }
            leaf recurring {
              type empty;
              description
                "probe to be scheduled automatically every day";
            }
            leaf operation-id {
              type uint32 {
                range "1..2048";
              }
              description
                "Operation number";
            }
          }
        }
        container reactions {
          description
            "Reaction configuration";
          list reaction {
            key "operation-id";
            description
              "Reaction configuration for an operation";
            container condition {
              description
                "Reaction condition specification";
              container jitter-average-ds {
                presence "CLI submode compatibility.";
                description
                  "React on destination to source jitter
                   threshold violation";
                uses live_ncs_THRESHOLD-LIMITS;
                uses live_ncs_ACTION-TYPE;
                uses live_ncs_IPSLA-OP-REACT-CFG-THRESHOLD-TYPE;
              }
              container timeout {
                presence "CLI submode compatibility.";
                description
                  "React on probe timeout";
                uses live_ncs_ACTION-TYPE;
                uses live_ncs_IPSLA-OP-REACT-CFG-THRESHOLD-TYPE;
              }
              container jitter-average {
                presence "CLI submode compatibility.";
                description
                  "React on average round trip jitter threshold
                   violation";
                uses live_ncs_THRESHOLD-LIMITS;
                uses live_ncs_ACTION-TYPE;
                uses live_ncs_IPSLA-OP-REACT-CFG-THRESHOLD-TYPE;
              }
              container verify-error {
                presence "CLI submode compatibility.";
                description
                  "React on error verfication violation";
                uses live_ncs_ACTION-TYPE;
                uses live_ncs_IPSLA-OP-REACT-CFG-THRESHOLD-TYPE;
              }
              container rtt {
                presence "CLI submode compatibility.";
                description
                  "React on round trip time threshold violation";
                uses live_ncs_THRESHOLD-LIMITS;
                uses live_ncs_ACTION-TYPE;
                uses live_ncs_IPSLA-OP-REACT-CFG-THRESHOLD-TYPE;
              }
              container packet-loss-sd {
                presence "CLI submode compatibility.";
                description
                  "React on destination to source packet loss
                   threshold violation";
                uses live_ncs_THRESHOLD-LIMITS;
                uses live_ncs_ACTION-TYPE;
                uses live_ncs_IPSLA-OP-REACT-CFG-THRESHOLD-TYPE;
              }
              container jitter-average-sd {
                presence "CLI submode compatibility.";
                description
                  "React on average source to destination
                   jitter threshold violation";
                uses live_ncs_THRESHOLD-LIMITS;
                uses live_ncs_ACTION-TYPE;
                uses live_ncs_IPSLA-OP-REACT-CFG-THRESHOLD-TYPE;
              }
              container connection-loss {
                presence "CLI submode compatibility.";
                description
                  "React on connection loss for a monitored
                   operation";
                uses live_ncs_ACTION-TYPE;
                uses live_ncs_IPSLA-OP-REACT-CFG-THRESHOLD-TYPE;
              }
              container packet-loss-ds {
                presence "CLI submode compatibility.";
                description
                  "React on source to destination packet loss
                   threshold violation";
                uses live_ncs_THRESHOLD-LIMITS;
                uses live_ncs_ACTION-TYPE;
                uses live_ncs_IPSLA-OP-REACT-CFG-THRESHOLD-TYPE;
              }
            }
            leaf operation-id {
              type uint32 {
                range "1..2048";
              }
              description
                "Operation number";
            }
          }
        }
        container reaction-triggers {
          description
            "Reaction trigger configuration";
          list reaction-trigger {
            key "operation-id";
            description
              "Reaction trigger for an operation";
            leaf triggered-op-id {
              type uint32 {
                range "1..2048";
              }
              description
                "Operation number of the operation to be
                 triggered";
            }
            leaf operation-id {
              type uint32 {
                range "1..2048";
              }
              description
                "Operation number of the operation generating
                 a trigger";
            }
          }
        }
        container definitions {
          description
            "Operation definition table";
          list definition {
            key "operation-id";
            description
              "Operation definition";
            container operation-type {
              description
                "Operation type specification";
              container icmp-echo {
                presence "CLI submode compatibility.";
                description
                  "ICMPEcho Operation type";
                container data-size {
                  description
                    "Protocol data size in payload of probe
                     packets";
                  leaf request {
                    type uint32 {
                      range "0..16384";
                    }
                    units "byte";
                    // NCS drop default statement
                    description
                      "Payload size in request probe packet";
                  }
                }
                leaf source-address-v6 {
                  type string;
                  description
                    "Enter IPv6 address of the source device";
                }
                leaf dest-address-v6 {
                  type string;
                  description
                    "Enter IPv6 address of the destination
                     device";
                }
                uses live_ncs_SOURCE-ADDRESS;
                uses live_ncs_TOS;
                uses live_ncs_STATISTICS;
                uses live_ncs_VRF;
                uses live_ncs_HISTORY;
                uses live_ncs_IPSLA-OP-DEF-COMMON-CFG-TIMEOUT;
                uses live_ncs_FREQUENCY;
                uses live_ncs_DEST-ADDRESS;
                uses live_ncs_ENHANCED-STATS-TABLE;
                uses live_ncs_IPSLA-OP-DEF-COMMON-CFG-TAG;
              }
              container mpls-lsp-ping {
                presence "CLI submode compatibility.";
                description
                  "MPLS LSP Ping Operation type";
                container data-size {
                  description
                    "Protocol data size in payload of probe
                     packets";
                  leaf request {
                    type uint32 {
                      range "100..17986";
                    }
                    // NCS drop default statement
                    description
                      "Payload size in request probe packet";
                  }
                }
                container reply {
                  description
                    "Echo reply options for the MPLS LSP
                     operation";
                  leaf mode {
                    type live_ncs_Ipsla-lsp-ping-reply-mode;
                    description
                      "Enables use of router alert in echo reply
                       packets";
                  }
                  uses live_ncs_DSCP-BITS;
                }
                container target {
                  description
                    "Target for the MPLS LSP operation";
                  container traffic-engineering {
                    description
                      "Traffic engineering target";
                    leaf tunnel {
                      type uint32 {
                        range "0..65535";
                      }
                      description
                        "Tunnel interface number";
                    }
                  }
                  container ipv4 {
                    description
                      "Target specified as an IPv4 address";
                    container fec-address {
                      presence "Indicates a fec-address node is configured.";
                      description
                        "Target FEC address with mask";
                      leaf address {
                        type inet:ipv4-address-no-zone;
                        // NCS drop mandatory statement
                        description
                          "IP address for target";
                      }
                      leaf mask {
                        type inet:ipv4-address-no-zone;
                        // NCS drop mandatory statement
                        description
                          "IP netmask for target";
                      }
                    }
                  }
                  container pseudowire {
                    description
                      "Pseudowire target";
                    container target-address {
                      presence "Indicates a target-address node is configured.";
                      description
                        "Target address";
                      leaf address {
                        type inet:ipv4-address-no-zone;
                        // NCS drop mandatory statement
                        description
                          "Target address";
                      }
                      leaf vc-id {
                        type uint32 {
                          range "1..4294967295";
                        }
                        // NCS drop mandatory statement
                        description
                          "Virtual circuit ID";
                      }
                    }
                  }
                }
                leaf ttl {
                  type uint32 {
                    range "1..255";
                  }
                  // NCS drop default statement
                  description
                    "Time to live value";
                }
                uses live_ncs_SOURCE-ADDRESS;
                uses live_ncs_OUTPUT-NEXTHOP;
                uses live_ncs_LSP-SELECTOR;
                uses live_ncs_STATISTICS;
                uses live_ncs_IPSLA-OP-DEF-MPLS-LSP-CFG-EXP-BITS;
                uses live_ncs_FORCE-EXPLICIT-NULL;
                uses live_ncs_HISTORY;
                uses live_ncs_IPSLA-OP-DEF-COMMON-CFG-TIMEOUT;
                uses live_ncs_IPSLA-OP-DEF-MPLS-LSP-CFG-OUTPUT-INTERFACE;
                uses live_ncs_FREQUENCY;
                uses live_ncs_ENHANCED-STATS-TABLE;
                uses live_ncs_IPSLA-OP-DEF-COMMON-CFG-TAG;
              }
              container udp-echo {
                presence "CLI submode compatibility.";
                description
                  "UDPEcho Operation type";
                container data-size {
                  description
                    "Protocol data size in payload of probe
                     packets";
                  leaf request {
                    type uint32 {
                      range "16..1500";
                    }
                    units "byte";
                    // NCS drop default statement
                    description
                      "Payload size in request probe packet";
                  }
                }
                uses live_ncs_SOURCE-ADDRESS;
                uses live_ncs_TOS;
                uses live_ncs_CONTROL-DISABLE;
                uses live_ncs_SOURCE-PORT;
                uses live_ncs_STATISTICS;
                uses live_ncs_VRF;
                uses live_ncs_HISTORY;
                uses live_ncs_IPSLA-OP-DEF-COMMON-CFG-TIMEOUT;
                uses live_ncs_FREQUENCY;
                uses live_ncs_DEST-PORT;
                uses live_ncs_VERIFY-DATA;
                uses live_ncs_DEST-ADDRESS;
                uses live_ncs_ENHANCED-STATS-TABLE;
                uses live_ncs_IPSLA-OP-DEF-COMMON-CFG-TAG;
              }
              container mpls-lsp-trace {
                presence "CLI submode compatibility.";
                description
                  "MPLS LSP Trace Operation type";
                container target {
                  description
                    "Target for the MPLS LSP operation";
                  container traffic-engineering {
                    description
                      "Traffic engineering target";
                    leaf tunnel {
                      type uint32 {
                        range "0..65535";
                      }
                      description
                        "Tunnel interface number";
                    }
                  }
                  container ipv4 {
                    description
                      "Target specified as an IPv4 address";
                    container fec-address {
                      presence "Indicates a fec-address node is configured.";
                      description
                        "Target FEC address with mask";
                      leaf address {
                        type inet:ipv4-address-no-zone;
                        // NCS drop mandatory statement
                        description
                          "IP address for target";
                      }
                      leaf mask {
                        type inet:ipv4-address-no-zone;
                        // NCS drop mandatory statement
                        description
                          "IP netmask for target";
                      }
                    }
                  }
                }
                container reply {
                  description
                    "Echo reply options for the MPLS LSP
                     operation";
                  leaf mode {
                    type live_ncs_Ipsla-lsp-trace-reply-mode;
                    description
                      "Enables use of router alert in echo reply
                       packets";
                  }
                  uses live_ncs_DSCP-BITS;
                }
                leaf ttl {
                  type uint32 {
                    range "1..255";
                  }
                  // NCS drop default statement
                  description
                    "Time to live value";
                }
                uses live_ncs_SOURCE-ADDRESS;
                uses live_ncs_OUTPUT-NEXTHOP;
                uses live_ncs_LSP-SELECTOR;
                uses live_ncs_STATISTICS;
                uses live_ncs_IPSLA-OP-DEF-MPLS-LSP-CFG-EXP-BITS;
                uses live_ncs_FORCE-EXPLICIT-NULL;
                uses live_ncs_HISTORY;
                uses live_ncs_IPSLA-OP-DEF-COMMON-CFG-TIMEOUT;
                uses live_ncs_IPSLA-OP-DEF-MPLS-LSP-CFG-OUTPUT-INTERFACE;
                uses live_ncs_FREQUENCY;
                uses live_ncs_IPSLA-OP-DEF-COMMON-CFG-TAG;
              }
              container udp-jitter {
                presence "CLI submode compatibility.";
                description
                  "UDPJitter Operation type";
                container data-size {
                  description
                    "Protocol data size in payload of probe
                     packets";
                  leaf request {
                    type uint32 {
                      range "28..1500";
                    }
                    units "byte";
                    // NCS drop default statement
                    description
                      "Payload size in request probe packet";
                  }
                }
                container packet {
                  description
                    "Probe packet stream configuration
                     parameters";
                  leaf count {
                    type uint32 {
                      range "1..60000";
                    }
                    // NCS drop default statement
                    description
                      "Number of packets to be transmitted during
                       a probe";
                  }
                  leaf interval {
                    type uint32 {
                      range "1..60000";
                    }
                    units "millisecond";
                    // NCS drop default statement
                    description
                      "Packet interval in milliseconds";
                  }
                }
                uses live_ncs_SOURCE-ADDRESS;
                uses live_ncs_TOS;
                uses live_ncs_CONTROL-DISABLE;
                uses live_ncs_SOURCE-PORT;
                uses live_ncs_STATISTICS;
                uses live_ncs_VRF;
                uses live_ncs_IPSLA-OP-DEF-COMMON-CFG-TIMEOUT;
                uses live_ncs_FREQUENCY;
                uses live_ncs_DEST-PORT;
                uses live_ncs_VERIFY-DATA;
                uses live_ncs_DEST-ADDRESS;
                uses live_ncs_ENHANCED-STATS-TABLE;
                uses live_ncs_IPSLA-OP-DEF-COMMON-CFG-TAG;
              }
              container icmp-path-echo {
                presence "CLI submode compatibility.";
                description
                  "ICMPPathEcho Operation type";
                container history {
                  description
                    "Configure the history parameters for this
                     operation";
                  leaf samples {
                    type uint32 {
                      range "1..30";
                    }
                    // NCS drop default statement
                    description
                      "Specify number of samples to keep";
                  }
                  leaf buckets {
                    type uint32 {
                      range "1..60";
                    }
                    // NCS drop default statement
                    description
                      "Specify number of history buckets";
                  }
                  leaf history-filter {
                    type live_ncs_Ipsla-history-filter;
                    description
                      "Choose type of data to be stored in
                       history buffer";
                  }
                  leaf lives {
                    type uint32 {
                      range "0..2";
                    }
                    // NCS drop default statement
                    description
                      "Specify number of lives to be kept";
                  }
                }
                container data-size {
                  description
                    "Protocol data size in payload of probe
                     packets";
                  leaf request {
                    type uint32 {
                      range "0..16384";
                    }
                    units "byte";
                    // NCS drop default statement
                    description
                      "Payload size in request probe packet";
                  }
                }
                container statistics {
                  description
                    "Statistics collection aggregated over an
                     hour";
                  leaf paths {
                    type uint32 {
                      range "1..128";
                    }
                    // NCS drop default statement
                    description
                      "Maximum number of paths for which
                       statistics are kept";
                  }
                  leaf dist-interval {
                    type uint32 {
                      range "1..100";
                    }
                    units "millisecond";
                    // NCS drop default statement
                    description
                      "Specify distribution interval in
                       milliseconds";
                  }
                  leaf dist-count {
                    type uint32 {
                      range "1..20";
                    }
                    // NCS drop default statement
                    description
                      "Count of distribution intervals maintained";
                  }
                  leaf hours {
                    type uint32 {
                      range "0..25";
                    }
                    units "hour";
                    // NCS drop default statement
                    description
                      "Number of hours for which hourly
                       statistics are kept";
                  }
                  leaf hops {
                    type uint32 {
                      range "1..30";
                    }
                    // NCS drop default statement
                    description
                      "Maximum hops per path for which statistics
                       are kept";
                  }
                }
                uses live_ncs_SOURCE-ADDRESS;
                uses live_ncs_TOS;
                uses live_ncs_LSR-PATH;
                uses live_ncs_VRF;
                uses live_ncs_IPSLA-OP-DEF-COMMON-CFG-TIMEOUT;
                uses live_ncs_FREQUENCY;
                uses live_ncs_DEST-ADDRESS;
                uses live_ncs_IPSLA-OP-DEF-COMMON-CFG-TAG;
              }
              container icmp-path-jitter {
                presence "CLI submode compatibility.";
                description
                  "ICMPPathJitter Operation type";
                container data-size {
                  description
                    "Protocol data size in payload of probe
                     packets";
                  leaf request {
                    type uint32 {
                      range "0..16384";
                    }
                    units "byte";
                    // NCS drop default statement
                    description
                      "Payload size in request probe packet";
                  }
                }
                container packet {
                  description
                    "Probe packet stream configuration
                     parameters";
                  leaf count {
                    type uint32 {
                      range "1..100";
                    }
                    // NCS drop default statement
                    description
                      "Number of packets to be transmitted during
                       a probe";
                  }
                  leaf interval {
                    type uint32 {
                      range "1..60000";
                    }
                    units "millisecond";
                    // NCS drop default statement
                    description
                      "Packet interval in milliseconds";
                  }
                }
                uses live_ncs_SOURCE-ADDRESS;
                uses live_ncs_TOS;
                uses live_ncs_LSR-PATH;
                uses live_ncs_VRF;
                uses live_ncs_IPSLA-OP-DEF-COMMON-CFG-TIMEOUT;
                uses live_ncs_FREQUENCY;
                uses live_ncs_DEST-ADDRESS;
                uses live_ncs_IPSLA-OP-DEF-COMMON-CFG-TAG;
              }
            }
            leaf operation-id {
              type uint32 {
                range "1..2048";
              }
              description
                "Operation number";
            }
          }
        }
      }
      container responder {
        presence "CLI submode compatibility.";
        description
          "Responder configuration";
        container twamp {
          presence "CLI submode compatibility.";
          description
            "Responder TWAMP configuration";
          leaf timeout {
            type uint32 {
              range "1..604800";
            }
            units "second";
            // NCS drop default statement
            description
              "Configure responder timeout value in seconds";
          }
        }
        container type {
          description
            "Configure IPSLA Responder port type";
          container udp {
            description
              "Configure IPSLA Responder UDP address and port";
            container addresses {
              description
                "Configure IP address";
              list address {
                key "local-address";
                description
                  "Configure IP address for the permanent port";
                container ports {
                  description
                    "Configure port";
                  list port {
                    key "port";
                    description
                      "Configure port number for the permanent
                       port";
                    leaf port {
                      type inet:port-number;
                      description
                        "Port number to be enabled";
                    }
                  }
                }
                leaf local-address {
                  type inet:ipv4-address-no-zone;
                  description
                    "IP address of the Responder";
                }
              }
            }
          }
        }
        container twamp-light {
          description
            "Enter twamp-light session details";
          container session-ids {
            description
              "Create twamp-light session";
            list session-id {
              key "session-id";
              description
                "Configure session ID";
              container local-ip {
                description
                  "Configure local ip address";
                container local-ipv6-addresses {
                  description
                    "Configure IPV6 address";
                  list local-ipv6-address {
                    key "localv6-address";
                    description
                      "Enter value of local ip address";
                    leaf localv6-address {
                      type xr:live_ncs_Cisco-ios-xr-string;
                      description
                        "Local IPv6 address";
                    }
                    uses live_ncs_LOCAL-PORT;
                  }
                }
                container local-ipv4-addresses {
                  description
                    "Configure IPV4 address";
                  list local-ipv4-address {
                    key "localv4-address";
                    description
                      "Enter value of local ipv4 address";
                    leaf localv4-address {
                      type xr:live_ncs_Cisco-ios-xr-string;
                      description
                        "Local IPv4 address";
                    }
                    uses live_ncs_LOCAL-PORT;
                  }
                }
              }
              leaf twamp-light-timeout {
                type uint32 {
                  range "60..86400";
                }
                units "second";
                description
                  "Configure session timeout";
              }
              leaf session-id {
                type uint32 {
                  range "1..65535";
                }
                description
                  "SessionID";
              }
            }
          }
        }
      }
      container mpls-discovery {
        description
          "Provider Edge(PE) discovery configuration";
        container vpn {
          description
            "Layer 3 VPN PE discovery configuration";
          leaf interval {
            type uint32 {
              range "30..70560";
            }
            units "minute";
            // NCS drop default statement
            description
              "Specify a discovery refresh interval";
          }
        }
      }
      container server-twamp {
        presence "CLI submode compatibility.";
        description
          "IPPM Server configuration";
        leaf inactivity-timer {
          type uint32 {
            range "1..6000";
          }
          units "second";
          // NCS drop default statement
          description
            "Configure ippmserver inactivity timer value in
             seconds";
        }
        leaf port {
          type xr:live_ncs_Cisco-ios-xr-port-number;
          // NCS drop default statement
          description
            "Configure port number for ippmserver listening
             port";
        }
      }
    }
  }
  augment "/ncs:devices/ncs:template/ncs:ned-id/ncs:config" {
    container ipsla {
      description
        "IPSLA configuration";
      container common {
        description
          "IPSLA application common configuration";
        container hardware-timestamp {
          description
            "Hardware Timestamp configuration";
          leaf disable {
            type empty;
            description
              "states true if hw-timestamp is disabled";
          }
        }
        container authentication {
          description
            "Authenticaion configuration";
          leaf key-chain {
            type string;
            description
              "Use MD5 authentication for IPSLA control
               message";
          }
        }
        leaf low-memory {
          type string;
          // NCS drop default statement
          description
            "Configure low memory water mark (default 20M)";
        }
      }
      container mpls-lsp-monitor {
        description
          "MPLS LSP Monitor(MPLSLM) configuration";
        container reactions {
          description
            "MPLSLM Reaction configuration";
          list reaction {
            // NCS patched for predictable order
            ordered-by user;
            key "monitor-id";
            description
              "Reaction configuration for an MPLSLM instance";
            container condition {
              description
                "Reaction condition specification";
              container lpd-tree-trace {
                presence "CLI submode compatibility.";
                description
                  "React on LPD Tree Trace violation for a
                   monitored MPLSLM";
                uses ncs_template_IPSLA-MPLSLM-REACT-CFG-ACTION-TYPE;
              }
              container timeout {
                presence "CLI submode compatibility.";
                description
                  "React on probe timeout";
                uses ncs_template_IPSLA-MPLSLM-REACT-CFG-ACTION-TYPE;
                uses ncs_template_THRESHOLD-TYPE;
              }
              container lpd-group {
                presence "CLI submode compatibility.";
                description
                  "React on LPD Group violation for a monitored
                   MPLSLM";
                uses ncs_template_IPSLA-MPLSLM-REACT-CFG-ACTION-TYPE;
              }
              container connection-loss {
                presence "CLI submode compatibility.";
                description
                  "React on connection loss for a monitored
                   MPLSLM";
                uses ncs_template_IPSLA-MPLSLM-REACT-CFG-ACTION-TYPE;
                uses ncs_template_THRESHOLD-TYPE;
              }
            }
            leaf monitor-id {
              type string;
              description
                "Monitor identifier";
            }
          }
        }
        container schedules {
          description
            "MPLSLM schedule configuration";
          list schedule {
            // NCS patched for predictable order
            ordered-by user;
            key "monitor-id";
            description
              "Schedule an MPLSLM instance";
            container start-time {
              description
                "Start time of MPLSLM instance";
              leaf schedule-type {
                type ncs_template_Ipsla-sched;
                description
                  "Type of schedule";
              }
              leaf hour {
                // NCS drop when statement
                type string;
                description
                  "Hour value(hh) in hh:mm:ss specification";
              }
              leaf minute {
                // NCS drop when statement
                type string;
                description
                  "Minute value(mm) in hh:mm:ss specification";
              }
              leaf second {
                // NCS drop when statement
                type string;
                description
                  "Second value(ss) in hh:mm:ss specification";
              }
              leaf month {
                // NCS drop when statement
                type ncs_template_Ipsla-month;
                description
                  "Month of the year (optional. Default current
                   month)";
              }
              leaf day {
                // NCS drop when statement
                type string;
                description
                  "Day of the month(optional. Default today)";
              }
              leaf year {
                // NCS drop when statement
                type string;
                description
                  "Year (optional. Default current year)";
              }
            }
            leaf frequency {
              type string;
              units "second";
              description
                "Group schedule frequency of the probing";
            }
            leaf period {
              type string;
              units "second";
              description
                "Group schedule period range";
            }
            leaf monitor-id {
              type string;
              description
                "Monitor indentifier";
            }
          }
        }
        container definitions {
          description
            "MPLS LSP Monitor definition table";
          list definition {
            // NCS patched for predictable order
            ordered-by user;
            key "monitor-id";
            description
              "MPLS LSP Monitor definition";
            container operation-type {
              description
                "Operation type specification";
              container mpls-lsp-trace {
                presence "CLI submode compatibility.";
                description
                  "Perform MPLS LSP Trace operation";
                leaf ttl {
                  type string;
                  // NCS drop default statement
                  description
                    "Time to live value";
                }
                uses ncs_template_EXP-BITS;
                uses ncs_template_REPLY;
                uses ncs_template_TAG;
                uses ncs_template_IPSLA-MPLSLM-DEF-CFG-LSP-SELECTOR;
                uses ncs_template_OUTPUT-INTERFACE;
                uses ncs_template_ACCESSLIST;
                uses ncs_template_IPSLA-MPLSLM-DEF-CFG-OUTPUT-NEXTHOP;
                uses ncs_template_IPSLA-MPLSLM-DEF-CFG-STATISTICS;
                uses ncs_template_TIMEOUT;
                uses ncs_template_IPSLA-MPLSLM-DEF-CFG-FORCE-EXPLICIT-NULL;
                uses ncs_template_SCAN;
                uses ncs_template_IPSLA-MPLSLM-DEF-CFG-VRF;
              }
              container mpls-lsp-ping {
                presence "CLI submode compatibility.";
                description
                  "Perform MPLS LSP Ping operation";
                container data-size {
                  description
                    "Protocol data size in payload of probe
                     packets";
                  leaf request {
                    type string;
                    units "byte";
                    // NCS drop default statement
                    description
                      "Payload size in request probe packet";
                  }
                }
                container path-discover {
                  presence "CLI submode compatibility.";
                  description
                    "Path discover configuration";
                  container session {
                    description
                      "Session parameters configuration";
                    leaf timeout {
                      type string;
                      units "second";
                      // NCS drop default statement
                      description
                        "Timeout value for path discovery request";
                    }
                    leaf limit {
                      type string;
                      // NCS drop default statement
                      description
                        "Number of concurrent active path
                         discovery requests at one time";
                    }
                  }
                  container path {
                    description
                      "Path parameters configuration";
                    container secondary-frequency {
                      presence "Indicates a secondary-frequency node is configured.";
                      description
                        "Frequency to be used if path failure
                         condition is detected";
                      leaf type {
                        type ncs_template_Ipsla-secondary-frequency;
                        // NCS drop mandatory statement
                        description
                          "Condition type of path failure";
                      }
                      leaf frequency {
                        type string;
                        units "second";
                        // NCS drop mandatory statement
                        description
                          "Frequency value in seconds";
                      }
                    }
                    leaf retry {
                      type string;
                      // NCS drop default statement
                      description
                        "Number of attempts before declaring the
                         path as down";
                    }
                  }
                  container echo {
                    description
                      "Echo parameters configuration";
                    container multipath {
                      description
                        "Downstream map multipath settings";
                      leaf bitmap-size {
                        type string;
                        // NCS drop default statement
                        description
                          "Multipath bit size";
                      }
                    }
                    leaf interval {
                      type string;
                      units "millisecond";
                      // NCS drop default statement
                      description
                        "Send interval between echo requests
                         during path discovery";
                    }
                    leaf timeout {
                      type string;
                      units "second";
                      // NCS drop default statement
                      description
                        "Timeout value for echo requests during
                         path discovery";
                    }
                    leaf retry {
                      type string;
                      // NCS drop default statement
                      description
                        "Number of timeout retry attempts during
                         path discovery";
                    }
                    leaf maximum-lsp-selector {
                      type string;
                      // NCS drop default statement
                      description
                        "Maximum IPv4 address used as destination
                         in echo request";
                    }
                  }
                  leaf scan-period {
                    type string;
                    units "minute";
                    // NCS drop default statement
                    description
                      "Time period for finishing path discovery";
                  }
                }
                leaf ttl {
                  type string;
                  // NCS drop default statement
                  description
                    "Time to live value";
                }
                uses ncs_template_EXP-BITS;
                uses ncs_template_REPLY;
                uses ncs_template_TAG;
                uses ncs_template_IPSLA-MPLSLM-DEF-CFG-LSP-SELECTOR;
                uses ncs_template_OUTPUT-INTERFACE;
                uses ncs_template_ACCESSLIST;
                uses ncs_template_IPSLA-MPLSLM-DEF-CFG-OUTPUT-NEXTHOP;
                uses ncs_template_IPSLA-MPLSLM-DEF-CFG-STATISTICS;
                uses ncs_template_TIMEOUT;
                uses ncs_template_IPSLA-MPLSLM-DEF-CFG-FORCE-EXPLICIT-NULL;
                uses ncs_template_SCAN;
                uses ncs_template_IPSLA-MPLSLM-DEF-CFG-VRF;
              }
            }
            leaf monitor-id {
              type string;
              description
                "Monitor identifier";
            }
          }
        }
      }
      container operation {
        description
          "IPSLA Operation configuration";
        container schedules {
          description
            "Schedule an operation";
          list schedule {
            // NCS patched for predictable order
            ordered-by user;
            key "operation-id";
            description
              "Operation schedule configuration";
            container start-time {
              description
                "Start time of the operation";
              leaf schedule-type {
                type ncs_template_Ipsla-sched;
                description
                  "Type of schedule";
              }
              leaf hour {
                // NCS drop when statement
                type string;
                description
                  "Hour value(hh) in hh:mm:ss specification";
              }
              leaf minute {
                // NCS drop when statement
                type string;
                description
                  "Minute value(mm) in hh:mm:ss specification";
              }
              leaf second {
                // NCS drop when statement
                type string;
                description
                  "Second value(ss) in hh:mm:ss specification";
              }
              leaf month {
                // NCS drop when statement
                type ncs_template_Ipsla-month;
                description
                  "Month of the year (optional. Default current
                   month)";
              }
              leaf day {
                // NCS drop when statement
                type string;
                description
                  "Day of the month(optional. Default today)";
              }
              leaf year {
                // NCS drop when statement
                type string;
                description
                  "Year(optional. Default current year)";
              }
            }
            leaf life {
              type ncs_template_Ipsla-life;
              units "second";
              description
                "Length of the time to execute (default 3600
                 seconds)";
            }
            leaf ageout {
              type string;
              units "second";
              description
                "How long to keep this entry after it becomes
                 inactive";
            }
            leaf recurring {
              type empty;
              description
                "probe to be scheduled automatically every day";
            }
            leaf operation-id {
              type string;
              description
                "Operation number";
            }
          }
        }
        container reactions {
          description
            "Reaction configuration";
          list reaction {
            // NCS patched for predictable order
            ordered-by user;
            key "operation-id";
            description
              "Reaction configuration for an operation";
            container condition {
              description
                "Reaction condition specification";
              container jitter-average-ds {
                presence "CLI submode compatibility.";
                description
                  "React on destination to source jitter
                   threshold violation";
                uses ncs_template_THRESHOLD-LIMITS;
                uses ncs_template_ACTION-TYPE;
                uses ncs_template_IPSLA-OP-REACT-CFG-THRESHOLD-TYPE;
              }
              container timeout {
                presence "CLI submode compatibility.";
                description
                  "React on probe timeout";
                uses ncs_template_ACTION-TYPE;
                uses ncs_template_IPSLA-OP-REACT-CFG-THRESHOLD-TYPE;
              }
              container jitter-average {
                presence "CLI submode compatibility.";
                description
                  "React on average round trip jitter threshold
                   violation";
                uses ncs_template_THRESHOLD-LIMITS;
                uses ncs_template_ACTION-TYPE;
                uses ncs_template_IPSLA-OP-REACT-CFG-THRESHOLD-TYPE;
              }
              container verify-error {
                presence "CLI submode compatibility.";
                description
                  "React on error verfication violation";
                uses ncs_template_ACTION-TYPE;
                uses ncs_template_IPSLA-OP-REACT-CFG-THRESHOLD-TYPE;
              }
              container rtt {
                presence "CLI submode compatibility.";
                description
                  "React on round trip time threshold violation";
                uses ncs_template_THRESHOLD-LIMITS;
                uses ncs_template_ACTION-TYPE;
                uses ncs_template_IPSLA-OP-REACT-CFG-THRESHOLD-TYPE;
              }
              container packet-loss-sd {
                presence "CLI submode compatibility.";
                description
                  "React on destination to source packet loss
                   threshold violation";
                uses ncs_template_THRESHOLD-LIMITS;
                uses ncs_template_ACTION-TYPE;
                uses ncs_template_IPSLA-OP-REACT-CFG-THRESHOLD-TYPE;
              }
              container jitter-average-sd {
                presence "CLI submode compatibility.";
                description
                  "React on average source to destination
                   jitter threshold violation";
                uses ncs_template_THRESHOLD-LIMITS;
                uses ncs_template_ACTION-TYPE;
                uses ncs_template_IPSLA-OP-REACT-CFG-THRESHOLD-TYPE;
              }
              container connection-loss {
                presence "CLI submode compatibility.";
                description
                  "React on connection loss for a monitored
                   operation";
                uses ncs_template_ACTION-TYPE;
                uses ncs_template_IPSLA-OP-REACT-CFG-THRESHOLD-TYPE;
              }
              container packet-loss-ds {
                presence "CLI submode compatibility.";
                description
                  "React on source to destination packet loss
                   threshold violation";
                uses ncs_template_THRESHOLD-LIMITS;
                uses ncs_template_ACTION-TYPE;
                uses ncs_template_IPSLA-OP-REACT-CFG-THRESHOLD-TYPE;
              }
            }
            leaf operation-id {
              type string;
              description
                "Operation number";
            }
          }
        }
        container reaction-triggers {
          description
            "Reaction trigger configuration";
          list reaction-trigger {
            // NCS patched for predictable order
            ordered-by user;
            key "operation-id";
            description
              "Reaction trigger for an operation";
            leaf triggered-op-id {
              type string;
              description
                "Operation number of the operation to be
                 triggered";
            }
            leaf operation-id {
              type string;
              description
                "Operation number of the operation generating
                 a trigger";
            }
          }
        }
        container definitions {
          description
            "Operation definition table";
          list definition {
            // NCS patched for predictable order
            ordered-by user;
            key "operation-id";
            description
              "Operation definition";
            container operation-type {
              description
                "Operation type specification";
              container icmp-echo {
                presence "CLI submode compatibility.";
                description
                  "ICMPEcho Operation type";
                container data-size {
                  description
                    "Protocol data size in payload of probe
                     packets";
                  leaf request {
                    type string;
                    units "byte";
                    // NCS drop default statement
                    description
                      "Payload size in request probe packet";
                  }
                }
                leaf source-address-v6 {
                  type string;
                  description
                    "Enter IPv6 address of the source device";
                }
                leaf dest-address-v6 {
                  type string;
                  description
                    "Enter IPv6 address of the destination
                     device";
                }
                uses ncs_template_SOURCE-ADDRESS;
                uses ncs_template_TOS;
                uses ncs_template_STATISTICS;
                uses ncs_template_VRF;
                uses ncs_template_HISTORY;
                uses ncs_template_IPSLA-OP-DEF-COMMON-CFG-TIMEOUT;
                uses ncs_template_FREQUENCY;
                uses ncs_template_DEST-ADDRESS;
                uses ncs_template_ENHANCED-STATS-TABLE;
                uses ncs_template_IPSLA-OP-DEF-COMMON-CFG-TAG;
              }
              container mpls-lsp-ping {
                presence "CLI submode compatibility.";
                description
                  "MPLS LSP Ping Operation type";
                container data-size {
                  description
                    "Protocol data size in payload of probe
                     packets";
                  leaf request {
                    type string;
                    // NCS drop default statement
                    description
                      "Payload size in request probe packet";
                  }
                }
                container reply {
                  description
                    "Echo reply options for the MPLS LSP
                     operation";
                  leaf mode {
                    type ncs_template_Ipsla-lsp-ping-reply-mode;
                    description
                      "Enables use of router alert in echo reply
                       packets";
                  }
                  uses ncs_template_DSCP-BITS;
                }
                container target {
                  description
                    "Target for the MPLS LSP operation";
                  container traffic-engineering {
                    description
                      "Traffic engineering target";
                    leaf tunnel {
                      type string;
                      description
                        "Tunnel interface number";
                    }
                  }
                  container ipv4 {
                    description
                      "Target specified as an IPv4 address";
                    container fec-address {
                      presence "Indicates a fec-address node is configured.";
                      description
                        "Target FEC address with mask";
                      leaf address {
                        type string;
                        // NCS drop mandatory statement
                        description
                          "IP address for target";
                      }
                      leaf mask {
                        type string;
                        // NCS drop mandatory statement
                        description
                          "IP netmask for target";
                      }
                    }
                  }
                  container pseudowire {
                    description
                      "Pseudowire target";
                    container target-address {
                      presence "Indicates a target-address node is configured.";
                      description
                        "Target address";
                      leaf address {
                        type string;
                        // NCS drop mandatory statement
                        description
                          "Target address";
                      }
                      leaf vc-id {
                        type string;
                        // NCS drop mandatory statement
                        description
                          "Virtual circuit ID";
                      }
                    }
                  }
                }
                leaf ttl {
                  type string;
                  // NCS drop default statement
                  description
                    "Time to live value";
                }
                uses ncs_template_SOURCE-ADDRESS;
                uses ncs_template_OUTPUT-NEXTHOP;
                uses ncs_template_LSP-SELECTOR;
                uses ncs_template_STATISTICS;
                uses ncs_template_IPSLA-OP-DEF-MPLS-LSP-CFG-EXP-BITS;
                uses ncs_template_FORCE-EXPLICIT-NULL;
                uses ncs_template_HISTORY;
                uses ncs_template_IPSLA-OP-DEF-COMMON-CFG-TIMEOUT;
                uses ncs_template_IPSLA-OP-DEF-MPLS-LSP-CFG-OUTPUT-INTERFACE;
                uses ncs_template_FREQUENCY;
                uses ncs_template_ENHANCED-STATS-TABLE;
                uses ncs_template_IPSLA-OP-DEF-COMMON-CFG-TAG;
              }
              container udp-echo {
                presence "CLI submode compatibility.";
                description
                  "UDPEcho Operation type";
                container data-size {
                  description
                    "Protocol data size in payload of probe
                     packets";
                  leaf request {
                    type string;
                    units "byte";
                    // NCS drop default statement
                    description
                      "Payload size in request probe packet";
                  }
                }
                uses ncs_template_SOURCE-ADDRESS;
                uses ncs_template_TOS;
                uses ncs_template_CONTROL-DISABLE;
                uses ncs_template_SOURCE-PORT;
                uses ncs_template_STATISTICS;
                uses ncs_template_VRF;
                uses ncs_template_HISTORY;
                uses ncs_template_IPSLA-OP-DEF-COMMON-CFG-TIMEOUT;
                uses ncs_template_FREQUENCY;
                uses ncs_template_DEST-PORT;
                uses ncs_template_VERIFY-DATA;
                uses ncs_template_DEST-ADDRESS;
                uses ncs_template_ENHANCED-STATS-TABLE;
                uses ncs_template_IPSLA-OP-DEF-COMMON-CFG-TAG;
              }
              container mpls-lsp-trace {
                presence "CLI submode compatibility.";
                description
                  "MPLS LSP Trace Operation type";
                container target {
                  description
                    "Target for the MPLS LSP operation";
                  container traffic-engineering {
                    description
                      "Traffic engineering target";
                    leaf tunnel {
                      type string;
                      description
                        "Tunnel interface number";
                    }
                  }
                  container ipv4 {
                    description
                      "Target specified as an IPv4 address";
                    container fec-address {
                      presence "Indicates a fec-address node is configured.";
                      description
                        "Target FEC address with mask";
                      leaf address {
                        type string;
                        // NCS drop mandatory statement
                        description
                          "IP address for target";
                      }
                      leaf mask {
                        type string;
                        // NCS drop mandatory statement
                        description
                          "IP netmask for target";
                      }
                    }
                  }
                }
                container reply {
                  description
                    "Echo reply options for the MPLS LSP
                     operation";
                  leaf mode {
                    type ncs_template_Ipsla-lsp-trace-reply-mode;
                    description
                      "Enables use of router alert in echo reply
                       packets";
                  }
                  uses ncs_template_DSCP-BITS;
                }
                leaf ttl {
                  type string;
                  // NCS drop default statement
                  description
                    "Time to live value";
                }
                uses ncs_template_SOURCE-ADDRESS;
                uses ncs_template_OUTPUT-NEXTHOP;
                uses ncs_template_LSP-SELECTOR;
                uses ncs_template_STATISTICS;
                uses ncs_template_IPSLA-OP-DEF-MPLS-LSP-CFG-EXP-BITS;
                uses ncs_template_FORCE-EXPLICIT-NULL;
                uses ncs_template_HISTORY;
                uses ncs_template_IPSLA-OP-DEF-COMMON-CFG-TIMEOUT;
                uses ncs_template_IPSLA-OP-DEF-MPLS-LSP-CFG-OUTPUT-INTERFACE;
                uses ncs_template_FREQUENCY;
                uses ncs_template_IPSLA-OP-DEF-COMMON-CFG-TAG;
              }
              container udp-jitter {
                presence "CLI submode compatibility.";
                description
                  "UDPJitter Operation type";
                container data-size {
                  description
                    "Protocol data size in payload of probe
                     packets";
                  leaf request {
                    type string;
                    units "byte";
                    // NCS drop default statement
                    description
                      "Payload size in request probe packet";
                  }
                }
                container packet {
                  description
                    "Probe packet stream configuration
                     parameters";
                  leaf count {
                    type string;
                    // NCS drop default statement
                    description
                      "Number of packets to be transmitted during
                       a probe";
                  }
                  leaf interval {
                    type string;
                    units "millisecond";
                    // NCS drop default statement
                    description
                      "Packet interval in milliseconds";
                  }
                }
                uses ncs_template_SOURCE-ADDRESS;
                uses ncs_template_TOS;
                uses ncs_template_CONTROL-DISABLE;
                uses ncs_template_SOURCE-PORT;
                uses ncs_template_STATISTICS;
                uses ncs_template_VRF;
                uses ncs_template_IPSLA-OP-DEF-COMMON-CFG-TIMEOUT;
                uses ncs_template_FREQUENCY;
                uses ncs_template_DEST-PORT;
                uses ncs_template_VERIFY-DATA;
                uses ncs_template_DEST-ADDRESS;
                uses ncs_template_ENHANCED-STATS-TABLE;
                uses ncs_template_IPSLA-OP-DEF-COMMON-CFG-TAG;
              }
              container icmp-path-echo {
                presence "CLI submode compatibility.";
                description
                  "ICMPPathEcho Operation type";
                container history {
                  description
                    "Configure the history parameters for this
                     operation";
                  leaf samples {
                    type string;
                    // NCS drop default statement
                    description
                      "Specify number of samples to keep";
                  }
                  leaf buckets {
                    type string;
                    // NCS drop default statement
                    description
                      "Specify number of history buckets";
                  }
                  leaf history-filter {
                    type ncs_template_Ipsla-history-filter;
                    description
                      "Choose type of data to be stored in
                       history buffer";
                  }
                  leaf lives {
                    type string;
                    // NCS drop default statement
                    description
                      "Specify number of lives to be kept";
                  }
                }
                container data-size {
                  description
                    "Protocol data size in payload of probe
                     packets";
                  leaf request {
                    type string;
                    units "byte";
                    // NCS drop default statement
                    description
                      "Payload size in request probe packet";
                  }
                }
                container statistics {
                  description
                    "Statistics collection aggregated over an
                     hour";
                  leaf paths {
                    type string;
                    // NCS drop default statement
                    description
                      "Maximum number of paths for which
                       statistics are kept";
                  }
                  leaf dist-interval {
                    type string;
                    units "millisecond";
                    // NCS drop default statement
                    description
                      "Specify distribution interval in
                       milliseconds";
                  }
                  leaf dist-count {
                    type string;
                    // NCS drop default statement
                    description
                      "Count of distribution intervals maintained";
                  }
                  leaf hours {
                    type string;
                    units "hour";
                    // NCS drop default statement
                    description
                      "Number of hours for which hourly
                       statistics are kept";
                  }
                  leaf hops {
                    type string;
                    // NCS drop default statement
                    description
                      "Maximum hops per path for which statistics
                       are kept";
                  }
                }
                uses ncs_template_SOURCE-ADDRESS;
                uses ncs_template_TOS;
                uses ncs_template_LSR-PATH;
                uses ncs_template_VRF;
                uses ncs_template_IPSLA-OP-DEF-COMMON-CFG-TIMEOUT;
                uses ncs_template_FREQUENCY;
                uses ncs_template_DEST-ADDRESS;
                uses ncs_template_IPSLA-OP-DEF-COMMON-CFG-TAG;
              }
              container icmp-path-jitter {
                presence "CLI submode compatibility.";
                description
                  "ICMPPathJitter Operation type";
                container data-size {
                  description
                    "Protocol data size in payload of probe
                     packets";
                  leaf request {
                    type string;
                    units "byte";
                    // NCS drop default statement
                    description
                      "Payload size in request probe packet";
                  }
                }
                container packet {
                  description
                    "Probe packet stream configuration
                     parameters";
                  leaf count {
                    type string;
                    // NCS drop default statement
                    description
                      "Number of packets to be transmitted during
                       a probe";
                  }
                  leaf interval {
                    type string;
                    units "millisecond";
                    // NCS drop default statement
                    description
                      "Packet interval in milliseconds";
                  }
                }
                uses ncs_template_SOURCE-ADDRESS;
                uses ncs_template_TOS;
                uses ncs_template_LSR-PATH;
                uses ncs_template_VRF;
                uses ncs_template_IPSLA-OP-DEF-COMMON-CFG-TIMEOUT;
                uses ncs_template_FREQUENCY;
                uses ncs_template_DEST-ADDRESS;
                uses ncs_template_IPSLA-OP-DEF-COMMON-CFG-TAG;
              }
            }
            leaf operation-id {
              type string;
              description
                "Operation number";
            }
          }
        }
      }
      container responder {
        presence "CLI submode compatibility.";
        description
          "Responder configuration";
        container twamp {
          presence "CLI submode compatibility.";
          description
            "Responder TWAMP configuration";
          leaf timeout {
            type string;
            units "second";
            // NCS drop default statement
            description
              "Configure responder timeout value in seconds";
          }
        }
        container type {
          description
            "Configure IPSLA Responder port type";
          container udp {
            description
              "Configure IPSLA Responder UDP address and port";
            container addresses {
              description
                "Configure IP address";
              list address {
                // NCS patched for predictable order
                ordered-by user;
                key "local-address";
                description
                  "Configure IP address for the permanent port";
                container ports {
                  description
                    "Configure port";
                  list port {
                    // NCS patched for predictable order
                    ordered-by user;
                    key "port";
                    description
                      "Configure port number for the permanent
                       port";
                    leaf port {
                      type string;
                      description
                        "Port number to be enabled";
                    }
                  }
                }
                leaf local-address {
                  type string;
                  description
                    "IP address of the Responder";
                }
              }
            }
          }
        }
        container twamp-light {
          description
            "Enter twamp-light session details";
          container session-ids {
            description
              "Create twamp-light session";
            list session-id {
              // NCS patched for predictable order
              ordered-by user;
              key "session-id";
              description
                "Configure session ID";
              container local-ip {
                description
                  "Configure local ip address";
                container local-ipv6-addresses {
                  description
                    "Configure IPV6 address";
                  list local-ipv6-address {
                    // NCS patched for predictable order
                    ordered-by user;
                    key "localv6-address";
                    description
                      "Enter value of local ip address";
                    leaf localv6-address {
                      type xr:ncs_template_Cisco-ios-xr-string;
                      description
                        "Local IPv6 address";
                    }
                    uses ncs_template_LOCAL-PORT;
                  }
                }
                container local-ipv4-addresses {
                  description
                    "Configure IPV4 address";
                  list local-ipv4-address {
                    // NCS patched for predictable order
                    ordered-by user;
                    key "localv4-address";
                    description
                      "Enter value of local ipv4 address";
                    leaf localv4-address {
                      type xr:ncs_template_Cisco-ios-xr-string;
                      description
                        "Local IPv4 address";
                    }
                    uses ncs_template_LOCAL-PORT;
                  }
                }
              }
              leaf twamp-light-timeout {
                type string;
                units "second";
                description
                  "Configure session timeout";
              }
              leaf session-id {
                type string;
                description
                  "SessionID";
              }
            }
          }
        }
      }
      container mpls-discovery {
        description
          "Provider Edge(PE) discovery configuration";
        container vpn {
          description
            "Layer 3 VPN PE discovery configuration";
          leaf interval {
            type string;
            units "minute";
            // NCS drop default statement
            description
              "Specify a discovery refresh interval";
          }
        }
      }
      container server-twamp {
        presence "CLI submode compatibility.";
        description
          "IPPM Server configuration";
        leaf inactivity-timer {
          type string;
          units "second";
          // NCS drop default statement
          description
            "Configure ippmserver inactivity timer value in
             seconds";
        }
        leaf port {
          type xr:ncs_template_Cisco-ios-xr-port-number;
          // NCS drop default statement
          description
            "Configure port number for ippmserver listening
             port";
        }
      }
    }
  }
  augment "/ncs:devices/ncs:template/ncs:ned-id/ncs:config/a1:snmp/a1:notification" {
    description
      "This augment extends the configuration data of
       'Cisco-IOS-XR-snmp-agent-cfg'";
    leaf ipsla {
      type string;
      description
        "Enable SNMP RTTMON-MIB IPSLA traps";
    }
  }
  augment "/ncs:devices/ncs:device/ncs:live-status/a1:snmp/a1:notification" {
    description
      "This augment extends the configuration data of
       'Cisco-IOS-XR-snmp-agent-cfg'";
    leaf ipsla {
      tailf:ncs-device-type "netconf";
      tailf:display-when "not(../../../../ncs:module) or ../../../../ncs:module[ncs:name='Cisco-IOS-XR-man-ipsla-cfg'] or (../../../../ncs:live-status-protocol[not(ncs:capability)]) or (../../../../ncs:live-status-protocol/ncs:capability/ncs:module[.='Cisco-IOS-XR-man-ipsla-cfg'])";
      type boolean;
      description
        "Enable SNMP RTTMON-MIB IPSLA traps";
    }
  }
  augment "/ncs:devices/ncs:device/ncs:config/a1:snmp/a1:notification" {
    description
      "This augment extends the configuration data of
       'Cisco-IOS-XR-snmp-agent-cfg'";
    leaf ipsla {
      tailf:ncs-device-type "netconf";
      tailf:display-when "not(../../../../ncs:module) or ../../../../ncs:module[ncs:name='Cisco-IOS-XR-man-ipsla-cfg']";
      type boolean;
      description
        "Enable SNMP RTTMON-MIB IPSLA traps";
    }
  }
}

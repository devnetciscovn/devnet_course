module Cisco-IOS-XR-pbr-vrf-policy-cfg {
  // Generated by yanger -t ncs
  tailf:mount-id "cisco-iosxr-nc-7.3:cisco-iosxr-nc-7.3";
  tailf:ncs-device-type "netconf";

  namespace "http://cisco.com/ns/yang/Cisco-IOS-XR-pbr-vrf-policy-cfg";
  prefix pbr-vrf-policy-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr-vrf-policy package configuration.

     This module contains definitions
     for the following management objects:
       vrf-policy: VRF Policy PBR configuration

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Pbr-afi {
    type string;
    description
      "ipv4: Comment: v4 string for <afi_name>, ipv6:
       Comment: v6 string for <afi_name>";
  }

  typedef ncs_rpc_notif_Pbr-afi {
    type string {
      pattern '(ipv4)|(ipv6)';
    }
    description
      "ipv4: Comment: v4 string for <afi_name>, ipv6:
       Comment: v6 string for <afi_name>";
  }

  typedef live_ncs_Pbr-afi {
    type string {
      pattern '(ipv4)|(ipv6)';
    }
    description
      "ipv4: Comment: v4 string for <afi_name>, ipv6:
       Comment: v6 string for <afi_name>";
  }

  typedef Pbr-afi {
    type string {
      pattern '(ipv4)|(ipv6)';
    }
    description
      "ipv4: Comment: v4 string for <afi_name>, ipv6:
       Comment: v6 string for <afi_name>";
  }

  augment "/ncs:devices/ncs:device/ncs:config" {
    container vrf-policy {
      tailf:ncs-device-type "netconf";
      tailf:display-when "not(../../ncs:module) or ../../ncs:module[ncs:name='Cisco-IOS-XR-pbr-vrf-policy-cfg']";
      description
        "VRF Policy PBR configuration";
      list vrf {
        key "vrf-name";
        description
          "VRF Name";
        leaf vrf-name {
          type xr:Cisco-ios-xr-string;
          description
            "VRF name";
        }
        list afi {
          key "afi-type";
          description
            "address family";
          leaf service-policy-in {
            type string;
            description
              "Policy map name";
          }
          leaf afi-type {
            type Pbr-afi;
            description
              "AFI name";
          }
        }
      }
    }
  }
  augment "/ncs:devices/ncs:device/ncs:live-status" {
    container vrf-policy {
      tailf:ncs-device-type "netconf";
      tailf:display-when "not(../../ncs:module) or ../../ncs:module[ncs:name='Cisco-IOS-XR-pbr-vrf-policy-cfg'] or (../../ncs:live-status-protocol[not(ncs:capability)]) or (../../ncs:live-status-protocol/ncs:capability/ncs:module[.='Cisco-IOS-XR-pbr-vrf-policy-cfg'])";
      description
        "VRF Policy PBR configuration";
      list vrf {
        key "vrf-name";
        description
          "VRF Name";
        leaf vrf-name {
          type xr:live_ncs_Cisco-ios-xr-string;
          description
            "VRF name";
        }
        list afi {
          key "afi-type";
          description
            "address family";
          leaf service-policy-in {
            type string;
            description
              "Policy map name";
          }
          leaf afi-type {
            type live_ncs_Pbr-afi;
            description
              "AFI name";
          }
        }
      }
    }
  }
  augment "/ncs:devices/ncs:template/ncs:ned-id/ncs:config" {
    container vrf-policy {
      description
        "VRF Policy PBR configuration";
      list vrf {
        // NCS patched for predictable order
        ordered-by user;
        key "vrf-name";
        description
          "VRF Name";
        leaf vrf-name {
          type xr:ncs_template_Cisco-ios-xr-string;
          description
            "VRF name";
        }
        list afi {
          // NCS patched for predictable order
          ordered-by user;
          key "afi-type";
          description
            "address family";
          leaf service-policy-in {
            type string;
            description
              "Policy map name";
          }
          leaf afi-type {
            type ncs_template_Pbr-afi;
            description
              "AFI name";
          }
        }
      }
    }
  }
}

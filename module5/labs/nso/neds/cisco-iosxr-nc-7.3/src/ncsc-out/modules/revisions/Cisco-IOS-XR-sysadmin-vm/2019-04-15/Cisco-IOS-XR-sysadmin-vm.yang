module Cisco-IOS-XR-sysadmin-vm {
  // Generated by yanger -t ncs
  tailf:mount-id "cisco-iosxr-nc-7.3:cisco-iosxr-nc-7.3";
  tailf:ncs-device-type "netconf";

  namespace "http://www.cisco.com/ns/yang/Cisco-IOS-XR-sysadmin-vm";
  prefix vm;

  import tailf-common {
    prefix tailf;
  }
  import cisco-semver {
    prefix semver;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'vm profile|cpu|memory' commands.

     Copyright(c) 2018 by Cisco Systems, Inc.
     All rights reserved.

     Copyright (c) 2012-2020 by Cisco Systems, Inc.
     All rights reserved.";

  revision 2019-04-15 {
    description
      "Establish semantic version baseline.";
    semver:module-version "1.1.0";
  }
  revision 2018-11-20 {
    description
      "CSCvn05746, force hw-profile to be vrr";
  }
  revision 2018-06-20 {
    description
      "Initial revision";
  }

  typedef ncs_template_cp-dp-cores {
    type string;
    description
      "assign cpu cores to control/data plane";
  }

  typedef ncs_rpc_notif_cp-dp-cores {
    type string {
      pattern '0(-[0-9]+)?/[0-9]+(-[0-9]+)?';
    }
    description
      "assign cpu cores to control/data plane";
  }

  typedef live_ncs_cp-dp-cores {
    type string {
      pattern '0(-[0-9]+)?/[0-9]+(-[0-9]+)?';
    }
    description
      "assign cpu cores to control/data plane";
  }

  typedef cp-dp-cores {
    type string {
      pattern '0(-[0-9]+)?/[0-9]+(-[0-9]+)?';
    }
    description
      "assign cpu cores to control/data plane";
  }

  augment "/ncs:devices/ncs:device/ncs:config" {
    container vm {
      tailf:ncs-device-type "netconf";
      tailf:display-when "not(../../ncs:module) or ../../ncs:module[ncs:name='Cisco-IOS-XR-sysadmin-vm']";
      // NCS dropped explicit config true
      container config {
        choice cpu_mem-profile {
          case choose-profile {
            container hw-profile {
              leaf profile {
                type enumeration {
                  enum "vrr";
                }
                description
                  "xrv9k profile vpe|vrr";
              }
            }
          }
          case choose-cpu_mem {
            container memory {
              leaf admin {
                type uint32;
                description
                  "admin container memory in GB";
              }
              leaf rp {
                type uint32;
                description
                  "rp container memory in GB";
              }
              leaf lc {
                type uint32;
                description
                  "lc container memory in GB";
              }
            }
            container cpu {
              leaf assign {
                type cp-dp-cores;
                description
                  "assign cpu cores to control/data plane";
              }
            }
          }
        }
      }
    }
  }
  augment "/ncs:devices/ncs:device/ncs:live-status" {
    container vm {
      tailf:ncs-device-type "netconf";
      tailf:display-when "not(../../ncs:module) or ../../ncs:module[ncs:name='Cisco-IOS-XR-sysadmin-vm'] or (../../ncs:live-status-protocol[not(ncs:capability)]) or (../../ncs:live-status-protocol/ncs:capability/ncs:module[.='Cisco-IOS-XR-sysadmin-vm'])";
      container config {
        choice cpu_mem-profile {
          case choose-profile {
            container hw-profile {
              leaf profile {
                type enumeration {
                  enum "vrr";
                }
                description
                  "xrv9k profile vpe|vrr";
              }
            }
          }
          case choose-cpu_mem {
            container memory {
              leaf admin {
                type uint32;
                description
                  "admin container memory in GB";
              }
              leaf rp {
                type uint32;
                description
                  "rp container memory in GB";
              }
              leaf lc {
                type uint32;
                description
                  "lc container memory in GB";
              }
            }
            container cpu {
              leaf assign {
                type live_ncs_cp-dp-cores;
                description
                  "assign cpu cores to control/data plane";
              }
            }
          }
        }
      }
    }
  }
  augment "/ncs:devices/ncs:template/ncs:ned-id/ncs:config" {
    container vm {
      // NCS dropped explicit config true
      container config {
        choice cpu_mem-profile {
          case choose-profile {
            container hw-profile {
              leaf profile {
                type string;
                description
                  "xrv9k profile vpe|vrr";
              }
            }
          }
          case choose-cpu_mem {
            container memory {
              leaf admin {
                type string;
                description
                  "admin container memory in GB";
              }
              leaf rp {
                type string;
                description
                  "rp container memory in GB";
              }
              leaf lc {
                type string;
                description
                  "lc container memory in GB";
              }
            }
            container cpu {
              leaf assign {
                type ncs_template_cp-dp-cores;
                description
                  "assign cpu cores to control/data plane";
              }
            }
          }
        }
      }
    }
  }
}

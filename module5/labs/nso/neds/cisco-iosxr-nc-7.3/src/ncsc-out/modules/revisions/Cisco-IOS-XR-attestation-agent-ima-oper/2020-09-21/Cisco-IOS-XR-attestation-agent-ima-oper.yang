module Cisco-IOS-XR-attestation-agent-ima-oper {
  // Generated by yanger -t ncs
  tailf:mount-id "cisco-iosxr-nc-7.3:cisco-iosxr-nc-7.3";
  tailf:ncs-device-type "netconf";

  namespace "http://cisco.com/ns/yang/Cisco-IOS-XR-attestation-agent-ima-oper";
  prefix attestation-agent-ima-oper;

  import cisco-semver {
    prefix semver;
  }
  include Cisco-IOS-XR-attestation-agent-ima-oper-sub1 {
    revision-date 2020-09-21;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR attestation-agent-ima package operational data.

     This module contains definitions
     for the following management objects:
       attestation: Oper data for IMA cache and Cron job statistics

     Copyright (c) 2013-2020 by Cisco Systems, Inc.
     All rights reserved.";

  revision 2020-09-21 {
    description
      "Fixed bag mismatch issue for dossier stat.";
    semver:module-version "1.0.0";
  }
  revision 2020-09-15 {
    description
      "Added task for netconf support.";
  }
  revision 2019-04-05 {
    description
      "Establish semantic version baseline.";
  }
  revision 2015-11-09 {
    description
      "IOS XR 6.0 revision.";
  }

  augment "/ncs:devices/ncs:device/ncs:config" {
    // NCS drop config false container attestation
  }
  augment "/ncs:devices/ncs:device/ncs:live-status" {
    container attestation {
      tailf:ncs-device-type "netconf";
      tailf:display-when "not(../../ncs:module) or ../../ncs:module[ncs:name='Cisco-IOS-XR-attestation-agent-ima-oper'] or (../../ncs:live-status-protocol[not(ncs:capability)]) or (../../ncs:live-status-protocol/ncs:capability/ncs:module[.='Cisco-IOS-XR-attestation-agent-ima-oper'])";
      description
        "Oper data for IMA cache and Cron job statistics ";
      container ima-cache {
        description
          "Oper data for IMA cache and Cron job statistics ";
        container ima-corrupt-stat {
          description
            "Cron job running stats";
          uses live_ncs_BLOCK-VALID-DET;
        }
        container dossier-stat {
          description
            "Dossier running stats";
          uses live_ncs_DOSSIER-STAT;
        }
        container cron-stat {
          description
            "Cron job running stats";
          uses live_ncs_CRON-DET;
        }
        container node-cache-summary {
          description
            "Cache summary for nodes running agent";
          uses live_ncs_CACHE-DET;
        }
        container node-block-summary {
          description
            "Block summary for nodes running agent";
          uses live_ncs_BLOCK-DET;
        }
      }
    }
  }
  augment "/ncs:devices/ncs:template/ncs:ned-id/ncs:config" {
    // NCS drop config false container attestation
  }
}

module Cisco-IOS-XR-um-traps-mpls-ldp-cfg {
  // Generated by yanger -t ncs
  tailf:mount-id "cisco-iosxr-nc-7.3:cisco-iosxr-nc-7.3";
  tailf:ncs-device-type "netconf";

  namespace "http://cisco.com/ns/yang/Cisco-IOS-XR-um-traps-mpls-ldp-cfg";
  prefix um-traps-mpls-ldp-cfg;

  import cisco-semver {
    prefix semver;
  }
  import Cisco-IOS-XR-um-snmp-server-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traps mpls-ldp package configuration.

     This YANG module augments the
     modules with configuration data.

     Copyright (c) 2019 by Cisco Systems, Inc.
     All rights reserved.";

  revision 2019-10-10 {
    description
      "Initial version";
    semver:module-version "1.0.0";
  }

  augment "/ncs:devices/ncs:template/ncs:ned-id/ncs:config/a1:snmp-server/a1:traps" {
    container mpls {
      description
        "Enable SNMP MPLS traps";
      container ldp {
        description
          "Enable MPLS LDP traps";
        container down {
          presence "Indicates a down node is configured.";
          description
            "Enable MPLS LDP session down traps";
        }
        container up {
          presence "Indicates a up node is configured.";
          description
            "Enable MPLS LDP session up traps";
        }
        container threshold {
          presence "Indicates a threshold node is configured.";
          description
            "Enable MPLS LDP threshold traps";
        }
      }
    }
  }
  augment "/ncs:devices/ncs:device/ncs:live-status/a1:snmp-server/a1:traps" {
    container mpls {
      tailf:ncs-device-type "netconf";
      tailf:display-when "not(../../../../ncs:module) or ../../../../ncs:module[ncs:name='Cisco-IOS-XR-um-traps-mpls-ldp-cfg'] or (../../../../ncs:live-status-protocol[not(ncs:capability)]) or (../../../../ncs:live-status-protocol/ncs:capability/ncs:module[.='Cisco-IOS-XR-um-traps-mpls-ldp-cfg'])";
      description
        "Enable SNMP MPLS traps";
      container ldp {
        description
          "Enable MPLS LDP traps";
        container down {
          presence "Indicates a down node is configured.";
          description
            "Enable MPLS LDP session down traps";
        }
        container up {
          presence "Indicates a up node is configured.";
          description
            "Enable MPLS LDP session up traps";
        }
        container threshold {
          presence "Indicates a threshold node is configured.";
          description
            "Enable MPLS LDP threshold traps";
        }
      }
    }
  }
  augment "/ncs:devices/ncs:device/ncs:config/a1:snmp-server/a1:traps" {
    container mpls {
      tailf:ncs-device-type "netconf";
      tailf:display-when "not(../../../../ncs:module) or ../../../../ncs:module[ncs:name='Cisco-IOS-XR-um-traps-mpls-ldp-cfg']";
      description
        "Enable SNMP MPLS traps";
      container ldp {
        description
          "Enable MPLS LDP traps";
        container down {
          presence "Indicates a down node is configured.";
          description
            "Enable MPLS LDP session down traps";
        }
        container up {
          presence "Indicates a up node is configured.";
          description
            "Enable MPLS LDP session up traps";
        }
        container threshold {
          presence "Indicates a threshold node is configured.";
          description
            "Enable MPLS LDP threshold traps";
        }
      }
    }
  }
}

module Cisco-IOS-XR-platforms-ofa-table-stats-oper {
  // Generated by yanger -t ncs
  tailf:mount-id "cisco-iosxr-nc-7.3:cisco-iosxr-nc-7.3";
  tailf:ncs-device-type "netconf";

  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2020-06-19;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platforms-ofa-table-stats package operational data.

     This module contains definitions
     for the following management objects:
       ofa: OFA Data

     Copyright (c) 2013-2020 by Cisco Systems, Inc.
     All rights reserved.";

  revision 2020-06-19 {
    description
      "Bwalk Error Counters IosSetYangSchemaRev Cisco-IOS-XR-platforms-ofa-table-stats-oper";
    semver:module-version "3.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef ncs_template_Ofa-table {
    type string;
    description
      "Ofa table";
  }

  typedef ncs_rpc_notif_Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npu-host-port" {
        value 29;
        description
          "npuhostport";
      }
      enum "npuhwid" {
        value 30;
        description
          "npuhwid";
      }
      enum "optics-port" {
        value 31;
        description
          "opticsport";
      }
      enum "gi-port" {
        value 32;
        description
          "giport";
      }
      enum "l1-port" {
        value 33;
        description
          "l1port";
      }
      enum "mac-port" {
        value 34;
        description
          "macport";
      }
      enum "l2-port" {
        value 35;
        description
          "l2port";
      }
      enum "eth-port" {
        value 36;
        description
          "ethport";
      }
      enum "l2intf" {
        value 37;
        description
          "l2intf";
      }
      enum "l2if" {
        value 38;
        description
          "l2if";
      }
      enum "mplspwe-port" {
        value 39;
        description
          "mplspweport";
      }
      enum "mplspwe-port-o-list" {
        value 40;
        description
          "mplspweport olist";
      }
      enum "mhpwe-port" {
        value 41;
        description
          "mhpweport";
      }
      enum "l2xc" {
        value 42;
        description
          "l2xc";
      }
      enum "l2vpnstats" {
        value 43;
        description
          "l2vpnstats";
      }
      enum "l1-ports-tats" {
        value 44;
        description
          "l1portstats";
      }
      enum "mac-ports-tats" {
        value 45;
        description
          "macportstats";
      }
      enum "l3intf" {
        value 46;
        description
          "l3intf";
      }
      enum "l3if" {
        value 47;
        description
          "l3if";
      }
      enum "l3intfrxstats" {
        value 48;
        description
          "l3intfrxstats";
      }
      enum "ip-route" {
        value 49;
        description
          "iproute";
      }
      enum "ip6-route" {
        value 50;
        description
          "ip6route";
      }
      enum "punt-policy-stats" {
        value 51;
        description
          "puntpolicystats";
      }
      enum "lpts-policy-stats" {
        value 52;
        description
          "lptspolicystats";
      }
      enum "tep" {
        value 53;
        description
          "tep";
      }
      enum "ip-punt-policy" {
        value 54;
        description
          "ippuntpolicy";
      }
      enum "ip6-punt-policy" {
        value 55;
        description
          "ip6puntpolicy";
      }
      enum "iplpts-policy" {
        value 56;
        description
          "iplptspolicy";
      }
      enum "ip6lpts-policy" {
        value 57;
        description
          "ip6lptspolicy";
      }
      enum "isis-punt-policy" {
        value 58;
        description
          "isispuntpolicy";
      }
      enum "isislpts-policy" {
        value 59;
        description
          "isislptspolicy";
      }
      enum "nh-group" {
        value 60;
        description
          "nhgroup";
      }
      enum "ipnh-group" {
        value 61;
        description
          "ipnhgroup";
      }
      enum "ip6nh-group" {
        value 62;
        description
          "ip6nhgroup";
      }
      enum "ipnh" {
        value 63;
        description
          "ipnh";
      }
      enum "ip6nh" {
        value 64;
        description
          "ip6nh";
      }
      enum "ipvrf" {
        value 65;
        description
          "ipvrf";
      }
      enum "vrfid" {
        value 66;
        description
          "vrfid";
      }
      enum "mplsnh" {
        value 67;
        description
          "mplsnh";
      }
      enum "lspnh" {
        value 68;
        description
          "lspnh";
      }
      enum "mpls-label" {
        value 69;
        description
          "mplslabel";
      }
      enum "punt" {
        value 70;
        description
          "punt";
      }
      enum "punt-police-r" {
        value 71;
        description
          "puntpolicer";
      }
      enum "lpts-police-r" {
        value 72;
        description
          "lptspolicer";
      }
      enum "punt-lpts-police-r" {
        value 73;
        description
          "puntlptspolicer";
      }
      enum "punt-stats" {
        value 74;
        description
          "puntstats";
      }
      enum "tm-port" {
        value 75;
        description
          "tmport";
      }
      enum "span-session" {
        value 76;
        description
          "spansession";
      }
      enum "police-rstats" {
        value 77;
        description
          "policerstats";
      }
      enum "tm-ports-tats" {
        value 78;
        description
          "tmportstats";
      }
      enum "voq-grp" {
        value 79;
        description
          "voqgrp";
      }
      enum "l3intftxstats" {
        value 80;
        description
          "l3intftxstats";
      }
      enum "mplstetxstats" {
        value 81;
        description
          "mplstetxstats";
      }
      enum "mplslblstats" {
        value 82;
        description
          "mplslblstats";
      }
      enum "police-r" {
        value 83;
        description
          "policer";
      }
      enum "l2intfrxstats" {
        value 84;
        description
          "l2intfrxstats";
      }
      enum "l2intftxstats" {
        value 85;
        description
          "l2intftxstats";
      }
      enum "pbr-tt-ipv4" {
        value 86;
        description
          "pbr tt ipv4";
      }
      enum "pbr-tt-ipv6" {
        value 87;
        description
          "pbr tt ipv6";
      }
      enum "bfdhwoff" {
        value 88;
        description
          "bfdhwoff";
      }
      enum "bfdoff" {
        value 89;
        description
          "bfdoff";
      }
      enum "bfdoffstats" {
        value 90;
        description
          "bfdoffstats";
      }
      enum "global" {
        value 91;
        description
          "global";
      }
      enum "lag-port" {
        value 92;
        description
          "lagport";
      }
      enum "agg-port" {
        value 93;
        description
          "aggport";
      }
      enum "agg-member" {
        value 94;
        description
          "aggmember";
      }
      enum "qos-profile" {
        value 95;
        description
          "qosprofile";
      }
      enum "acl-profile" {
        value 96;
        description
          "acl profile";
      }
      enum "tmrate-profile" {
        value 97;
        description
          "tmrateprofile";
      }
      enum "ipacl" {
        value 98;
        description
          "ipacl";
      }
      enum "ip6acl" {
        value 99;
        description
          "ip6acl";
      }
      enum "sched-tree" {
        value 100;
        description
          "schedtree";
      }
      enum "tmcos" {
        value 101;
        description
          "tmcos";
      }
      enum "statsagg" {
        value 102;
        description
          "statsagg";
      }
      enum "nhprotect" {
        value 103;
        description
          "nhprotect";
      }
      enum "sampler" {
        value 104;
        description
          "sampler";
      }
      enum "l2qos" {
        value 105;
        description
          "l2qos";
      }
      enum "peer-qos" {
        value 106;
        description
          "peerqos";
      }
      enum "ipqos" {
        value 107;
        description
          "ipqos";
      }
      enum "ip6qos" {
        value 108;
        description
          "ip6qos";
      }
      enum "mplsqos" {
        value 109;
        description
          "mplsqos";
      }
      enum "qos-group" {
        value 110;
        description
          "qosgroup";
      }
      enum "qosid" {
        value 111;
        description
          "qosid";
      }
      enum "extlif" {
        value 112;
        description
          "extlif";
      }
      enum "elif" {
        value 113;
        description
          "elif";
      }
      enum "ingaclstats" {
        value 114;
        description
          "ingaclstats";
      }
      enum "egraclstats" {
        value 115;
        description
          "egraclstats";
      }
      enum "edpl" {
        value 116;
        description
          "edpl";
      }
      enum "l2protect" {
        value 117;
        description
          "l2protect";
      }
      enum "sat" {
        value 118;
        description
          "sat";
      }
      enum "satstats" {
        value 119;
        description
          "satstats";
      }
      enum "cfmoam-profile-def" {
        value 120;
        description
          "cfmoamprofiledef";
      }
      enum "cfmmaid" {
        value 121;
        description
          "cfmmaid";
      }
      enum "cfmdefmps" {
        value 122;
        description
          "cfmdefmps";
      }
      enum "cfmofflmep" {
        value 123;
        description
          "cfmofflmep";
      }
      enum "cfmoffrmep" {
        value 124;
        description
          "cfmoffrmep";
      }
      enum "cfmnonoff" {
        value 125;
        description
          "cfmnonoff";
      }
      enum "cfmhwoffrxstats" {
        value 126;
        description
          "cfmhwoffrxstats";
      }
      enum "ipmc-route" {
        value 127;
        description
          "ipmcroute";
      }
      enum "l2ipmc-route" {
        value 128;
        description
          "l2ipmcroute";
      }
      enum "ipmco-list" {
        value 129;
        description
          "ipmcolist";
      }
      enum "l2mco-list" {
        value 130;
        description
          "l2mcolist";
      }
      enum "meshmc" {
        value 131;
        description
          "meshmc";
      }
      enum "l2-bridge" {
        value 132;
        description
          "l2bridge";
      }
      enum "l2-bridge-port" {
        value 133;
        description
          "l2bridgeport";
      }
      enum "l2-bridge-vni" {
        value 134;
        description
          "l2bridgevni";
      }
      enum "l2-bridge-vnidecap" {
        value 135;
        description
          "l2bridgevnidecap";
      }
      enum "l2-bridge-mac" {
        value 136;
        description
          "l2bridgemac";
      }
      enum "l2brmac" {
        value 137;
        description
          "l2brmac";
      }
      enum "ip-tunnel-decap" {
        value 138;
        description
          "iptunneldecap";
      }
      enum "l2vlan-range" {
        value 139;
        description
          "l2vlanrange";
      }
      enum "ip-tunnel-encap" {
        value 140;
        description
          "iptunnelencap";
      }
      enum "iptnl-encap" {
        value 141;
        description
          "iptnlencap";
      }
      enum "iptnldecap" {
        value 142;
        description
          "iptnldecap";
      }
      enum "iptnlnh" {
        value 143;
        description
          "iptnlnh";
      }
      enum "rawget" {
        value 144;
        description
          "rawget";
      }
      enum "ip6mc-route" {
        value 145;
        description
          "ip6mcroute";
      }
      enum "ip6mc-comp-grp" {
        value 146;
        description
          "ip6mc comp grp";
      }
      enum "l2evpnact-remote-peer-id" {
        value 147;
        description
          "l2evpnactremotepeerid";
      }
      enum "l2evpnact-local-shl" {
        value 148;
        description
          "l2evpnactlocalshl";
      }
      enum "l2evpnact-remote-shl" {
        value 149;
        description
          "l2evpnactremoteshl";
      }
      enum "evpn-iml-range" {
        value 150;
        description
          "evpn imlrange";
      }
      enum "l2-bridge-o-list" {
        value 151;
        description
          "l2bridgeolist";
      }
      enum "l2-bridge-vnio-list" {
        value 152;
        description
          "l2bridgevniolist";
      }
      enum "l2acl" {
        value 153;
        description
          "l2acl";
      }
      enum "l2evpn-nh" {
        value 154;
        description
          "l2evpn nh";
      }
      enum "l2-bridge-port-sc" {
        value 155;
        description
          "l2bridgeport sc";
      }
      enum "l3intfmctxstats" {
        value 156;
        description
          "l3intfmctxstats";
      }
      enum "tidl-sample" {
        value 157;
        description
          "tidl sample";
      }
      enum "tidl-ref-sample" {
        value 158;
        description
          "tidl ref sample";
      }
      enum "ipacl-prefix" {
        value 159;
        description
          "ipaclprefix";
      }
      enum "ip6acl-prefix" {
        value 160;
        description
          "ip6aclprefix";
      }
      enum "ipacl-port" {
        value 161;
        description
          "ipaclport";
      }
      enum "scaleacl" {
        value 162;
        description
          "scaleacl";
      }
      enum "ipmcf-hop" {
        value 163;
        description
          "ipmcfhop";
      }
      enum "bundle-swoff" {
        value 164;
        description
          "bundle swoff";
      }
      enum "mcidswoff" {
        value 165;
        description
          "mcidswoff";
      }
      enum "dest-map" {
        value 166;
        description
          "destmap";
      }
      enum "l2-bridge-port-pw" {
        value 167;
        description
          "l2bridgeport pw";
      }
      enum "l2evpnact-local-shlstats" {
        value 168;
        description
          "l2evpnactlocalshlstats";
      }
      enum "test-hidden" {
        value 169;
        description
          "testhidden";
      }
      enum "test-local" {
        value 170;
        description
          "testlocal";
      }
      enum "test-repeated" {
        value 171;
        description
          "testrepeated";
      }
      enum "limd" {
        value 172;
        description
          "limd";
      }
      enum "litap" {
        value 173;
        description
          "litap";
      }
      enum "l3ifstats" {
        value 174;
        description
          "l3ifstats";
      }
      enum "mplsstats" {
        value 175;
        description
          "mplsstats";
      }
      enum "sr-test-ats" {
        value 176;
        description
          "srtestats";
      }
      enum "srteifstats" {
        value 177;
        description
          "srteifstats";
      }
      enum "exception-nh" {
        value 178;
        description
          "exceptionnh";
      }
      enum "srv6-global" {
        value 179;
        description
          "srv6 global";
      }
      enum "srv6sid" {
        value 180;
        description
          "srv6sid";
      }
      enum "srv6nh" {
        value 181;
        description
          "srv6nh";
      }
      enum "sr6sid" {
        value 182;
        description
          "sr6sid";
      }
      enum "sr6nh" {
        value 183;
        description
          "sr6nh";
      }
      enum "redirect-vrf" {
        value 184;
        description
          "redirectvrf";
      }
      enum "test-xtf" {
        value 185;
        description
          "test xtf";
      }
      enum "ippbr" {
        value 186;
        description
          "ippbr";
      }
      enum "ippbrstats" {
        value 187;
        description
          "ippbrstats";
      }
      enum "mpls-mdt-bud" {
        value 188;
        description
          "mplsmdtbud";
      }
      enum "mpls-label-rxstats" {
        value 189;
        description
          "mplslabelrxstats";
      }
      enum "l2mac-static" {
        value 190;
        description
          "l2macstatic";
      }
      enum "dot1x" {
        value 191;
        description
          "dot1x";
      }
      enum "iprte" {
        value 192;
        description
          "iprte";
      }
      enum "ip6rte" {
        value 193;
        description
          "ip6rte";
      }
      enum "llnh" {
        value 194;
        description
          "llnh";
      }
      enum "urpfintf" {
        value 195;
        description
          "urpfintf";
      }
      enum "ipmcrxstats" {
        value 196;
        description
          "ipmcrxstats";
      }
      enum "mplsrte" {
        value 197;
        description
          "mplsrte";
      }
      enum "protectnh" {
        value 198;
        description
          "protectnh";
      }
      enum "ipllnh" {
        value 199;
        description
          "ipllnh";
      }
      enum "ip6llnh" {
        value 200;
        description
          "ip6llnh";
      }
      enum "macnh" {
        value 201;
        description
          "macnh";
      }
      enum "qos-match-stats" {
        value 202;
        description
          "qosmatchstats";
      }
      enum "ofal2xc" {
        value 203;
        description
          "ofal2xc";
      }
      enum "ofamplspwe-port" {
        value 204;
        description
          "ofamplspweport";
      }
      enum "pwenh" {
        value 205;
        description
          "pwenh";
      }
      enum "pwenh-group" {
        value 206;
        description
          "pwenhgroup";
      }
      enum "ipmcrte" {
        value 207;
        description
          "ipmcrte";
      }
      enum "ip6mcrte" {
        value 208;
        description
          "ip6mcrte";
      }
      enum "ipmcr-test-ats" {
        value 209;
        description
          "ipmcrtestats";
      }
      enum "ip6mcr-test-ats" {
        value 210;
        description
          "ip6mcrtestats";
      }
      enum "transport-nh" {
        value 211;
        description
          "transportnh";
      }
      enum "port-range" {
        value 212;
        description
          "portrange";
      }
      enum "bvi-port" {
        value 213;
        description
          "bviport";
      }
      enum "mcid" {
        value 214;
        description
          "mcid";
      }
      enum "mc-gid" {
        value 215;
        description
          "mc gid";
      }
      enum "mcgidole" {
        value 216;
        description
          "mcgidole";
      }
      enum "mco-list" {
        value 217;
        description
          "mcolist";
      }
      enum "test-da" {
        value 218;
        description
          "testda";
      }
      enum "test-ca" {
        value 219;
        description
          "testca";
      }
      enum "test-ba" {
        value 220;
        description
          "testba";
      }
      enum "test-aa" {
        value 221;
        description
          "testaa";
      }
      enum "test-async-aa" {
        value 222;
        description
          "testasyncaa";
      }
      enum "test-reliable-notif" {
        value 223;
        description
          "testreliablenotif";
      }
      enum "test-de" {
        value 224;
        description
          "testde";
      }
      enum "test-ce" {
        value 225;
        description
          "testce";
      }
      enum "test-be" {
        value 226;
        description
          "testbe";
      }
      enum "test-db" {
        value 227;
        description
          "testdb";
      }
      enum "test-cb" {
        value 228;
        description
          "testcb";
      }
      enum "test-bb" {
        value 229;
        description
          "testbb";
      }
      enum "test-df" {
        value 230;
        description
          "testdf";
      }
      enum "test-cf" {
        value 231;
        description
          "testcf";
      }
      enum "test-bf" {
        value 232;
        description
          "testbf";
      }
      enum "test-af" {
        value 233;
        description
          "testaf";
      }
      enum "test-cz" {
        value 234;
        description
          "testcz";
      }
      enum "test-ax" {
        value 235;
        description
          "testax";
      }
      enum "test-ay" {
        value 236;
        description
          "testay";
      }
      enum "test-ef" {
        value 237;
        description
          "testef";
      }
      enum "test-ff" {
        value 238;
        description
          "testff";
      }
      enum "test-gf" {
        value 239;
        description
          "testgf";
      }
      enum "test-eastwestscheduling" {
        value 240;
        description
          "testeastwestscheduling";
      }
      enum "test-transnh" {
        value 241;
        description
          "testtransnh";
      }
      enum "test-eth-port" {
        value 242;
        description
          "testethport";
      }
      enum "test-eastwest" {
        value 243;
        description
          "testeastwest";
      }
      enum "test-ifstats" {
        value 244;
        description
          "testifstats";
      }
      enum "test-async-oor" {
        value 245;
        description
          "testasyncoor";
      }
      enum "test-syncmcas-too-r" {
        value 246;
        description
          "testsyncmcastoor";
      }
      enum "test-syncdeviceoor" {
        value 247;
        description
          "testsyncdeviceoor";
      }
      enum "test-az" {
        value 248;
        description
          "testaz";
      }
      enum "test-by" {
        value 249;
        description
          "testby";
      }
      enum "police-r-group" {
        value 250;
        description
          "policergroup";
      }
      enum "meter-profile" {
        value 251;
        description
          "meterprofile";
      }
      enum "acl-mirror" {
        value 252;
        description
          "acl mirror";
      }
      enum "meter-action-profile" {
        value 253;
        description
          "meteractionprofile";
      }
      enum "voqrm" {
        value 254;
        description
          "voqrm";
      }
      enum "port-wfq-profile" {
        value 255;
        description
          "portwfqprofile";
      }
      enum "rpfif" {
        value 256;
        description
          "rpfif";
      }
      enum "brmac" {
        value 257;
        description
          "brmac";
      }
      enum "br-static-mac" {
        value 258;
        description
          "brstaticmac";
      }
      enum "xconnect" {
        value 259;
        description
          "xconnect";
      }
      enum "bridge" {
        value 260;
        description
          "bridge";
      }
      enum "pwe-port" {
        value 261;
        description
          "pweport";
      }
      enum "olist" {
        value 262;
        description
          "olist";
      }
      enum "lsmprotect" {
        value 263;
        description
          "lsmprotect";
      }
      enum "monitor-session" {
        value 264;
        description
          "monitorsession";
      }
      enum "monitor-session-stats" {
        value 265;
        description
          "monitorsessionstats";
      }
      enum "mplsmcast" {
        value 266;
        description
          "mplsmcast";
      }
      enum "l2ifstats" {
        value 267;
        description
          "l2ifstats";
      }
      enum "imlnh" {
        value 268;
        description
          "imlnh";
      }
      enum "evinh" {
        value 269;
        description
          "evinh";
      }
      enum "member-list" {
        value 270;
        description
          "memberlist";
      }
      enum "test-oor" {
        value 271;
        description
          "testoor";
      }
      enum "hwre-source-s-oor" {
        value 272;
        description
          "hwresources oor";
      }
      enum "qospfcstats" {
        value 273;
        description
          "qospfcstats";
      }
      enum "pfctc" {
        value 274;
        description
          "pfctc";
      }
      enum "pfc-watchdog" {
        value 275;
        description
          "pfc watchdog";
      }
      enum "qos-shared" {
        value 276;
        description
          "qosshared";
      }
      enum "ecntxstats" {
        value 277;
        description
          "ecntxstats";
      }
      enum "tm-remote-credit" {
        value 278;
        description
          "tmremotecredit";
      }
      enum "ipmcole" {
        value 279;
        description
          "ipmcole";
      }
      enum "ip6mcole" {
        value 280;
        description
          "ip6mcole";
      }
      enum "pbr" {
        value 281;
        description
          "pbr";
      }
      enum "pbrstats" {
        value 282;
        description
          "pbrstats";
      }
      enum "punt-stormcontrol" {
        value 283;
        description
          "puntstormcontrol";
      }
      enum "ip6mcrxstats" {
        value 284;
        description
          "ip6mcrxstats";
      }
      enum "ipmctxintf" {
        value 285;
        description
          "ipmctxintf";
      }
      enum "ipmc-mdt-encap" {
        value 286;
        description
          "ipmcmdtencap";
      }
      enum "ipmc-mdt-decap" {
        value 287;
        description
          "ipmcmdtdecap";
      }
      enum "op2tap" {
        value 288;
        description
          "op2tap";
      }
      enum "mplsole" {
        value 289;
        description
          "mplsole";
      }
      enum "syncrpc" {
        value 290;
        description
          "syncrpc";
      }
      enum "tnlstats" {
        value 291;
        description
          "tnlstats";
      }
      enum "l2dhcp" {
        value 292;
        description
          "l2dhcp";
      }
      enum "pbrsbf" {
        value 293;
        description
          "pbrsbf";
      }
      enum "statsrpc" {
        value 294;
        description
          "statsrpc";
      }
      enum "oglpts" {
        value 295;
        description
          "oglpts";
      }
      enum "oglpts-prefix" {
        value 296;
        description
          "oglptsprefix";
      }
      enum "og6lpts-prefix" {
        value 297;
        description
          "og6lptsprefix";
      }
      enum "stormcontrol" {
        value 298;
        description
          "stormcontrol";
      }
      enum "acl-police-r" {
        value 299;
        description
          "aclpolicer";
      }
      enum "acl-police-rstats" {
        value 300;
        description
          "aclpolicerstats";
      }
      enum "aclkey-profile" {
        value 301;
        description
          "aclkeyprofile";
      }
      enum "acl-action-profile" {
        value 302;
        description
          "aclactionprofile";
      }
    }
    description
      "Ofa table";
  }

  typedef live_ncs_Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npu-host-port" {
        value 29;
        description
          "npuhostport";
      }
      enum "npuhwid" {
        value 30;
        description
          "npuhwid";
      }
      enum "optics-port" {
        value 31;
        description
          "opticsport";
      }
      enum "gi-port" {
        value 32;
        description
          "giport";
      }
      enum "l1-port" {
        value 33;
        description
          "l1port";
      }
      enum "mac-port" {
        value 34;
        description
          "macport";
      }
      enum "l2-port" {
        value 35;
        description
          "l2port";
      }
      enum "eth-port" {
        value 36;
        description
          "ethport";
      }
      enum "l2intf" {
        value 37;
        description
          "l2intf";
      }
      enum "l2if" {
        value 38;
        description
          "l2if";
      }
      enum "mplspwe-port" {
        value 39;
        description
          "mplspweport";
      }
      enum "mplspwe-port-o-list" {
        value 40;
        description
          "mplspweport olist";
      }
      enum "mhpwe-port" {
        value 41;
        description
          "mhpweport";
      }
      enum "l2xc" {
        value 42;
        description
          "l2xc";
      }
      enum "l2vpnstats" {
        value 43;
        description
          "l2vpnstats";
      }
      enum "l1-ports-tats" {
        value 44;
        description
          "l1portstats";
      }
      enum "mac-ports-tats" {
        value 45;
        description
          "macportstats";
      }
      enum "l3intf" {
        value 46;
        description
          "l3intf";
      }
      enum "l3if" {
        value 47;
        description
          "l3if";
      }
      enum "l3intfrxstats" {
        value 48;
        description
          "l3intfrxstats";
      }
      enum "ip-route" {
        value 49;
        description
          "iproute";
      }
      enum "ip6-route" {
        value 50;
        description
          "ip6route";
      }
      enum "punt-policy-stats" {
        value 51;
        description
          "puntpolicystats";
      }
      enum "lpts-policy-stats" {
        value 52;
        description
          "lptspolicystats";
      }
      enum "tep" {
        value 53;
        description
          "tep";
      }
      enum "ip-punt-policy" {
        value 54;
        description
          "ippuntpolicy";
      }
      enum "ip6-punt-policy" {
        value 55;
        description
          "ip6puntpolicy";
      }
      enum "iplpts-policy" {
        value 56;
        description
          "iplptspolicy";
      }
      enum "ip6lpts-policy" {
        value 57;
        description
          "ip6lptspolicy";
      }
      enum "isis-punt-policy" {
        value 58;
        description
          "isispuntpolicy";
      }
      enum "isislpts-policy" {
        value 59;
        description
          "isislptspolicy";
      }
      enum "nh-group" {
        value 60;
        description
          "nhgroup";
      }
      enum "ipnh-group" {
        value 61;
        description
          "ipnhgroup";
      }
      enum "ip6nh-group" {
        value 62;
        description
          "ip6nhgroup";
      }
      enum "ipnh" {
        value 63;
        description
          "ipnh";
      }
      enum "ip6nh" {
        value 64;
        description
          "ip6nh";
      }
      enum "ipvrf" {
        value 65;
        description
          "ipvrf";
      }
      enum "vrfid" {
        value 66;
        description
          "vrfid";
      }
      enum "mplsnh" {
        value 67;
        description
          "mplsnh";
      }
      enum "lspnh" {
        value 68;
        description
          "lspnh";
      }
      enum "mpls-label" {
        value 69;
        description
          "mplslabel";
      }
      enum "punt" {
        value 70;
        description
          "punt";
      }
      enum "punt-police-r" {
        value 71;
        description
          "puntpolicer";
      }
      enum "lpts-police-r" {
        value 72;
        description
          "lptspolicer";
      }
      enum "punt-lpts-police-r" {
        value 73;
        description
          "puntlptspolicer";
      }
      enum "punt-stats" {
        value 74;
        description
          "puntstats";
      }
      enum "tm-port" {
        value 75;
        description
          "tmport";
      }
      enum "span-session" {
        value 76;
        description
          "spansession";
      }
      enum "police-rstats" {
        value 77;
        description
          "policerstats";
      }
      enum "tm-ports-tats" {
        value 78;
        description
          "tmportstats";
      }
      enum "voq-grp" {
        value 79;
        description
          "voqgrp";
      }
      enum "l3intftxstats" {
        value 80;
        description
          "l3intftxstats";
      }
      enum "mplstetxstats" {
        value 81;
        description
          "mplstetxstats";
      }
      enum "mplslblstats" {
        value 82;
        description
          "mplslblstats";
      }
      enum "police-r" {
        value 83;
        description
          "policer";
      }
      enum "l2intfrxstats" {
        value 84;
        description
          "l2intfrxstats";
      }
      enum "l2intftxstats" {
        value 85;
        description
          "l2intftxstats";
      }
      enum "pbr-tt-ipv4" {
        value 86;
        description
          "pbr tt ipv4";
      }
      enum "pbr-tt-ipv6" {
        value 87;
        description
          "pbr tt ipv6";
      }
      enum "bfdhwoff" {
        value 88;
        description
          "bfdhwoff";
      }
      enum "bfdoff" {
        value 89;
        description
          "bfdoff";
      }
      enum "bfdoffstats" {
        value 90;
        description
          "bfdoffstats";
      }
      enum "global" {
        value 91;
        description
          "global";
      }
      enum "lag-port" {
        value 92;
        description
          "lagport";
      }
      enum "agg-port" {
        value 93;
        description
          "aggport";
      }
      enum "agg-member" {
        value 94;
        description
          "aggmember";
      }
      enum "qos-profile" {
        value 95;
        description
          "qosprofile";
      }
      enum "acl-profile" {
        value 96;
        description
          "acl profile";
      }
      enum "tmrate-profile" {
        value 97;
        description
          "tmrateprofile";
      }
      enum "ipacl" {
        value 98;
        description
          "ipacl";
      }
      enum "ip6acl" {
        value 99;
        description
          "ip6acl";
      }
      enum "sched-tree" {
        value 100;
        description
          "schedtree";
      }
      enum "tmcos" {
        value 101;
        description
          "tmcos";
      }
      enum "statsagg" {
        value 102;
        description
          "statsagg";
      }
      enum "nhprotect" {
        value 103;
        description
          "nhprotect";
      }
      enum "sampler" {
        value 104;
        description
          "sampler";
      }
      enum "l2qos" {
        value 105;
        description
          "l2qos";
      }
      enum "peer-qos" {
        value 106;
        description
          "peerqos";
      }
      enum "ipqos" {
        value 107;
        description
          "ipqos";
      }
      enum "ip6qos" {
        value 108;
        description
          "ip6qos";
      }
      enum "mplsqos" {
        value 109;
        description
          "mplsqos";
      }
      enum "qos-group" {
        value 110;
        description
          "qosgroup";
      }
      enum "qosid" {
        value 111;
        description
          "qosid";
      }
      enum "extlif" {
        value 112;
        description
          "extlif";
      }
      enum "elif" {
        value 113;
        description
          "elif";
      }
      enum "ingaclstats" {
        value 114;
        description
          "ingaclstats";
      }
      enum "egraclstats" {
        value 115;
        description
          "egraclstats";
      }
      enum "edpl" {
        value 116;
        description
          "edpl";
      }
      enum "l2protect" {
        value 117;
        description
          "l2protect";
      }
      enum "sat" {
        value 118;
        description
          "sat";
      }
      enum "satstats" {
        value 119;
        description
          "satstats";
      }
      enum "cfmoam-profile-def" {
        value 120;
        description
          "cfmoamprofiledef";
      }
      enum "cfmmaid" {
        value 121;
        description
          "cfmmaid";
      }
      enum "cfmdefmps" {
        value 122;
        description
          "cfmdefmps";
      }
      enum "cfmofflmep" {
        value 123;
        description
          "cfmofflmep";
      }
      enum "cfmoffrmep" {
        value 124;
        description
          "cfmoffrmep";
      }
      enum "cfmnonoff" {
        value 125;
        description
          "cfmnonoff";
      }
      enum "cfmhwoffrxstats" {
        value 126;
        description
          "cfmhwoffrxstats";
      }
      enum "ipmc-route" {
        value 127;
        description
          "ipmcroute";
      }
      enum "l2ipmc-route" {
        value 128;
        description
          "l2ipmcroute";
      }
      enum "ipmco-list" {
        value 129;
        description
          "ipmcolist";
      }
      enum "l2mco-list" {
        value 130;
        description
          "l2mcolist";
      }
      enum "meshmc" {
        value 131;
        description
          "meshmc";
      }
      enum "l2-bridge" {
        value 132;
        description
          "l2bridge";
      }
      enum "l2-bridge-port" {
        value 133;
        description
          "l2bridgeport";
      }
      enum "l2-bridge-vni" {
        value 134;
        description
          "l2bridgevni";
      }
      enum "l2-bridge-vnidecap" {
        value 135;
        description
          "l2bridgevnidecap";
      }
      enum "l2-bridge-mac" {
        value 136;
        description
          "l2bridgemac";
      }
      enum "l2brmac" {
        value 137;
        description
          "l2brmac";
      }
      enum "ip-tunnel-decap" {
        value 138;
        description
          "iptunneldecap";
      }
      enum "l2vlan-range" {
        value 139;
        description
          "l2vlanrange";
      }
      enum "ip-tunnel-encap" {
        value 140;
        description
          "iptunnelencap";
      }
      enum "iptnl-encap" {
        value 141;
        description
          "iptnlencap";
      }
      enum "iptnldecap" {
        value 142;
        description
          "iptnldecap";
      }
      enum "iptnlnh" {
        value 143;
        description
          "iptnlnh";
      }
      enum "rawget" {
        value 144;
        description
          "rawget";
      }
      enum "ip6mc-route" {
        value 145;
        description
          "ip6mcroute";
      }
      enum "ip6mc-comp-grp" {
        value 146;
        description
          "ip6mc comp grp";
      }
      enum "l2evpnact-remote-peer-id" {
        value 147;
        description
          "l2evpnactremotepeerid";
      }
      enum "l2evpnact-local-shl" {
        value 148;
        description
          "l2evpnactlocalshl";
      }
      enum "l2evpnact-remote-shl" {
        value 149;
        description
          "l2evpnactremoteshl";
      }
      enum "evpn-iml-range" {
        value 150;
        description
          "evpn imlrange";
      }
      enum "l2-bridge-o-list" {
        value 151;
        description
          "l2bridgeolist";
      }
      enum "l2-bridge-vnio-list" {
        value 152;
        description
          "l2bridgevniolist";
      }
      enum "l2acl" {
        value 153;
        description
          "l2acl";
      }
      enum "l2evpn-nh" {
        value 154;
        description
          "l2evpn nh";
      }
      enum "l2-bridge-port-sc" {
        value 155;
        description
          "l2bridgeport sc";
      }
      enum "l3intfmctxstats" {
        value 156;
        description
          "l3intfmctxstats";
      }
      enum "tidl-sample" {
        value 157;
        description
          "tidl sample";
      }
      enum "tidl-ref-sample" {
        value 158;
        description
          "tidl ref sample";
      }
      enum "ipacl-prefix" {
        value 159;
        description
          "ipaclprefix";
      }
      enum "ip6acl-prefix" {
        value 160;
        description
          "ip6aclprefix";
      }
      enum "ipacl-port" {
        value 161;
        description
          "ipaclport";
      }
      enum "scaleacl" {
        value 162;
        description
          "scaleacl";
      }
      enum "ipmcf-hop" {
        value 163;
        description
          "ipmcfhop";
      }
      enum "bundle-swoff" {
        value 164;
        description
          "bundle swoff";
      }
      enum "mcidswoff" {
        value 165;
        description
          "mcidswoff";
      }
      enum "dest-map" {
        value 166;
        description
          "destmap";
      }
      enum "l2-bridge-port-pw" {
        value 167;
        description
          "l2bridgeport pw";
      }
      enum "l2evpnact-local-shlstats" {
        value 168;
        description
          "l2evpnactlocalshlstats";
      }
      enum "test-hidden" {
        value 169;
        description
          "testhidden";
      }
      enum "test-local" {
        value 170;
        description
          "testlocal";
      }
      enum "test-repeated" {
        value 171;
        description
          "testrepeated";
      }
      enum "limd" {
        value 172;
        description
          "limd";
      }
      enum "litap" {
        value 173;
        description
          "litap";
      }
      enum "l3ifstats" {
        value 174;
        description
          "l3ifstats";
      }
      enum "mplsstats" {
        value 175;
        description
          "mplsstats";
      }
      enum "sr-test-ats" {
        value 176;
        description
          "srtestats";
      }
      enum "srteifstats" {
        value 177;
        description
          "srteifstats";
      }
      enum "exception-nh" {
        value 178;
        description
          "exceptionnh";
      }
      enum "srv6-global" {
        value 179;
        description
          "srv6 global";
      }
      enum "srv6sid" {
        value 180;
        description
          "srv6sid";
      }
      enum "srv6nh" {
        value 181;
        description
          "srv6nh";
      }
      enum "sr6sid" {
        value 182;
        description
          "sr6sid";
      }
      enum "sr6nh" {
        value 183;
        description
          "sr6nh";
      }
      enum "redirect-vrf" {
        value 184;
        description
          "redirectvrf";
      }
      enum "test-xtf" {
        value 185;
        description
          "test xtf";
      }
      enum "ippbr" {
        value 186;
        description
          "ippbr";
      }
      enum "ippbrstats" {
        value 187;
        description
          "ippbrstats";
      }
      enum "mpls-mdt-bud" {
        value 188;
        description
          "mplsmdtbud";
      }
      enum "mpls-label-rxstats" {
        value 189;
        description
          "mplslabelrxstats";
      }
      enum "l2mac-static" {
        value 190;
        description
          "l2macstatic";
      }
      enum "dot1x" {
        value 191;
        description
          "dot1x";
      }
      enum "iprte" {
        value 192;
        description
          "iprte";
      }
      enum "ip6rte" {
        value 193;
        description
          "ip6rte";
      }
      enum "llnh" {
        value 194;
        description
          "llnh";
      }
      enum "urpfintf" {
        value 195;
        description
          "urpfintf";
      }
      enum "ipmcrxstats" {
        value 196;
        description
          "ipmcrxstats";
      }
      enum "mplsrte" {
        value 197;
        description
          "mplsrte";
      }
      enum "protectnh" {
        value 198;
        description
          "protectnh";
      }
      enum "ipllnh" {
        value 199;
        description
          "ipllnh";
      }
      enum "ip6llnh" {
        value 200;
        description
          "ip6llnh";
      }
      enum "macnh" {
        value 201;
        description
          "macnh";
      }
      enum "qos-match-stats" {
        value 202;
        description
          "qosmatchstats";
      }
      enum "ofal2xc" {
        value 203;
        description
          "ofal2xc";
      }
      enum "ofamplspwe-port" {
        value 204;
        description
          "ofamplspweport";
      }
      enum "pwenh" {
        value 205;
        description
          "pwenh";
      }
      enum "pwenh-group" {
        value 206;
        description
          "pwenhgroup";
      }
      enum "ipmcrte" {
        value 207;
        description
          "ipmcrte";
      }
      enum "ip6mcrte" {
        value 208;
        description
          "ip6mcrte";
      }
      enum "ipmcr-test-ats" {
        value 209;
        description
          "ipmcrtestats";
      }
      enum "ip6mcr-test-ats" {
        value 210;
        description
          "ip6mcrtestats";
      }
      enum "transport-nh" {
        value 211;
        description
          "transportnh";
      }
      enum "port-range" {
        value 212;
        description
          "portrange";
      }
      enum "bvi-port" {
        value 213;
        description
          "bviport";
      }
      enum "mcid" {
        value 214;
        description
          "mcid";
      }
      enum "mc-gid" {
        value 215;
        description
          "mc gid";
      }
      enum "mcgidole" {
        value 216;
        description
          "mcgidole";
      }
      enum "mco-list" {
        value 217;
        description
          "mcolist";
      }
      enum "test-da" {
        value 218;
        description
          "testda";
      }
      enum "test-ca" {
        value 219;
        description
          "testca";
      }
      enum "test-ba" {
        value 220;
        description
          "testba";
      }
      enum "test-aa" {
        value 221;
        description
          "testaa";
      }
      enum "test-async-aa" {
        value 222;
        description
          "testasyncaa";
      }
      enum "test-reliable-notif" {
        value 223;
        description
          "testreliablenotif";
      }
      enum "test-de" {
        value 224;
        description
          "testde";
      }
      enum "test-ce" {
        value 225;
        description
          "testce";
      }
      enum "test-be" {
        value 226;
        description
          "testbe";
      }
      enum "test-db" {
        value 227;
        description
          "testdb";
      }
      enum "test-cb" {
        value 228;
        description
          "testcb";
      }
      enum "test-bb" {
        value 229;
        description
          "testbb";
      }
      enum "test-df" {
        value 230;
        description
          "testdf";
      }
      enum "test-cf" {
        value 231;
        description
          "testcf";
      }
      enum "test-bf" {
        value 232;
        description
          "testbf";
      }
      enum "test-af" {
        value 233;
        description
          "testaf";
      }
      enum "test-cz" {
        value 234;
        description
          "testcz";
      }
      enum "test-ax" {
        value 235;
        description
          "testax";
      }
      enum "test-ay" {
        value 236;
        description
          "testay";
      }
      enum "test-ef" {
        value 237;
        description
          "testef";
      }
      enum "test-ff" {
        value 238;
        description
          "testff";
      }
      enum "test-gf" {
        value 239;
        description
          "testgf";
      }
      enum "test-eastwestscheduling" {
        value 240;
        description
          "testeastwestscheduling";
      }
      enum "test-transnh" {
        value 241;
        description
          "testtransnh";
      }
      enum "test-eth-port" {
        value 242;
        description
          "testethport";
      }
      enum "test-eastwest" {
        value 243;
        description
          "testeastwest";
      }
      enum "test-ifstats" {
        value 244;
        description
          "testifstats";
      }
      enum "test-async-oor" {
        value 245;
        description
          "testasyncoor";
      }
      enum "test-syncmcas-too-r" {
        value 246;
        description
          "testsyncmcastoor";
      }
      enum "test-syncdeviceoor" {
        value 247;
        description
          "testsyncdeviceoor";
      }
      enum "test-az" {
        value 248;
        description
          "testaz";
      }
      enum "test-by" {
        value 249;
        description
          "testby";
      }
      enum "police-r-group" {
        value 250;
        description
          "policergroup";
      }
      enum "meter-profile" {
        value 251;
        description
          "meterprofile";
      }
      enum "acl-mirror" {
        value 252;
        description
          "acl mirror";
      }
      enum "meter-action-profile" {
        value 253;
        description
          "meteractionprofile";
      }
      enum "voqrm" {
        value 254;
        description
          "voqrm";
      }
      enum "port-wfq-profile" {
        value 255;
        description
          "portwfqprofile";
      }
      enum "rpfif" {
        value 256;
        description
          "rpfif";
      }
      enum "brmac" {
        value 257;
        description
          "brmac";
      }
      enum "br-static-mac" {
        value 258;
        description
          "brstaticmac";
      }
      enum "xconnect" {
        value 259;
        description
          "xconnect";
      }
      enum "bridge" {
        value 260;
        description
          "bridge";
      }
      enum "pwe-port" {
        value 261;
        description
          "pweport";
      }
      enum "olist" {
        value 262;
        description
          "olist";
      }
      enum "lsmprotect" {
        value 263;
        description
          "lsmprotect";
      }
      enum "monitor-session" {
        value 264;
        description
          "monitorsession";
      }
      enum "monitor-session-stats" {
        value 265;
        description
          "monitorsessionstats";
      }
      enum "mplsmcast" {
        value 266;
        description
          "mplsmcast";
      }
      enum "l2ifstats" {
        value 267;
        description
          "l2ifstats";
      }
      enum "imlnh" {
        value 268;
        description
          "imlnh";
      }
      enum "evinh" {
        value 269;
        description
          "evinh";
      }
      enum "member-list" {
        value 270;
        description
          "memberlist";
      }
      enum "test-oor" {
        value 271;
        description
          "testoor";
      }
      enum "hwre-source-s-oor" {
        value 272;
        description
          "hwresources oor";
      }
      enum "qospfcstats" {
        value 273;
        description
          "qospfcstats";
      }
      enum "pfctc" {
        value 274;
        description
          "pfctc";
      }
      enum "pfc-watchdog" {
        value 275;
        description
          "pfc watchdog";
      }
      enum "qos-shared" {
        value 276;
        description
          "qosshared";
      }
      enum "ecntxstats" {
        value 277;
        description
          "ecntxstats";
      }
      enum "tm-remote-credit" {
        value 278;
        description
          "tmremotecredit";
      }
      enum "ipmcole" {
        value 279;
        description
          "ipmcole";
      }
      enum "ip6mcole" {
        value 280;
        description
          "ip6mcole";
      }
      enum "pbr" {
        value 281;
        description
          "pbr";
      }
      enum "pbrstats" {
        value 282;
        description
          "pbrstats";
      }
      enum "punt-stormcontrol" {
        value 283;
        description
          "puntstormcontrol";
      }
      enum "ip6mcrxstats" {
        value 284;
        description
          "ip6mcrxstats";
      }
      enum "ipmctxintf" {
        value 285;
        description
          "ipmctxintf";
      }
      enum "ipmc-mdt-encap" {
        value 286;
        description
          "ipmcmdtencap";
      }
      enum "ipmc-mdt-decap" {
        value 287;
        description
          "ipmcmdtdecap";
      }
      enum "op2tap" {
        value 288;
        description
          "op2tap";
      }
      enum "mplsole" {
        value 289;
        description
          "mplsole";
      }
      enum "syncrpc" {
        value 290;
        description
          "syncrpc";
      }
      enum "tnlstats" {
        value 291;
        description
          "tnlstats";
      }
      enum "l2dhcp" {
        value 292;
        description
          "l2dhcp";
      }
      enum "pbrsbf" {
        value 293;
        description
          "pbrsbf";
      }
      enum "statsrpc" {
        value 294;
        description
          "statsrpc";
      }
      enum "oglpts" {
        value 295;
        description
          "oglpts";
      }
      enum "oglpts-prefix" {
        value 296;
        description
          "oglptsprefix";
      }
      enum "og6lpts-prefix" {
        value 297;
        description
          "og6lptsprefix";
      }
      enum "stormcontrol" {
        value 298;
        description
          "stormcontrol";
      }
      enum "acl-police-r" {
        value 299;
        description
          "aclpolicer";
      }
      enum "acl-police-rstats" {
        value 300;
        description
          "aclpolicerstats";
      }
      enum "aclkey-profile" {
        value 301;
        description
          "aclkeyprofile";
      }
      enum "acl-action-profile" {
        value 302;
        description
          "aclactionprofile";
      }
    }
    description
      "Ofa table";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npu-host-port" {
        value 29;
        description
          "npuhostport";
      }
      enum "npuhwid" {
        value 30;
        description
          "npuhwid";
      }
      enum "optics-port" {
        value 31;
        description
          "opticsport";
      }
      enum "gi-port" {
        value 32;
        description
          "giport";
      }
      enum "l1-port" {
        value 33;
        description
          "l1port";
      }
      enum "mac-port" {
        value 34;
        description
          "macport";
      }
      enum "l2-port" {
        value 35;
        description
          "l2port";
      }
      enum "eth-port" {
        value 36;
        description
          "ethport";
      }
      enum "l2intf" {
        value 37;
        description
          "l2intf";
      }
      enum "l2if" {
        value 38;
        description
          "l2if";
      }
      enum "mplspwe-port" {
        value 39;
        description
          "mplspweport";
      }
      enum "mplspwe-port-o-list" {
        value 40;
        description
          "mplspweport olist";
      }
      enum "mhpwe-port" {
        value 41;
        description
          "mhpweport";
      }
      enum "l2xc" {
        value 42;
        description
          "l2xc";
      }
      enum "l2vpnstats" {
        value 43;
        description
          "l2vpnstats";
      }
      enum "l1-ports-tats" {
        value 44;
        description
          "l1portstats";
      }
      enum "mac-ports-tats" {
        value 45;
        description
          "macportstats";
      }
      enum "l3intf" {
        value 46;
        description
          "l3intf";
      }
      enum "l3if" {
        value 47;
        description
          "l3if";
      }
      enum "l3intfrxstats" {
        value 48;
        description
          "l3intfrxstats";
      }
      enum "ip-route" {
        value 49;
        description
          "iproute";
      }
      enum "ip6-route" {
        value 50;
        description
          "ip6route";
      }
      enum "punt-policy-stats" {
        value 51;
        description
          "puntpolicystats";
      }
      enum "lpts-policy-stats" {
        value 52;
        description
          "lptspolicystats";
      }
      enum "tep" {
        value 53;
        description
          "tep";
      }
      enum "ip-punt-policy" {
        value 54;
        description
          "ippuntpolicy";
      }
      enum "ip6-punt-policy" {
        value 55;
        description
          "ip6puntpolicy";
      }
      enum "iplpts-policy" {
        value 56;
        description
          "iplptspolicy";
      }
      enum "ip6lpts-policy" {
        value 57;
        description
          "ip6lptspolicy";
      }
      enum "isis-punt-policy" {
        value 58;
        description
          "isispuntpolicy";
      }
      enum "isislpts-policy" {
        value 59;
        description
          "isislptspolicy";
      }
      enum "nh-group" {
        value 60;
        description
          "nhgroup";
      }
      enum "ipnh-group" {
        value 61;
        description
          "ipnhgroup";
      }
      enum "ip6nh-group" {
        value 62;
        description
          "ip6nhgroup";
      }
      enum "ipnh" {
        value 63;
        description
          "ipnh";
      }
      enum "ip6nh" {
        value 64;
        description
          "ip6nh";
      }
      enum "ipvrf" {
        value 65;
        description
          "ipvrf";
      }
      enum "vrfid" {
        value 66;
        description
          "vrfid";
      }
      enum "mplsnh" {
        value 67;
        description
          "mplsnh";
      }
      enum "lspnh" {
        value 68;
        description
          "lspnh";
      }
      enum "mpls-label" {
        value 69;
        description
          "mplslabel";
      }
      enum "punt" {
        value 70;
        description
          "punt";
      }
      enum "punt-police-r" {
        value 71;
        description
          "puntpolicer";
      }
      enum "lpts-police-r" {
        value 72;
        description
          "lptspolicer";
      }
      enum "punt-lpts-police-r" {
        value 73;
        description
          "puntlptspolicer";
      }
      enum "punt-stats" {
        value 74;
        description
          "puntstats";
      }
      enum "tm-port" {
        value 75;
        description
          "tmport";
      }
      enum "span-session" {
        value 76;
        description
          "spansession";
      }
      enum "police-rstats" {
        value 77;
        description
          "policerstats";
      }
      enum "tm-ports-tats" {
        value 78;
        description
          "tmportstats";
      }
      enum "voq-grp" {
        value 79;
        description
          "voqgrp";
      }
      enum "l3intftxstats" {
        value 80;
        description
          "l3intftxstats";
      }
      enum "mplstetxstats" {
        value 81;
        description
          "mplstetxstats";
      }
      enum "mplslblstats" {
        value 82;
        description
          "mplslblstats";
      }
      enum "police-r" {
        value 83;
        description
          "policer";
      }
      enum "l2intfrxstats" {
        value 84;
        description
          "l2intfrxstats";
      }
      enum "l2intftxstats" {
        value 85;
        description
          "l2intftxstats";
      }
      enum "pbr-tt-ipv4" {
        value 86;
        description
          "pbr tt ipv4";
      }
      enum "pbr-tt-ipv6" {
        value 87;
        description
          "pbr tt ipv6";
      }
      enum "bfdhwoff" {
        value 88;
        description
          "bfdhwoff";
      }
      enum "bfdoff" {
        value 89;
        description
          "bfdoff";
      }
      enum "bfdoffstats" {
        value 90;
        description
          "bfdoffstats";
      }
      enum "global" {
        value 91;
        description
          "global";
      }
      enum "lag-port" {
        value 92;
        description
          "lagport";
      }
      enum "agg-port" {
        value 93;
        description
          "aggport";
      }
      enum "agg-member" {
        value 94;
        description
          "aggmember";
      }
      enum "qos-profile" {
        value 95;
        description
          "qosprofile";
      }
      enum "acl-profile" {
        value 96;
        description
          "acl profile";
      }
      enum "tmrate-profile" {
        value 97;
        description
          "tmrateprofile";
      }
      enum "ipacl" {
        value 98;
        description
          "ipacl";
      }
      enum "ip6acl" {
        value 99;
        description
          "ip6acl";
      }
      enum "sched-tree" {
        value 100;
        description
          "schedtree";
      }
      enum "tmcos" {
        value 101;
        description
          "tmcos";
      }
      enum "statsagg" {
        value 102;
        description
          "statsagg";
      }
      enum "nhprotect" {
        value 103;
        description
          "nhprotect";
      }
      enum "sampler" {
        value 104;
        description
          "sampler";
      }
      enum "l2qos" {
        value 105;
        description
          "l2qos";
      }
      enum "peer-qos" {
        value 106;
        description
          "peerqos";
      }
      enum "ipqos" {
        value 107;
        description
          "ipqos";
      }
      enum "ip6qos" {
        value 108;
        description
          "ip6qos";
      }
      enum "mplsqos" {
        value 109;
        description
          "mplsqos";
      }
      enum "qos-group" {
        value 110;
        description
          "qosgroup";
      }
      enum "qosid" {
        value 111;
        description
          "qosid";
      }
      enum "extlif" {
        value 112;
        description
          "extlif";
      }
      enum "elif" {
        value 113;
        description
          "elif";
      }
      enum "ingaclstats" {
        value 114;
        description
          "ingaclstats";
      }
      enum "egraclstats" {
        value 115;
        description
          "egraclstats";
      }
      enum "edpl" {
        value 116;
        description
          "edpl";
      }
      enum "l2protect" {
        value 117;
        description
          "l2protect";
      }
      enum "sat" {
        value 118;
        description
          "sat";
      }
      enum "satstats" {
        value 119;
        description
          "satstats";
      }
      enum "cfmoam-profile-def" {
        value 120;
        description
          "cfmoamprofiledef";
      }
      enum "cfmmaid" {
        value 121;
        description
          "cfmmaid";
      }
      enum "cfmdefmps" {
        value 122;
        description
          "cfmdefmps";
      }
      enum "cfmofflmep" {
        value 123;
        description
          "cfmofflmep";
      }
      enum "cfmoffrmep" {
        value 124;
        description
          "cfmoffrmep";
      }
      enum "cfmnonoff" {
        value 125;
        description
          "cfmnonoff";
      }
      enum "cfmhwoffrxstats" {
        value 126;
        description
          "cfmhwoffrxstats";
      }
      enum "ipmc-route" {
        value 127;
        description
          "ipmcroute";
      }
      enum "l2ipmc-route" {
        value 128;
        description
          "l2ipmcroute";
      }
      enum "ipmco-list" {
        value 129;
        description
          "ipmcolist";
      }
      enum "l2mco-list" {
        value 130;
        description
          "l2mcolist";
      }
      enum "meshmc" {
        value 131;
        description
          "meshmc";
      }
      enum "l2-bridge" {
        value 132;
        description
          "l2bridge";
      }
      enum "l2-bridge-port" {
        value 133;
        description
          "l2bridgeport";
      }
      enum "l2-bridge-vni" {
        value 134;
        description
          "l2bridgevni";
      }
      enum "l2-bridge-vnidecap" {
        value 135;
        description
          "l2bridgevnidecap";
      }
      enum "l2-bridge-mac" {
        value 136;
        description
          "l2bridgemac";
      }
      enum "l2brmac" {
        value 137;
        description
          "l2brmac";
      }
      enum "ip-tunnel-decap" {
        value 138;
        description
          "iptunneldecap";
      }
      enum "l2vlan-range" {
        value 139;
        description
          "l2vlanrange";
      }
      enum "ip-tunnel-encap" {
        value 140;
        description
          "iptunnelencap";
      }
      enum "iptnl-encap" {
        value 141;
        description
          "iptnlencap";
      }
      enum "iptnldecap" {
        value 142;
        description
          "iptnldecap";
      }
      enum "iptnlnh" {
        value 143;
        description
          "iptnlnh";
      }
      enum "rawget" {
        value 144;
        description
          "rawget";
      }
      enum "ip6mc-route" {
        value 145;
        description
          "ip6mcroute";
      }
      enum "ip6mc-comp-grp" {
        value 146;
        description
          "ip6mc comp grp";
      }
      enum "l2evpnact-remote-peer-id" {
        value 147;
        description
          "l2evpnactremotepeerid";
      }
      enum "l2evpnact-local-shl" {
        value 148;
        description
          "l2evpnactlocalshl";
      }
      enum "l2evpnact-remote-shl" {
        value 149;
        description
          "l2evpnactremoteshl";
      }
      enum "evpn-iml-range" {
        value 150;
        description
          "evpn imlrange";
      }
      enum "l2-bridge-o-list" {
        value 151;
        description
          "l2bridgeolist";
      }
      enum "l2-bridge-vnio-list" {
        value 152;
        description
          "l2bridgevniolist";
      }
      enum "l2acl" {
        value 153;
        description
          "l2acl";
      }
      enum "l2evpn-nh" {
        value 154;
        description
          "l2evpn nh";
      }
      enum "l2-bridge-port-sc" {
        value 155;
        description
          "l2bridgeport sc";
      }
      enum "l3intfmctxstats" {
        value 156;
        description
          "l3intfmctxstats";
      }
      enum "tidl-sample" {
        value 157;
        description
          "tidl sample";
      }
      enum "tidl-ref-sample" {
        value 158;
        description
          "tidl ref sample";
      }
      enum "ipacl-prefix" {
        value 159;
        description
          "ipaclprefix";
      }
      enum "ip6acl-prefix" {
        value 160;
        description
          "ip6aclprefix";
      }
      enum "ipacl-port" {
        value 161;
        description
          "ipaclport";
      }
      enum "scaleacl" {
        value 162;
        description
          "scaleacl";
      }
      enum "ipmcf-hop" {
        value 163;
        description
          "ipmcfhop";
      }
      enum "bundle-swoff" {
        value 164;
        description
          "bundle swoff";
      }
      enum "mcidswoff" {
        value 165;
        description
          "mcidswoff";
      }
      enum "dest-map" {
        value 166;
        description
          "destmap";
      }
      enum "l2-bridge-port-pw" {
        value 167;
        description
          "l2bridgeport pw";
      }
      enum "l2evpnact-local-shlstats" {
        value 168;
        description
          "l2evpnactlocalshlstats";
      }
      enum "test-hidden" {
        value 169;
        description
          "testhidden";
      }
      enum "test-local" {
        value 170;
        description
          "testlocal";
      }
      enum "test-repeated" {
        value 171;
        description
          "testrepeated";
      }
      enum "limd" {
        value 172;
        description
          "limd";
      }
      enum "litap" {
        value 173;
        description
          "litap";
      }
      enum "l3ifstats" {
        value 174;
        description
          "l3ifstats";
      }
      enum "mplsstats" {
        value 175;
        description
          "mplsstats";
      }
      enum "sr-test-ats" {
        value 176;
        description
          "srtestats";
      }
      enum "srteifstats" {
        value 177;
        description
          "srteifstats";
      }
      enum "exception-nh" {
        value 178;
        description
          "exceptionnh";
      }
      enum "srv6-global" {
        value 179;
        description
          "srv6 global";
      }
      enum "srv6sid" {
        value 180;
        description
          "srv6sid";
      }
      enum "srv6nh" {
        value 181;
        description
          "srv6nh";
      }
      enum "sr6sid" {
        value 182;
        description
          "sr6sid";
      }
      enum "sr6nh" {
        value 183;
        description
          "sr6nh";
      }
      enum "redirect-vrf" {
        value 184;
        description
          "redirectvrf";
      }
      enum "test-xtf" {
        value 185;
        description
          "test xtf";
      }
      enum "ippbr" {
        value 186;
        description
          "ippbr";
      }
      enum "ippbrstats" {
        value 187;
        description
          "ippbrstats";
      }
      enum "mpls-mdt-bud" {
        value 188;
        description
          "mplsmdtbud";
      }
      enum "mpls-label-rxstats" {
        value 189;
        description
          "mplslabelrxstats";
      }
      enum "l2mac-static" {
        value 190;
        description
          "l2macstatic";
      }
      enum "dot1x" {
        value 191;
        description
          "dot1x";
      }
      enum "iprte" {
        value 192;
        description
          "iprte";
      }
      enum "ip6rte" {
        value 193;
        description
          "ip6rte";
      }
      enum "llnh" {
        value 194;
        description
          "llnh";
      }
      enum "urpfintf" {
        value 195;
        description
          "urpfintf";
      }
      enum "ipmcrxstats" {
        value 196;
        description
          "ipmcrxstats";
      }
      enum "mplsrte" {
        value 197;
        description
          "mplsrte";
      }
      enum "protectnh" {
        value 198;
        description
          "protectnh";
      }
      enum "ipllnh" {
        value 199;
        description
          "ipllnh";
      }
      enum "ip6llnh" {
        value 200;
        description
          "ip6llnh";
      }
      enum "macnh" {
        value 201;
        description
          "macnh";
      }
      enum "qos-match-stats" {
        value 202;
        description
          "qosmatchstats";
      }
      enum "ofal2xc" {
        value 203;
        description
          "ofal2xc";
      }
      enum "ofamplspwe-port" {
        value 204;
        description
          "ofamplspweport";
      }
      enum "pwenh" {
        value 205;
        description
          "pwenh";
      }
      enum "pwenh-group" {
        value 206;
        description
          "pwenhgroup";
      }
      enum "ipmcrte" {
        value 207;
        description
          "ipmcrte";
      }
      enum "ip6mcrte" {
        value 208;
        description
          "ip6mcrte";
      }
      enum "ipmcr-test-ats" {
        value 209;
        description
          "ipmcrtestats";
      }
      enum "ip6mcr-test-ats" {
        value 210;
        description
          "ip6mcrtestats";
      }
      enum "transport-nh" {
        value 211;
        description
          "transportnh";
      }
      enum "port-range" {
        value 212;
        description
          "portrange";
      }
      enum "bvi-port" {
        value 213;
        description
          "bviport";
      }
      enum "mcid" {
        value 214;
        description
          "mcid";
      }
      enum "mc-gid" {
        value 215;
        description
          "mc gid";
      }
      enum "mcgidole" {
        value 216;
        description
          "mcgidole";
      }
      enum "mco-list" {
        value 217;
        description
          "mcolist";
      }
      enum "test-da" {
        value 218;
        description
          "testda";
      }
      enum "test-ca" {
        value 219;
        description
          "testca";
      }
      enum "test-ba" {
        value 220;
        description
          "testba";
      }
      enum "test-aa" {
        value 221;
        description
          "testaa";
      }
      enum "test-async-aa" {
        value 222;
        description
          "testasyncaa";
      }
      enum "test-reliable-notif" {
        value 223;
        description
          "testreliablenotif";
      }
      enum "test-de" {
        value 224;
        description
          "testde";
      }
      enum "test-ce" {
        value 225;
        description
          "testce";
      }
      enum "test-be" {
        value 226;
        description
          "testbe";
      }
      enum "test-db" {
        value 227;
        description
          "testdb";
      }
      enum "test-cb" {
        value 228;
        description
          "testcb";
      }
      enum "test-bb" {
        value 229;
        description
          "testbb";
      }
      enum "test-df" {
        value 230;
        description
          "testdf";
      }
      enum "test-cf" {
        value 231;
        description
          "testcf";
      }
      enum "test-bf" {
        value 232;
        description
          "testbf";
      }
      enum "test-af" {
        value 233;
        description
          "testaf";
      }
      enum "test-cz" {
        value 234;
        description
          "testcz";
      }
      enum "test-ax" {
        value 235;
        description
          "testax";
      }
      enum "test-ay" {
        value 236;
        description
          "testay";
      }
      enum "test-ef" {
        value 237;
        description
          "testef";
      }
      enum "test-ff" {
        value 238;
        description
          "testff";
      }
      enum "test-gf" {
        value 239;
        description
          "testgf";
      }
      enum "test-eastwestscheduling" {
        value 240;
        description
          "testeastwestscheduling";
      }
      enum "test-transnh" {
        value 241;
        description
          "testtransnh";
      }
      enum "test-eth-port" {
        value 242;
        description
          "testethport";
      }
      enum "test-eastwest" {
        value 243;
        description
          "testeastwest";
      }
      enum "test-ifstats" {
        value 244;
        description
          "testifstats";
      }
      enum "test-async-oor" {
        value 245;
        description
          "testasyncoor";
      }
      enum "test-syncmcas-too-r" {
        value 246;
        description
          "testsyncmcastoor";
      }
      enum "test-syncdeviceoor" {
        value 247;
        description
          "testsyncdeviceoor";
      }
      enum "test-az" {
        value 248;
        description
          "testaz";
      }
      enum "test-by" {
        value 249;
        description
          "testby";
      }
      enum "police-r-group" {
        value 250;
        description
          "policergroup";
      }
      enum "meter-profile" {
        value 251;
        description
          "meterprofile";
      }
      enum "acl-mirror" {
        value 252;
        description
          "acl mirror";
      }
      enum "meter-action-profile" {
        value 253;
        description
          "meteractionprofile";
      }
      enum "voqrm" {
        value 254;
        description
          "voqrm";
      }
      enum "port-wfq-profile" {
        value 255;
        description
          "portwfqprofile";
      }
      enum "rpfif" {
        value 256;
        description
          "rpfif";
      }
      enum "brmac" {
        value 257;
        description
          "brmac";
      }
      enum "br-static-mac" {
        value 258;
        description
          "brstaticmac";
      }
      enum "xconnect" {
        value 259;
        description
          "xconnect";
      }
      enum "bridge" {
        value 260;
        description
          "bridge";
      }
      enum "pwe-port" {
        value 261;
        description
          "pweport";
      }
      enum "olist" {
        value 262;
        description
          "olist";
      }
      enum "lsmprotect" {
        value 263;
        description
          "lsmprotect";
      }
      enum "monitor-session" {
        value 264;
        description
          "monitorsession";
      }
      enum "monitor-session-stats" {
        value 265;
        description
          "monitorsessionstats";
      }
      enum "mplsmcast" {
        value 266;
        description
          "mplsmcast";
      }
      enum "l2ifstats" {
        value 267;
        description
          "l2ifstats";
      }
      enum "imlnh" {
        value 268;
        description
          "imlnh";
      }
      enum "evinh" {
        value 269;
        description
          "evinh";
      }
      enum "member-list" {
        value 270;
        description
          "memberlist";
      }
      enum "test-oor" {
        value 271;
        description
          "testoor";
      }
      enum "hwre-source-s-oor" {
        value 272;
        description
          "hwresources oor";
      }
      enum "qospfcstats" {
        value 273;
        description
          "qospfcstats";
      }
      enum "pfctc" {
        value 274;
        description
          "pfctc";
      }
      enum "pfc-watchdog" {
        value 275;
        description
          "pfc watchdog";
      }
      enum "qos-shared" {
        value 276;
        description
          "qosshared";
      }
      enum "ecntxstats" {
        value 277;
        description
          "ecntxstats";
      }
      enum "tm-remote-credit" {
        value 278;
        description
          "tmremotecredit";
      }
      enum "ipmcole" {
        value 279;
        description
          "ipmcole";
      }
      enum "ip6mcole" {
        value 280;
        description
          "ip6mcole";
      }
      enum "pbr" {
        value 281;
        description
          "pbr";
      }
      enum "pbrstats" {
        value 282;
        description
          "pbrstats";
      }
      enum "punt-stormcontrol" {
        value 283;
        description
          "puntstormcontrol";
      }
      enum "ip6mcrxstats" {
        value 284;
        description
          "ip6mcrxstats";
      }
      enum "ipmctxintf" {
        value 285;
        description
          "ipmctxintf";
      }
      enum "ipmc-mdt-encap" {
        value 286;
        description
          "ipmcmdtencap";
      }
      enum "ipmc-mdt-decap" {
        value 287;
        description
          "ipmcmdtdecap";
      }
      enum "op2tap" {
        value 288;
        description
          "op2tap";
      }
      enum "mplsole" {
        value 289;
        description
          "mplsole";
      }
      enum "syncrpc" {
        value 290;
        description
          "syncrpc";
      }
      enum "tnlstats" {
        value 291;
        description
          "tnlstats";
      }
      enum "l2dhcp" {
        value 292;
        description
          "l2dhcp";
      }
      enum "pbrsbf" {
        value 293;
        description
          "pbrsbf";
      }
      enum "statsrpc" {
        value 294;
        description
          "statsrpc";
      }
      enum "oglpts" {
        value 295;
        description
          "oglpts";
      }
      enum "oglpts-prefix" {
        value 296;
        description
          "oglptsprefix";
      }
      enum "og6lpts-prefix" {
        value 297;
        description
          "og6lptsprefix";
      }
      enum "stormcontrol" {
        value 298;
        description
          "stormcontrol";
      }
      enum "acl-police-r" {
        value 299;
        description
          "aclpolicer";
      }
      enum "acl-police-rstats" {
        value 300;
        description
          "aclpolicerstats";
      }
      enum "aclkey-profile" {
        value 301;
        description
          "aclkeyprofile";
      }
      enum "acl-action-profile" {
        value 302;
        description
          "aclactionprofile";
      }
    }
    description
      "Ofa table";
  }

  augment "/ncs:devices/ncs:device/ncs:config" {
    // NCS drop config false container ofa
  }
  augment "/ncs:devices/ncs:device/ncs:live-status" {
    container ofa {
      tailf:ncs-device-type "netconf";
      tailf:display-when "not(../../ncs:module) or ../../ncs:module[ncs:name='Cisco-IOS-XR-platforms-ofa-table-stats-oper'] or (../../ncs:live-status-protocol[not(ncs:capability)]) or (../../ncs:live-status-protocol/ncs:capability/ncs:module[.='Cisco-IOS-XR-platforms-ofa-table-stats-oper'])";
      description
        "OFA Data";
      container stats {
        description
          "OFA Stats Data";
        container nodes {
          description
            "OFA data for available nodes";
          list node {
            key "node-name";
            description
              "OFA operational data for a particular node";
            container table-datas {
              description
                "OFA Resources table";
              list table-data {
                key "resource";
                description
                  "OFA Resources table";
                leaf resource {
                  type live_ncs_Ofa-table;
                  description
                    "Resource type";
                }
                uses live_ncs_OFA-NPD-SYSDB-TABLE-RESOURCE;
              }
            }
            leaf node-name {
              type xr:live_ncs_Node-id;
              description
                "Node ID";
            }
          }
        }
      }
    }
  }
  augment "/ncs:devices/ncs:template/ncs:ned-id/ncs:config" {
    // NCS drop config false container ofa
  }
}

module Cisco-IOS-XR-pbr-datatypes {
  // Generated by yanger -t ncs
  tailf:mount-id "cisco-iosxr-nc-7.3:cisco-iosxr-nc-7.3";
  tailf:ncs-device-type "netconf";

  namespace "http://cisco.com/ns/yang/Cisco-IOS-XR-pbr-datatypes";
  prefix pbr-datatypes;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef ncs_template_Vservice-nsh-path-id-range {
    type string;
    description
      "Vservice nsh path id range";
  }

  typedef ncs_template_Vservice-nsh-service-index-range {
    type string;
    description
      "Vservice nsh service index range";
  }

  typedef ncs_rpc_notif_Vservice-nsh-path-id-range {
    type uint32 {
      range "1..16777215";
    }
    description
      "Vservice nsh path id range";
  }

  typedef ncs_rpc_notif_Vservice-nsh-service-index-range {
    type uint32 {
      range "1..255";
    }
    description
      "Vservice nsh service index range";
  }

  typedef live_ncs_Vservice-nsh-path-id-range {
    type uint32 {
      range "1..16777215";
    }
    description
      "Vservice nsh path id range";
  }

  typedef live_ncs_Vservice-nsh-service-index-range {
    type uint32 {
      range "1..255";
    }
    description
      "Vservice nsh service index range";
  }

  typedef Vservice-nsh-path-id-range {
    type uint32 {
      range "1..16777215";
    }
    description
      "Vservice nsh path id range";
  }

  typedef Vservice-nsh-service-index-range {
    type uint32 {
      range "1..255";
    }
    description
      "Vservice nsh service index range";
  }
}

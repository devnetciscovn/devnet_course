module Cisco-IOS-XR-sysadmin-obfl {
  // Generated by yanger -t ncs
  tailf:mount-id "cisco-iosxr-nc-7.3:cisco-iosxr-nc-7.3";
  tailf:ncs-device-type "netconf";

  namespace "http://www.cisco.com/ns/yang/Cisco-IOS-XR-sysadmin-obfl";
  prefix obfl;

  import Cisco-IOS-XR-sysadmin-show-trace {
    prefix show_trace;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module holds OBFL data.

     Copyright (c) 2012-2020 by Cisco Systems, Inc.
     All rights reserved.";

  revision 2019-04-15 {
    description
      "Establish semantic version baseline.";
    semver:module-version "1.0.0";
  }
  revision 2017-07-31 {
    description
      "Changed namespace to follow Cisco guidelines on naming convention";
  }
  revision 2012-10-10 {
    description
      "Initial revision of show obfl related commands";
  }

  grouping ncs_template_obfl_trace {
    container obfl_mgr {
      uses show_trace:ncs_template_traceable;
    }
    container obfl_show {
      uses show_trace:ncs_template_traceable;
    }
  }

  grouping ncs_rpc_notif_obfl_trace {
    container obfl_mgr {
      uses show_trace:ncs_rpc_notif_traceable;
    }
    container obfl_show {
      uses show_trace:ncs_rpc_notif_traceable;
    }
  }

  grouping live_ncs_obfl_trace {
    container obfl_mgr {
      uses show_trace:live_ncs_traceable;
    }
    container obfl_show {
      uses show_trace:live_ncs_traceable;
    }
  }

  grouping obfl_trace {
    container obfl_mgr {
      uses show_trace:traceable;
    }
    container obfl_show {
      uses show_trace:traceable;
    }
  }

  augment "/ncs:devices/ncs:device/ncs:config" {
    // NCS drop config false container obfl
  }
  augment "/ncs:devices/ncs:device/ncs:live-status" {
    container obfl {
      tailf:ncs-device-type "netconf";
      tailf:display-when "not(../../ncs:module) or ../../ncs:module[ncs:name='Cisco-IOS-XR-sysadmin-obfl'] or (../../ncs:live-status-protocol[not(ncs:capability)]) or (../../ncs:live-status-protocol/ncs:capability/ncs:module[.='Cisco-IOS-XR-sysadmin-obfl'])";
      uses live_ncs_obfl_trace;
    }
  }
  augment "/ncs:devices/ncs:template/ncs:ned-id/ncs:config" {
    // NCS drop config false container obfl
  }
}

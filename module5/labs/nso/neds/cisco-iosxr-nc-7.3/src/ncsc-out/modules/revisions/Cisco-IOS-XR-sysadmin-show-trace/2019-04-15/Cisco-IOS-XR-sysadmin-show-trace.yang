module Cisco-IOS-XR-sysadmin-show-trace {
  // Generated by yanger -t ncs
  tailf:mount-id "cisco-iosxr-nc-7.3:cisco-iosxr-nc-7.3";
  tailf:ncs-device-type "netconf";

  namespace "http://www.cisco.com/ns/yang/Cisco-IOS-XR-sysadmin-show-trace";
  prefix show_trace;

  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright (c) 2012-2020 by Cisco Systems, Inc.
     All rights reserved.";

  revision 2019-04-15 {
    description
      "Establish semantic version baseline.";
    semver:module-version "1.0.0";
  }
  revision 2017-04-12 {
    description
      "Changed namespace and module name";
  }
  revision 2016-05-11 {
    description
      "Initial version.";
  }

  grouping ncs_template_traceable {
    // NCS drop config false list trace
  }

  grouping ncs_template_traceable_process {
    // NCS drop config false list instance
  }

  grouping ncs_template_traceable_with_keypath_location {
    // NCS drop config false list trace
  }

  grouping ncs_rpc_notif_traceable {
    list trace {
      key "buffer";
      config false;
      description
        "show traceable processes";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping ncs_rpc_notif_traceable_process {
    list instance {
      key "process_name";
      config false;
      description
        "show traceable process instance names";
      leaf process_name {
        type string;
      }
      list trace {
        key "buffer";
        config false;
        description
          "show traceable processes";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping ncs_rpc_notif_traceable_with_keypath_location {
    list trace {
      key "buffer";
      config false;
      leaf buffer {
        type string;
      }
      list all-options {
        key "option";
        leaf option {
          type string;
        }
        list trace-blocks {
          leaf data {
            type string;
          }
        }
      }
    }
  }

  grouping live_ncs_traceable {
    list trace {
      key "buffer";
      description
        "show traceable processes";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping live_ncs_traceable_process {
    list instance {
      key "process_name";
      description
        "show traceable process instance names";
      leaf process_name {
        type string;
      }
      list trace {
        key "buffer";
        description
          "show traceable processes";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping live_ncs_traceable_with_keypath_location {
    list trace {
      key "buffer";
      leaf buffer {
        type string;
      }
      list all-options {
        key "option";
        leaf option {
          type string;
        }
        list trace-blocks {
          leaf data {
            type string;
          }
        }
      }
    }
  }

  grouping traceable {
    // NCS drop config false list trace
  }

  grouping traceable_process {
    // NCS drop config false list instance
  }

  grouping traceable_with_keypath_location {
    // NCS drop config false list trace
  }
}

module Cisco-IOS-XR-man-ems-oper {
  // Generated by yanger -t ncs
  tailf:mount-id "cisco-iosxr-nc-7.3:cisco-iosxr-nc-7.3";
  tailf:ncs-device-type "netconf";

  namespace "http://cisco.com/ns/yang/Cisco-IOS-XR-man-ems-oper";
  prefix man-ems-oper;

  import cisco-semver {
    prefix semver;
  }
  include Cisco-IOS-XR-man-ems-oper-sub1 {
    revision-date 2020-03-19;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-ems package operational data.

     This module contains definitions
     for the following management objects:
       grpc: grpc commands

     Copyright (c) 2013-2020 by Cisco Systems, Inc.
     All rights reserved.";

  revision 2020-03-19 {
    description
      "Added grpc server status.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  augment "/ncs:devices/ncs:device/ncs:config" {
    // NCS drop config false container grpc
  }
  augment "/ncs:devices/ncs:device/ncs:live-status" {
    container grpc {
      tailf:ncs-device-type "netconf";
      tailf:display-when "not(../../ncs:module) or ../../ncs:module[ncs:name='Cisco-IOS-XR-man-ems-oper'] or (../../ncs:live-status-protocol[not(ncs:capability)]) or (../../ncs:live-status-protocol/ncs:capability/ncs:module[.='Cisco-IOS-XR-man-ems-oper'])";
      description
        "grpc commands";
      container state {
        description
          "Grpc State";
        uses live_ncs_GRPC-STATE;
      }
      container status {
        description
          "Grpc Status";
        uses live_ncs_GRPC-STATUS-INFO-B;
      }
      container statistics {
        description
          "Grpc Statistics";
        uses live_ncs_GRPC-STATISTICS-INFO-B;
      }
    }
  }
  augment "/ncs:devices/ncs:template/ncs:ned-id/ncs:config" {
    // NCS drop config false container grpc
  }
}

submodule Cisco-IOS-XR-telemetry-model-driven-oper-sub1 {
  // Generated by yanger -t ncs
  tailf:mount-id "cisco-iosxr-nc-7.3:cisco-iosxr-nc-7.3";

  belongs-to Cisco-IOS-XR-telemetry-model-driven-oper {
    prefix Cisco-IOS-XR-telemetry-model-driven-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR telemetry-model-driven package operational data.

     Copyright (c) 2013-2021 by Cisco Systems, Inc.
     All rights reserved.";

  revision 2021-09-13 {
    description
      "Added pending message memory size to destination endpoint";
    semver:module-version "1.3.0";
  }
  revision 2020-06-11 {
    description
      "Heartbeat interval IosSetYangSchemaRev Cisco-IOS-XR-telemetry-model-driven-oper";
    semver:module-version "1.2.0";
  }
  revision 2020-03-11 {
    description
      "Updated the encodings supported
       2020-01-30
       Added compression leaf to destination container
       2020-01-10
       GRPC channel statistics added
       2019-09-25
       Added minimum-cadence and cadence-factor options for target defined mode";
    semver:module-version "1.1.0";
  }
  revision 2019-04-05 {
    description
      "Establish semantic version baseline.";
    semver:module-version "1.0.1";
  }
  revision 2017-09-27 {
    description
      "Summary container added";
  }
  revision 2017-05-05 {
    description
      "Modified the type for the state variables";
  }
  revision 2017-05-01 {
    description
      "Fixing backward compatibility error in module.";
  }
  revision 2017-02-09 {
    description
      "Added DSCP";
  }
  revision 2017-01-30 {
    description
      "Initial 6.2.1 revision";
  }
  revision 2015-11-09 {
    description
      "IOS XR 6.0 revision.";
  }

  grouping ncs_template_TELEMETRY-SHOW-SUMMARY {
    description
      "Telemetry Summary information";
    leaf num-of-subscriptions {
      type string;
      description
        "Number of Subscriptions";
    }
    leaf num-of-active-subscriptions {
      type string;
      description
        "Number of Active Subscriptions";
    }
    leaf num-of-paused-subscriptions {
      type string;
      description
        "Number of Paused Subscriptions";
    }
    leaf num-of-destination-groups {
      type string;
      description
        "Number of Destination Groups";
    }
    leaf num-of-destinations {
      type string;
      description
        "Number of Destinations";
    }
    leaf num-of-tcp-dialouts {
      type string;
      description
        "Number of Tcp Dialout Destinations";
    }
    leaf num-of-udp-dialouts {
      type string;
      description
        "Number of Udp Dialout Destinations";
    }
    leaf num-of-grpc-tls-dialouts {
      type string;
      description
        "Number of GRPC TLS Dialout Destinations";
    }
    leaf num-of-grpc-non-tls-dialouts {
      type string;
      description
        "Number of GRPC Non-TLS Dialout Destinations";
    }
    leaf num-of-dialins {
      type string;
      description
        "Number of Dialin Destinations";
    }
    leaf num-of-active-destinations {
      type string;
      description
        "Number of Active Destinations";
    }
    leaf num-of-connected-sessions {
      type string;
      description
        "Number of Connected Sessions";
    }
    leaf num-of-connecting-sessions {
      type string;
      description
        "Number of Connecting Sessions";
    }
    leaf num-of-sensor-groups {
      type string;
      description
        "Number of Sensor Groups";
    }
    leaf num-of-unique-sensor-paths {
      type string;
      description
        "Number of Unique Sensor Paths";
    }
    leaf num-of-sensor-paths {
      type string;
      description
        "Number of Sensor Paths";
    }
    leaf num-of-not-resolved-sensor-paths {
      type string;
      description
        "Number of not resolved sensor paths";
    }
    leaf num-of-active-sensor-paths {
      type string;
      description
        "Number of Active Sensor Paths";
    }
    leaf max-sensor-paths {
      type string;
      description
        "Maximum Sensor Paths allowed";
    }
    leaf max-containers-per-path {
      type string;
      description
        "Max containers allowed per Sensor Path";
    }
    leaf min-target-def-cadence {
      type string;
      description
        "Minimum cadence for target defined subscriptions";
    }
    leaf target-def-cadence-factor {
      type string;
      description
        "Cadence factor for target defined subscriptions";
    }
  }

  grouping ncs_rpc_notif_TELEMETRY-SHOW-SUMMARY {
    description
      "Telemetry Summary information";
    leaf num-of-subscriptions {
      type uint32;
      description
        "Number of Subscriptions";
    }
    leaf num-of-active-subscriptions {
      type uint32;
      description
        "Number of Active Subscriptions";
    }
    leaf num-of-paused-subscriptions {
      type uint32;
      description
        "Number of Paused Subscriptions";
    }
    leaf num-of-destination-groups {
      type uint32;
      description
        "Number of Destination Groups";
    }
    leaf num-of-destinations {
      type uint32;
      description
        "Number of Destinations";
    }
    leaf num-of-tcp-dialouts {
      type uint32;
      description
        "Number of Tcp Dialout Destinations";
    }
    leaf num-of-udp-dialouts {
      type uint32;
      description
        "Number of Udp Dialout Destinations";
    }
    leaf num-of-grpc-tls-dialouts {
      type uint32;
      description
        "Number of GRPC TLS Dialout Destinations";
    }
    leaf num-of-grpc-non-tls-dialouts {
      type uint32;
      description
        "Number of GRPC Non-TLS Dialout Destinations";
    }
    leaf num-of-dialins {
      type uint32;
      description
        "Number of Dialin Destinations";
    }
    leaf num-of-active-destinations {
      type uint32;
      description
        "Number of Active Destinations";
    }
    leaf num-of-connected-sessions {
      type uint32;
      description
        "Number of Connected Sessions";
    }
    leaf num-of-connecting-sessions {
      type uint32;
      description
        "Number of Connecting Sessions";
    }
    leaf num-of-sensor-groups {
      type uint32;
      description
        "Number of Sensor Groups";
    }
    leaf num-of-unique-sensor-paths {
      type uint32;
      description
        "Number of Unique Sensor Paths";
    }
    leaf num-of-sensor-paths {
      type uint32;
      description
        "Number of Sensor Paths";
    }
    leaf num-of-not-resolved-sensor-paths {
      type uint32;
      description
        "Number of not resolved sensor paths";
    }
    leaf num-of-active-sensor-paths {
      type uint32;
      description
        "Number of Active Sensor Paths";
    }
    leaf max-sensor-paths {
      type uint32;
      description
        "Maximum Sensor Paths allowed";
    }
    leaf max-containers-per-path {
      type uint32;
      description
        "Max containers allowed per Sensor Path";
    }
    leaf min-target-def-cadence {
      type uint32;
      description
        "Minimum cadence for target defined subscriptions";
    }
    leaf target-def-cadence-factor {
      type uint32;
      description
        "Cadence factor for target defined subscriptions";
    }
  }

  grouping live_ncs_TELEMETRY-SHOW-SUMMARY {
    description
      "Telemetry Summary information";
    leaf num-of-subscriptions {
      type uint32;
      description
        "Number of Subscriptions";
    }
    leaf num-of-active-subscriptions {
      type uint32;
      description
        "Number of Active Subscriptions";
    }
    leaf num-of-paused-subscriptions {
      type uint32;
      description
        "Number of Paused Subscriptions";
    }
    leaf num-of-destination-groups {
      type uint32;
      description
        "Number of Destination Groups";
    }
    leaf num-of-destinations {
      type uint32;
      description
        "Number of Destinations";
    }
    leaf num-of-tcp-dialouts {
      type uint32;
      description
        "Number of Tcp Dialout Destinations";
    }
    leaf num-of-udp-dialouts {
      type uint32;
      description
        "Number of Udp Dialout Destinations";
    }
    leaf num-of-grpc-tls-dialouts {
      type uint32;
      description
        "Number of GRPC TLS Dialout Destinations";
    }
    leaf num-of-grpc-non-tls-dialouts {
      type uint32;
      description
        "Number of GRPC Non-TLS Dialout Destinations";
    }
    leaf num-of-dialins {
      type uint32;
      description
        "Number of Dialin Destinations";
    }
    leaf num-of-active-destinations {
      type uint32;
      description
        "Number of Active Destinations";
    }
    leaf num-of-connected-sessions {
      type uint32;
      description
        "Number of Connected Sessions";
    }
    leaf num-of-connecting-sessions {
      type uint32;
      description
        "Number of Connecting Sessions";
    }
    leaf num-of-sensor-groups {
      type uint32;
      description
        "Number of Sensor Groups";
    }
    leaf num-of-unique-sensor-paths {
      type uint32;
      description
        "Number of Unique Sensor Paths";
    }
    leaf num-of-sensor-paths {
      type uint32;
      description
        "Number of Sensor Paths";
    }
    leaf num-of-not-resolved-sensor-paths {
      type uint32;
      description
        "Number of not resolved sensor paths";
    }
    leaf num-of-active-sensor-paths {
      type uint32;
      description
        "Number of Active Sensor Paths";
    }
    leaf max-sensor-paths {
      type uint32;
      description
        "Maximum Sensor Paths allowed";
    }
    leaf max-containers-per-path {
      type uint32;
      description
        "Max containers allowed per Sensor Path";
    }
    leaf min-target-def-cadence {
      type uint32;
      description
        "Minimum cadence for target defined subscriptions";
    }
    leaf target-def-cadence-factor {
      type uint32;
      description
        "Cadence factor for target defined subscriptions";
    }
  }

  grouping TELEMETRY-SHOW-SUMMARY {
    description
      "Telemetry Summary information";
    leaf num-of-subscriptions {
      type uint32;
      description
        "Number of Subscriptions";
    }
    leaf num-of-active-subscriptions {
      type uint32;
      description
        "Number of Active Subscriptions";
    }
    leaf num-of-paused-subscriptions {
      type uint32;
      description
        "Number of Paused Subscriptions";
    }
    leaf num-of-destination-groups {
      type uint32;
      description
        "Number of Destination Groups";
    }
    leaf num-of-destinations {
      type uint32;
      description
        "Number of Destinations";
    }
    leaf num-of-tcp-dialouts {
      type uint32;
      description
        "Number of Tcp Dialout Destinations";
    }
    leaf num-of-udp-dialouts {
      type uint32;
      description
        "Number of Udp Dialout Destinations";
    }
    leaf num-of-grpc-tls-dialouts {
      type uint32;
      description
        "Number of GRPC TLS Dialout Destinations";
    }
    leaf num-of-grpc-non-tls-dialouts {
      type uint32;
      description
        "Number of GRPC Non-TLS Dialout Destinations";
    }
    leaf num-of-dialins {
      type uint32;
      description
        "Number of Dialin Destinations";
    }
    leaf num-of-active-destinations {
      type uint32;
      description
        "Number of Active Destinations";
    }
    leaf num-of-connected-sessions {
      type uint32;
      description
        "Number of Connected Sessions";
    }
    leaf num-of-connecting-sessions {
      type uint32;
      description
        "Number of Connecting Sessions";
    }
    leaf num-of-sensor-groups {
      type uint32;
      description
        "Number of Sensor Groups";
    }
    leaf num-of-unique-sensor-paths {
      type uint32;
      description
        "Number of Unique Sensor Paths";
    }
    leaf num-of-sensor-paths {
      type uint32;
      description
        "Number of Sensor Paths";
    }
    leaf num-of-not-resolved-sensor-paths {
      type uint32;
      description
        "Number of not resolved sensor paths";
    }
    leaf num-of-active-sensor-paths {
      type uint32;
      description
        "Number of Active Sensor Paths";
    }
    leaf max-sensor-paths {
      type uint32;
      description
        "Maximum Sensor Paths allowed";
    }
    leaf max-containers-per-path {
      type uint32;
      description
        "Max containers allowed per Sensor Path";
    }
    leaf min-target-def-cadence {
      type uint32;
      description
        "Minimum cadence for target defined subscriptions";
    }
    leaf target-def-cadence-factor {
      type uint32;
      description
        "Cadence factor for target defined subscriptions";
    }
  }
}

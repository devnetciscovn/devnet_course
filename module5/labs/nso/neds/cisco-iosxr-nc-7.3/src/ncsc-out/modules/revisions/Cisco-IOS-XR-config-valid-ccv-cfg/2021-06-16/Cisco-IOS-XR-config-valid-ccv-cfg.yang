module Cisco-IOS-XR-config-valid-ccv-cfg {
  // Generated by yanger -t ncs
  tailf:mount-id "cisco-iosxr-nc-7.3:cisco-iosxr-nc-7.3";
  tailf:ncs-device-type "netconf";

  namespace "http://cisco.com/ns/yang/Cisco-IOS-XR-config-valid-ccv-cfg";
  prefix config-valid-ccv-cfg;

  import cisco-semver {
    prefix semver;
  }
  import Cisco-IOS-XR-infra-script-mgmt-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-valid-ccv package configuration.

     This module contains definitions
     for the following management objects:
       configurationvalidation: Configuration for the Configuration
         Validation feature

     This YANG module augments the
       Cisco-IOS-XR-infra-script-mgmt-cfg
     module with configuration data.

     Copyright (c) 2013-2021 by Cisco Systems, Inc.
     All rights reserved.";

  revision 2021-06-16 {
    description
      "Deprecate nodes specific to commit check.";
    semver:module-version "1.1.0";
  }
  revision 2020-07-06 {
    description
      "Added Commit Scripts support.";
    semver:module-version "1.0.0";
  }
  revision 2019-04-05 {
    description
      "Establish semantic version baseline.";
    semver:module-version "1.0.0";
  }
  revision 2015-11-09 {
    description
      "IOS XR 6.0 revision.";
  }

  typedef ncs_template_Failure-action {
    type string;
    description
      "Failure action";
  }

  typedef ncs_template_Failure {
    type string;
    description
      "Failure";
  }

  typedef ncs_template_Enable {
    type string;
    description
      "Enable";
  }

  typedef ncs_template_Checksum {
    type string;
    description
      "Checksum";
  }

  typedef ncs_rpc_notif_Failure-action {
    type enumeration {
      enum "report" {
        value 1;
        description
          "Report this failure type";
      }
    }
    description
      "Failure action";
  }

  typedef ncs_rpc_notif_Failure {
    type enumeration {
      enum "unsupported" {
        value 0;
        description
          "Unsupported failure type";
      }
    }
    description
      "Failure";
  }

  typedef ncs_rpc_notif_Enable {
    type enumeration {
      enum "nonblocking" {
        value 1;
        description
          "Non-blocking enable type";
      }
      enum "blocking" {
        value 2;
        description
          "Blocking enable type";
      }
    }
    description
      "Enable";
  }

  typedef ncs_rpc_notif_Checksum {
    type enumeration {
      enum "sha256" {
        value 0;
        description
          "SHA256";
      }
    }
    description
      "Checksum";
  }

  typedef live_ncs_Failure-action {
    type enumeration {
      enum "report" {
        value 1;
        description
          "Report this failure type";
      }
    }
    description
      "Failure action";
  }

  typedef live_ncs_Failure {
    type enumeration {
      enum "unsupported" {
        value 0;
        description
          "Unsupported failure type";
      }
    }
    description
      "Failure";
  }

  typedef live_ncs_Enable {
    type enumeration {
      enum "nonblocking" {
        value 1;
        description
          "Non-blocking enable type";
      }
      enum "blocking" {
        value 2;
        description
          "Blocking enable type";
      }
    }
    description
      "Enable";
  }

  typedef live_ncs_Checksum {
    type enumeration {
      enum "sha256" {
        value 0;
        description
          "SHA256";
      }
    }
    description
      "Checksum";
  }

  typedef Failure-action {
    type enumeration {
      enum "report" {
        value 1;
        description
          "Report this failure type";
      }
    }
    description
      "Failure action";
  }

  typedef Failure {
    type enumeration {
      enum "unsupported" {
        value 0;
        description
          "Unsupported failure type";
      }
    }
    description
      "Failure";
  }

  typedef Enable {
    type enumeration {
      enum "nonblocking" {
        value 1;
        description
          "Non-blocking enable type";
      }
      enum "blocking" {
        value 2;
        description
          "Blocking enable type";
      }
    }
    description
      "Enable";
  }

  typedef Checksum {
    type enumeration {
      enum "sha256" {
        value 0;
        description
          "SHA256";
      }
    }
    description
      "Checksum";
  }

  augment "/ncs:devices/ncs:device/ncs:config" {
    container configurationvalidation {
      tailf:ncs-device-type "netconf";
      tailf:display-when "not(../../ncs:module) or ../../ncs:module[ncs:name='Cisco-IOS-XR-config-valid-ccv-cfg']";
      description
        "Configuration for the Configuration Validation
         feature";
      container failure-type-actions {
        status deprecated;
        description
          "DEPRECATED: not to be used in new deployments";
        list failure-type-action {
          key "failure";
          description
            "Failure type action configuration";
          leaf action {
            type Failure-action;
            description
              "Action configuration for this failure type";
          }
          leaf failure {
            type Failure;
            description
              "Failure type";
          }
        }
      }
      leaf enable {
        type Enable;
        status deprecated;
        description
          "DEPRECATED: not to be used in new deployments.
           Incompatible with use of ScriptsEnable.";
      }
      leaf scripts-enable {
        type boolean;
        description
          "Enable configuration validation via scripts";
      }
    }
  }
  augment "/ncs:devices/ncs:device/ncs:live-status" {
    container configurationvalidation {
      tailf:ncs-device-type "netconf";
      tailf:display-when "not(../../ncs:module) or ../../ncs:module[ncs:name='Cisco-IOS-XR-config-valid-ccv-cfg'] or (../../ncs:live-status-protocol[not(ncs:capability)]) or (../../ncs:live-status-protocol/ncs:capability/ncs:module[.='Cisco-IOS-XR-config-valid-ccv-cfg'])";
      description
        "Configuration for the Configuration Validation
         feature";
      container failure-type-actions {
        status deprecated;
        description
          "DEPRECATED: not to be used in new deployments";
        list failure-type-action {
          key "failure";
          description
            "Failure type action configuration";
          leaf action {
            type live_ncs_Failure-action;
            description
              "Action configuration for this failure type";
          }
          leaf failure {
            type live_ncs_Failure;
            description
              "Failure type";
          }
        }
      }
      leaf enable {
        type live_ncs_Enable;
        status deprecated;
        description
          "DEPRECATED: not to be used in new deployments.
           Incompatible with use of ScriptsEnable.";
      }
      leaf scripts-enable {
        type boolean;
        description
          "Enable configuration validation via scripts";
      }
    }
  }
  augment "/ncs:devices/ncs:template/ncs:ned-id/ncs:config" {
    container configurationvalidation {
      description
        "Configuration for the Configuration Validation
         feature";
      container failure-type-actions {
        status deprecated;
        description
          "DEPRECATED: not to be used in new deployments";
        list failure-type-action {
          // NCS patched for predictable order
          ordered-by user;
          key "failure";
          description
            "Failure type action configuration";
          leaf action {
            type ncs_template_Failure-action;
            description
              "Action configuration for this failure type";
          }
          leaf failure {
            type ncs_template_Failure;
            description
              "Failure type";
          }
        }
      }
      leaf enable {
        type ncs_template_Enable;
        status deprecated;
        description
          "DEPRECATED: not to be used in new deployments.
           Incompatible with use of ScriptsEnable.";
      }
      leaf scripts-enable {
        type string;
        description
          "Enable configuration validation via scripts";
      }
    }
  }
  augment "/ncs:devices/ncs:template/ncs:ned-id/ncs:config/a1:scripts" {
    description
      "This augment extends the configuration data of
       'Cisco-IOS-XR-infra-script-mgmt-cfg'";
    container config {
      description
        "Config script activation configuration";
      container scripts {
        description
          "Config script list";
        list script {
          // NCS patched for predictable order
          ordered-by user;
          key "name";
          description
            "Config script activation item";
          leaf name {
            type string;
            description
              "Script name";
          }
          leaf checksum-type {
            type ncs_template_Checksum;
            // NCS drop mandatory statement
            description
              "Checksum type";
          }
          leaf checksum {
            type string;
            // NCS drop mandatory statement
            description
              "Checksum value";
          }
          leaf priority {
            type string;
            // NCS drop default statement
            description
              "Script priority";
          }
        }
      }
    }
  }
  augment "/ncs:devices/ncs:device/ncs:live-status/a1:scripts" {
    description
      "This augment extends the configuration data of
       'Cisco-IOS-XR-infra-script-mgmt-cfg'";
    container config {
      tailf:ncs-device-type "netconf";
      tailf:display-when "not(../../../ncs:module) or ../../../ncs:module[ncs:name='Cisco-IOS-XR-config-valid-ccv-cfg'] or (../../../ncs:live-status-protocol[not(ncs:capability)]) or (../../../ncs:live-status-protocol/ncs:capability/ncs:module[.='Cisco-IOS-XR-config-valid-ccv-cfg'])";
      description
        "Config script activation configuration";
      container scripts {
        description
          "Config script list";
        list script {
          key "name";
          description
            "Config script activation item";
          leaf name {
            type string;
            description
              "Script name";
          }
          leaf checksum-type {
            type live_ncs_Checksum;
            // NCS drop mandatory statement
            description
              "Checksum type";
          }
          leaf checksum {
            type string {
              length "64";
            }
            // NCS drop mandatory statement
            description
              "Checksum value";
          }
          leaf priority {
            type uint32;
            // NCS drop default statement
            description
              "Script priority";
          }
        }
      }
    }
  }
  augment "/ncs:devices/ncs:device/ncs:config/a1:scripts" {
    description
      "This augment extends the configuration data of
       'Cisco-IOS-XR-infra-script-mgmt-cfg'";
    container config {
      tailf:ncs-device-type "netconf";
      tailf:display-when "not(../../../ncs:module) or ../../../ncs:module[ncs:name='Cisco-IOS-XR-config-valid-ccv-cfg']";
      description
        "Config script activation configuration";
      container scripts {
        description
          "Config script list";
        list script {
          key "name";
          description
            "Config script activation item";
          leaf name {
            type string;
            description
              "Script name";
          }
          leaf checksum-type {
            type Checksum;
            mandatory true;
            description
              "Checksum type";
          }
          leaf checksum {
            type string {
              length "64";
            }
            mandatory true;
            description
              "Checksum value";
          }
          leaf priority {
            type uint32;
            default "500";
            description
              "Script priority";
          }
        }
      }
    }
  }
}

module Cisco-IOS-XR-lcmode-oper {
  // Generated by yanger -t ncs
  tailf:mount-id "cisco-iosxr-nc-7.3:cisco-iosxr-nc-7.3";
  tailf:ncs-device-type "netconf";

  namespace "http://cisco.com/ns/yang/Cisco-IOS-XR-lcmode-oper";
  prefix lcmode-oper;

  import cisco-semver {
    prefix semver;
  }
  include Cisco-IOS-XR-lcmode-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lcmode package operational data.

     This module contains definitions
     for the following management objects:
       show-lcmodule: Show lc-module

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'show-lcmodule'
  }
  augment "/ncs:devices/ncs:device/ncs:live-status" {
    container show-lcmodule {
      tailf:ncs-device-type "netconf";
      tailf:display-when "not(../../ncs:module) or ../../ncs:module[ncs:name='Cisco-IOS-XR-lcmode-oper'] or (../../ncs:live-status-protocol[not(ncs:capability)]) or (../../ncs:live-status-protocol/ncs:capability/ncs:module[.='Cisco-IOS-XR-lcmode-oper'])";
      description
        "Show lc-module";
      container lcmode-gl {
        description
          "gl";
        container lcmode-slots {
          description
            "lcmode";
          list lcmode-slot {
            key "slot-id";
            description
              "Per slot lcmode data";
            leaf slot-id {
              type uint32;
              description
                "Slot Id";
            }
            uses live_ncs_LCMODE-INFO;
          }
        }
      }
    }
  }
  augment "/ncs:devices/ncs:template/ncs:ned-id/ncs:config" {
    // NCS drop config false container 'show-lcmodule'
  }
}

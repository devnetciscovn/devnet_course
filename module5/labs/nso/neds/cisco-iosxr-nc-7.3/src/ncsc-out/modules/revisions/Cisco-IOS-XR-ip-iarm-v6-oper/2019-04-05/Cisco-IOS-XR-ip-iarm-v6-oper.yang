module Cisco-IOS-XR-ip-iarm-v6-oper {
  // Generated by yanger -t ncs
  tailf:mount-id "cisco-iosxr-nc-7.3:cisco-iosxr-nc-7.3";
  tailf:ncs-device-type "netconf";

  namespace "http://cisco.com/ns/yang/Cisco-IOS-XR-ip-iarm-v6-oper";
  prefix ip-iarm-v6-oper;

  import ietf-inet-types {
    prefix inet;
  }
  import Cisco-IOS-XR-types {
    prefix xr;
  }
  import cisco-semver {
    prefix semver;
  }
  include Cisco-IOS-XR-ip-iarm-v6-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-iarm-v6 package operational data.

     This module contains definitions
     for the following management objects:
       ipv6arm: IPv6 Address Repository Manager (IPv6 ARM)
         operational data

     Copyright (c) 2013-2019 by Cisco Systems, Inc.
     All rights reserved.";

  revision 2019-04-05 {
    description
      "Establish semantic version baseline.";
    semver:module-version "1.0.0";
  }
  revision 2019-01-22 {
    description
      "Fixing yang usability issues.";
  }
  revision 2017-05-01 {
    description
      "Fixing backward compatibility error in module.";
  }
  revision 2016-12-19 {
    description
      "IOS XR 6.2.1 revision.";
  }
  revision 2015-11-09 {
    description
      "IOS XR 6.0 revision.";
  }

  typedef ncs_template_Ipv6arm-prefix-length {
    type string;
    description
      "Ipv6arm prefix length";
  }

  typedef ncs_rpc_notif_Ipv6arm-prefix-length {
    type uint32 {
      range "0..128";
    }
    description
      "Ipv6arm prefix length";
  }

  typedef live_ncs_Ipv6arm-prefix-length {
    type uint32 {
      range "0..128";
    }
    description
      "Ipv6arm prefix length";
  }

  typedef Ipv6arm-prefix-length {
    type uint32 {
      range "0..128";
    }
    description
      "Ipv6arm prefix length";
  }

  augment "/ncs:devices/ncs:device/ncs:config" {
    // NCS drop config false container ipv6arm
  }
  augment "/ncs:devices/ncs:device/ncs:live-status" {
    container ipv6arm {
      tailf:ncs-device-type "netconf";
      tailf:display-when "not(../../ncs:module) or ../../ncs:module[ncs:name='Cisco-IOS-XR-ip-iarm-v6-oper'] or (../../ncs:live-status-protocol[not(ncs:capability)]) or (../../ncs:live-status-protocol/ncs:capability/ncs:module[.='Cisco-IOS-XR-ip-iarm-v6-oper'])";
      description
        "IPv6 Address Repository Manager (IPv6 ARM)
         operational data";
      container addresses {
        description
          "IPv6 ARM address database information";
        container vrfs {
          description
            "IPv6 ARM address database information per VRF";
          list vrf {
            key "vrf-name";
            description
              "IPv6 ARM address database information in a VRF";
            container networks {
              description
                "IPv6 ARM address database information by
                 network";
              list network {
                description
                  "An IPv6 Address in IPv6 ARM";
                leaf address {
                  type inet:ipv6-address-no-zone;
                  description
                    "Ipv6 Address in the Network";
                }
                leaf prefix-length {
                  type live_ncs_Ipv6arm-prefix-length;
                  description
                    "IPv6 Arm prefix length for this address in
                     the Network";
                }
                leaf interface {
                  type xr:live_ncs_Interface-name;
                  description
                    "Ingress/Egress interface handle for this
                     address in the Network";
                }
                uses live_ncs_IP-ARM-EDM-DB-NET-BAG-TYPE;
              }
            }
            container interfaces {
              description
                "IPv6 ARM address database information by
                 interface";
              list interface {
                key "interface";
                description
                  "An IPv6 address in IPv6 ARM";
                leaf interface {
                  type xr:live_ncs_Interface-name;
                  description
                    "Interface";
                }
                uses live_ncs_IP-ARM-EDM-DB-IF-BAG-TYPE;
              }
            }
            leaf vrf-name {
              type xr:live_ncs_Cisco-ios-xr-string;
              description
                "VRF name";
            }
          }
        }
      }
      container summary {
        description
          "IPv6 ARM summary information";
        uses live_ncs_IP-ARM-EDM-SUMMARY-BAG-TYPE;
      }
      container vrf-summaries {
        description
          "IPv6 ARM VRFs summary information";
        list vrf-summary {
          key "vrf-name";
          description
            "IPv6 ARM VRF summary information";
          leaf vrf-name {
            type xr:live_ncs_Cisco-ios-xr-string;
            description
              "VRF name";
          }
          uses live_ncs_IP-ARM-EDM-DB-VRF-BAG-TYPE;
        }
      }
      leaf multicast-host-interface {
        type xr:live_ncs_Interface-name;
        description
          "Interface Handle of Default Multicast Host";
      }
    }
  }
  augment "/ncs:devices/ncs:template/ncs:ned-id/ncs:config" {
    // NCS drop config false container ipv6arm
  }
}

module Cisco-IOS-XR-xrv9k-lpts-oper {
  // Generated by yanger -t ncs
  tailf:mount-id "cisco-iosxr-nc-7.3:cisco-iosxr-nc-7.3";
  tailf:ncs-device-type "netconf";

  namespace "http://cisco.com/ns/yang/Cisco-IOS-XR-xrv9k-lpts-oper";
  prefix xrv9k-lpts-oper;

  import Cisco-IOS-XR-types {
    prefix xr;
  }
  import cisco-semver {
    prefix semver;
  }
  include Cisco-IOS-XR-xrv9k-lpts-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR xrv9k-lpts package operational data.

     This module contains definitions
     for the following management objects:
       platform-lptsp-ifib-static: ASR9K platform ifib operational
         data
       platform-lptsp-ifib: ASR9K platform ifib operational data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'platform-lptsp-ifib-static'
    // NCS drop config false container 'platform-lptsp-ifib'
  }
  augment "/ncs:devices/ncs:device/ncs:live-status" {
    container platform-lptsp-ifib-static {
      tailf:ncs-device-type "netconf";
      tailf:display-when "not(../../ncs:module) or ../../ncs:module[ncs:name='Cisco-IOS-XR-xrv9k-lpts-oper'] or (../../ncs:live-status-protocol[not(ncs:capability)]) or (../../ncs:live-status-protocol/ncs:capability/ncs:module[.='Cisco-IOS-XR-xrv9k-lpts-oper'])";
      description
        "ASR9K platform ifib operational data ";
      container node-statics {
        description
          "List of nodes with platform specific lpts
           operation data";
        list node-static {
          key "node-name";
          description
            "Node with platform specific lpts data";
          container stats {
            description
              "pl_pifib stats";
            uses live_ncs_PL-PIFIB-SHOW-STATS;
          }
          container police {
            description
              "pl_pifib police data";
            uses live_ncs_PL-PIFIB-SHOW-STATIC-POLICE;
          }
          leaf node-name {
            type xr:live_ncs_Node-id;
            description
              "Node name";
          }
        }
      }
    }
    container platform-lptsp-ifib {
      tailf:ncs-device-type "netconf";
      tailf:display-when "not(../../ncs:module) or ../../ncs:module[ncs:name='Cisco-IOS-XR-xrv9k-lpts-oper'] or (../../ncs:live-status-protocol[not(ncs:capability)]) or (../../ncs:live-status-protocol/ncs:capability/ncs:module[.='Cisco-IOS-XR-xrv9k-lpts-oper'])";
      description
        "ASR9K platform ifib operational data ";
      container nodes {
        description
          "List of nodes with platform specific lpts
           operation data";
        list node {
          key "node-name";
          description
            "Node with platform specific lpts data";
          container stats {
            description
              "pl_pifib stats";
            uses live_ncs_PL-PIFIB-SHOW-STATS;
          }
          container police {
            description
              "pl_pifib police data";
            uses live_ncs_PL-PIFIB-SHOW-POLICE;
          }
          leaf node-name {
            type xr:live_ncs_Node-id;
            description
              "Node name";
          }
        }
      }
    }
  }
  augment "/ncs:devices/ncs:template/ncs:ned-id/ncs:config" {
    // NCS drop config false container 'platform-lptsp-ifib-static'
    // NCS drop config false container 'platform-lptsp-ifib'
  }
}

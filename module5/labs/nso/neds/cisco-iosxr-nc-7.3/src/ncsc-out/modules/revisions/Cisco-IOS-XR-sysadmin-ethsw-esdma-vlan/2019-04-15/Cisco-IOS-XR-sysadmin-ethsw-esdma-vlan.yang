module Cisco-IOS-XR-sysadmin-ethsw-esdma-vlan {
  // Generated by yanger -t ncs
  tailf:mount-id "cisco-iosxr-nc-7.3:cisco-iosxr-nc-7.3";
  tailf:ncs-device-type "netconf";

  namespace "http://www.cisco.com/ns/yang/Cisco-IOS-XR-sysadmin-ethsw-esdma-vlan";
  prefix esdma_vlan;

  import Cisco-IOS-XR-sysadmin-ethsw-esdma-types {
    prefix esdma_types;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch vlan' commands.

     Copyright (c) 2011-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2016-07-06 {
    description
      "Initial revision with content extracted from esdma_cli.yang.";
  }

  grouping ncs_template_sdr-list-summary {
    list sdr-id {
      // NCS patched for predictable order
      ordered-by user;
      key "sdr";
      leaf sdr {
        type esdma_types:ncs_template_esdma-sdr-id;
      }
      leaf esd-sdr-name {
        type string;
      }
      list vlan-id {
        // NCS patched for predictable order
        ordered-by user;
        key "vlan";
        leaf vlan {
          type esdma_types:ncs_template_vlan-id-type;
        }
        leaf vlan-hex {
          type string;
        }
        leaf vlan-use {
          type string;
        }
      }
    }
  }

  grouping ncs_template_sdr-list {
    list sdr-id {
      // NCS patched for predictable order
      ordered-by user;
      key "sdr";
      leaf sdr {
        type esdma_types:ncs_template_esdma-sdr-id;
      }
      leaf esd-sdr-name {
        type string;
      }
      list vlan-id {
        // NCS patched for predictable order
        ordered-by user;
        key "vlan";
        leaf vlan {
          type esdma_types:ncs_template_vlan-id-type;
        }
        leaf vlan-hex {
          type string;
        }
        leaf vlan-use {
          type string;
        }
      }
    }
  }

  grouping ncs_template_vlan-information-group {
    container information {
      list location {
        // NCS patched for predictable order
        ordered-by user;
        key "rack card switch-id";
        leaf rack {
          type esdma_types:ncs_template_esdma-rack-num-enum;
        }
        leaf card {
          type esdma_types:ncs_template_esdma-cpu;
          description
            "Card to list the switch VLAN information for";
        }
        leaf switch-id {
          type esdma_types:ncs_template_esdma-switch-type-enum;
          description
            "Switch type";
        }
        leaf serial-num {
          type string;
          description
            "Rack serial number";
        }
        uses ncs_template_sdr-list;
      }
      container summary {
        uses ncs_template_sdr-list-summary;
      }
    }
  }

  grouping ncs_template_vlan-rule-info {
    list rule-id {
      // NCS patched for predictable order
      ordered-by user;
      leaf direction {
        type esdma_types:ncs_template_switch-data-direction-enum;
        description
          "Packet direction this rule applies to";
      }
      leaf match-table {
        type esdma_types:ncs_template_switch-table-type-enum;
      }
      leaf match-type {
        type esdma_types:ncs_template_switch-match-type-enum;
      }
      leaf match-vlan-id {
        type esdma_types:ncs_template_vlan-id-type;
      }
      leaf action {
        type esdma_types:ncs_template_switch-action-type-enum;
      }
      leaf action-vlan-id {
        type esdma_types:ncs_template_vlan-id-type;
      }
    }
  }

  grouping ncs_template_vlan-detail-group {
    container vlan-detail {
      list vlan-id {
        // NCS patched for predictable order
        ordered-by user;
        key "vlan";
        leaf vlan {
          type esdma_types:ncs_template_vlan-id-type;
        }
        container rules {
          list location {
            // NCS patched for predictable order
            ordered-by user;
            key "rack card switch-id";
            leaf rack {
              type esdma_types:ncs_template_esdma-rack-num-enum;
            }
            leaf card {
              type esdma_types:ncs_template_esdma-cpu;
              description
                "Card that owns a switch of interest";
            }
            leaf switch-id {
              type esdma_types:ncs_template_esdma-switch-type-enum;
              description
                "Switch type";
            }
            list port-iter {
              // NCS patched for predictable order
              ordered-by user;
              key "port";
              leaf port {
                type esdma_types:ncs_template_esdma-switch-port-type;
                description
                  "Switch port";
              }
              uses ncs_template_vlan-rule-info;
            }
          }
        }
      }
    }
  }

  grouping ncs_template_vlan-summary-group {
    container rules {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest to display the VLAN configuration for";
        }
        leaf switch-id {
          type esdma_types:ncs_template_esdma-switch-type-enum;
          description
            "Switch type";
        }
        list port-iter {
          // NCS patched for predictable order
          ordered-by user;
          key "port";
          leaf port {
            type esdma_types:ncs_template_esdma-switch-port-type;
            description
              "Switch port";
          }
          list vlan-id {
            // NCS patched for predictable order
            ordered-by user;
            key "vlan";
            leaf vlan {
              type esdma_types:ncs_template_vlan-id-type;
              description
                "This VLAN represents a VLAN membership for this switch port. Multiple rules may exist to support this VLAN.";
            }
            uses ncs_template_vlan-rule-info;
          }
        }
      }
    }
  }

  grouping ncs_template_vlan-membership-group {
    container membership {
      list location {
        // NCS patched for predictable order
        ordered-by user;
        key "rack card switch-id";
        leaf rack {
          type esdma_types:ncs_template_esdma-rack-num-enum;
        }
        leaf card {
          type esdma_types:ncs_template_esdma-cpu;
          description
            "Card that owns a switch of interest to display the VLAN configuration for";
        }
        leaf switch-id {
          type esdma_types:ncs_template_esdma-switch-type-enum;
          description
            "Switch type";
        }
        list vlan-id {
          // NCS patched for predictable order
          ordered-by user;
          key "vlan";
          leaf vlan {
            type esdma_types:ncs_template_vlan-id-type;
          }
          leaf vlan-hex {
            type string;
          }
          leaf-list port {
            // NCS patched for predictable order
            ordered-by user;
            type string;
          }
        }
      }
    }
  }

  grouping ncs_template_switch-vlan-group {
    container vlan {
      uses ncs_template_vlan-detail-group;
      uses ncs_template_vlan-summary-group;
      uses ncs_template_vlan-information-group;
      uses ncs_template_vlan-membership-group;
    }
  }

  grouping ncs_template_switch-vlan-group-ncs5500 {
    container vlan {
      uses ncs_template_vlan-information-group;
      uses ncs_template_vlan-membership-group;
    }
  }

  grouping ncs_rpc_notif_sdr-list-summary {
    list sdr-id {
      key "sdr";
      leaf sdr {
        type esdma_types:ncs_rpc_notif_esdma-sdr-id;
      }
      leaf esd-sdr-name {
        type string;
      }
      list vlan-id {
        key "vlan";
        leaf vlan {
          type esdma_types:ncs_rpc_notif_vlan-id-type;
        }
        leaf vlan-hex {
          type leafref {
            path "../vlan";
          }
        }
        leaf vlan-use {
          type string;
        }
      }
    }
  }

  grouping ncs_rpc_notif_sdr-list {
    list sdr-id {
      key "sdr";
      leaf sdr {
        type esdma_types:ncs_rpc_notif_esdma-sdr-id;
      }
      leaf esd-sdr-name {
        type string;
      }
      list vlan-id {
        key "vlan";
        leaf vlan {
          type esdma_types:ncs_rpc_notif_vlan-id-type;
        }
        leaf vlan-hex {
          type leafref {
            path "../vlan";
          }
        }
        leaf vlan-use {
          type string;
        }
      }
    }
  }

  grouping ncs_rpc_notif_vlan-information-group {
    container information {
      list location {
        key "rack card switch-id";
        leaf rack {
          type esdma_types:ncs_rpc_notif_esdma-rack-num-enum;
        }
        leaf card {
          type esdma_types:ncs_rpc_notif_esdma-cpu;
          description
            "Card to list the switch VLAN information for";
        }
        leaf switch-id {
          type esdma_types:ncs_rpc_notif_esdma-switch-type-enum;
          description
            "Switch type";
        }
        leaf serial-num {
          type string;
          description
            "Rack serial number";
        }
        uses ncs_rpc_notif_sdr-list;
      }
      container summary {
        uses ncs_rpc_notif_sdr-list-summary;
      }
    }
  }

  grouping ncs_rpc_notif_vlan-rule-info {
    list rule-id {
      leaf direction {
        type esdma_types:ncs_rpc_notif_switch-data-direction-enum;
        description
          "Packet direction this rule applies to";
      }
      leaf match-table {
        type esdma_types:ncs_rpc_notif_switch-table-type-enum;
      }
      leaf match-type {
        type esdma_types:ncs_rpc_notif_switch-match-type-enum;
      }
      leaf match-vlan-id {
        type esdma_types:ncs_rpc_notif_vlan-id-type;
      }
      leaf action {
        type esdma_types:ncs_rpc_notif_switch-action-type-enum;
      }
      leaf action-vlan-id {
        type esdma_types:ncs_rpc_notif_vlan-id-type;
      }
    }
  }

  grouping ncs_rpc_notif_vlan-detail-group {
    container vlan-detail {
      list vlan-id {
        key "vlan";
        leaf vlan {
          type esdma_types:ncs_rpc_notif_vlan-id-type;
        }
        container rules {
          list location {
            key "rack card switch-id";
            leaf rack {
              type esdma_types:ncs_rpc_notif_esdma-rack-num-enum;
            }
            leaf card {
              type esdma_types:ncs_rpc_notif_esdma-cpu;
              description
                "Card that owns a switch of interest";
            }
            leaf switch-id {
              type esdma_types:ncs_rpc_notif_esdma-switch-type-enum;
              description
                "Switch type";
            }
            list port-iter {
              key "port";
              leaf port {
                type esdma_types:ncs_rpc_notif_esdma-switch-port-type;
                description
                  "Switch port";
              }
              uses ncs_rpc_notif_vlan-rule-info;
            }
          }
        }
      }
    }
  }

  grouping ncs_rpc_notif_vlan-summary-group {
    container rules {
      list location {
        key "rack card switch-id";
        leaf rack {
          type esdma_types:ncs_rpc_notif_esdma-rack-num-enum;
        }
        leaf card {
          type esdma_types:ncs_rpc_notif_esdma-cpu;
          description
            "Card that owns a switch of interest to display the VLAN configuration for";
        }
        leaf switch-id {
          type esdma_types:ncs_rpc_notif_esdma-switch-type-enum;
          description
            "Switch type";
        }
        list port-iter {
          key "port";
          leaf port {
            type esdma_types:ncs_rpc_notif_esdma-switch-port-type;
            description
              "Switch port";
          }
          list vlan-id {
            key "vlan";
            leaf vlan {
              type esdma_types:ncs_rpc_notif_vlan-id-type;
              description
                "This VLAN represents a VLAN membership for this switch port. Multiple rules may exist to support this VLAN.";
            }
            uses ncs_rpc_notif_vlan-rule-info;
          }
        }
      }
    }
  }

  grouping ncs_rpc_notif_vlan-membership-group {
    container membership {
      list location {
        key "rack card switch-id";
        leaf rack {
          type esdma_types:ncs_rpc_notif_esdma-rack-num-enum;
        }
        leaf card {
          type esdma_types:ncs_rpc_notif_esdma-cpu;
          description
            "Card that owns a switch of interest to display the VLAN configuration for";
        }
        leaf switch-id {
          type esdma_types:ncs_rpc_notif_esdma-switch-type-enum;
          description
            "Switch type";
        }
        list vlan-id {
          key "vlan";
          leaf vlan {
            type esdma_types:ncs_rpc_notif_vlan-id-type;
          }
          leaf vlan-hex {
            type leafref {
              path "../vlan";
            }
          }
          leaf-list port {
            type uint8;
          }
        }
      }
    }
  }

  grouping ncs_rpc_notif_switch-vlan-group {
    container vlan {
      uses ncs_rpc_notif_vlan-detail-group;
      uses ncs_rpc_notif_vlan-summary-group;
      uses ncs_rpc_notif_vlan-information-group;
      uses ncs_rpc_notif_vlan-membership-group;
    }
  }

  grouping ncs_rpc_notif_switch-vlan-group-ncs5500 {
    container vlan {
      uses ncs_rpc_notif_vlan-information-group;
      uses ncs_rpc_notif_vlan-membership-group;
    }
  }

  grouping live_ncs_sdr-list-summary {
    list sdr-id {
      key "sdr";
      leaf sdr {
        type esdma_types:live_ncs_esdma-sdr-id;
      }
      leaf esd-sdr-name {
        type string;
      }
      list vlan-id {
        key "vlan";
        leaf vlan {
          type esdma_types:live_ncs_vlan-id-type;
        }
        leaf vlan-hex {
          type leafref {
            path "../vlan";
          }
        }
        leaf vlan-use {
          type string;
        }
      }
    }
  }

  grouping live_ncs_sdr-list {
    list sdr-id {
      key "sdr";
      leaf sdr {
        type esdma_types:live_ncs_esdma-sdr-id;
      }
      leaf esd-sdr-name {
        type string;
      }
      list vlan-id {
        key "vlan";
        leaf vlan {
          type esdma_types:live_ncs_vlan-id-type;
        }
        leaf vlan-hex {
          type leafref {
            path "../vlan";
          }
        }
        leaf vlan-use {
          type string;
        }
      }
    }
  }

  grouping live_ncs_vlan-information-group {
    container information {
      list location {
        key "rack card switch-id";
        leaf rack {
          type esdma_types:live_ncs_esdma-rack-num-enum;
        }
        leaf card {
          type esdma_types:live_ncs_esdma-cpu;
          description
            "Card to list the switch VLAN information for";
        }
        leaf switch-id {
          type esdma_types:live_ncs_esdma-switch-type-enum;
          description
            "Switch type";
        }
        leaf serial-num {
          type string;
          description
            "Rack serial number";
        }
        uses live_ncs_sdr-list;
      }
      container summary {
        uses live_ncs_sdr-list-summary;
      }
    }
  }

  grouping live_ncs_vlan-rule-info {
    list rule-id {
      leaf direction {
        type esdma_types:live_ncs_switch-data-direction-enum;
        description
          "Packet direction this rule applies to";
      }
      leaf match-table {
        type esdma_types:live_ncs_switch-table-type-enum;
      }
      leaf match-type {
        type esdma_types:live_ncs_switch-match-type-enum;
      }
      leaf match-vlan-id {
        type esdma_types:live_ncs_vlan-id-type;
      }
      leaf action {
        type esdma_types:live_ncs_switch-action-type-enum;
      }
      leaf action-vlan-id {
        type esdma_types:live_ncs_vlan-id-type;
      }
    }
  }

  grouping live_ncs_vlan-detail-group {
    container vlan-detail {
      list vlan-id {
        key "vlan";
        leaf vlan {
          type esdma_types:live_ncs_vlan-id-type;
        }
        container rules {
          list location {
            key "rack card switch-id";
            leaf rack {
              type esdma_types:live_ncs_esdma-rack-num-enum;
            }
            leaf card {
              type esdma_types:live_ncs_esdma-cpu;
              description
                "Card that owns a switch of interest";
            }
            leaf switch-id {
              type esdma_types:live_ncs_esdma-switch-type-enum;
              description
                "Switch type";
            }
            list port-iter {
              key "port";
              leaf port {
                type esdma_types:live_ncs_esdma-switch-port-type;
                description
                  "Switch port";
              }
              uses live_ncs_vlan-rule-info;
            }
          }
        }
      }
    }
  }

  grouping live_ncs_vlan-summary-group {
    container rules {
      list location {
        key "rack card switch-id";
        leaf rack {
          type esdma_types:live_ncs_esdma-rack-num-enum;
        }
        leaf card {
          type esdma_types:live_ncs_esdma-cpu;
          description
            "Card that owns a switch of interest to display the VLAN configuration for";
        }
        leaf switch-id {
          type esdma_types:live_ncs_esdma-switch-type-enum;
          description
            "Switch type";
        }
        list port-iter {
          key "port";
          leaf port {
            type esdma_types:live_ncs_esdma-switch-port-type;
            description
              "Switch port";
          }
          list vlan-id {
            key "vlan";
            leaf vlan {
              type esdma_types:live_ncs_vlan-id-type;
              description
                "This VLAN represents a VLAN membership for this switch port. Multiple rules may exist to support this VLAN.";
            }
            uses live_ncs_vlan-rule-info;
          }
        }
      }
    }
  }

  grouping live_ncs_vlan-membership-group {
    container membership {
      list location {
        key "rack card switch-id";
        leaf rack {
          type esdma_types:live_ncs_esdma-rack-num-enum;
        }
        leaf card {
          type esdma_types:live_ncs_esdma-cpu;
          description
            "Card that owns a switch of interest to display the VLAN configuration for";
        }
        leaf switch-id {
          type esdma_types:live_ncs_esdma-switch-type-enum;
          description
            "Switch type";
        }
        list vlan-id {
          key "vlan";
          leaf vlan {
            type esdma_types:live_ncs_vlan-id-type;
          }
          leaf vlan-hex {
            type leafref {
              path "../vlan";
            }
          }
          leaf-list port {
            type uint8;
          }
        }
      }
    }
  }

  grouping live_ncs_switch-vlan-group {
    container vlan {
      uses live_ncs_vlan-detail-group;
      uses live_ncs_vlan-summary-group;
      uses live_ncs_vlan-information-group;
      uses live_ncs_vlan-membership-group;
    }
  }

  grouping live_ncs_switch-vlan-group-ncs5500 {
    container vlan {
      uses live_ncs_vlan-information-group;
      uses live_ncs_vlan-membership-group;
    }
  }

  grouping sdr-list-summary {
    list sdr-id {
      key "sdr";
      leaf sdr {
        type esdma_types:esdma-sdr-id;
      }
      leaf esd-sdr-name {
        type string;
      }
      list vlan-id {
        key "vlan";
        leaf vlan {
          type esdma_types:vlan-id-type;
        }
        leaf vlan-hex {
          type leafref {
            path "../vlan";
          }
        }
        leaf vlan-use {
          type string;
        }
      }
    }
  }

  grouping sdr-list {
    list sdr-id {
      key "sdr";
      leaf sdr {
        type esdma_types:esdma-sdr-id;
      }
      leaf esd-sdr-name {
        type string;
      }
      list vlan-id {
        key "vlan";
        leaf vlan {
          type esdma_types:vlan-id-type;
        }
        leaf vlan-hex {
          type leafref {
            path "../vlan";
          }
        }
        leaf vlan-use {
          type string;
        }
      }
    }
  }

  grouping vlan-information-group {
    container information {
      list location {
        key "rack card switch-id";
        leaf rack {
          type esdma_types:esdma-rack-num-enum;
        }
        leaf card {
          type esdma_types:esdma-cpu;
          description
            "Card to list the switch VLAN information for";
        }
        leaf switch-id {
          type esdma_types:esdma-switch-type-enum;
          description
            "Switch type";
        }
        leaf serial-num {
          type string;
          description
            "Rack serial number";
        }
        uses sdr-list;
      }
      container summary {
        uses sdr-list-summary;
      }
    }
  }

  grouping vlan-rule-info {
    list rule-id {
      leaf direction {
        type esdma_types:switch-data-direction-enum;
        description
          "Packet direction this rule applies to";
      }
      leaf match-table {
        type esdma_types:switch-table-type-enum;
      }
      leaf match-type {
        type esdma_types:switch-match-type-enum;
      }
      leaf match-vlan-id {
        type esdma_types:vlan-id-type;
      }
      leaf action {
        type esdma_types:switch-action-type-enum;
      }
      leaf action-vlan-id {
        type esdma_types:vlan-id-type;
      }
    }
  }

  grouping vlan-detail-group {
    container vlan-detail {
      list vlan-id {
        key "vlan";
        leaf vlan {
          type esdma_types:vlan-id-type;
        }
        container rules {
          list location {
            key "rack card switch-id";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              leaf port {
                type esdma_types:esdma-switch-port-type;
                description
                  "Switch port";
              }
              uses vlan-rule-info;
            }
          }
        }
      }
    }
  }

  grouping vlan-summary-group {
    container rules {
      list location {
        key "rack card switch-id";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list port-iter {
          key "port";
          leaf port {
            type esdma_types:esdma-switch-port-type;
            description
              "Switch port";
          }
          list vlan-id {
            key "vlan";
            leaf vlan {
              type esdma_types:vlan-id-type;
              description
                "This VLAN represents a VLAN membership for this switch port. Multiple rules may exist to support this VLAN.";
            }
            uses vlan-rule-info;
          }
        }
      }
    }
  }

  grouping vlan-membership-group {
    container membership {
      list location {
        key "rack card switch-id";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list vlan-id {
          key "vlan";
          leaf vlan {
            type esdma_types:vlan-id-type;
          }
          leaf vlan-hex {
            type leafref {
              path "../vlan";
            }
          }
          leaf-list port {
            type uint8;
          }
        }
      }
    }
  }

  grouping switch-vlan-group {
    container vlan {
      uses vlan-detail-group;
      uses vlan-summary-group;
      uses vlan-information-group;
      uses vlan-membership-group;
    }
  }

  grouping switch-vlan-group-ncs5500 {
    container vlan {
      uses vlan-information-group;
      uses vlan-membership-group;
    }
  }
}

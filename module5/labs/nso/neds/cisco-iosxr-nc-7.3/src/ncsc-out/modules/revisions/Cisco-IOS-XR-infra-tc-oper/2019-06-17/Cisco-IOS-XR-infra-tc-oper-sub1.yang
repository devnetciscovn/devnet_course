submodule Cisco-IOS-XR-infra-tc-oper-sub1 {
  // Generated by yanger -t ncs
  tailf:mount-id "cisco-iosxr-nc-7.3:cisco-iosxr-nc-7.3";

  belongs-to Cisco-IOS-XR-infra-tc-oper {
    prefix Cisco-IOS-XR-infra-tc-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR infra-tc package operational data.

     Copyright (c) 2013-2019 by Cisco Systems, Inc.
     All rights reserved.";

  revision 2019-06-17 {
    description
      "Change type of tunnel interface name to string";
    semver:module-version "1.0.0";
  }
  revision 2019-05-30 {
    description
      "Fix to extend range of valid OC-AFT Labels";
  }
  revision 2019-04-05 {
    description
      "Establish semantic version baseline.";
  }
  revision 2019-01-01 {
    description
      "Yang evaluator: updates to schema descriptions.";
  }
  revision 2018-11-30 {
    description
      "Adding label data and total count stats for OC-AFT.";
  }
  revision 2018-10-05 {
    description
      "Removed stat collection message statistics. LDP label is provided in prefix info if present.";
  }
  revision 2015-11-09 {
    description
      "IOS XR 6.0 revision.";
  }

  grouping ncs_template_TC-MGMT-MSG-STAT {
    description
      "TC Server Message Statistics";
    leaf packet-sent {
      type string;
      description
        "Number of packets sent";
    }
    leaf byte-sent {
      type string;
      units "byte";
      description
        "Number of bytes sent";
    }
    leaf packet-received {
      type string;
      description
        "Number of packets received";
    }
    leaf byte-received {
      type string;
      units "byte";
      description
        "Number of bytes received";
    }
    leaf maximum-roundtrip-latency {
      type string;
      description
        "Maximum message roundtrip latency in msec";
    }
    leaf maimum-latency-timestamp {
      type string;
      description
        "Timestamp of maximum latency";
    }
  }

  grouping ncs_template_TC-MGMT-VRF-STAT {
    description
      "Statistics on VRF Table and its sub-tables";
    container database-statistics-ipv4 {
      description
        "Database statistics for IPv4 table";
      uses ncs_template_TC-MGMT-DB-STAT;
    }
    container database-statistics-tunnel {
      description
        "Database statistics for Tunnel table";
      uses ncs_template_TC-MGMT-DB-STAT;
    }
    leaf vrf-name {
      type string;
      description
        "VRF name";
    }
  }

  grouping ncs_template_TC-MGMT-DB-STAT {
    description
      "Database statistics";
    leaf number-of-entries {
      type string;
      description
        "Number of entries in the database";
    }
    leaf number-of-stale-entries {
      type string;
      description
        "Number of stale entries in the database";
    }
    leaf number-of-add-operations {
      type string;
      description
        "Number of add operations for the database";
    }
    leaf number-of-delete-operations {
      type string;
      description
        "Number of delete operations for the database";
    }
  }

  grouping ncs_template_TC-MGMT-SUMMARY {
    description
      "TC Server Summary";
    container database-statistics-external-interface {
      description
        "Configured external interface counts";
      uses ncs_template_TC-MGMT-DB-STAT;
    }
    leaf collection-interval {
      type string;
      units "minute";
      description
        "Statistic collection interval in minutes";
    }
    leaf collection-timer-is-running {
      type string;
      description
        "Flag to indicate if collection timer is running";
    }
    leaf timeout-interval {
      type string;
      units "hour";
      description
        "Statistic history timeout interval in hours";
    }
    leaf timeout-timer-is-running {
      type string;
      description
        "Flag to indicate if history timeout timer is
         running";
    }
    leaf history-size {
      type string;
      description
        "Statistics history size";
    }
    leaf total-prefix-count {
      type string;
      description
        "Total count of prefix entries";
    }
    list vrf-statistic {
      // NCS patched for predictable order
      ordered-by user;
      description
        "VRF table statistics";
      uses ncs_template_TC-MGMT-VRF-STAT;
    }
    list checkpoint-message-statistic {
      // NCS patched for predictable order
      ordered-by user;
      description
        "Statistics per message type for Chkpt";
      uses ncs_template_TC-MGMT-MSG-STAT;
    }
  }

  grouping ncs_template_TC-MGMT-EXT-IF-DATA {
    description
      "TC Server external interface data";
    leaf interface-name-xr {
      type string;
      description
        "Interface name in Display format";
    }
    leaf interface-handle {
      type string;
      description
        "Interface handle for the external interface";
    }
    leaf vrfid {
      type string;
      description
        "Interface VRF ID";
    }
    leaf is-interface-enabled {
      type string;
      description
        "Flag to indicate interface enabled or not";
    }
  }

  grouping ncs_template_TC-MGMT-OCAFT-SUMMARY {
    description
      "TC oc-aft Server Summary";
    leaf collection-interval {
      type string;
      units "minute";
      description
        "Statistic collection interval in minutes";
    }
    leaf collection-timer-is-running {
      type string;
      description
        "Flag to indicate if collection timer is running";
    }
    leaf total-label-count {
      type string;
      description
        "Total count of oc-aft label entries";
    }
  }

  grouping ncs_template_TC-MGMT-TUNNEL-DATA {
    description
      "TC Server tunnel data";
    container base-counter-statistics {
      description
        "Base counter statistics for the tunnel";
      uses ncs_template_TC-MGMT-COUNT-STATS;
    }
    leaf interface-name-xr {
      type string;
      description
        "Interface name in Display format";
    }
    leaf interface-handle {
      type string;
      description
        "Interface handle for the tunnel";
    }
    leaf vrfid {
      type string;
      description
        "Interface VRF ID";
    }
    leaf is-active {
      type string;
      description
        "Interface is Active and collecting new
         Statistics";
    }
  }

  grouping ncs_template_TC-MGMT-COUNT-HISTORY {
    description
      "TC Server counter statistics";
    leaf event-start-timestamp {
      type string;
      description
        "Time when the collection interval started";
    }
    leaf event-end-timestamp {
      type string;
      description
        "Time when the collection interval ended";
    }
    leaf transmit-number-of-packets-switched {
      type string;
      description
        "Number of packets switched in this interval";
    }
    leaf transmit-number-of-bytes-switched {
      type string;
      units "byte";
      description
        "Number of Bytes switched in this interval";
    }
    leaf is-valid {
      type string;
      description
        "Flag to indicate if this history entry is valid";
    }
  }

  grouping ncs_template_TC-MGMT-COUNT-STATS {
    description
      "TC Server counter statistics";
    leaf transmit-packets-per-second-switched {
      type string;
      units "packet/s";
      description
        "Average Rate of Packets/second switched";
    }
    leaf transmit-bytes-per-second-switched {
      type string;
      units "byte/s";
      description
        "Average Rate of Bytes/second switched";
    }
    list count-history {
      // NCS patched for predictable order
      ordered-by user;
      description
        "Counter History";
      uses ncs_template_TC-MGMT-COUNT-HISTORY;
    }
  }

  grouping ncs_template_TC-MGMT-PREFIX-DATA {
    description
      "TC Server Prefix data";
    container base-counter-statistics {
      description
        "Base counter statistics for the prefix";
      uses ncs_template_TC-MGMT-COUNT-STATS;
    }
    container traffic-matrix-counter-statistics {
      description
        "Traffic Matrix (TM) counter statistics for the
         prefix";
      uses ncs_template_TC-MGMT-COUNT-STATS;
    }
    leaf prefix {
      type string;
      description
        "Prefix Address (V4 or V6 Format)";
    }
    leaf label-xr {
      type string;
      description
        "SR Label";
    }
    leaf ldp-label {
      type string;
      description
        "LDP Label";
    }
    leaf is-active {
      type string;
      description
        "Prefix is Active and collecting new Statistics";
    }
  }

  grouping ncs_template_TC-MGMT-COUNT-TOTAL {
    description
      "TC Server total counts";
    leaf last-collection-time {
      type string;
      description
        "Last time the stats were collected";
    }
    leaf transmit-packets-switched {
      type string;
      description
        "Total Packets switched";
    }
    leaf transmit-bytes-switched {
      type string;
      units "byte";
      description
        "Total Bytes switched";
    }
  }

  grouping ncs_template_TC-MGMT-LABEL-DATA {
    description
      "TC Server Label data";
    container base-counter-total {
      description
        "Base counter total bytes/packets";
      uses ncs_template_TC-MGMT-COUNT-TOTAL;
    }
    leaf label-xr {
      type string;
      description
        "Label";
    }
    leaf is-active {
      type string;
      description
        "Label is Active and collecting new Statistics";
    }
  }

  grouping ncs_rpc_notif_TC-MGMT-MSG-STAT {
    description
      "TC Server Message Statistics";
    leaf packet-sent {
      type uint64;
      description
        "Number of packets sent";
    }
    leaf byte-sent {
      type uint64;
      units "byte";
      description
        "Number of bytes sent";
    }
    leaf packet-received {
      type uint64;
      description
        "Number of packets received";
    }
    leaf byte-received {
      type uint64;
      units "byte";
      description
        "Number of bytes received";
    }
    leaf maximum-roundtrip-latency {
      type uint32;
      description
        "Maximum message roundtrip latency in msec";
    }
    leaf maimum-latency-timestamp {
      type uint64;
      description
        "Timestamp of maximum latency";
    }
  }

  grouping ncs_rpc_notif_TC-MGMT-VRF-STAT {
    description
      "Statistics on VRF Table and its sub-tables";
    container database-statistics-ipv4 {
      description
        "Database statistics for IPv4 table";
      uses ncs_rpc_notif_TC-MGMT-DB-STAT;
    }
    container database-statistics-tunnel {
      description
        "Database statistics for Tunnel table";
      uses ncs_rpc_notif_TC-MGMT-DB-STAT;
    }
    leaf vrf-name {
      type string;
      description
        "VRF name";
    }
  }

  grouping ncs_rpc_notif_TC-MGMT-DB-STAT {
    description
      "Database statistics";
    leaf number-of-entries {
      type uint32;
      description
        "Number of entries in the database";
    }
    leaf number-of-stale-entries {
      type uint32;
      description
        "Number of stale entries in the database";
    }
    leaf number-of-add-operations {
      type uint64;
      description
        "Number of add operations for the database";
    }
    leaf number-of-delete-operations {
      type uint64;
      description
        "Number of delete operations for the database";
    }
  }

  grouping ncs_rpc_notif_TC-MGMT-SUMMARY {
    description
      "TC Server Summary";
    container database-statistics-external-interface {
      description
        "Configured external interface counts";
      uses ncs_rpc_notif_TC-MGMT-DB-STAT;
    }
    leaf collection-interval {
      type uint8;
      units "minute";
      description
        "Statistic collection interval in minutes";
    }
    leaf collection-timer-is-running {
      type boolean;
      description
        "Flag to indicate if collection timer is running";
    }
    leaf timeout-interval {
      type uint16;
      units "hour";
      description
        "Statistic history timeout interval in hours";
    }
    leaf timeout-timer-is-running {
      type boolean;
      description
        "Flag to indicate if history timeout timer is
         running";
    }
    leaf history-size {
      type uint8;
      description
        "Statistics history size";
    }
    leaf total-prefix-count {
      type uint32;
      description
        "Total count of prefix entries";
    }
    list vrf-statistic {
      description
        "VRF table statistics";
      uses ncs_rpc_notif_TC-MGMT-VRF-STAT;
    }
    list checkpoint-message-statistic {
      description
        "Statistics per message type for Chkpt";
      uses ncs_rpc_notif_TC-MGMT-MSG-STAT;
    }
  }

  grouping ncs_rpc_notif_TC-MGMT-EXT-IF-DATA {
    description
      "TC Server external interface data";
    leaf interface-name-xr {
      type string;
      description
        "Interface name in Display format";
    }
    leaf interface-handle {
      type uint32;
      description
        "Interface handle for the external interface";
    }
    leaf vrfid {
      type uint32;
      description
        "Interface VRF ID";
    }
    leaf is-interface-enabled {
      type boolean;
      description
        "Flag to indicate interface enabled or not";
    }
  }

  grouping ncs_rpc_notif_TC-MGMT-OCAFT-SUMMARY {
    description
      "TC oc-aft Server Summary";
    leaf collection-interval {
      type uint8;
      units "minute";
      description
        "Statistic collection interval in minutes";
    }
    leaf collection-timer-is-running {
      type boolean;
      description
        "Flag to indicate if collection timer is running";
    }
    leaf total-label-count {
      type uint32;
      description
        "Total count of oc-aft label entries";
    }
  }

  grouping ncs_rpc_notif_TC-MGMT-TUNNEL-DATA {
    description
      "TC Server tunnel data";
    container base-counter-statistics {
      description
        "Base counter statistics for the tunnel";
      uses ncs_rpc_notif_TC-MGMT-COUNT-STATS;
    }
    leaf interface-name-xr {
      type string;
      description
        "Interface name in Display format";
    }
    leaf interface-handle {
      type uint32;
      description
        "Interface handle for the tunnel";
    }
    leaf vrfid {
      type uint32;
      description
        "Interface VRF ID";
    }
    leaf is-active {
      type boolean;
      description
        "Interface is Active and collecting new
         Statistics";
    }
  }

  grouping ncs_rpc_notif_TC-MGMT-COUNT-HISTORY {
    description
      "TC Server counter statistics";
    leaf event-start-timestamp {
      type uint64;
      description
        "Time when the collection interval started";
    }
    leaf event-end-timestamp {
      type uint64;
      description
        "Time when the collection interval ended";
    }
    leaf transmit-number-of-packets-switched {
      type uint64;
      description
        "Number of packets switched in this interval";
    }
    leaf transmit-number-of-bytes-switched {
      type uint64;
      units "byte";
      description
        "Number of Bytes switched in this interval";
    }
    leaf is-valid {
      type boolean;
      description
        "Flag to indicate if this history entry is valid";
    }
  }

  grouping ncs_rpc_notif_TC-MGMT-COUNT-STATS {
    description
      "TC Server counter statistics";
    leaf transmit-packets-per-second-switched {
      type uint64;
      units "packet/s";
      description
        "Average Rate of Packets/second switched";
    }
    leaf transmit-bytes-per-second-switched {
      type uint64;
      units "byte/s";
      description
        "Average Rate of Bytes/second switched";
    }
    list count-history {
      description
        "Counter History";
      uses ncs_rpc_notif_TC-MGMT-COUNT-HISTORY;
    }
  }

  grouping ncs_rpc_notif_TC-MGMT-PREFIX-DATA {
    description
      "TC Server Prefix data";
    container base-counter-statistics {
      description
        "Base counter statistics for the prefix";
      uses ncs_rpc_notif_TC-MGMT-COUNT-STATS;
    }
    container traffic-matrix-counter-statistics {
      description
        "Traffic Matrix (TM) counter statistics for the
         prefix";
      uses ncs_rpc_notif_TC-MGMT-COUNT-STATS;
    }
    leaf prefix {
      type string;
      description
        "Prefix Address (V4 or V6 Format)";
    }
    leaf label-xr {
      type uint32;
      description
        "SR Label";
    }
    leaf ldp-label {
      type uint32;
      description
        "LDP Label";
    }
    leaf is-active {
      type boolean;
      description
        "Prefix is Active and collecting new Statistics";
    }
  }

  grouping ncs_rpc_notif_TC-MGMT-COUNT-TOTAL {
    description
      "TC Server total counts";
    leaf last-collection-time {
      type uint64;
      description
        "Last time the stats were collected";
    }
    leaf transmit-packets-switched {
      type uint64;
      description
        "Total Packets switched";
    }
    leaf transmit-bytes-switched {
      type uint64;
      units "byte";
      description
        "Total Bytes switched";
    }
  }

  grouping ncs_rpc_notif_TC-MGMT-LABEL-DATA {
    description
      "TC Server Label data";
    container base-counter-total {
      description
        "Base counter total bytes/packets";
      uses ncs_rpc_notif_TC-MGMT-COUNT-TOTAL;
    }
    leaf label-xr {
      type uint32;
      description
        "Label";
    }
    leaf is-active {
      type boolean;
      description
        "Label is Active and collecting new Statistics";
    }
  }

  grouping live_ncs_TC-MGMT-MSG-STAT {
    description
      "TC Server Message Statistics";
    leaf packet-sent {
      type uint64;
      description
        "Number of packets sent";
    }
    leaf byte-sent {
      type uint64;
      units "byte";
      description
        "Number of bytes sent";
    }
    leaf packet-received {
      type uint64;
      description
        "Number of packets received";
    }
    leaf byte-received {
      type uint64;
      units "byte";
      description
        "Number of bytes received";
    }
    leaf maximum-roundtrip-latency {
      type uint32;
      description
        "Maximum message roundtrip latency in msec";
    }
    leaf maimum-latency-timestamp {
      type uint64;
      description
        "Timestamp of maximum latency";
    }
  }

  grouping live_ncs_TC-MGMT-VRF-STAT {
    description
      "Statistics on VRF Table and its sub-tables";
    container database-statistics-ipv4 {
      description
        "Database statistics for IPv4 table";
      uses live_ncs_TC-MGMT-DB-STAT;
    }
    container database-statistics-tunnel {
      description
        "Database statistics for Tunnel table";
      uses live_ncs_TC-MGMT-DB-STAT;
    }
    leaf vrf-name {
      type string;
      description
        "VRF name";
    }
  }

  grouping live_ncs_TC-MGMT-DB-STAT {
    description
      "Database statistics";
    leaf number-of-entries {
      type uint32;
      description
        "Number of entries in the database";
    }
    leaf number-of-stale-entries {
      type uint32;
      description
        "Number of stale entries in the database";
    }
    leaf number-of-add-operations {
      type uint64;
      description
        "Number of add operations for the database";
    }
    leaf number-of-delete-operations {
      type uint64;
      description
        "Number of delete operations for the database";
    }
  }

  grouping live_ncs_TC-MGMT-SUMMARY {
    description
      "TC Server Summary";
    container database-statistics-external-interface {
      description
        "Configured external interface counts";
      uses live_ncs_TC-MGMT-DB-STAT;
    }
    leaf collection-interval {
      type uint8;
      units "minute";
      description
        "Statistic collection interval in minutes";
    }
    leaf collection-timer-is-running {
      type boolean;
      description
        "Flag to indicate if collection timer is running";
    }
    leaf timeout-interval {
      type uint16;
      units "hour";
      description
        "Statistic history timeout interval in hours";
    }
    leaf timeout-timer-is-running {
      type boolean;
      description
        "Flag to indicate if history timeout timer is
         running";
    }
    leaf history-size {
      type uint8;
      description
        "Statistics history size";
    }
    leaf total-prefix-count {
      type uint32;
      description
        "Total count of prefix entries";
    }
    list vrf-statistic {
      description
        "VRF table statistics";
      uses live_ncs_TC-MGMT-VRF-STAT;
    }
    list checkpoint-message-statistic {
      description
        "Statistics per message type for Chkpt";
      uses live_ncs_TC-MGMT-MSG-STAT;
    }
  }

  grouping live_ncs_TC-MGMT-EXT-IF-DATA {
    description
      "TC Server external interface data";
    leaf interface-name-xr {
      type string;
      description
        "Interface name in Display format";
    }
    leaf interface-handle {
      type uint32;
      description
        "Interface handle for the external interface";
    }
    leaf vrfid {
      type uint32;
      description
        "Interface VRF ID";
    }
    leaf is-interface-enabled {
      type boolean;
      description
        "Flag to indicate interface enabled or not";
    }
  }

  grouping live_ncs_TC-MGMT-OCAFT-SUMMARY {
    description
      "TC oc-aft Server Summary";
    leaf collection-interval {
      type uint8;
      units "minute";
      description
        "Statistic collection interval in minutes";
    }
    leaf collection-timer-is-running {
      type boolean;
      description
        "Flag to indicate if collection timer is running";
    }
    leaf total-label-count {
      type uint32;
      description
        "Total count of oc-aft label entries";
    }
  }

  grouping live_ncs_TC-MGMT-TUNNEL-DATA {
    description
      "TC Server tunnel data";
    container base-counter-statistics {
      description
        "Base counter statistics for the tunnel";
      uses live_ncs_TC-MGMT-COUNT-STATS;
    }
    leaf interface-name-xr {
      type string;
      description
        "Interface name in Display format";
    }
    leaf interface-handle {
      type uint32;
      description
        "Interface handle for the tunnel";
    }
    leaf vrfid {
      type uint32;
      description
        "Interface VRF ID";
    }
    leaf is-active {
      type boolean;
      description
        "Interface is Active and collecting new
         Statistics";
    }
  }

  grouping live_ncs_TC-MGMT-COUNT-HISTORY {
    description
      "TC Server counter statistics";
    leaf event-start-timestamp {
      type uint64;
      description
        "Time when the collection interval started";
    }
    leaf event-end-timestamp {
      type uint64;
      description
        "Time when the collection interval ended";
    }
    leaf transmit-number-of-packets-switched {
      type uint64;
      description
        "Number of packets switched in this interval";
    }
    leaf transmit-number-of-bytes-switched {
      type uint64;
      units "byte";
      description
        "Number of Bytes switched in this interval";
    }
    leaf is-valid {
      type boolean;
      description
        "Flag to indicate if this history entry is valid";
    }
  }

  grouping live_ncs_TC-MGMT-COUNT-STATS {
    description
      "TC Server counter statistics";
    leaf transmit-packets-per-second-switched {
      type uint64;
      units "packet/s";
      description
        "Average Rate of Packets/second switched";
    }
    leaf transmit-bytes-per-second-switched {
      type uint64;
      units "byte/s";
      description
        "Average Rate of Bytes/second switched";
    }
    list count-history {
      description
        "Counter History";
      uses live_ncs_TC-MGMT-COUNT-HISTORY;
    }
  }

  grouping live_ncs_TC-MGMT-PREFIX-DATA {
    description
      "TC Server Prefix data";
    container base-counter-statistics {
      description
        "Base counter statistics for the prefix";
      uses live_ncs_TC-MGMT-COUNT-STATS;
    }
    container traffic-matrix-counter-statistics {
      description
        "Traffic Matrix (TM) counter statistics for the
         prefix";
      uses live_ncs_TC-MGMT-COUNT-STATS;
    }
    leaf prefix {
      type string;
      description
        "Prefix Address (V4 or V6 Format)";
    }
    leaf label-xr {
      type uint32;
      description
        "SR Label";
    }
    leaf ldp-label {
      type uint32;
      description
        "LDP Label";
    }
    leaf is-active {
      type boolean;
      description
        "Prefix is Active and collecting new Statistics";
    }
  }

  grouping live_ncs_TC-MGMT-COUNT-TOTAL {
    description
      "TC Server total counts";
    leaf last-collection-time {
      type uint64;
      description
        "Last time the stats were collected";
    }
    leaf transmit-packets-switched {
      type uint64;
      description
        "Total Packets switched";
    }
    leaf transmit-bytes-switched {
      type uint64;
      units "byte";
      description
        "Total Bytes switched";
    }
  }

  grouping live_ncs_TC-MGMT-LABEL-DATA {
    description
      "TC Server Label data";
    container base-counter-total {
      description
        "Base counter total bytes/packets";
      uses live_ncs_TC-MGMT-COUNT-TOTAL;
    }
    leaf label-xr {
      type uint32;
      description
        "Label";
    }
    leaf is-active {
      type boolean;
      description
        "Label is Active and collecting new Statistics";
    }
  }

  grouping TC-MGMT-MSG-STAT {
    description
      "TC Server Message Statistics";
    leaf packet-sent {
      type uint64;
      description
        "Number of packets sent";
    }
    leaf byte-sent {
      type uint64;
      units "byte";
      description
        "Number of bytes sent";
    }
    leaf packet-received {
      type uint64;
      description
        "Number of packets received";
    }
    leaf byte-received {
      type uint64;
      units "byte";
      description
        "Number of bytes received";
    }
    leaf maximum-roundtrip-latency {
      type uint32;
      description
        "Maximum message roundtrip latency in msec";
    }
    leaf maimum-latency-timestamp {
      type uint64;
      description
        "Timestamp of maximum latency";
    }
  }

  grouping TC-MGMT-VRF-STAT {
    description
      "Statistics on VRF Table and its sub-tables";
    container database-statistics-ipv4 {
      description
        "Database statistics for IPv4 table";
      uses TC-MGMT-DB-STAT;
    }
    container database-statistics-tunnel {
      description
        "Database statistics for Tunnel table";
      uses TC-MGMT-DB-STAT;
    }
    leaf vrf-name {
      type string;
      description
        "VRF name";
    }
  }

  grouping TC-MGMT-DB-STAT {
    description
      "Database statistics";
    leaf number-of-entries {
      type uint32;
      description
        "Number of entries in the database";
    }
    leaf number-of-stale-entries {
      type uint32;
      description
        "Number of stale entries in the database";
    }
    leaf number-of-add-operations {
      type uint64;
      description
        "Number of add operations for the database";
    }
    leaf number-of-delete-operations {
      type uint64;
      description
        "Number of delete operations for the database";
    }
  }

  grouping TC-MGMT-SUMMARY {
    description
      "TC Server Summary";
    container database-statistics-external-interface {
      description
        "Configured external interface counts";
      uses TC-MGMT-DB-STAT;
    }
    leaf collection-interval {
      type uint8;
      units "minute";
      description
        "Statistic collection interval in minutes";
    }
    leaf collection-timer-is-running {
      type boolean;
      description
        "Flag to indicate if collection timer is running";
    }
    leaf timeout-interval {
      type uint16;
      units "hour";
      description
        "Statistic history timeout interval in hours";
    }
    leaf timeout-timer-is-running {
      type boolean;
      description
        "Flag to indicate if history timeout timer is
         running";
    }
    leaf history-size {
      type uint8;
      description
        "Statistics history size";
    }
    leaf total-prefix-count {
      type uint32;
      description
        "Total count of prefix entries";
    }
    list vrf-statistic {
      description
        "VRF table statistics";
      uses TC-MGMT-VRF-STAT;
    }
    list checkpoint-message-statistic {
      description
        "Statistics per message type for Chkpt";
      uses TC-MGMT-MSG-STAT;
    }
  }

  grouping TC-MGMT-EXT-IF-DATA {
    description
      "TC Server external interface data";
    leaf interface-name-xr {
      type string;
      description
        "Interface name in Display format";
    }
    leaf interface-handle {
      type uint32;
      description
        "Interface handle for the external interface";
    }
    leaf vrfid {
      type uint32;
      description
        "Interface VRF ID";
    }
    leaf is-interface-enabled {
      type boolean;
      description
        "Flag to indicate interface enabled or not";
    }
  }

  grouping TC-MGMT-OCAFT-SUMMARY {
    description
      "TC oc-aft Server Summary";
    leaf collection-interval {
      type uint8;
      units "minute";
      description
        "Statistic collection interval in minutes";
    }
    leaf collection-timer-is-running {
      type boolean;
      description
        "Flag to indicate if collection timer is running";
    }
    leaf total-label-count {
      type uint32;
      description
        "Total count of oc-aft label entries";
    }
  }

  grouping TC-MGMT-TUNNEL-DATA {
    description
      "TC Server tunnel data";
    container base-counter-statistics {
      description
        "Base counter statistics for the tunnel";
      uses TC-MGMT-COUNT-STATS;
    }
    leaf interface-name-xr {
      type string;
      description
        "Interface name in Display format";
    }
    leaf interface-handle {
      type uint32;
      description
        "Interface handle for the tunnel";
    }
    leaf vrfid {
      type uint32;
      description
        "Interface VRF ID";
    }
    leaf is-active {
      type boolean;
      description
        "Interface is Active and collecting new
         Statistics";
    }
  }

  grouping TC-MGMT-COUNT-HISTORY {
    description
      "TC Server counter statistics";
    leaf event-start-timestamp {
      type uint64;
      description
        "Time when the collection interval started";
    }
    leaf event-end-timestamp {
      type uint64;
      description
        "Time when the collection interval ended";
    }
    leaf transmit-number-of-packets-switched {
      type uint64;
      description
        "Number of packets switched in this interval";
    }
    leaf transmit-number-of-bytes-switched {
      type uint64;
      units "byte";
      description
        "Number of Bytes switched in this interval";
    }
    leaf is-valid {
      type boolean;
      description
        "Flag to indicate if this history entry is valid";
    }
  }

  grouping TC-MGMT-COUNT-STATS {
    description
      "TC Server counter statistics";
    leaf transmit-packets-per-second-switched {
      type uint64;
      units "packet/s";
      description
        "Average Rate of Packets/second switched";
    }
    leaf transmit-bytes-per-second-switched {
      type uint64;
      units "byte/s";
      description
        "Average Rate of Bytes/second switched";
    }
    list count-history {
      description
        "Counter History";
      uses TC-MGMT-COUNT-HISTORY;
    }
  }

  grouping TC-MGMT-PREFIX-DATA {
    description
      "TC Server Prefix data";
    container base-counter-statistics {
      description
        "Base counter statistics for the prefix";
      uses TC-MGMT-COUNT-STATS;
    }
    container traffic-matrix-counter-statistics {
      description
        "Traffic Matrix (TM) counter statistics for the
         prefix";
      uses TC-MGMT-COUNT-STATS;
    }
    leaf prefix {
      type string;
      description
        "Prefix Address (V4 or V6 Format)";
    }
    leaf label-xr {
      type uint32;
      description
        "SR Label";
    }
    leaf ldp-label {
      type uint32;
      description
        "LDP Label";
    }
    leaf is-active {
      type boolean;
      description
        "Prefix is Active and collecting new Statistics";
    }
  }

  grouping TC-MGMT-COUNT-TOTAL {
    description
      "TC Server total counts";
    leaf last-collection-time {
      type uint64;
      description
        "Last time the stats were collected";
    }
    leaf transmit-packets-switched {
      type uint64;
      description
        "Total Packets switched";
    }
    leaf transmit-bytes-switched {
      type uint64;
      units "byte";
      description
        "Total Bytes switched";
    }
  }

  grouping TC-MGMT-LABEL-DATA {
    description
      "TC Server Label data";
    container base-counter-total {
      description
        "Base counter total bytes/packets";
      uses TC-MGMT-COUNT-TOTAL;
    }
    leaf label-xr {
      type uint32;
      description
        "Label";
    }
    leaf is-active {
      type boolean;
      description
        "Label is Active and collecting new Statistics";
    }
  }
}

module Cisco-IOS-XR-freqsync-sat-cfg {
  // Generated by yanger -t ncs
  tailf:mount-id "cisco-iosxr-nc-7.3:cisco-iosxr-nc-7.3";
  tailf:ncs-device-type "netconf";

  namespace "http://cisco.com/ns/yang/Cisco-IOS-XR-freqsync-sat-cfg";
  prefix freqsync-sat-cfg;

  import cisco-semver {
    prefix semver;
  }
  import Cisco-IOS-XR-ifmgr-cfg {
    prefix a1;
  }
  import Cisco-IOS-XR-l2-eth-infra-cfg {
    prefix a2;
  }
  import Cisco-IOS-XR-icpe-infra-cfg {
    prefix a3;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR freqsync-sat package configuration.

     This YANG module augments the
       Cisco-IOS-XR-ifmgr-cfg,
       Cisco-IOS-XR-l2-eth-infra-cfg,
       Cisco-IOS-XR-icpe-infra-cfg
     modules with configuration data.

     Copyright (c) 2013-2020 by Cisco Systems, Inc.
     All rights reserved.";

  revision 2020-01-31 {
    description
      "Added submode-enter Enable handling.";
    semver:module-version "1.0.0";
  }
  revision 2019-04-05 {
    description
      "Establish semantic version baseline.";
  }
  revision 2015-11-09 {
    description
      "IOS XR 6.0 revision.";
  }

  augment "/ncs:devices/ncs:template/ncs:ned-id/ncs:config/a1:interface-configurations/a1:interface-configuration/a3:nv-satellite-fabric-link" {
    description
      "This augment extends the configuration data of
       'Cisco-IOS-XR-icpe-infra-cfg'";
    container frequency-synchronization {
      presence "CLI submode compatibility.";
      description
        "Frequency Synchronization satellite
         configuration";
      leaf enable {
        type empty;
        description
          "Enable Frequency Synchronization";
      }
    }
  }
  augment "/ncs:devices/ncs:device/ncs:live-status/a1:interface-configurations/a1:interface-configuration/a3:nv-satellite-fabric-link" {
    description
      "This augment extends the configuration data of
       'Cisco-IOS-XR-icpe-infra-cfg'";
    container frequency-synchronization {
      tailf:ncs-device-type "netconf";
      tailf:display-when "not(../../../../../ncs:module) or ../../../../../ncs:module[ncs:name='Cisco-IOS-XR-freqsync-sat-cfg'] or (../../../../../ncs:live-status-protocol[not(ncs:capability)]) or (../../../../../ncs:live-status-protocol/ncs:capability/ncs:module[.='Cisco-IOS-XR-freqsync-sat-cfg'])";
      presence "CLI submode compatibility.";
      description
        "Frequency Synchronization satellite
         configuration";
      leaf enable {
        type empty;
        description
          "Enable Frequency Synchronization";
      }
    }
  }
  augment "/ncs:devices/ncs:device/ncs:config/a1:interface-configurations/a1:interface-configuration/a3:nv-satellite-fabric-link" {
    description
      "This augment extends the configuration data of
       'Cisco-IOS-XR-icpe-infra-cfg'";
    container frequency-synchronization {
      tailf:ncs-device-type "netconf";
      tailf:display-when "not(../../../../../ncs:module) or ../../../../../ncs:module[ncs:name='Cisco-IOS-XR-freqsync-sat-cfg']";
      presence "CLI submode compatibility.";
      description
        "Frequency Synchronization satellite
         configuration";
      leaf enable {
        type empty;
        description
          "Enable Frequency Synchronization";
      }
    }
  }
}

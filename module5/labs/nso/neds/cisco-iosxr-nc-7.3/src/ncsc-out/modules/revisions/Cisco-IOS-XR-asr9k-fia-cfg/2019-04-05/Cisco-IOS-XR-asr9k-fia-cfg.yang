module Cisco-IOS-XR-asr9k-fia-cfg {
  // Generated by yanger -t ncs
  tailf:mount-id "cisco-iosxr-nc-7.3:cisco-iosxr-nc-7.3";
  tailf:ncs-device-type "netconf";

  namespace "http://cisco.com/ns/yang/Cisco-IOS-XR-asr9k-fia-cfg";
  prefix asr9k-fia-cfg;

  import Cisco-IOS-XR-config-mda-cfg {
    prefix node;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-fia package configuration.

     This module contains definitions
     for the following management objects:
       fabric-fia-config: Configure Global Fabric Fia Settings

     This YANG module augments the
       Cisco-IOS-XR-config-mda-cfg
     module with configuration data.

     Copyright (c) 2013-2019 by Cisco Systems, Inc.
     All rights reserved.";

  revision 2019-04-05 {
    description
      "Establish semantic version baseline.";
    semver:module-version "1.0.0";
  }
  revision 2017-08-17 {
    description
      "IOS XR 6.4.1 revision.";
  }
  revision 2015-11-09 {
    description
      "IOS XR 6.0 revision.";
  }

  grouping ncs_template_NODE-CFG {
    description
      "active/preconfigured nodes configuration";
    container fia-buffer-profile-cfg {
      description
        "Fia Buffer Profile configuration";
      leaf xl {
        type string;
        description
          "Enable to use Extra large Buffer profile";
      }
    }
    container fia-vqi-shaper-cfg {
      description
        "Fia VQI Shaper configuration";
      leaf enhance {
        type string;
        description
          "Enable to use Enhanced VQI shaper limit";
      }
    }
    container port-queue-remaps {
      description
        "Remap front panel port to fabric queue for
         A9K-48X10GE-1G-xx and A9K-24X10GE-1G-xx ";
      list port-queue-remap {
        // NCS patched for predictable order
        ordered-by user;
        key "port";
        description
          "Front panel port number";
        leaf fabric-queue {
          type string;
          description
            "queue number <0-19>";
        }
        leaf port {
          type string;
          description
            "port number <10,11,22,23 34,35,46,47>";
        }
      }
    }
  }

  grouping ncs_rpc_notif_NODE-CFG {
    description
      "active/preconfigured nodes configuration";
    container fia-buffer-profile-cfg {
      description
        "Fia Buffer Profile configuration";
      leaf xl {
        type boolean;
        description
          "Enable to use Extra large Buffer profile";
      }
    }
    container fia-vqi-shaper-cfg {
      description
        "Fia VQI Shaper configuration";
      leaf enhance {
        type boolean;
        description
          "Enable to use Enhanced VQI shaper limit";
      }
    }
    container port-queue-remaps {
      description
        "Remap front panel port to fabric queue for
         A9K-48X10GE-1G-xx and A9K-24X10GE-1G-xx ";
      list port-queue-remap {
        key "port";
        description
          "Front panel port number";
        leaf fabric-queue {
          type uint32 {
            range "0..19";
          }
          description
            "queue number <0-19>";
        }
        leaf port {
          type uint32 {
            range "0..47";
          }
          description
            "port number <10,11,22,23 34,35,46,47>";
        }
      }
    }
  }

  grouping live_ncs_NODE-CFG {
    description
      "active/preconfigured nodes configuration";
    container fia-buffer-profile-cfg {
      description
        "Fia Buffer Profile configuration";
      leaf xl {
        type boolean;
        description
          "Enable to use Extra large Buffer profile";
      }
    }
    container fia-vqi-shaper-cfg {
      description
        "Fia VQI Shaper configuration";
      leaf enhance {
        type boolean;
        description
          "Enable to use Enhanced VQI shaper limit";
      }
    }
    container port-queue-remaps {
      description
        "Remap front panel port to fabric queue for
         A9K-48X10GE-1G-xx and A9K-24X10GE-1G-xx ";
      list port-queue-remap {
        key "port";
        description
          "Front panel port number";
        leaf fabric-queue {
          type uint32 {
            range "0..19";
          }
          description
            "queue number <0-19>";
        }
        leaf port {
          type uint32 {
            range "0..47";
          }
          description
            "port number <10,11,22,23 34,35,46,47>";
        }
      }
    }
  }

  grouping NODE-CFG {
    description
      "active/preconfigured nodes configuration";
    container fia-buffer-profile-cfg {
      description
        "Fia Buffer Profile configuration";
      leaf xl {
        type boolean;
        description
          "Enable to use Extra large Buffer profile";
      }
    }
    container fia-vqi-shaper-cfg {
      description
        "Fia VQI Shaper configuration";
      leaf enhance {
        type boolean;
        description
          "Enable to use Enhanced VQI shaper limit";
      }
    }
    container port-queue-remaps {
      description
        "Remap front panel port to fabric queue for
         A9K-48X10GE-1G-xx and A9K-24X10GE-1G-xx ";
      list port-queue-remap {
        key "port";
        description
          "Front panel port number";
        leaf fabric-queue {
          type uint32 {
            range "0..19";
          }
          description
            "queue number <0-19>";
        }
        leaf port {
          type uint32 {
            range "0..47";
          }
          description
            "port number <10,11,22,23 34,35,46,47>";
        }
      }
    }
  }

  augment "/ncs:devices/ncs:device/ncs:config" {
    container fabric-fia-config {
      tailf:ncs-device-type "netconf";
      tailf:display-when "not(../../ncs:module) or ../../ncs:module[ncs:name='Cisco-IOS-XR-asr9k-fia-cfg']";
      description
        "Configure Global Fabric Fia Settings";
      container fia-intf-policer {
        description
          "FIA interface rate-limiter on 7-Fabric LC";
        leaf disable {
          type boolean;
          description
            "disable FIA interface policer ";
        }
      }
    }
  }
  augment "/ncs:devices/ncs:device/ncs:live-status" {
    container fabric-fia-config {
      tailf:ncs-device-type "netconf";
      tailf:display-when "not(../../ncs:module) or ../../ncs:module[ncs:name='Cisco-IOS-XR-asr9k-fia-cfg'] or (../../ncs:live-status-protocol[not(ncs:capability)]) or (../../ncs:live-status-protocol/ncs:capability/ncs:module[.='Cisco-IOS-XR-asr9k-fia-cfg'])";
      description
        "Configure Global Fabric Fia Settings";
      container fia-intf-policer {
        description
          "FIA interface rate-limiter on 7-Fabric LC";
        leaf disable {
          type boolean;
          description
            "disable FIA interface policer ";
        }
      }
    }
  }
  augment "/ncs:devices/ncs:template/ncs:ned-id/ncs:config" {
    container fabric-fia-config {
      description
        "Configure Global Fabric Fia Settings";
      container fia-intf-policer {
        description
          "FIA interface rate-limiter on 7-Fabric LC";
        leaf disable {
          type string;
          description
            "disable FIA interface policer ";
        }
      }
    }
  }
  augment "/ncs:devices/ncs:template/ncs:ned-id/ncs:config/node:active-nodes/node:active-node" {
    description
      "This augment extends active nodes configuration";
    uses ncs_template_NODE-CFG;
  }
  augment "/ncs:devices/ncs:device/ncs:live-status/node:active-nodes/node:active-node" {
    description
      "This augment extends active nodes configuration";
    uses live_ncs_NODE-CFG {
      refine port-queue-remaps {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
      refine fia-vqi-shaper-cfg {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
      refine fia-buffer-profile-cfg {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
    }
  }
  augment "/ncs:devices/ncs:device/ncs:config/node:active-nodes/node:active-node" {
    description
      "This augment extends active nodes configuration";
    uses NODE-CFG {
      refine port-queue-remaps {
        tailf:ncs-device-type "netconf";
        tailf:display-when "not(../../../../ncs:module) or ../../../../ncs:module[ncs:name='Cisco-IOS-XR-asr9k-fia-cfg']";
      }
      refine fia-vqi-shaper-cfg {
        tailf:ncs-device-type "netconf";
        tailf:display-when "not(../../../../ncs:module) or ../../../../ncs:module[ncs:name='Cisco-IOS-XR-asr9k-fia-cfg']";
      }
      refine fia-buffer-profile-cfg {
        tailf:ncs-device-type "netconf";
        tailf:display-when "not(../../../../ncs:module) or ../../../../ncs:module[ncs:name='Cisco-IOS-XR-asr9k-fia-cfg']";
      }
    }
  }
  augment "/ncs:devices/ncs:template/ncs:ned-id/ncs:config/node:preconfigured-nodes/node:preconfigured-node" {
    description
      "This augment extends preconfigured nodes
       configuration";
    uses ncs_template_NODE-CFG;
  }
  augment "/ncs:devices/ncs:device/ncs:live-status/node:preconfigured-nodes/node:preconfigured-node" {
    description
      "This augment extends preconfigured nodes
       configuration";
    uses live_ncs_NODE-CFG {
      refine port-queue-remaps {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
      refine fia-vqi-shaper-cfg {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
      refine fia-buffer-profile-cfg {
        tailf:ncs-device-type "netconf";
        tailf:display-when "not(../../../../ncs:module) or ../../../../ncs:module[ncs:name='Cisco-IOS-XR-asr9k-fia-cfg'] or (../../../../ncs:live-status-protocol[not(ncs:capability)]) or (../../../../ncs:live-status-protocol/ncs:capability/ncs:module[.='Cisco-IOS-XR-asr9k-fia-cfg'])";
      }
    }
  }
  augment "/ncs:devices/ncs:device/ncs:config/node:preconfigured-nodes/node:preconfigured-node" {
    description
      "This augment extends preconfigured nodes
       configuration";
    uses NODE-CFG {
      refine port-queue-remaps {
        tailf:ncs-device-type "netconf";
        tailf:display-when "not(../../../../ncs:module) or ../../../../ncs:module[ncs:name='Cisco-IOS-XR-asr9k-fia-cfg']";
      }
      refine fia-vqi-shaper-cfg {
        tailf:ncs-device-type "netconf";
        tailf:display-when "not(../../../../ncs:module) or ../../../../ncs:module[ncs:name='Cisco-IOS-XR-asr9k-fia-cfg']";
      }
      refine fia-buffer-profile-cfg {
        tailf:ncs-device-type "netconf";
        tailf:display-when "not(../../../../ncs:module) or ../../../../ncs:module[ncs:name='Cisco-IOS-XR-asr9k-fia-cfg']";
      }
    }
  }
}

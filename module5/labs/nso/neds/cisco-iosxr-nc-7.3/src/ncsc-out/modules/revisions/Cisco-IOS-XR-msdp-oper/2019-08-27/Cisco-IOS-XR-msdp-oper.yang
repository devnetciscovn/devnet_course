module Cisco-IOS-XR-msdp-oper {
  // Generated by yanger -t ncs
  tailf:mount-id "cisco-iosxr-nc-7.3:cisco-iosxr-nc-7.3";
  tailf:ncs-device-type "netconf";

  namespace "http://cisco.com/ns/yang/Cisco-IOS-XR-msdp-oper";
  prefix msdp-oper;

  import ietf-inet-types {
    prefix inet;
  }
  import Cisco-IOS-XR-types {
    prefix xr;
  }
  import cisco-semver {
    prefix semver;
  }
  include Cisco-IOS-XR-msdp-oper-sub1 {
    revision-date 2019-08-27;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR msdp package operational data.

     This module contains definitions
     for the following management objects:
       msdp: MSDP operational data

     Copyright (c) 2013-2019 by Cisco Systems, Inc.
     All rights reserved.";

  revision 2019-08-27 {
    description
      "Providing MSDP information.";
    semver:module-version "1.0.0";
  }
  revision 2019-04-05 {
    description
      "Establish semantic version baseline.";
  }
  revision 2015-11-09 {
    description
      "IOS XR 6.0 revision.";
  }

  typedef ncs_template_Bgp-asn-plain {
    type string;
    description
      "Bgp asn plain";
  }

  typedef ncs_rpc_notif_Bgp-asn-plain {
    type uint32 {
      range "1..4294967295";
    }
    description
      "Bgp asn plain";
  }

  typedef live_ncs_Bgp-asn-plain {
    type uint32 {
      range "1..4294967295";
    }
    description
      "Bgp asn plain";
  }

  typedef Bgp-asn-plain {
    type uint32 {
      range "1..4294967295";
    }
    description
      "Bgp asn plain";
  }

  grouping ncs_template_PEER-TABLE {
    description
      "Common node of default-context, vrf";
    container peers {
      description
        "MSDP Peers";
      list peer {
        // NCS patched for predictable order
        ordered-by user;
        key "peer-address";
        description
          "MSDP Peer Info";
        leaf peer-address {
          type string;
          description
            "Peer Address";
        }
        uses ncs_template_MSDP-PEER-BAG;
      }
    }
  }

  grouping ncs_template_VRF-TABLE {
    description
      "Common node of active, standby";
    container vrfs {
      description
        "VRF Table";
      list vrf {
        // NCS patched for predictable order
        ordered-by user;
        key "vrf-name";
        description
          "VRF Name";
        leaf vrf-name {
          type xr:ncs_template_Cisco-ios-xr-string;
          description
            "VRF name";
        }
        uses ncs_template_STAT-PEER-TABLE;
        uses ncs_template_PEER-TABLE;
        uses ncs_template_PEER-SUMMARY-TABLE;
        uses ncs_template_SA-CACHE-TABLE;
        uses ncs_template_RPF-TABLE;
        uses ncs_template_ROUTING-CONTEXT;
        uses ncs_template_CACHE-SUMMARY;
        uses ncs_template_ALL-SA-CACHE-TABLE;
        uses ncs_template_AS-SOURCE-GROUP-SA-CACHE-TABLE;
        uses ncs_template_RP-SOURCE-GROUP-SA-CACHE-TABLE;
      }
    }
  }

  grouping ncs_template_SA-CACHE-TABLE {
    description
      "Common node of default-context, vrf";
    container sa-caches {
      description
        "MSDP SA Cache table - sources with Local &
         External flags Set";
      list sa-cache {
        // NCS patched for predictable order
        ordered-by user;
        key "source-address group-address";
        description
          "MSDP SA Cache Entry - Sources with Local &
           External flags set";
        leaf source-address {
          type string;
          description
            "Previous Source Address";
        }
        leaf group-address {
          type string;
          description
            "Previous Group Address";
        }
        uses ncs_template_MSDP-SRC-BAG;
      }
    }
  }

  grouping ncs_template_AS-SOURCE-GROUP-SA-CACHE-TABLE {
    description
      "Common node of default-context, vrf";
    container as-source-group-sa-caches {
      description
        "AS Filtered MSDP SA Cache table";
      list as-source-group-sa-cache {
        // NCS patched for predictable order
        ordered-by user;
        key "as source-address group-address";
        description
          "AS Filtered MSDP SA Cache Entries";
        leaf as {
          type ncs_template_Bgp-asn-plain;
          description
            "AS Number";
        }
        leaf source-address {
          type string;
          description
            "Source Address";
        }
        leaf group-address {
          type string;
          description
            "Group Address";
        }
        uses ncs_template_MSDP-SRC-BAG;
      }
    }
  }

  grouping ncs_template_ALL-SA-CACHE-TABLE {
    description
      "Common node of default-context, vrf";
    container all-sa-caches {
      description
        "All of MSDP SA Cache ignoring source flags";
      list all-sa-cache {
        // NCS patched for predictable order
        ordered-by user;
        key "source-address group-address";
        description
          "MSDP All SA Cache Entries ignoring source flags";
        leaf source-address {
          type string;
          description
            "Source Address";
        }
        leaf group-address {
          type string;
          description
            "Group Address";
        }
        uses ncs_template_MSDP-SRC-BAG;
      }
    }
  }

  grouping ncs_template_PROCESS {
    description
      "Common node of active, standby";
    container process {
      description
        "Process";
      container globals {
        description
          "MSDP Global Data";
        uses ncs_template_MSDP-GLOBAL-BAG;
      }
      container nsf {
        description
          "NSF Information";
        uses ncs_template_MSDP-EDM-NSF-BAG;
      }
      container summary {
        description
          "MSDP Process Summary Info";
        uses ncs_template_MSDP-PROCESS-SUMM-BAG;
      }
      container nsr {
        description
          "NSR Information";
        uses ncs_template_MSDP-NSR-BAG;
      }
    }
  }

  grouping ncs_template_RPF-TABLE {
    description
      "Common node of default-context, vrf";
    container rpfs {
      description
        "MSDP Reverse Path Forwarding Info";
      list rpf {
        // NCS patched for predictable order
        ordered-by user;
        key "rp-address";
        description
          "MSDP Reverse Path Forwarding entries";
        leaf rp-address {
          type string;
          description
            "RP Address";
        }
        uses ncs_template_MSDP-RPF-BAG;
      }
    }
  }

  grouping ncs_template_RP-SOURCE-GROUP-SA-CACHE-TABLE {
    description
      "Common node of default-context, vrf";
    container rp-source-group-sa-caches {
      description
        "RP Filtered MSDP SA Cache table";
      list rp-source-group-sa-cache {
        // NCS patched for predictable order
        ordered-by user;
        key "rp-address source-address group-address";
        description
          "RP Filtered MSDP SA Cache Entries";
        leaf rp-address {
          type string;
          description
            "RP Address";
        }
        leaf source-address {
          type string;
          description
            "Source Address";
        }
        leaf group-address {
          type string;
          description
            "Group Address";
        }
        uses ncs_template_MSDP-SRC-BAG;
      }
    }
  }

  grouping ncs_template_CACHE-SUMMARY {
    description
      "Common node of default-context, vrf";
    container cache-summary {
      description
        "Cache Summary";
      container rp-cache-summaries {
        description
          "RP specific Cache Summary Table";
        list rp-cache-summary {
          // NCS patched for predictable order
          ordered-by user;
          key "rp-address";
          description
            "Cache Summary RP";
          leaf rp-address {
            type string;
            description
              "RP Address";
          }
          uses ncs_template_MSDP-SUMMARY-RP-BAG;
        }
      }
      container cache-summary-preface {
        description
          "Cache Summary Preface";
        uses ncs_template_MSDP-SUMMARY-PREFACE-BAG;
      }
      container as-cache-summaries {
        description
          "AS specific Cache Summary Table";
        list as-cache-summary {
          // NCS patched for predictable order
          ordered-by user;
          key "as";
          description
            "Cache Summary AS";
          leaf as {
            type ncs_template_Bgp-asn-plain;
            description
              "AS Number";
          }
          uses ncs_template_MSDP-SUMMARY-AS-BAG;
        }
      }
    }
  }

  grouping ncs_template_ROUTING-CONTEXT {
    description
      "Common node of default-context, vrf";
    container routing-context {
      description
        "MSDP routing context";
      uses ncs_template_MSDP-CONTEXT;
    }
  }

  grouping ncs_template_STAT-PEER-TABLE {
    description
      "Common node of default-context, vrf";
    container stat-peers {
      description
        "Statistics for MSDP Peers";
      list stat-peer {
        // NCS patched for predictable order
        ordered-by user;
        key "peer-address";
        description
          "MSDP Peer Statistics Info";
        leaf peer-address {
          type string;
          description
            "Peer Address";
        }
        uses ncs_template_MSDP-STATS-PEER-BAG;
      }
    }
  }

  grouping ncs_template_DEFAULT-CONTEXT {
    description
      "Common node of active, standby";
    container default-context {
      description
        "Default Context";
      uses ncs_template_STAT-PEER-TABLE;
      uses ncs_template_PEER-TABLE;
      uses ncs_template_PEER-SUMMARY-TABLE;
      uses ncs_template_SA-CACHE-TABLE;
      uses ncs_template_RPF-TABLE;
      uses ncs_template_ROUTING-CONTEXT;
      uses ncs_template_CACHE-SUMMARY;
      uses ncs_template_ALL-SA-CACHE-TABLE;
      uses ncs_template_AS-SOURCE-GROUP-SA-CACHE-TABLE;
      uses ncs_template_RP-SOURCE-GROUP-SA-CACHE-TABLE;
    }
  }

  grouping ncs_template_PEER-SUMMARY-TABLE {
    description
      "Common node of default-context, vrf";
    container peer-summaries {
      description
        "MSDP Peers summary";
      list peer-summary {
        // NCS patched for predictable order
        ordered-by user;
        key "peer-address";
        description
          "MSDP Peer Summary Info";
        leaf peer-address {
          type string;
          description
            "Peer Address";
        }
        uses ncs_template_MSDP-PEER-SUMM-BAG;
      }
    }
  }

  grouping ncs_rpc_notif_PEER-TABLE {
    description
      "Common node of default-context, vrf";
    container peers {
      description
        "MSDP Peers";
      list peer {
        key "peer-address";
        description
          "MSDP Peer Info";
        leaf peer-address {
          type inet:ipv4-address-no-zone;
          description
            "Peer Address";
        }
        uses ncs_rpc_notif_MSDP-PEER-BAG;
      }
    }
  }

  grouping ncs_rpc_notif_VRF-TABLE {
    description
      "Common node of active, standby";
    container vrfs {
      description
        "VRF Table";
      list vrf {
        key "vrf-name";
        description
          "VRF Name";
        leaf vrf-name {
          type xr:ncs_rpc_notif_Cisco-ios-xr-string;
          description
            "VRF name";
        }
        uses ncs_rpc_notif_STAT-PEER-TABLE;
        uses ncs_rpc_notif_PEER-TABLE;
        uses ncs_rpc_notif_PEER-SUMMARY-TABLE;
        uses ncs_rpc_notif_SA-CACHE-TABLE;
        uses ncs_rpc_notif_RPF-TABLE;
        uses ncs_rpc_notif_ROUTING-CONTEXT;
        uses ncs_rpc_notif_CACHE-SUMMARY;
        uses ncs_rpc_notif_ALL-SA-CACHE-TABLE;
        uses ncs_rpc_notif_AS-SOURCE-GROUP-SA-CACHE-TABLE;
        uses ncs_rpc_notif_RP-SOURCE-GROUP-SA-CACHE-TABLE;
      }
    }
  }

  grouping ncs_rpc_notif_SA-CACHE-TABLE {
    description
      "Common node of default-context, vrf";
    container sa-caches {
      description
        "MSDP SA Cache table - sources with Local &
         External flags Set";
      list sa-cache {
        key "source-address group-address";
        description
          "MSDP SA Cache Entry - Sources with Local &
           External flags set";
        leaf source-address {
          type inet:ipv4-address-no-zone;
          description
            "Previous Source Address";
        }
        leaf group-address {
          type inet:ipv4-address-no-zone;
          description
            "Previous Group Address";
        }
        uses ncs_rpc_notif_MSDP-SRC-BAG;
      }
    }
  }

  grouping ncs_rpc_notif_AS-SOURCE-GROUP-SA-CACHE-TABLE {
    description
      "Common node of default-context, vrf";
    container as-source-group-sa-caches {
      description
        "AS Filtered MSDP SA Cache table";
      list as-source-group-sa-cache {
        key "as source-address group-address";
        description
          "AS Filtered MSDP SA Cache Entries";
        leaf as {
          type ncs_rpc_notif_Bgp-asn-plain;
          description
            "AS Number";
        }
        leaf source-address {
          type inet:ipv4-address-no-zone;
          description
            "Source Address";
        }
        leaf group-address {
          type inet:ipv4-address-no-zone;
          description
            "Group Address";
        }
        uses ncs_rpc_notif_MSDP-SRC-BAG;
      }
    }
  }

  grouping ncs_rpc_notif_ALL-SA-CACHE-TABLE {
    description
      "Common node of default-context, vrf";
    container all-sa-caches {
      description
        "All of MSDP SA Cache ignoring source flags";
      list all-sa-cache {
        key "source-address group-address";
        description
          "MSDP All SA Cache Entries ignoring source flags";
        leaf source-address {
          type inet:ipv4-address-no-zone;
          description
            "Source Address";
        }
        leaf group-address {
          type inet:ipv4-address-no-zone;
          description
            "Group Address";
        }
        uses ncs_rpc_notif_MSDP-SRC-BAG;
      }
    }
  }

  grouping ncs_rpc_notif_PROCESS {
    description
      "Common node of active, standby";
    container process {
      description
        "Process";
      container globals {
        description
          "MSDP Global Data";
        uses ncs_rpc_notif_MSDP-GLOBAL-BAG;
      }
      container nsf {
        description
          "NSF Information";
        uses ncs_rpc_notif_MSDP-EDM-NSF-BAG;
      }
      container summary {
        description
          "MSDP Process Summary Info";
        uses ncs_rpc_notif_MSDP-PROCESS-SUMM-BAG;
      }
      container nsr {
        description
          "NSR Information";
        uses ncs_rpc_notif_MSDP-NSR-BAG;
      }
    }
  }

  grouping ncs_rpc_notif_RPF-TABLE {
    description
      "Common node of default-context, vrf";
    container rpfs {
      description
        "MSDP Reverse Path Forwarding Info";
      list rpf {
        key "rp-address";
        description
          "MSDP Reverse Path Forwarding entries";
        leaf rp-address {
          type inet:ipv4-address-no-zone;
          description
            "RP Address";
        }
        uses ncs_rpc_notif_MSDP-RPF-BAG;
      }
    }
  }

  grouping ncs_rpc_notif_RP-SOURCE-GROUP-SA-CACHE-TABLE {
    description
      "Common node of default-context, vrf";
    container rp-source-group-sa-caches {
      description
        "RP Filtered MSDP SA Cache table";
      list rp-source-group-sa-cache {
        key "rp-address source-address group-address";
        description
          "RP Filtered MSDP SA Cache Entries";
        leaf rp-address {
          type inet:ipv4-address-no-zone;
          description
            "RP Address";
        }
        leaf source-address {
          type inet:ipv4-address-no-zone;
          description
            "Source Address";
        }
        leaf group-address {
          type inet:ipv4-address-no-zone;
          description
            "Group Address";
        }
        uses ncs_rpc_notif_MSDP-SRC-BAG;
      }
    }
  }

  grouping ncs_rpc_notif_CACHE-SUMMARY {
    description
      "Common node of default-context, vrf";
    container cache-summary {
      description
        "Cache Summary";
      container rp-cache-summaries {
        description
          "RP specific Cache Summary Table";
        list rp-cache-summary {
          key "rp-address";
          description
            "Cache Summary RP";
          leaf rp-address {
            type inet:ipv4-address-no-zone;
            description
              "RP Address";
          }
          uses ncs_rpc_notif_MSDP-SUMMARY-RP-BAG;
        }
      }
      container cache-summary-preface {
        description
          "Cache Summary Preface";
        uses ncs_rpc_notif_MSDP-SUMMARY-PREFACE-BAG;
      }
      container as-cache-summaries {
        description
          "AS specific Cache Summary Table";
        list as-cache-summary {
          key "as";
          description
            "Cache Summary AS";
          leaf as {
            type ncs_rpc_notif_Bgp-asn-plain;
            description
              "AS Number";
          }
          uses ncs_rpc_notif_MSDP-SUMMARY-AS-BAG;
        }
      }
    }
  }

  grouping ncs_rpc_notif_ROUTING-CONTEXT {
    description
      "Common node of default-context, vrf";
    container routing-context {
      description
        "MSDP routing context";
      uses ncs_rpc_notif_MSDP-CONTEXT;
    }
  }

  grouping ncs_rpc_notif_STAT-PEER-TABLE {
    description
      "Common node of default-context, vrf";
    container stat-peers {
      description
        "Statistics for MSDP Peers";
      list stat-peer {
        key "peer-address";
        description
          "MSDP Peer Statistics Info";
        leaf peer-address {
          type inet:ip-address-no-zone;
          description
            "Peer Address";
        }
        uses ncs_rpc_notif_MSDP-STATS-PEER-BAG;
      }
    }
  }

  grouping ncs_rpc_notif_DEFAULT-CONTEXT {
    description
      "Common node of active, standby";
    container default-context {
      description
        "Default Context";
      uses ncs_rpc_notif_STAT-PEER-TABLE;
      uses ncs_rpc_notif_PEER-TABLE;
      uses ncs_rpc_notif_PEER-SUMMARY-TABLE;
      uses ncs_rpc_notif_SA-CACHE-TABLE;
      uses ncs_rpc_notif_RPF-TABLE;
      uses ncs_rpc_notif_ROUTING-CONTEXT;
      uses ncs_rpc_notif_CACHE-SUMMARY;
      uses ncs_rpc_notif_ALL-SA-CACHE-TABLE;
      uses ncs_rpc_notif_AS-SOURCE-GROUP-SA-CACHE-TABLE;
      uses ncs_rpc_notif_RP-SOURCE-GROUP-SA-CACHE-TABLE;
    }
  }

  grouping ncs_rpc_notif_PEER-SUMMARY-TABLE {
    description
      "Common node of default-context, vrf";
    container peer-summaries {
      description
        "MSDP Peers summary";
      list peer-summary {
        key "peer-address";
        description
          "MSDP Peer Summary Info";
        leaf peer-address {
          type inet:ipv4-address-no-zone;
          description
            "Peer Address";
        }
        uses ncs_rpc_notif_MSDP-PEER-SUMM-BAG;
      }
    }
  }

  grouping live_ncs_PEER-TABLE {
    description
      "Common node of default-context, vrf";
    container peers {
      description
        "MSDP Peers";
      list peer {
        key "peer-address";
        description
          "MSDP Peer Info";
        leaf peer-address {
          type inet:ipv4-address-no-zone;
          description
            "Peer Address";
        }
        uses live_ncs_MSDP-PEER-BAG;
      }
    }
  }

  grouping live_ncs_VRF-TABLE {
    description
      "Common node of active, standby";
    container vrfs {
      description
        "VRF Table";
      list vrf {
        key "vrf-name";
        description
          "VRF Name";
        leaf vrf-name {
          type xr:live_ncs_Cisco-ios-xr-string;
          description
            "VRF name";
        }
        uses live_ncs_STAT-PEER-TABLE;
        uses live_ncs_PEER-TABLE;
        uses live_ncs_PEER-SUMMARY-TABLE;
        uses live_ncs_SA-CACHE-TABLE;
        uses live_ncs_RPF-TABLE;
        uses live_ncs_ROUTING-CONTEXT;
        uses live_ncs_CACHE-SUMMARY;
        uses live_ncs_ALL-SA-CACHE-TABLE;
        uses live_ncs_AS-SOURCE-GROUP-SA-CACHE-TABLE;
        uses live_ncs_RP-SOURCE-GROUP-SA-CACHE-TABLE;
      }
    }
  }

  grouping live_ncs_SA-CACHE-TABLE {
    description
      "Common node of default-context, vrf";
    container sa-caches {
      description
        "MSDP SA Cache table - sources with Local &
         External flags Set";
      list sa-cache {
        key "source-address group-address";
        description
          "MSDP SA Cache Entry - Sources with Local &
           External flags set";
        leaf source-address {
          type inet:ipv4-address-no-zone;
          description
            "Previous Source Address";
        }
        leaf group-address {
          type inet:ipv4-address-no-zone;
          description
            "Previous Group Address";
        }
        uses live_ncs_MSDP-SRC-BAG;
      }
    }
  }

  grouping live_ncs_AS-SOURCE-GROUP-SA-CACHE-TABLE {
    description
      "Common node of default-context, vrf";
    container as-source-group-sa-caches {
      description
        "AS Filtered MSDP SA Cache table";
      list as-source-group-sa-cache {
        key "as source-address group-address";
        description
          "AS Filtered MSDP SA Cache Entries";
        leaf as {
          type live_ncs_Bgp-asn-plain;
          description
            "AS Number";
        }
        leaf source-address {
          type inet:ipv4-address-no-zone;
          description
            "Source Address";
        }
        leaf group-address {
          type inet:ipv4-address-no-zone;
          description
            "Group Address";
        }
        uses live_ncs_MSDP-SRC-BAG;
      }
    }
  }

  grouping live_ncs_ALL-SA-CACHE-TABLE {
    description
      "Common node of default-context, vrf";
    container all-sa-caches {
      description
        "All of MSDP SA Cache ignoring source flags";
      list all-sa-cache {
        key "source-address group-address";
        description
          "MSDP All SA Cache Entries ignoring source flags";
        leaf source-address {
          type inet:ipv4-address-no-zone;
          description
            "Source Address";
        }
        leaf group-address {
          type inet:ipv4-address-no-zone;
          description
            "Group Address";
        }
        uses live_ncs_MSDP-SRC-BAG;
      }
    }
  }

  grouping live_ncs_PROCESS {
    description
      "Common node of active, standby";
    container process {
      description
        "Process";
      container globals {
        description
          "MSDP Global Data";
        uses live_ncs_MSDP-GLOBAL-BAG;
      }
      container nsf {
        description
          "NSF Information";
        uses live_ncs_MSDP-EDM-NSF-BAG;
      }
      container summary {
        description
          "MSDP Process Summary Info";
        uses live_ncs_MSDP-PROCESS-SUMM-BAG;
      }
      container nsr {
        description
          "NSR Information";
        uses live_ncs_MSDP-NSR-BAG;
      }
    }
  }

  grouping live_ncs_RPF-TABLE {
    description
      "Common node of default-context, vrf";
    container rpfs {
      description
        "MSDP Reverse Path Forwarding Info";
      list rpf {
        key "rp-address";
        description
          "MSDP Reverse Path Forwarding entries";
        leaf rp-address {
          type inet:ipv4-address-no-zone;
          description
            "RP Address";
        }
        uses live_ncs_MSDP-RPF-BAG;
      }
    }
  }

  grouping live_ncs_RP-SOURCE-GROUP-SA-CACHE-TABLE {
    description
      "Common node of default-context, vrf";
    container rp-source-group-sa-caches {
      description
        "RP Filtered MSDP SA Cache table";
      list rp-source-group-sa-cache {
        key "rp-address source-address group-address";
        description
          "RP Filtered MSDP SA Cache Entries";
        leaf rp-address {
          type inet:ipv4-address-no-zone;
          description
            "RP Address";
        }
        leaf source-address {
          type inet:ipv4-address-no-zone;
          description
            "Source Address";
        }
        leaf group-address {
          type inet:ipv4-address-no-zone;
          description
            "Group Address";
        }
        uses live_ncs_MSDP-SRC-BAG;
      }
    }
  }

  grouping live_ncs_CACHE-SUMMARY {
    description
      "Common node of default-context, vrf";
    container cache-summary {
      description
        "Cache Summary";
      container rp-cache-summaries {
        description
          "RP specific Cache Summary Table";
        list rp-cache-summary {
          key "rp-address";
          description
            "Cache Summary RP";
          leaf rp-address {
            type inet:ipv4-address-no-zone;
            description
              "RP Address";
          }
          uses live_ncs_MSDP-SUMMARY-RP-BAG;
        }
      }
      container cache-summary-preface {
        description
          "Cache Summary Preface";
        uses live_ncs_MSDP-SUMMARY-PREFACE-BAG;
      }
      container as-cache-summaries {
        description
          "AS specific Cache Summary Table";
        list as-cache-summary {
          key "as";
          description
            "Cache Summary AS";
          leaf as {
            type live_ncs_Bgp-asn-plain;
            description
              "AS Number";
          }
          uses live_ncs_MSDP-SUMMARY-AS-BAG;
        }
      }
    }
  }

  grouping live_ncs_ROUTING-CONTEXT {
    description
      "Common node of default-context, vrf";
    container routing-context {
      description
        "MSDP routing context";
      uses live_ncs_MSDP-CONTEXT;
    }
  }

  grouping live_ncs_STAT-PEER-TABLE {
    description
      "Common node of default-context, vrf";
    container stat-peers {
      description
        "Statistics for MSDP Peers";
      list stat-peer {
        key "peer-address";
        description
          "MSDP Peer Statistics Info";
        leaf peer-address {
          type inet:ip-address-no-zone;
          description
            "Peer Address";
        }
        uses live_ncs_MSDP-STATS-PEER-BAG;
      }
    }
  }

  grouping live_ncs_DEFAULT-CONTEXT {
    description
      "Common node of active, standby";
    container default-context {
      description
        "Default Context";
      uses live_ncs_STAT-PEER-TABLE;
      uses live_ncs_PEER-TABLE;
      uses live_ncs_PEER-SUMMARY-TABLE;
      uses live_ncs_SA-CACHE-TABLE;
      uses live_ncs_RPF-TABLE;
      uses live_ncs_ROUTING-CONTEXT;
      uses live_ncs_CACHE-SUMMARY;
      uses live_ncs_ALL-SA-CACHE-TABLE;
      uses live_ncs_AS-SOURCE-GROUP-SA-CACHE-TABLE;
      uses live_ncs_RP-SOURCE-GROUP-SA-CACHE-TABLE;
    }
  }

  grouping live_ncs_PEER-SUMMARY-TABLE {
    description
      "Common node of default-context, vrf";
    container peer-summaries {
      description
        "MSDP Peers summary";
      list peer-summary {
        key "peer-address";
        description
          "MSDP Peer Summary Info";
        leaf peer-address {
          type inet:ipv4-address-no-zone;
          description
            "Peer Address";
        }
        uses live_ncs_MSDP-PEER-SUMM-BAG;
      }
    }
  }

  grouping PEER-TABLE {
    description
      "Common node of default-context, vrf";
    container peers {
      description
        "MSDP Peers";
      list peer {
        key "peer-address";
        description
          "MSDP Peer Info";
        leaf peer-address {
          type inet:ipv4-address-no-zone;
          description
            "Peer Address";
        }
        uses MSDP-PEER-BAG;
      }
    }
  }

  grouping VRF-TABLE {
    description
      "Common node of active, standby";
    container vrfs {
      description
        "VRF Table";
      list vrf {
        key "vrf-name";
        description
          "VRF Name";
        leaf vrf-name {
          type xr:Cisco-ios-xr-string {
            length "1..32";
          }
          description
            "VRF name";
        }
        uses STAT-PEER-TABLE;
        uses PEER-TABLE;
        uses PEER-SUMMARY-TABLE;
        uses SA-CACHE-TABLE;
        uses RPF-TABLE;
        uses ROUTING-CONTEXT;
        uses CACHE-SUMMARY;
        uses ALL-SA-CACHE-TABLE;
        uses AS-SOURCE-GROUP-SA-CACHE-TABLE;
        uses RP-SOURCE-GROUP-SA-CACHE-TABLE;
      }
    }
  }

  grouping SA-CACHE-TABLE {
    description
      "Common node of default-context, vrf";
    container sa-caches {
      description
        "MSDP SA Cache table - sources with Local &
         External flags Set";
      list sa-cache {
        key "source-address group-address";
        description
          "MSDP SA Cache Entry - Sources with Local &
           External flags set";
        leaf source-address {
          type inet:ipv4-address-no-zone;
          description
            "Previous Source Address";
        }
        leaf group-address {
          type inet:ipv4-address-no-zone;
          description
            "Previous Group Address";
        }
        uses MSDP-SRC-BAG;
      }
    }
  }

  grouping AS-SOURCE-GROUP-SA-CACHE-TABLE {
    description
      "Common node of default-context, vrf";
    container as-source-group-sa-caches {
      description
        "AS Filtered MSDP SA Cache table";
      list as-source-group-sa-cache {
        key "as source-address group-address";
        description
          "AS Filtered MSDP SA Cache Entries";
        leaf as {
          type Bgp-asn-plain;
          description
            "AS Number";
        }
        leaf source-address {
          type inet:ipv4-address-no-zone;
          description
            "Source Address";
        }
        leaf group-address {
          type inet:ipv4-address-no-zone;
          description
            "Group Address";
        }
        uses MSDP-SRC-BAG;
      }
    }
  }

  grouping ALL-SA-CACHE-TABLE {
    description
      "Common node of default-context, vrf";
    container all-sa-caches {
      description
        "All of MSDP SA Cache ignoring source flags";
      list all-sa-cache {
        key "source-address group-address";
        description
          "MSDP All SA Cache Entries ignoring source flags";
        leaf source-address {
          type inet:ipv4-address-no-zone;
          description
            "Source Address";
        }
        leaf group-address {
          type inet:ipv4-address-no-zone;
          description
            "Group Address";
        }
        uses MSDP-SRC-BAG;
      }
    }
  }

  grouping PROCESS {
    description
      "Common node of active, standby";
    container process {
      description
        "Process";
      container globals {
        description
          "MSDP Global Data";
        uses MSDP-GLOBAL-BAG;
      }
      container nsf {
        description
          "NSF Information";
        uses MSDP-EDM-NSF-BAG;
      }
      container summary {
        description
          "MSDP Process Summary Info";
        uses MSDP-PROCESS-SUMM-BAG;
      }
      container nsr {
        description
          "NSR Information";
        uses MSDP-NSR-BAG;
      }
    }
  }

  grouping RPF-TABLE {
    description
      "Common node of default-context, vrf";
    container rpfs {
      description
        "MSDP Reverse Path Forwarding Info";
      list rpf {
        key "rp-address";
        description
          "MSDP Reverse Path Forwarding entries";
        leaf rp-address {
          type inet:ipv4-address-no-zone;
          description
            "RP Address";
        }
        uses MSDP-RPF-BAG;
      }
    }
  }

  grouping RP-SOURCE-GROUP-SA-CACHE-TABLE {
    description
      "Common node of default-context, vrf";
    container rp-source-group-sa-caches {
      description
        "RP Filtered MSDP SA Cache table";
      list rp-source-group-sa-cache {
        key "rp-address source-address group-address";
        description
          "RP Filtered MSDP SA Cache Entries";
        leaf rp-address {
          type inet:ipv4-address-no-zone;
          description
            "RP Address";
        }
        leaf source-address {
          type inet:ipv4-address-no-zone;
          description
            "Source Address";
        }
        leaf group-address {
          type inet:ipv4-address-no-zone;
          description
            "Group Address";
        }
        uses MSDP-SRC-BAG;
      }
    }
  }

  grouping CACHE-SUMMARY {
    description
      "Common node of default-context, vrf";
    container cache-summary {
      description
        "Cache Summary";
      container rp-cache-summaries {
        description
          "RP specific Cache Summary Table";
        list rp-cache-summary {
          key "rp-address";
          description
            "Cache Summary RP";
          leaf rp-address {
            type inet:ipv4-address-no-zone;
            description
              "RP Address";
          }
          uses MSDP-SUMMARY-RP-BAG;
        }
      }
      container cache-summary-preface {
        description
          "Cache Summary Preface";
        uses MSDP-SUMMARY-PREFACE-BAG;
      }
      container as-cache-summaries {
        description
          "AS specific Cache Summary Table";
        list as-cache-summary {
          key "as";
          description
            "Cache Summary AS";
          leaf as {
            type Bgp-asn-plain;
            description
              "AS Number";
          }
          uses MSDP-SUMMARY-AS-BAG;
        }
      }
    }
  }

  grouping ROUTING-CONTEXT {
    description
      "Common node of default-context, vrf";
    container routing-context {
      description
        "MSDP routing context";
      uses MSDP-CONTEXT;
    }
  }

  grouping STAT-PEER-TABLE {
    description
      "Common node of default-context, vrf";
    container stat-peers {
      description
        "Statistics for MSDP Peers";
      list stat-peer {
        key "peer-address";
        description
          "MSDP Peer Statistics Info";
        leaf peer-address {
          type inet:ip-address-no-zone;
          description
            "Peer Address";
        }
        uses MSDP-STATS-PEER-BAG;
      }
    }
  }

  grouping DEFAULT-CONTEXT {
    description
      "Common node of active, standby";
    container default-context {
      description
        "Default Context";
      uses STAT-PEER-TABLE;
      uses PEER-TABLE;
      uses PEER-SUMMARY-TABLE;
      uses SA-CACHE-TABLE;
      uses RPF-TABLE;
      uses ROUTING-CONTEXT;
      uses CACHE-SUMMARY;
      uses ALL-SA-CACHE-TABLE;
      uses AS-SOURCE-GROUP-SA-CACHE-TABLE;
      uses RP-SOURCE-GROUP-SA-CACHE-TABLE;
    }
  }

  grouping PEER-SUMMARY-TABLE {
    description
      "Common node of default-context, vrf";
    container peer-summaries {
      description
        "MSDP Peers summary";
      list peer-summary {
        key "peer-address";
        description
          "MSDP Peer Summary Info";
        leaf peer-address {
          type inet:ipv4-address-no-zone;
          description
            "Peer Address";
        }
        uses MSDP-PEER-SUMM-BAG;
      }
    }
  }

  augment "/ncs:devices/ncs:device/ncs:config" {
    // NCS drop config false container msdp
  }
  augment "/ncs:devices/ncs:device/ncs:live-status" {
    container msdp {
      tailf:ncs-device-type "netconf";
      tailf:display-when "not(../../ncs:module) or ../../ncs:module[ncs:name='Cisco-IOS-XR-msdp-oper'] or (../../ncs:live-status-protocol[not(ncs:capability)]) or (../../ncs:live-status-protocol/ncs:capability/ncs:module[.='Cisco-IOS-XR-msdp-oper'])";
      description
        "MSDP operational data";
      container standby {
        description
          "Standby Process";
        uses live_ncs_DEFAULT-CONTEXT;
        uses live_ncs_PROCESS;
        uses live_ncs_VRF-TABLE;
      }
      container active {
        description
          "Active Process";
        uses live_ncs_DEFAULT-CONTEXT;
        uses live_ncs_PROCESS;
        uses live_ncs_VRF-TABLE;
      }
    }
  }
  augment "/ncs:devices/ncs:template/ncs:ned-id/ncs:config" {
    // NCS drop config false container msdp
  }
}

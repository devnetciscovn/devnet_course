submodule Cisco-IOS-XR-rgmgr-oper-sub1 {
  // Generated by yanger -t ncs
  tailf:mount-id "cisco-iosxr-nc-7.3:cisco-iosxr-nc-7.3";

  belongs-to Cisco-IOS-XR-rgmgr-oper {
    prefix Cisco-IOS-XR-rgmgr-oper;
  }

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR rgmgr package operational data.

     Copyright (c) 2013-2019 by Cisco Systems, Inc.
     All rights reserved.";

  revision 2019-04-05 {
    description
      "Establish semantic version baseline.";
    semver:module-version "1.0.1";
  }
  revision 2015-01-07 {
    description
      "IOS XR 5.3.1 revision.";
  }

  grouping ncs_template_RGMGR-RED-GRP {
    description
      "RGMGR RED GRP";
    leaf multi-router-aps-group-number {
      type string;
      description
        "Configured interchassis redundancy group number";
    }
    leaf controller-name-xr {
      type string;
      description
        "Name of controller being backed up";
    }
    leaf controller-handle {
      type xr:ncs_template_Interface-name;
      description
        "Handle of controller being backed up";
    }
    leaf backup-interface-name {
      type string;
      description
        "Backup interface name";
    }
    leaf backup-interface-handle {
      type xr:ncs_template_Interface-name;
      description
        "Backup interface handle";
    }
    leaf backup-interface-next-hop-ip-address {
      type string;
      description
        "Backup interface next hop IP address";
    }
    leaf inter-chassis-group-state {
      type string;
      description
        "Configured interchassis redundancy group state";
    }
  }

  grouping ncs_rpc_notif_RGMGR-RED-GRP {
    description
      "RGMGR RED GRP";
    leaf multi-router-aps-group-number {
      type string {
        length "0..64";
      }
      description
        "Configured interchassis redundancy group number";
    }
    leaf controller-name-xr {
      type string {
        length "0..64";
      }
      description
        "Name of controller being backed up";
    }
    leaf controller-handle {
      type xr:ncs_rpc_notif_Interface-name;
      description
        "Handle of controller being backed up";
    }
    leaf backup-interface-name {
      type string {
        length "0..64";
      }
      description
        "Backup interface name";
    }
    leaf backup-interface-handle {
      type xr:ncs_rpc_notif_Interface-name;
      description
        "Backup interface handle";
    }
    leaf backup-interface-next-hop-ip-address {
      type inet:ipv4-address;
      description
        "Backup interface next hop IP address";
    }
    leaf inter-chassis-group-state {
      type string {
        length "0..64";
      }
      description
        "Configured interchassis redundancy group state";
    }
  }

  grouping live_ncs_RGMGR-RED-GRP {
    description
      "RGMGR RED GRP";
    leaf multi-router-aps-group-number {
      type string {
        length "0..64";
      }
      description
        "Configured interchassis redundancy group number";
    }
    leaf controller-name-xr {
      type string {
        length "0..64";
      }
      description
        "Name of controller being backed up";
    }
    leaf controller-handle {
      type xr:live_ncs_Interface-name;
      description
        "Handle of controller being backed up";
    }
    leaf backup-interface-name {
      type string {
        length "0..64";
      }
      description
        "Backup interface name";
    }
    leaf backup-interface-handle {
      type xr:live_ncs_Interface-name;
      description
        "Backup interface handle";
    }
    leaf backup-interface-next-hop-ip-address {
      type inet:ipv4-address;
      description
        "Backup interface next hop IP address";
    }
    leaf inter-chassis-group-state {
      type string {
        length "0..64";
      }
      description
        "Configured interchassis redundancy group state";
    }
  }

  grouping RGMGR-RED-GRP {
    description
      "RGMGR RED GRP";
    leaf multi-router-aps-group-number {
      type string {
        length "0..64";
      }
      description
        "Configured interchassis redundancy group number";
    }
    leaf controller-name-xr {
      type string {
        length "0..64";
      }
      description
        "Name of controller being backed up";
    }
    leaf controller-handle {
      type xr:Interface-name;
      description
        "Handle of controller being backed up";
    }
    leaf backup-interface-name {
      type string {
        length "0..64";
      }
      description
        "Backup interface name";
    }
    leaf backup-interface-handle {
      type xr:Interface-name;
      description
        "Backup interface handle";
    }
    leaf backup-interface-next-hop-ip-address {
      type inet:ipv4-address;
      description
        "Backup interface next hop IP address";
    }
    leaf inter-chassis-group-state {
      type string {
        length "0..64";
      }
      description
        "Configured interchassis redundancy group state";
    }
  }
}

module Cisco-IOS-XR-mpls-over-udp-cfg {
  // Generated by yanger -t ncs
  tailf:mount-id "cisco-iosxr-nc-7.3:cisco-iosxr-nc-7.3";
  tailf:ncs-device-type "netconf";

  namespace "http://cisco.com/ns/yang/Cisco-IOS-XR-mpls-over-udp-cfg";
  prefix mpls-over-udp-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-over-udp package configuration.

     This module contains definitions
     for the following management objects:
       hardware-module-pdfib: PD FIB configuration

     Copyright (c) 2013-2020 by Cisco Systems, Inc.
     All rights reserved.";

  revision 2020-04-15 {
    description
      "Schema added.";
    semver:module-version "1.0.0";
  }
  revision 2019-04-05 {
    description
      "Establish semantic version baseline.";
  }
  revision 2015-11-09 {
    description
      "IOS XR 6.0 revision.";
  }

  augment "/ncs:devices/ncs:device/ncs:config" {
    container hardware-module-pdfib {
      tailf:ncs-device-type "netconf";
      tailf:display-when "not(../../ncs:module) or ../../ncs:module[ncs:name='Cisco-IOS-XR-mpls-over-udp-cfg']";
      description
        "PD FIB configuration";
      leaf mpls-over-udp-decap {
        type empty;
        description
          "PD FIB Feature RFC 7510 MPLS-over-UDP decap";
      }
    }
  }
  augment "/ncs:devices/ncs:device/ncs:live-status" {
    container hardware-module-pdfib {
      tailf:ncs-device-type "netconf";
      tailf:display-when "not(../../ncs:module) or ../../ncs:module[ncs:name='Cisco-IOS-XR-mpls-over-udp-cfg'] or (../../ncs:live-status-protocol[not(ncs:capability)]) or (../../ncs:live-status-protocol/ncs:capability/ncs:module[.='Cisco-IOS-XR-mpls-over-udp-cfg'])";
      description
        "PD FIB configuration";
      leaf mpls-over-udp-decap {
        type empty;
        description
          "PD FIB Feature RFC 7510 MPLS-over-UDP decap";
      }
    }
  }
  augment "/ncs:devices/ncs:template/ncs:ned-id/ncs:config" {
    container hardware-module-pdfib {
      description
        "PD FIB configuration";
      leaf mpls-over-udp-decap {
        type empty;
        description
          "PD FIB Feature RFC 7510 MPLS-over-UDP decap";
      }
    }
  }
}

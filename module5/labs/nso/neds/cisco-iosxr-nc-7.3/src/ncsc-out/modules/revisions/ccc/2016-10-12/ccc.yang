module ccc {
  // Generated by yanger -t ncs
  tailf:mount-id "cisco-iosxr-nc-7.3:cisco-iosxr-nc-7.3";
  tailf:ncs-device-type "netconf";

  namespace "http://cisco.com/calvados/ccc";
  prefix ccc;

  import tailf-common {
    prefix tailf;
  }
  import Cisco-IOS-XR-sysadmin-show-trace {
    prefix show_trace;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2016-10-12 {
    description
      "Unhide commands and configs. Moved to advanced-grp";
  }

  typedef ncs_template_startHexOffset {
    type string;
  }

  typedef ncs_template_endHexOffset {
    type string;
  }

  typedef ncs_template_HexOffset {
    type string;
  }

  typedef ncs_template_cdrNumber {
    type string;
  }

  typedef ncs_template_laneMask {
    type string;
  }

  typedef ncs_rpc_notif_startHexOffset {
    type string;
  }

  typedef ncs_rpc_notif_endHexOffset {
    type string;
  }

  typedef ncs_rpc_notif_HexOffset {
    type string;
  }

  typedef ncs_rpc_notif_cdrNumber {
    type uint32;
  }

  typedef ncs_rpc_notif_laneMask {
    type string;
  }

  typedef live_ncs_startHexOffset {
    type string;
  }

  typedef live_ncs_endHexOffset {
    type string;
  }

  typedef live_ncs_HexOffset {
    type string;
  }

  typedef live_ncs_cdrNumber {
    type uint32;
  }

  typedef live_ncs_laneMask {
    type string;
  }

  typedef startHexOffset {
    type string;
  }

  typedef endHexOffset {
    type string;
  }

  typedef HexOffset {
    type string;
  }

  typedef cdrNumber {
    type uint32;
  }

  typedef laneMask {
    type string;
  }

  grouping ncs_template_ccc-grp {
    container ccc_driver {
      uses show_trace:ncs_template_traceable;
      uses ncs_template_show-ccc-cli-group-master;
      uses ncs_template_show-ccc-cli-group-slave;
      uses ncs_template_ccc-action-group;
    }
  }

  grouping ncs_template_show-ccc-cli-group-master {
    uses ncs_template_bootflash-group;
    uses ncs_template_inventory-group;
    uses ncs_template_power-group;
    uses ncs_template_reset-hist-group;
    uses ncs_template_register-group;
    uses ncs_template_ejector-group;
    uses ncs_template_i2c-dev-group;
    uses ncs_template_ethernet-group;
    uses ncs_template_tla-dump-group;
    uses ncs_template_master-event-hist-group;
    uses ncs_template_master-oir-hist-group;
    uses ncs_template_master-notif-hist-group;
  }

  grouping ncs_template_show-ccc-cli-group-slave {
    container slave {
      uses ncs_template_slave-event-hist-group;
      uses ncs_template_slave-notif-hist-group;
      uses ncs_template_slave-oir-hist-group;
    }
  }

  grouping ncs_template_bootflash-group {
    // NCS drop config false container bootflash
  }

  grouping ncs_template_master-health-group {
    // NCS drop config false container health
  }

  grouping ncs_template_slave-health-group {
    // NCS drop config false container health
  }

  grouping ncs_template_health-group {
    list location {
      // NCS patched for predictable order
      ordered-by user;
      key "location";
      leaf location {
        type string;
      }
      container health_status {
        leaf-list health_status_values {
          // NCS patched for predictable order
          ordered-by user;
          type string;
        }
      }
    }
  }

  grouping ncs_template_inventory-group {
    // NCS drop config false container inventory
  }

  grouping ncs_template_inventory-summary-group {
    // NCS drop config false container summary
    // NCS drop config false container version
  }

  grouping ncs_template_inventory-status-group {
    // NCS drop config false container status
  }

  grouping ncs_template_inventory-detail-group {
    // NCS drop config false container detail
  }

  grouping ncs_template_power-group {
    // NCS drop config false container power
  }

  grouping ncs_template_ccc-master-access-group {
    // NCS drop config false container 'master-access'
  }

  grouping ncs_template_ccc-power-summary-group {
    // NCS drop config false container summary
  }

  grouping ncs_template_ccc-power-detail-group {
    // NCS drop config false container detail
  }

  grouping ncs_template_reset-hist-group {
    // NCS drop config false container 'reset-history'
  }

  grouping ncs_template_reset-hist-chip-group {
    // NCS drop config false container onchip
  }

  grouping ncs_template_reset-hist-onboard-group {
    // NCS drop config false container onboard
  }

  grouping ncs_template_register-group {
    // NCS drop config false container register
  }

  grouping ncs_template_ccc-block-number-group {
    // NCS drop config false list ccc_block_number
  }

  grouping ncs_template_ccc-offset-group {
    // NCS drop config false list ccc_offset
  }

  grouping ncs_template_ccc-address-group {
    // NCS drop config false list ccc_address
  }

  grouping ncs_template_ejector-group {
    // NCS drop config false container ejector
  }

  grouping ncs_template_ejector-status-group {
    // NCS drop config false container status
  }

  grouping ncs_template_master-event-hist-group {
    // NCS drop config false container 'event-history'
  }

  grouping ncs_template_slave-event-hist-group {
    // NCS drop config false container 'event-history'
  }

  grouping ncs_template_event-hist-group-brief {
    list location {
      // NCS patched for predictable order
      ordered-by user;
      key "location";
      leaf location {
        type string;
      }
      container card_event_hist_brief {
        leaf-list card_event_hist_brief_values {
          // NCS patched for predictable order
          ordered-by user;
          type string;
        }
      }
    }
  }

  grouping ncs_template_event-hist-group-detail {
    list location {
      // NCS patched for predictable order
      ordered-by user;
      key "location";
      leaf location {
        type string;
      }
      container card_event_hist_detail {
        leaf-list card_event_hist_detail_values {
          // NCS patched for predictable order
          ordered-by user;
          type string;
        }
      }
    }
  }

  grouping ncs_template_master-notif-hist-group {
    // NCS drop config false container 'notif-history'
  }

  grouping ncs_template_slave-notif-hist-group {
    // NCS drop config false container 'notif-history'
  }

  grouping ncs_template_notif-hist-group-brief {
    list location {
      // NCS patched for predictable order
      ordered-by user;
      key "location";
      leaf location {
        type string;
      }
      container card_notif_hist_brief {
        leaf-list card_notif_hist_brief_values {
          // NCS patched for predictable order
          ordered-by user;
          type string;
        }
      }
    }
  }

  grouping ncs_template_notif-hist-group-detail {
    list location {
      // NCS patched for predictable order
      ordered-by user;
      key "location";
      leaf location {
        type string;
      }
      container card_notif_hist_detail {
        leaf-list card_notif_hist_detail_values {
          // NCS patched for predictable order
          ordered-by user;
          type string;
        }
      }
    }
  }

  grouping ncs_template_i2c-dev-group {
    // NCS drop config false container 'i2c-dev'
  }

  grouping ncs_template_cpu-complex-group {
    // NCS drop config false container 'cpu-complex'
  }

  grouping ncs_template_io-expander-group {
    // NCS drop config false container ioexpander
  }

  grouping ncs_template_cdr-group {
    // NCS drop config false container cdr
  }

  grouping ncs_template_master-cdr-group {
    // NCS drop config false container master
  }

  grouping ncs_template_slave-cdr-group {
    // NCS drop config false container slave
  }

  grouping ncs_template_summary-group {
    list location {
      // NCS patched for predictable order
      ordered-by user;
      key "location";
      leaf location {
        type string;
      }
      container cdr_status {
        leaf-list cdr_summary_status {
          // NCS patched for predictable order
          ordered-by user;
          type string;
        }
      }
    }
  }

  grouping ncs_template_version-group {
    // NCS drop config false list location
  }

  grouping ncs_template_cdr-number-group {
    // NCS drop config false list cdr_number
  }

  grouping ncs_template_si-dump-group {
    // NCS drop config false list location
  }

  grouping ncs_template_si-group {
    // NCS drop config false list cdr_number
  }

  grouping ncs_template_eye-scan-group {
    // NCS drop config false list location
  }

  grouping ncs_template_cdr-eye-scan-group {
    // NCS drop config false list cdr_number
  }

  grouping ncs_template_ccc-action-group {
    // NCS drop config false container action
  }

  grouping ncs_template_master-oir-hist-group {
    // NCS drop config false container 'oir-history'
  }

  grouping ncs_template_slave-oir-hist-group {
    // NCS drop config false container 'oir-history'
  }

  grouping ncs_template_oir-hist-group {
    list rack {
      // NCS patched for predictable order
      ordered-by user;
      key "rack";
      leaf rack {
        type string;
      }
      container card_oir_hist {
        leaf-list card_oir_events {
          // NCS patched for predictable order
          ordered-by user;
          type string;
        }
      }
    }
  }

  grouping ncs_template_ethernet-group {
    // NCS drop config false container ethernet
  }

  grouping ncs_template_ethernet-status {
    // NCS drop config false container ethernet_status
  }

  grouping ncs_template_ethernet-counters {
    // NCS drop config false container ethernet_counters
  }

  grouping ncs_template_tla-dump-group {
    // NCS drop config false container 'tla-dump'
  }

  grouping ncs_rpc_notif_ccc-grp {
    container ccc_driver {
      uses show_trace:ncs_rpc_notif_traceable;
      uses ncs_rpc_notif_show-ccc-cli-group-master;
      uses ncs_rpc_notif_show-ccc-cli-group-slave;
      uses ncs_rpc_notif_ccc-action-group;
    }
  }

  grouping ncs_rpc_notif_show-ccc-cli-group-master {
    uses ncs_rpc_notif_bootflash-group;
    uses ncs_rpc_notif_inventory-group;
    uses ncs_rpc_notif_power-group;
    uses ncs_rpc_notif_reset-hist-group;
    uses ncs_rpc_notif_register-group;
    uses ncs_rpc_notif_ejector-group;
    uses ncs_rpc_notif_i2c-dev-group;
    uses ncs_rpc_notif_ethernet-group;
    uses ncs_rpc_notif_tla-dump-group;
    uses ncs_rpc_notif_master-event-hist-group;
    uses ncs_rpc_notif_master-oir-hist-group;
    uses ncs_rpc_notif_master-notif-hist-group;
  }

  grouping ncs_rpc_notif_show-ccc-cli-group-slave {
    container slave {
      uses ncs_rpc_notif_slave-event-hist-group;
      uses ncs_rpc_notif_slave-notif-hist-group;
      uses ncs_rpc_notif_slave-oir-hist-group;
    }
  }

  grouping ncs_rpc_notif_bootflash-group {
    container bootflash {
      config false;
      container info {
        config false;
        list location {
          key "location";
          leaf location {
            type string;
          }
          container bf_info {
            leaf-list bf_info_values {
              type string;
            }
          }
        }
      }
      container status {
        config false;
        list location {
          key "location";
          leaf location {
            type string;
          }
          container bf_status {
            leaf-list bf_status_values {
              type string;
            }
          }
        }
      }
      container cre_status {
        config false;
        list location {
          key "location";
          leaf location {
            type string;
          }
          container bf_status {
            leaf-list bf_status_values {
              type string;
            }
          }
        }
      }
    }
  }

  grouping ncs_rpc_notif_master-health-group {
    container health {
      config false;
      uses ncs_rpc_notif_health-group;
    }
  }

  grouping ncs_rpc_notif_slave-health-group {
    container health {
      config false;
      uses ncs_rpc_notif_health-group;
    }
  }

  grouping ncs_rpc_notif_health-group {
    list location {
      key "location";
      leaf location {
        type string;
      }
      container health_status {
        leaf-list health_status_values {
          type string;
        }
      }
    }
  }

  grouping ncs_rpc_notif_inventory-group {
    container inventory {
      config false;
      uses ncs_rpc_notif_inventory-summary-group;
      uses ncs_rpc_notif_inventory-status-group;
      uses ncs_rpc_notif_inventory-detail-group;
    }
  }

  grouping ncs_rpc_notif_inventory-summary-group {
    container summary {
      config false;
      list ccc_inv_summary {
        key "location";
        leaf location {
          type string;
          mandatory true;
        }
        leaf ccc_inv_PID_string {
          type string;
        }
        leaf ccc_inv_slot_number {
          type uint32;
        }
        leaf ccc_inv_serial_number {
          type string;
        }
        leaf ccc_inv_hw_version {
          type string;
        }
        leaf ccc_inv_card_state {
          type string;
        }
      }
    }
    container version {
      config false;
      list ccc_inv_version {
        key "location";
        leaf location {
          type string;
          mandatory true;
        }
        leaf ccc_inv_PID_string {
          type string;
        }
        leaf ccc_inv_ccc_version {
          type string;
        }
        leaf ccc_inv_FPGA_version {
          type string;
        }
        leaf ccc_inv_pon_version {
          type string;
        }
        leaf ccc_inv_switch_version {
          type string;
        }
      }
    }
  }

  grouping ncs_rpc_notif_inventory-status-group {
    container status {
      config false;
      list ccc_inv_status {
        key "location";
        leaf location {
          type string;
          mandatory true;
        }
        container ccc_inv_status_list {
          leaf-list ccc_inv_status_values {
            type string;
          }
        }
      }
    }
  }

  grouping ncs_rpc_notif_inventory-detail-group {
    container detail {
      config false;
      list ccc_inv_detail {
        key "location";
        leaf location {
          type string;
        }
        container ccc_inv_detail_list {
          leaf-list ccc_inv_detail_values {
            type string;
          }
        }
      }
    }
  }

  grouping ncs_rpc_notif_power-group {
    container power {
      config false;
      uses ncs_rpc_notif_ccc-master-access-group;
    }
  }

  grouping ncs_rpc_notif_ccc-master-access-group {
    container master-access {
      config false;
      uses ncs_rpc_notif_ccc-power-summary-group;
      uses ncs_rpc_notif_ccc-power-detail-group;
    }
  }

  grouping ncs_rpc_notif_ccc-power-summary-group {
    container summary {
      config false;
      list power_summary {
        key "ccc_power_location";
        leaf ccc_power_location {
          type string;
          mandatory true;
        }
        leaf card_type {
          type string;
        }
        leaf power_state {
          type string;
        }
      }
    }
  }

  grouping ncs_rpc_notif_ccc-power-detail-group {
    container detail {
      config false;
      list location {
        key "location";
        leaf location {
          type string;
        }
        container power_details {
          leaf-list power_details_values {
            type string;
          }
        }
      }
    }
  }

  grouping ncs_rpc_notif_reset-hist-group {
    container reset-history {
      config false;
      uses ncs_rpc_notif_reset-hist-chip-group;
      uses ncs_rpc_notif_reset-hist-onboard-group;
    }
  }

  grouping ncs_rpc_notif_reset-hist-chip-group {
    container onchip {
      config false;
      list location {
        key "loc";
        leaf loc {
          type string;
        }
        leaf ccc_reset_timeofday {
          type string;
        }
        leaf ccc_reset_uptime {
          type string;
        }
        leaf ccc_hw_reset_count {
          type uint32;
        }
        list ccc_reset_entry {
          key "ccc_reset_entry";
          leaf ccc_reset_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping ncs_rpc_notif_reset-hist-onboard-group {
    container onboard {
      config false;
      list location {
        key "loc";
        leaf loc {
          type string;
        }
        leaf ccc_reset_scratch_sig {
          type string;
        }
        leaf ccc_reset_scratch_version {
          type uint32;
        }
        leaf ccc_reset_history_sig {
          type string;
        }
        leaf ccc_reset_history_count {
          type uint32;
        }
        leaf ccc_reset_history_disp {
          type uint32;
        }
        list ccc_reset_onboard_entry {
          key "ccc_reset_onboard_entry";
          leaf ccc_reset_onboard_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping ncs_rpc_notif_register-group {
    container register {
      config false;
      list register_location {
        config false;
        key "register_location";
        leaf register_location {
          type string;
        }
        uses ncs_rpc_notif_ccc-block-number-group;
        uses ncs_rpc_notif_ccc-offset-group;
        uses ncs_rpc_notif_ccc-address-group;
      }
    }
  }

  grouping ncs_rpc_notif_ccc-block-number-group {
    list ccc_block_number {
      config false;
      key "ccc_block_num";
      leaf ccc_block_num {
        type uint32;
      }
      leaf block_location {
        type string;
      }
      leaf ccc_block_nm {
        type string;
      }
      list ccc_register_number {
        key "index";
        leaf index {
          type uint32;
        }
        leaf ccc_register_name {
          type string;
        }
        list ccc_data {
          leaf name {
            type string;
          }
          leaf offset {
            type uint32;
          }
          leaf value {
            type uint32;
          }
        }
      }
    }
  }

  grouping ncs_rpc_notif_ccc-offset-group {
    list ccc_offset {
      config false;
      key "hex_offset";
      leaf hex_offset {
        type ncs_rpc_notif_HexOffset;
      }
      list ccc_reg_offset_data {
        leaf ccc_reg_off_addr {
          type uint32;
        }
        leaf reg_off_value {
          type string;
        }
      }
    }
  }

  grouping ncs_rpc_notif_ccc-address-group {
    list ccc_address {
      config false;
      key "start_hex_addr end_hex_addr";
      leaf start_hex_addr {
        type ncs_rpc_notif_startHexOffset;
      }
      leaf end_hex_addr {
        type ncs_rpc_notif_endHexOffset;
      }
      list ccc_reg_range_addr_list {
        key "ccc_reg_range_addr";
        leaf ccc_reg_range_addr {
          type uint32;
        }
        list ccc_reg_data {
          leaf ccc_reg_addr {
            type uint32;
          }
          leaf reg_value {
            type string;
          }
        }
      }
    }
  }

  grouping ncs_rpc_notif_ejector-group {
    container ejector {
      config false;
      uses ncs_rpc_notif_ejector-status-group;
    }
  }

  grouping ncs_rpc_notif_ejector-status-group {
    container status {
      config false;
      list ccc_ejector_status {
        key "location";
        leaf location {
          type string;
        }
        leaf ccc_is_fc_card_type {
          type boolean;
          default "false";
        }
        leaf ccc_is_lc_card_type {
          type boolean;
          default "false";
        }
        leaf ccc_is_rp_sc_card_type {
          type boolean;
          default "false";
        }
        leaf ccc_ejc_card_type {
          type uint32;
        }
        leaf ccc_ejc_platform {
          type uint32;
        }
        leaf ccc_ejc_board_type {
          type string;
        }
        leaf ccc_ejc_card_slot {
          type uint32;
        }
        leaf ccc_ejc_card_version {
          type string;
        }
        leaf ccc_ejc_board_version {
          type string;
        }
        leaf ccc_ejc_hw_version {
          type string;
        }
        leaf ccc_ejc_core_version {
          type string;
        }
        leaf ccc_ejc_pon_version {
          type string;
        }
        leaf ccc_ejc_rp_supported {
          type string;
        }
        leaf ccc_ejc_enable {
          type string;
        }
        leaf ccc_ejc_status {
          type string;
        }
        leaf ccc_ejc_rp_pex_csr {
          type string;
        }
        leaf ccc_ejc_gp_live {
          type string;
        }
        leaf ccc_ejc_gp_status {
          type string;
        }
        leaf ccc_ejc_fc_pex_csr {
          type string;
        }
        leaf ccc_ejc_fc_ejector_support {
          type string;
        }
        leaf ccc_ejc_lc_pex_csr {
          type string;
        }
        leaf ccc_ejc_lc_ejector_support {
          type string;
        }
      }
    }
  }

  grouping ncs_rpc_notif_master-event-hist-group {
    container event-history {
      config false;
      container brief {
        config false;
        uses ncs_rpc_notif_event-hist-group-brief;
      }
      container detail {
        config false;
        uses ncs_rpc_notif_event-hist-group-detail;
      }
    }
  }

  grouping ncs_rpc_notif_slave-event-hist-group {
    container event-history {
      config false;
      container brief {
        config false;
        uses ncs_rpc_notif_event-hist-group-brief;
      }
      container detail {
        config false;
        uses ncs_rpc_notif_event-hist-group-detail;
      }
    }
  }

  grouping ncs_rpc_notif_event-hist-group-brief {
    list location {
      key "location";
      leaf location {
        type string;
      }
      container card_event_hist_brief {
        leaf-list card_event_hist_brief_values {
          type string;
        }
      }
    }
  }

  grouping ncs_rpc_notif_event-hist-group-detail {
    list location {
      key "location";
      leaf location {
        type string;
      }
      container card_event_hist_detail {
        leaf-list card_event_hist_detail_values {
          type string;
        }
      }
    }
  }

  grouping ncs_rpc_notif_master-notif-hist-group {
    container notif-history {
      config false;
      container brief {
        config false;
        uses ncs_rpc_notif_notif-hist-group-brief;
      }
      container detail {
        config false;
        uses ncs_rpc_notif_notif-hist-group-detail;
      }
    }
  }

  grouping ncs_rpc_notif_slave-notif-hist-group {
    container notif-history {
      config false;
      container brief {
        config false;
        uses ncs_rpc_notif_notif-hist-group-brief;
      }
      container detail {
        config false;
        uses ncs_rpc_notif_notif-hist-group-detail;
      }
    }
  }

  grouping ncs_rpc_notif_notif-hist-group-brief {
    list location {
      key "location";
      leaf location {
        type string;
      }
      container card_notif_hist_brief {
        leaf-list card_notif_hist_brief_values {
          type string;
        }
      }
    }
  }

  grouping ncs_rpc_notif_notif-hist-group-detail {
    list location {
      key "location";
      leaf location {
        type string;
      }
      container card_notif_hist_detail {
        leaf-list card_notif_hist_detail_values {
          type string;
        }
      }
    }
  }

  grouping ncs_rpc_notif_i2c-dev-group {
    container i2c-dev {
      config false;
      uses ncs_rpc_notif_cpu-complex-group;
      uses ncs_rpc_notif_io-expander-group;
      uses ncs_rpc_notif_cdr-group;
    }
  }

  grouping ncs_rpc_notif_cpu-complex-group {
    container cpu-complex {
      config false;
      list location {
        key "location";
        leaf location {
          type string;
        }
        container cpu_complex_detail {
          leaf-list cpu_complex_values {
            type string;
          }
        }
      }
    }
  }

  grouping ncs_rpc_notif_io-expander-group {
    container ioexpander {
      config false;
      list location {
        key "location";
        leaf location {
          type string;
        }
        container io_exp_val {
          leaf-list io_exp_details {
            type string;
          }
        }
      }
    }
  }

  grouping ncs_rpc_notif_cdr-group {
    container cdr {
      config false;
      uses ncs_rpc_notif_master-cdr-group;
      uses ncs_rpc_notif_slave-cdr-group;
    }
  }

  grouping ncs_rpc_notif_master-cdr-group {
    container master {
      config false;
      container summary {
        config false;
        uses ncs_rpc_notif_summary-group;
      }
      container version {
        config false;
        uses ncs_rpc_notif_version-group;
      }
      container si_dump {
        config false;
        uses ncs_rpc_notif_si-dump-group;
      }
      container eye_scan {
        config false;
        uses ncs_rpc_notif_eye-scan-group;
      }
    }
  }

  grouping ncs_rpc_notif_slave-cdr-group {
    container slave {
      config false;
      container summary {
        config false;
        uses ncs_rpc_notif_summary-group;
      }
      container version {
        config false;
        uses ncs_rpc_notif_version-group;
      }
      container si_dump {
        config false;
        uses ncs_rpc_notif_si-dump-group;
      }
      container eye_scan {
        config false;
        uses ncs_rpc_notif_eye-scan-group;
      }
    }
  }

  grouping ncs_rpc_notif_summary-group {
    list location {
      key "location";
      leaf location {
        type string;
      }
      container cdr_status {
        leaf-list cdr_summary_status {
          type string;
        }
      }
    }
  }

  grouping ncs_rpc_notif_version-group {
    list location {
      config false;
      key "location";
      leaf location {
        type string;
      }
      uses ncs_rpc_notif_cdr-number-group;
    }
  }

  grouping ncs_rpc_notif_cdr-number-group {
    list cdr_number {
      config false;
      key "cdr_num";
      leaf cdr_num {
        type ncs_rpc_notif_cdrNumber;
        description
          "CDR number";
      }
      list cdr_version_data {
        leaf version_data {
          type string;
        }
      }
    }
  }

  grouping ncs_rpc_notif_si-dump-group {
    list location {
      config false;
      key "location";
      leaf location {
        type string;
      }
      uses ncs_rpc_notif_si-group;
    }
  }

  grouping ncs_rpc_notif_si-group {
    list cdr_number {
      config false;
      key "cdr_num";
      leaf cdr_num {
        type ncs_rpc_notif_cdrNumber;
        description
          "CDR number";
      }
      list lane {
        config false;
        key "lane_mask";
        leaf lane_mask {
          type ncs_rpc_notif_laneMask;
          description
            "Lane mask";
        }
        list cdr_si_dump_data {
          leaf si_dump_data {
            type string;
          }
        }
      }
    }
  }

  grouping ncs_rpc_notif_eye-scan-group {
    list location {
      config false;
      key "location";
      leaf location {
        type string;
      }
      uses ncs_rpc_notif_cdr-eye-scan-group;
    }
  }

  grouping ncs_rpc_notif_cdr-eye-scan-group {
    list cdr_number {
      config false;
      key "cdr_num";
      leaf cdr_num {
        type ncs_rpc_notif_cdrNumber;
        description
          "CDR number";
      }
      list lane {
        config false;
        key "lane_mask";
        leaf lane_mask {
          type ncs_rpc_notif_laneMask;
          description
            "Lane mask";
        }
        list cdr_eye_scan_data {
          leaf eye_scan_data {
            type string;
          }
        }
      }
    }
  }

  grouping ncs_rpc_notif_ccc-action-group {
    container action {
      config false;
      container register {
        config false;
        list location {
          key "location";
          config false;
          leaf location {
            type string;
          }
        }
      }
    }
  }

  grouping ncs_rpc_notif_master-oir-hist-group {
    container oir-history {
      config false;
      uses ncs_rpc_notif_oir-hist-group;
    }
  }

  grouping ncs_rpc_notif_slave-oir-hist-group {
    container oir-history {
      config false;
      uses ncs_rpc_notif_oir-hist-group;
    }
  }

  grouping ncs_rpc_notif_oir-hist-group {
    list rack {
      key "rack";
      leaf rack {
        type string;
      }
      container card_oir_hist {
        leaf-list card_oir_events {
          type string;
        }
      }
    }
  }

  grouping ncs_rpc_notif_ethernet-group {
    container ethernet {
      config false;
      uses ncs_rpc_notif_ethernet-status;
      uses ncs_rpc_notif_ethernet-counters;
    }
  }

  grouping ncs_rpc_notif_ethernet-status {
    container ethernet_status {
      config false;
      list location {
        key "location";
        leaf location {
          type string;
        }
        container ethernet_status {
          leaf-list ethernet_status_values {
            type string;
          }
        }
      }
    }
  }

  grouping ncs_rpc_notif_ethernet-counters {
    container ethernet_counters {
      config false;
      list location {
        key "location";
        leaf location {
          type string;
        }
        container ethernet_counters {
          leaf-list ethernet_counter_values {
            type string;
          }
        }
      }
    }
  }

  grouping ncs_rpc_notif_tla-dump-group {
    container tla-dump {
      config false;
      list location {
        config false;
        key "location";
        leaf location {
          type string;
        }
        container tla-dump {
          leaf-list ccc_tla_register_dump {
            type string;
          }
        }
      }
    }
  }

  grouping live_ncs_ccc-grp {
    container ccc_driver {
      uses show_trace:live_ncs_traceable;
      uses live_ncs_show-ccc-cli-group-master;
      uses live_ncs_show-ccc-cli-group-slave;
      uses live_ncs_ccc-action-group;
    }
  }

  grouping live_ncs_show-ccc-cli-group-master {
    uses live_ncs_bootflash-group;
    uses live_ncs_inventory-group;
    uses live_ncs_power-group;
    uses live_ncs_reset-hist-group;
    uses live_ncs_register-group;
    uses live_ncs_ejector-group;
    uses live_ncs_i2c-dev-group;
    uses live_ncs_ethernet-group;
    uses live_ncs_tla-dump-group;
    uses live_ncs_master-event-hist-group;
    uses live_ncs_master-oir-hist-group;
    uses live_ncs_master-notif-hist-group;
  }

  grouping live_ncs_show-ccc-cli-group-slave {
    container slave {
      uses live_ncs_slave-event-hist-group;
      uses live_ncs_slave-notif-hist-group;
      uses live_ncs_slave-oir-hist-group;
    }
  }

  grouping live_ncs_bootflash-group {
    container bootflash {
      container info {
        list location {
          key "location";
          leaf location {
            type string;
          }
          container bf_info {
            leaf-list bf_info_values {
              type string;
            }
          }
        }
      }
      container status {
        list location {
          key "location";
          leaf location {
            type string;
          }
          container bf_status {
            leaf-list bf_status_values {
              type string;
            }
          }
        }
      }
      container cre_status {
        list location {
          key "location";
          leaf location {
            type string;
          }
          container bf_status {
            leaf-list bf_status_values {
              type string;
            }
          }
        }
      }
    }
  }

  grouping live_ncs_master-health-group {
    container health {
      uses live_ncs_health-group;
    }
  }

  grouping live_ncs_slave-health-group {
    container health {
      uses live_ncs_health-group;
    }
  }

  grouping live_ncs_health-group {
    list location {
      key "location";
      leaf location {
        type string;
      }
      container health_status {
        leaf-list health_status_values {
          type string;
        }
      }
    }
  }

  grouping live_ncs_inventory-group {
    container inventory {
      uses live_ncs_inventory-summary-group;
      uses live_ncs_inventory-status-group;
      uses live_ncs_inventory-detail-group;
    }
  }

  grouping live_ncs_inventory-summary-group {
    container summary {
      list ccc_inv_summary {
        key "location";
        leaf location {
          type string;
          // NCS drop mandatory statement
        }
        leaf ccc_inv_PID_string {
          type string;
        }
        leaf ccc_inv_slot_number {
          type uint32;
        }
        leaf ccc_inv_serial_number {
          type string;
        }
        leaf ccc_inv_hw_version {
          type string;
        }
        leaf ccc_inv_card_state {
          type string;
        }
      }
    }
    container version {
      list ccc_inv_version {
        key "location";
        leaf location {
          type string;
          // NCS drop mandatory statement
        }
        leaf ccc_inv_PID_string {
          type string;
        }
        leaf ccc_inv_ccc_version {
          type string;
        }
        leaf ccc_inv_FPGA_version {
          type string;
        }
        leaf ccc_inv_pon_version {
          type string;
        }
        leaf ccc_inv_switch_version {
          type string;
        }
      }
    }
  }

  grouping live_ncs_inventory-status-group {
    container status {
      list ccc_inv_status {
        key "location";
        leaf location {
          type string;
          // NCS drop mandatory statement
        }
        container ccc_inv_status_list {
          leaf-list ccc_inv_status_values {
            type string;
          }
        }
      }
    }
  }

  grouping live_ncs_inventory-detail-group {
    container detail {
      list ccc_inv_detail {
        key "location";
        leaf location {
          type string;
        }
        container ccc_inv_detail_list {
          leaf-list ccc_inv_detail_values {
            type string;
          }
        }
      }
    }
  }

  grouping live_ncs_power-group {
    container power {
      uses live_ncs_ccc-master-access-group;
    }
  }

  grouping live_ncs_ccc-master-access-group {
    container master-access {
      uses live_ncs_ccc-power-summary-group;
      uses live_ncs_ccc-power-detail-group;
    }
  }

  grouping live_ncs_ccc-power-summary-group {
    container summary {
      list power_summary {
        key "ccc_power_location";
        leaf ccc_power_location {
          type string;
          // NCS drop mandatory statement
        }
        leaf card_type {
          type string;
        }
        leaf power_state {
          type string;
        }
      }
    }
  }

  grouping live_ncs_ccc-power-detail-group {
    container detail {
      list location {
        key "location";
        leaf location {
          type string;
        }
        container power_details {
          leaf-list power_details_values {
            type string;
          }
        }
      }
    }
  }

  grouping live_ncs_reset-hist-group {
    container reset-history {
      uses live_ncs_reset-hist-chip-group;
      uses live_ncs_reset-hist-onboard-group;
    }
  }

  grouping live_ncs_reset-hist-chip-group {
    container onchip {
      list location {
        key "loc";
        leaf loc {
          type string;
        }
        leaf ccc_reset_timeofday {
          type string;
        }
        leaf ccc_reset_uptime {
          type string;
        }
        leaf ccc_hw_reset_count {
          type uint32;
        }
        list ccc_reset_entry {
          key "ccc_reset_entry";
          leaf ccc_reset_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping live_ncs_reset-hist-onboard-group {
    container onboard {
      list location {
        key "loc";
        leaf loc {
          type string;
        }
        leaf ccc_reset_scratch_sig {
          type string;
        }
        leaf ccc_reset_scratch_version {
          type uint32;
        }
        leaf ccc_reset_history_sig {
          type string;
        }
        leaf ccc_reset_history_count {
          type uint32;
        }
        leaf ccc_reset_history_disp {
          type uint32;
        }
        list ccc_reset_onboard_entry {
          key "ccc_reset_onboard_entry";
          leaf ccc_reset_onboard_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping live_ncs_register-group {
    container register {
      list register_location {
        key "register_location";
        leaf register_location {
          type string;
        }
        uses live_ncs_ccc-block-number-group;
        uses live_ncs_ccc-offset-group;
        uses live_ncs_ccc-address-group;
      }
    }
  }

  grouping live_ncs_ccc-block-number-group {
    list ccc_block_number {
      key "ccc_block_num";
      leaf ccc_block_num {
        type uint32;
      }
      leaf block_location {
        type string;
      }
      leaf ccc_block_nm {
        type string;
      }
      list ccc_register_number {
        key "index";
        leaf index {
          type uint32;
        }
        leaf ccc_register_name {
          type string;
        }
        list ccc_data {
          leaf name {
            type string;
          }
          leaf offset {
            type uint32;
          }
          leaf value {
            type uint32;
          }
        }
      }
    }
  }

  grouping live_ncs_ccc-offset-group {
    list ccc_offset {
      key "hex_offset";
      leaf hex_offset {
        type live_ncs_HexOffset;
      }
      list ccc_reg_offset_data {
        leaf ccc_reg_off_addr {
          type uint32;
        }
        leaf reg_off_value {
          type string;
        }
      }
    }
  }

  grouping live_ncs_ccc-address-group {
    list ccc_address {
      key "start_hex_addr end_hex_addr";
      leaf start_hex_addr {
        type live_ncs_startHexOffset;
      }
      leaf end_hex_addr {
        type live_ncs_endHexOffset;
      }
      list ccc_reg_range_addr_list {
        key "ccc_reg_range_addr";
        leaf ccc_reg_range_addr {
          type uint32;
        }
        list ccc_reg_data {
          leaf ccc_reg_addr {
            type uint32;
          }
          leaf reg_value {
            type string;
          }
        }
      }
    }
  }

  grouping live_ncs_ejector-group {
    container ejector {
      uses live_ncs_ejector-status-group;
    }
  }

  grouping live_ncs_ejector-status-group {
    container status {
      list ccc_ejector_status {
        key "location";
        leaf location {
          type string;
        }
        leaf ccc_is_fc_card_type {
          type boolean;
          // NCS drop default statement
        }
        leaf ccc_is_lc_card_type {
          type boolean;
          // NCS drop default statement
        }
        leaf ccc_is_rp_sc_card_type {
          type boolean;
          // NCS drop default statement
        }
        leaf ccc_ejc_card_type {
          type uint32;
        }
        leaf ccc_ejc_platform {
          type uint32;
        }
        leaf ccc_ejc_board_type {
          type string;
        }
        leaf ccc_ejc_card_slot {
          type uint32;
        }
        leaf ccc_ejc_card_version {
          type string;
        }
        leaf ccc_ejc_board_version {
          type string;
        }
        leaf ccc_ejc_hw_version {
          type string;
        }
        leaf ccc_ejc_core_version {
          type string;
        }
        leaf ccc_ejc_pon_version {
          type string;
        }
        leaf ccc_ejc_rp_supported {
          type string;
        }
        leaf ccc_ejc_enable {
          type string;
        }
        leaf ccc_ejc_status {
          type string;
        }
        leaf ccc_ejc_rp_pex_csr {
          type string;
        }
        leaf ccc_ejc_gp_live {
          type string;
        }
        leaf ccc_ejc_gp_status {
          type string;
        }
        leaf ccc_ejc_fc_pex_csr {
          type string;
        }
        leaf ccc_ejc_fc_ejector_support {
          type string;
        }
        leaf ccc_ejc_lc_pex_csr {
          type string;
        }
        leaf ccc_ejc_lc_ejector_support {
          type string;
        }
      }
    }
  }

  grouping live_ncs_master-event-hist-group {
    container event-history {
      container brief {
        uses live_ncs_event-hist-group-brief;
      }
      container detail {
        uses live_ncs_event-hist-group-detail;
      }
    }
  }

  grouping live_ncs_slave-event-hist-group {
    container event-history {
      container brief {
        uses live_ncs_event-hist-group-brief;
      }
      container detail {
        uses live_ncs_event-hist-group-detail;
      }
    }
  }

  grouping live_ncs_event-hist-group-brief {
    list location {
      key "location";
      leaf location {
        type string;
      }
      container card_event_hist_brief {
        leaf-list card_event_hist_brief_values {
          type string;
        }
      }
    }
  }

  grouping live_ncs_event-hist-group-detail {
    list location {
      key "location";
      leaf location {
        type string;
      }
      container card_event_hist_detail {
        leaf-list card_event_hist_detail_values {
          type string;
        }
      }
    }
  }

  grouping live_ncs_master-notif-hist-group {
    container notif-history {
      container brief {
        uses live_ncs_notif-hist-group-brief;
      }
      container detail {
        uses live_ncs_notif-hist-group-detail;
      }
    }
  }

  grouping live_ncs_slave-notif-hist-group {
    container notif-history {
      container brief {
        uses live_ncs_notif-hist-group-brief;
      }
      container detail {
        uses live_ncs_notif-hist-group-detail;
      }
    }
  }

  grouping live_ncs_notif-hist-group-brief {
    list location {
      key "location";
      leaf location {
        type string;
      }
      container card_notif_hist_brief {
        leaf-list card_notif_hist_brief_values {
          type string;
        }
      }
    }
  }

  grouping live_ncs_notif-hist-group-detail {
    list location {
      key "location";
      leaf location {
        type string;
      }
      container card_notif_hist_detail {
        leaf-list card_notif_hist_detail_values {
          type string;
        }
      }
    }
  }

  grouping live_ncs_i2c-dev-group {
    container i2c-dev {
      uses live_ncs_cpu-complex-group;
      uses live_ncs_io-expander-group;
      uses live_ncs_cdr-group;
    }
  }

  grouping live_ncs_cpu-complex-group {
    container cpu-complex {
      list location {
        key "location";
        leaf location {
          type string;
        }
        container cpu_complex_detail {
          leaf-list cpu_complex_values {
            type string;
          }
        }
      }
    }
  }

  grouping live_ncs_io-expander-group {
    container ioexpander {
      list location {
        key "location";
        leaf location {
          type string;
        }
        container io_exp_val {
          leaf-list io_exp_details {
            type string;
          }
        }
      }
    }
  }

  grouping live_ncs_cdr-group {
    container cdr {
      uses live_ncs_master-cdr-group;
      uses live_ncs_slave-cdr-group;
    }
  }

  grouping live_ncs_master-cdr-group {
    container master {
      container summary {
        uses live_ncs_summary-group;
      }
      container version {
        uses live_ncs_version-group;
      }
      container si_dump {
        uses live_ncs_si-dump-group;
      }
      container eye_scan {
        uses live_ncs_eye-scan-group;
      }
    }
  }

  grouping live_ncs_slave-cdr-group {
    container slave {
      container summary {
        uses live_ncs_summary-group;
      }
      container version {
        uses live_ncs_version-group;
      }
      container si_dump {
        uses live_ncs_si-dump-group;
      }
      container eye_scan {
        uses live_ncs_eye-scan-group;
      }
    }
  }

  grouping live_ncs_summary-group {
    list location {
      key "location";
      leaf location {
        type string;
      }
      container cdr_status {
        leaf-list cdr_summary_status {
          type string;
        }
      }
    }
  }

  grouping live_ncs_version-group {
    list location {
      key "location";
      leaf location {
        type string;
      }
      uses live_ncs_cdr-number-group;
    }
  }

  grouping live_ncs_cdr-number-group {
    list cdr_number {
      key "cdr_num";
      leaf cdr_num {
        type live_ncs_cdrNumber;
        description
          "CDR number";
      }
      list cdr_version_data {
        leaf version_data {
          type string;
        }
      }
    }
  }

  grouping live_ncs_si-dump-group {
    list location {
      key "location";
      leaf location {
        type string;
      }
      uses live_ncs_si-group;
    }
  }

  grouping live_ncs_si-group {
    list cdr_number {
      key "cdr_num";
      leaf cdr_num {
        type live_ncs_cdrNumber;
        description
          "CDR number";
      }
      list lane {
        key "lane_mask";
        leaf lane_mask {
          type live_ncs_laneMask;
          description
            "Lane mask";
        }
        list cdr_si_dump_data {
          leaf si_dump_data {
            type string;
          }
        }
      }
    }
  }

  grouping live_ncs_eye-scan-group {
    list location {
      key "location";
      leaf location {
        type string;
      }
      uses live_ncs_cdr-eye-scan-group;
    }
  }

  grouping live_ncs_cdr-eye-scan-group {
    list cdr_number {
      key "cdr_num";
      leaf cdr_num {
        type live_ncs_cdrNumber;
        description
          "CDR number";
      }
      list lane {
        key "lane_mask";
        leaf lane_mask {
          type live_ncs_laneMask;
          description
            "Lane mask";
        }
        list cdr_eye_scan_data {
          leaf eye_scan_data {
            type string;
          }
        }
      }
    }
  }

  grouping live_ncs_ccc-action-group {
    container action {
      container register {
        list location {
          key "location";
          leaf location {
            type string;
          }
        }
      }
    }
  }

  grouping live_ncs_master-oir-hist-group {
    container oir-history {
      uses live_ncs_oir-hist-group;
    }
  }

  grouping live_ncs_slave-oir-hist-group {
    container oir-history {
      uses live_ncs_oir-hist-group;
    }
  }

  grouping live_ncs_oir-hist-group {
    list rack {
      key "rack";
      leaf rack {
        type string;
      }
      container card_oir_hist {
        leaf-list card_oir_events {
          type string;
        }
      }
    }
  }

  grouping live_ncs_ethernet-group {
    container ethernet {
      uses live_ncs_ethernet-status;
      uses live_ncs_ethernet-counters;
    }
  }

  grouping live_ncs_ethernet-status {
    container ethernet_status {
      list location {
        key "location";
        leaf location {
          type string;
        }
        container ethernet_status {
          leaf-list ethernet_status_values {
            type string;
          }
        }
      }
    }
  }

  grouping live_ncs_ethernet-counters {
    container ethernet_counters {
      list location {
        key "location";
        leaf location {
          type string;
        }
        container ethernet_counters {
          leaf-list ethernet_counter_values {
            type string;
          }
        }
      }
    }
  }

  grouping live_ncs_tla-dump-group {
    container tla-dump {
      list location {
        key "location";
        leaf location {
          type string;
        }
        container tla-dump {
          leaf-list ccc_tla_register_dump {
            type string;
          }
        }
      }
    }
  }

  grouping ccc-grp {
    container ccc_driver {
      uses show_trace:traceable;
      uses show-ccc-cli-group-master;
      uses show-ccc-cli-group-slave;
      uses ccc-action-group;
    }
  }

  grouping show-ccc-cli-group-master {
    uses bootflash-group;
    uses inventory-group;
    uses power-group;
    uses reset-hist-group;
    uses register-group;
    uses ejector-group;
    uses i2c-dev-group;
    uses ethernet-group;
    uses tla-dump-group;
    uses master-event-hist-group;
    uses master-oir-hist-group;
    uses master-notif-hist-group;
  }

  grouping show-ccc-cli-group-slave {
    container slave {
      uses slave-event-hist-group;
      uses slave-notif-hist-group;
      uses slave-oir-hist-group;
    }
  }

  grouping bootflash-group {
    // NCS drop config false container bootflash
  }

  grouping master-health-group {
    // NCS drop config false container health
  }

  grouping slave-health-group {
    // NCS drop config false container health
  }

  grouping health-group {
    list location {
      key "location";
      leaf location {
        type string;
      }
      container health_status {
        leaf-list health_status_values {
          type string;
        }
      }
    }
  }

  grouping inventory-group {
    // NCS drop config false container inventory
  }

  grouping inventory-summary-group {
    // NCS drop config false container summary
    // NCS drop config false container version
  }

  grouping inventory-status-group {
    // NCS drop config false container status
  }

  grouping inventory-detail-group {
    // NCS drop config false container detail
  }

  grouping power-group {
    // NCS drop config false container power
  }

  grouping ccc-master-access-group {
    // NCS drop config false container 'master-access'
  }

  grouping ccc-power-summary-group {
    // NCS drop config false container summary
  }

  grouping ccc-power-detail-group {
    // NCS drop config false container detail
  }

  grouping reset-hist-group {
    // NCS drop config false container 'reset-history'
  }

  grouping reset-hist-chip-group {
    // NCS drop config false container onchip
  }

  grouping reset-hist-onboard-group {
    // NCS drop config false container onboard
  }

  grouping register-group {
    // NCS drop config false container register
  }

  grouping ccc-block-number-group {
    // NCS drop config false list ccc_block_number
  }

  grouping ccc-offset-group {
    // NCS drop config false list ccc_offset
  }

  grouping ccc-address-group {
    // NCS drop config false list ccc_address
  }

  grouping ejector-group {
    // NCS drop config false container ejector
  }

  grouping ejector-status-group {
    // NCS drop config false container status
  }

  grouping master-event-hist-group {
    // NCS drop config false container 'event-history'
  }

  grouping slave-event-hist-group {
    // NCS drop config false container 'event-history'
  }

  grouping event-hist-group-brief {
    list location {
      key "location";
      leaf location {
        type string;
      }
      container card_event_hist_brief {
        leaf-list card_event_hist_brief_values {
          type string;
        }
      }
    }
  }

  grouping event-hist-group-detail {
    list location {
      key "location";
      leaf location {
        type string;
      }
      container card_event_hist_detail {
        leaf-list card_event_hist_detail_values {
          type string;
        }
      }
    }
  }

  grouping master-notif-hist-group {
    // NCS drop config false container 'notif-history'
  }

  grouping slave-notif-hist-group {
    // NCS drop config false container 'notif-history'
  }

  grouping notif-hist-group-brief {
    list location {
      key "location";
      leaf location {
        type string;
      }
      container card_notif_hist_brief {
        leaf-list card_notif_hist_brief_values {
          type string;
        }
      }
    }
  }

  grouping notif-hist-group-detail {
    list location {
      key "location";
      leaf location {
        type string;
      }
      container card_notif_hist_detail {
        leaf-list card_notif_hist_detail_values {
          type string;
        }
      }
    }
  }

  grouping i2c-dev-group {
    // NCS drop config false container 'i2c-dev'
  }

  grouping cpu-complex-group {
    // NCS drop config false container 'cpu-complex'
  }

  grouping io-expander-group {
    // NCS drop config false container ioexpander
  }

  grouping cdr-group {
    // NCS drop config false container cdr
  }

  grouping master-cdr-group {
    // NCS drop config false container master
  }

  grouping slave-cdr-group {
    // NCS drop config false container slave
  }

  grouping summary-group {
    list location {
      key "location";
      leaf location {
        type string;
      }
      container cdr_status {
        leaf-list cdr_summary_status {
          type string;
        }
      }
    }
  }

  grouping version-group {
    // NCS drop config false list location
  }

  grouping cdr-number-group {
    // NCS drop config false list cdr_number
  }

  grouping si-dump-group {
    // NCS drop config false list location
  }

  grouping si-group {
    // NCS drop config false list cdr_number
  }

  grouping eye-scan-group {
    // NCS drop config false list location
  }

  grouping cdr-eye-scan-group {
    // NCS drop config false list cdr_number
  }

  grouping ccc-action-group {
    // NCS drop config false container action
  }

  grouping master-oir-hist-group {
    // NCS drop config false container 'oir-history'
  }

  grouping slave-oir-hist-group {
    // NCS drop config false container 'oir-history'
  }

  grouping oir-hist-group {
    list rack {
      key "rack";
      leaf rack {
        type string;
      }
      container card_oir_hist {
        leaf-list card_oir_events {
          type string;
        }
      }
    }
  }

  grouping ethernet-group {
    // NCS drop config false container ethernet
  }

  grouping ethernet-status {
    // NCS drop config false container ethernet_status
  }

  grouping ethernet-counters {
    // NCS drop config false container ethernet_counters
  }

  grouping tla-dump-group {
    // NCS drop config false container 'tla-dump'
  }
}

module fit {
  // Generated by yanger -t ncs
  tailf:mount-id "cisco-iosxr-nc-7.3:cisco-iosxr-nc-7.3";
  tailf:ncs-device-type "netconf";

  namespace "http://cisco.com/panini/calvados/fit";
  prefix fit;

  import tailf-common {
    prefix tailf;
  }
  import Cisco-IOS-XR-sysadmin-types {
    prefix calvados;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2018-06-16 {
    description
      "Remove the duplicate entry of container set";
  }
  revision 2012-05-20 {
    description
      "Initial revision";
  }

  grouping ncs_template_fit-cmd-end-grp {
    list location {
      // NCS patched for predictable order
      ordered-by user;
      key "fit-location-name";
      leaf fit-location-name {
        type calvados:ncs_template_location-id;
      }
    }
  }

  grouping ncs_template_fit-rate-grp {
    container rate {
      list error-number {
        // NCS patched for predictable order
        ordered-by user;
        key "num-errs";
        leaf num-errs {
          type string;
        }
        list duration {
          // NCS patched for predictable order
          ordered-by user;
          key "num-seconds";
          leaf num-seconds {
            type string;
          }
          uses ncs_template_fit-cmd-end-grp;
        }
      }
    }
  }

  grouping ncs_template_fit-thresh-grp {
    list threshold {
      // NCS patched for predictable order
      ordered-by user;
      key "num-seconds";
      leaf num-seconds {
        type string;
        // NCS drop mandatory statement
      }
      uses ncs_template_fit-cmd-end-grp;
    }
  }

  grouping ncs_template_fit-block-grp {
    container all {
      uses ncs_template_fit-thresh-grp;
      uses ncs_template_fit-cmd-end-grp;
    }
    list block-name-lst {
      // NCS patched for predictable order
      ordered-by user;
      key "block-name";
      leaf block-name {
        type string;
      }
      container one {
        uses ncs_template_fit-rate-grp;
        uses ncs_template_fit-cmd-end-grp;
      }
      container continuous {
        uses ncs_template_fit-rate-grp;
        uses ncs_template_fit-cmd-end-grp;
      }
      container stop {
        uses ncs_template_fit-cmd-end-grp;
      }
    }
  }

  grouping ncs_template_fit-module-grp {
    list module {
      // NCS patched for predictable order
      ordered-by user;
      key "module-name";
      leaf module-name {
        type string;
      }
      container fault-type {
        container ecc {
          uses ncs_template_fit-block-grp;
        }
        container parity {
          uses ncs_template_fit-block-grp;
        }
        container other {
          uses ncs_template_fit-block-grp;
        }
      }
    }
  }

  grouping ncs_template_fit-grp {
    // NCS drop config false list asic
  }

  grouping ncs_rpc_notif_fit-cmd-end-grp {
    list location {
      key "fit-location-name";
      leaf fit-location-name {
        type calvados:ncs_rpc_notif_location-id;
      }
    }
  }

  grouping ncs_rpc_notif_fit-rate-grp {
    container rate {
      list error-number {
        key "num-errs";
        leaf num-errs {
          type uint32;
        }
        list duration {
          key "num-seconds";
          leaf num-seconds {
            type uint32;
          }
          uses ncs_rpc_notif_fit-cmd-end-grp;
        }
      }
    }
  }

  grouping ncs_rpc_notif_fit-thresh-grp {
    list threshold {
      key "num-seconds";
      leaf num-seconds {
        type uint32;
        mandatory true;
      }
      uses ncs_rpc_notif_fit-cmd-end-grp;
    }
  }

  grouping ncs_rpc_notif_fit-block-grp {
    container all {
      uses ncs_rpc_notif_fit-thresh-grp;
      uses ncs_rpc_notif_fit-cmd-end-grp;
    }
    list block-name-lst {
      key "block-name";
      leaf block-name {
        type string;
      }
      container one {
        uses ncs_rpc_notif_fit-rate-grp;
        uses ncs_rpc_notif_fit-cmd-end-grp;
      }
      container continuous {
        uses ncs_rpc_notif_fit-rate-grp;
        uses ncs_rpc_notif_fit-cmd-end-grp;
      }
      container stop {
        uses ncs_rpc_notif_fit-cmd-end-grp;
      }
    }
  }

  grouping ncs_rpc_notif_fit-module-grp {
    list module {
      key "module-name";
      leaf module-name {
        type string;
      }
      container fault-type {
        container ecc {
          uses ncs_rpc_notif_fit-block-grp;
        }
        container parity {
          uses ncs_rpc_notif_fit-block-grp;
        }
        container other {
          uses ncs_rpc_notif_fit-block-grp;
        }
      }
    }
  }

  grouping ncs_rpc_notif_fit-grp {
    list asic {
      config false;
      key "asic-name";
      leaf asic-name {
        type string;
      }
      list instance {
        key "instance-ids";
        leaf instance-ids {
          type uint32;
        }
        container fault-injection {
          uses ncs_rpc_notif_fit-module-grp;
        }
      }
    }
  }

  grouping live_ncs_fit-cmd-end-grp {
    list location {
      key "fit-location-name";
      leaf fit-location-name {
        type calvados:live_ncs_location-id;
      }
    }
  }

  grouping live_ncs_fit-rate-grp {
    container rate {
      list error-number {
        key "num-errs";
        leaf num-errs {
          type uint32;
        }
        list duration {
          key "num-seconds";
          leaf num-seconds {
            type uint32;
          }
          uses live_ncs_fit-cmd-end-grp;
        }
      }
    }
  }

  grouping live_ncs_fit-thresh-grp {
    list threshold {
      key "num-seconds";
      leaf num-seconds {
        type uint32;
        // NCS drop mandatory statement
      }
      uses live_ncs_fit-cmd-end-grp;
    }
  }

  grouping live_ncs_fit-block-grp {
    container all {
      uses live_ncs_fit-thresh-grp;
      uses live_ncs_fit-cmd-end-grp;
    }
    list block-name-lst {
      key "block-name";
      leaf block-name {
        type string;
      }
      container one {
        uses live_ncs_fit-rate-grp;
        uses live_ncs_fit-cmd-end-grp;
      }
      container continuous {
        uses live_ncs_fit-rate-grp;
        uses live_ncs_fit-cmd-end-grp;
      }
      container stop {
        uses live_ncs_fit-cmd-end-grp;
      }
    }
  }

  grouping live_ncs_fit-module-grp {
    list module {
      key "module-name";
      leaf module-name {
        type string;
      }
      container fault-type {
        container ecc {
          uses live_ncs_fit-block-grp;
        }
        container parity {
          uses live_ncs_fit-block-grp;
        }
        container other {
          uses live_ncs_fit-block-grp;
        }
      }
    }
  }

  grouping live_ncs_fit-grp {
    list asic {
      key "asic-name";
      leaf asic-name {
        type string;
      }
      list instance {
        key "instance-ids";
        leaf instance-ids {
          type uint32;
        }
        container fault-injection {
          uses live_ncs_fit-module-grp;
        }
      }
    }
  }

  grouping fit-cmd-end-grp {
    list location {
      key "fit-location-name";
      leaf fit-location-name {
        type calvados:location-id;
      }
    }
  }

  grouping fit-rate-grp {
    container rate {
      list error-number {
        key "num-errs";
        leaf num-errs {
          type uint32;
        }
        list duration {
          key "num-seconds";
          leaf num-seconds {
            type uint32;
          }
          uses fit-cmd-end-grp;
        }
      }
    }
  }

  grouping fit-thresh-grp {
    list threshold {
      key "num-seconds";
      leaf num-seconds {
        type uint32;
        mandatory true;
      }
      uses fit-cmd-end-grp;
    }
  }

  grouping fit-block-grp {
    container all {
      uses fit-thresh-grp;
      uses fit-cmd-end-grp;
    }
    list block-name-lst {
      key "block-name";
      leaf block-name {
        type string;
      }
      container one {
        uses fit-rate-grp;
        uses fit-cmd-end-grp;
      }
      container continuous {
        uses fit-rate-grp;
        uses fit-cmd-end-grp;
      }
      container stop {
        uses fit-cmd-end-grp;
      }
    }
  }

  grouping fit-module-grp {
    list module {
      key "module-name";
      leaf module-name {
        type string;
      }
      container fault-type {
        container ecc {
          uses fit-block-grp;
        }
        container parity {
          uses fit-block-grp;
        }
        container other {
          uses fit-block-grp;
        }
      }
    }
  }

  grouping fit-grp {
    // NCS drop config false list asic
  }
}

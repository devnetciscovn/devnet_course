module Cisco-IOS-XR-mpls-ldp-oper {
  // Generated by yanger -t ncs
  tailf:mount-id "cisco-iosxr-nc-7.3:cisco-iosxr-nc-7.3";
  tailf:ncs-device-type "netconf";

  namespace "http://cisco.com/ns/yang/Cisco-IOS-XR-mpls-ldp-oper";
  prefix mpls-ldp-oper;

  import ietf-inet-types {
    prefix inet;
  }
  import Cisco-IOS-XR-types {
    prefix xr;
  }
  import cisco-semver {
    prefix semver;
  }
  include Cisco-IOS-XR-mpls-ldp-oper-sub3 {
    revision-date 2021-04-06;
  }
  include Cisco-IOS-XR-mpls-ldp-oper-sub2 {
    revision-date 2021-04-06;
  }
  include Cisco-IOS-XR-mpls-ldp-oper-sub1 {
    revision-date 2021-04-06;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-ldp package operational data.

     This module contains definitions
     for the following management objects:
       mpls-ldp: MPLS LDP operational data

     Copyright (c) 2013-2021 by Cisco Systems, Inc.
     All rights reserved.";

  revision 2021-04-06 {
    description
      "Added BSID data in LDP forwarding
       2021-03-10
         Added adj_grp count leaf to ldp summary";
    semver:module-version "1.2.0";
  }
  revision 2020-08-14 {
    description
      "Added ELC parameter.";
    semver:module-version "1.1.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef ncs_template_Mpls-ldp-oper-af-name {
    type string;
    description
      "Mpls ldp oper af name";
  }

  typedef ncs_rpc_notif_Mpls-ldp-oper-af-name {
    type enumeration {
      enum "ipv4" {
        value 1;
        description
          "IPv4";
      }
      enum "ipv6" {
        value 2;
        description
          "IPv6";
      }
      enum "all" {
        value 65535;
        description
          "All";
      }
    }
    description
      "Mpls ldp oper af name";
  }

  typedef live_ncs_Mpls-ldp-oper-af-name {
    type enumeration {
      enum "ipv4" {
        value 1;
        description
          "IPv4";
      }
      enum "ipv6" {
        value 2;
        description
          "IPv6";
      }
      enum "all" {
        value 65535;
        description
          "All";
      }
    }
    description
      "Mpls ldp oper af name";
  }

  typedef Mpls-ldp-oper-af-name {
    type enumeration {
      enum "ipv4" {
        value 1;
        description
          "IPv4";
      }
      enum "ipv6" {
        value 2;
        description
          "IPv6";
      }
      enum "all" {
        value 65535;
        description
          "All";
      }
    }
    description
      "Mpls ldp oper af name";
  }

  grouping ncs_template_NSR-SUMMARY-ALL {
    description
      "Common node of active, standby, node";
    container nsr-summary-all {
      description
        "Summary information regarding LDP NSR State";
      uses ncs_template_LDP-NSR-SUM;
    }
  }

  grouping ncs_template_LDP-ID {
    description
      "Common node of default-vrf, vrf";
    container ldp-id {
      description
        "Local LDP Id";
      uses ncs_template_LDP-LDPID-INFO;
    }
  }

  grouping ncs_template_CAPABILITY-TABLE {
    description
      "Common node of default-vrf, vrf";
    container capabilities {
      description
        "LDP capability database information";
      list capability {
        // NCS patched for predictable order
        ordered-by user;
        key "capability-type";
        description
          "Information on LDP capability";
        leaf capability-type {
          type string;
          description
            "The capability type (IANA assigned)";
        }
        uses ncs_template_LDP-CAP-INFO;
      }
    }
  }

  grouping ncs_template_NEIGHBOR-CAPABILITY-TABLE {
    description
      "Common node of default-vrf, vrf";
    container neighbor-capabilities {
      description
        "LDP Neighbors Capabilities";
      list neighbor-capability {
        // NCS patched for predictable order
        ordered-by user;
        description
          "Information on capabilities of a particular LDP
           neighbor";
        leaf lsr-id {
          type string;
          description
            "LSR ID of neighbor";
        }
        leaf label-space-id {
          type string;
          description
            "Label space ID of neighbor";
        }
        uses ncs_template_LDP-NBR-CAP-INFO;
      }
    }
  }

  grouping ncs_template_VRF-TABLE {
    description
      "Common node of active, standby, node";
    container vrfs {
      description
        "VRF specific operational data";
      list vrf {
        // NCS patched for predictable order
        ordered-by user;
        key "vrf-name";
        description
          "Operational data for given VRF";
        leaf vrf-name {
          type xr:ncs_template_Cisco-ios-xr-string;
          description
            "VRF Name";
        }
        uses ncs_template_GRACEFUL-RESTART;
        uses ncs_template_CAPABILITY-TABLE;
        uses ncs_template_SUMMARY;
        uses ncs_template_AF-TABLE;
        uses ncs_template_NEIGHBOR-BRIEF-TABLE;
        uses ncs_template_BACKOFF-PARAMETERS;
        uses ncs_template_BACKOFF-TABLE;
        uses ncs_template_NSR;
        uses ncs_template_PARAMETERS;
        uses ncs_template_ISSU;
        uses ncs_template_NEIGHBOR-CAPABILITY-TABLE;
        uses ncs_template_NEIGHBOR-TABLE;
        uses ncs_template_LDP-ID;
        uses ncs_template_STATISTICS-TABLE;
      }
    }
  }

  grouping ncs_template_BACKOFF-PARAMETERS {
    description
      "Common node of default-vrf, vrf";
    container backoff-parameters {
      description
        "The LDP Backoff Parameters";
      uses ncs_template_LDP-BACKOFF-INFO;
    }
  }

  grouping ncs_template_HA-SUMMARY {
    description
      "Common node of nsr, issu";
    container ha-summary {
      description
        "LDP HA Summary";
      uses ncs_template_LDP-NSR-SUM;
    }
  }

  grouping ncs_template_STATISTICS-TABLE {
    description
      "Common node of default-vrf, vrf";
    container statistics {
      description
        "The LDP Statistics";
      list statistic {
        // NCS patched for predictable order
        ordered-by user;
        description
          "Statistical Information on a particular LDP
           neighbor";
        leaf lsr-id {
          type string;
          description
            "LSR ID of neighbor";
        }
        leaf label-space-id {
          type string;
          description
            "Label space ID of neighbor";
        }
        uses ncs_template_LDP-STATS-INFO;
      }
    }
  }

  grouping ncs_template_DISCOVERY-SUMMARY-ALL {
    description
      "Common node of active, standby, node";
    container discovery-summary-all {
      description
        "Summary information regarding LDP discovery";
      uses ncs_template_LDP-DISCOVERY-SUMMARY-INFO;
    }
  }

  grouping ncs_template_BINDINGS-SUMMARY-ALL {
    description
      "Common node of active, standby, node";
    container bindings-summary-all {
      description
        "Aggregate VRF counters for the LDP Label
         Infomation Base (LIB)";
      uses ncs_template_LDP-BINDING-SUMMARY;
    }
  }

  grouping ncs_template_DEFAULT-VRF {
    description
      "Common node of active, standby, node";
    container default-vrf {
      description
        "DefaultVRF specific operational data";
      uses ncs_template_GRACEFUL-RESTART;
      uses ncs_template_CAPABILITY-TABLE;
      uses ncs_template_SUMMARY;
      uses ncs_template_AF-TABLE;
      uses ncs_template_NEIGHBOR-BRIEF-TABLE;
      uses ncs_template_BACKOFF-PARAMETERS;
      uses ncs_template_BACKOFF-TABLE;
      uses ncs_template_NSR;
      uses ncs_template_PARAMETERS;
      uses ncs_template_ISSU;
      uses ncs_template_NEIGHBOR-CAPABILITY-TABLE;
      uses ncs_template_NEIGHBOR-TABLE;
      uses ncs_template_LDP-ID;
      uses ncs_template_STATISTICS-TABLE;
    }
  }

  grouping ncs_template_NEIGHBOR-BRIEF-TABLE {
    description
      "Common node of default-vrf, vrf";
    container neighbor-briefs {
      description
        "The LDP Neighbors (brief)";
      list neighbor-brief {
        // NCS patched for predictable order
        ordered-by user;
        description
          "Brief information on a particular LDP neighbor";
        leaf lsr-id {
          type string;
          description
            "LSR ID of neighbor";
        }
        leaf label-space-id {
          type string;
          description
            "Label space ID of neighbor";
        }
        uses ncs_template_LDP-NEIGHBOR-BRIEF-INFO;
      }
    }
  }

  grouping ncs_template_ATO-MDB-TABLE {
    description
      "Common node of active, standby, node";
    container ato-mdb-table-entries {
      description
        "AToM DB Table";
      list ato-mdb-table-entry {
        // NCS patched for predictable order
        ordered-by user;
        description
          "Entries in AToM DB";
        leaf peer-id {
          type string;
          description
            "Peer ID";
        }
        leaf fe-ctype {
          type string;
          description
            "FEC Type";
        }
        leaf pw-id {
          type string;
          description
            "PW ID";
        }
        leaf agi-type {
          type string;
          description
            "AGI Type";
        }
        leaf agi {
          type string;
          description
            "AGI";
        }
        leaf saii-type {
          type string;
          description
            "SAII Type";
        }
        leaf saii-local-id {
          type string;
          description
            "SAII Local ID";
        }
        leaf saii-global-id {
          type string;
          description
            "SAII Global ID";
        }
        leaf saii-prefix {
          type xr:ncs_template_Hex-integer;
          description
            "SAII Prefix";
        }
        leaf saii-ac-id {
          type string;
          description
            "SAII AC ID";
        }
        leaf taii-type {
          type string;
          description
            "TAII Type";
        }
        leaf taii-local-id {
          type string;
          description
            "TAII Local ID";
        }
        leaf taii-global-id {
          type string;
          description
            "TAII Global ID";
        }
        leaf taii-prefix {
          type xr:ncs_template_Hex-integer;
          description
            "TAII Prefix";
        }
        leaf taii-ac-id {
          type string;
          description
            "TAII AC ID";
        }
        uses ncs_template_L2VPN-LDP-ATOM;
      }
    }
  }

  grouping ncs_template_PARAMETERS {
    description
      "Common node of default-vrf, vrf";
    container parameters {
      description
        "LDP parameters";
      uses ncs_template_LDP-PARAMETERS;
    }
  }

  grouping ncs_template_FORWARDING-SUMMARY-ALL {
    description
      "Common node of active, standby, node";
    container forwarding-summary-all {
      description
        "Summary information regarding LDP forwarding
         setup";
      uses ncs_template_LDP-FWD-SUMM-INFO;
    }
  }

  grouping ncs_template_SUMMARY {
    description
      "Common node of default-vrf, vrf";
    container summary {
      description
        "LDP VRF summary";
      uses ncs_template_LDP-SUMMARY-VRF;
    }
  }

  grouping ncs_template_MPLS-LDP-OPER-SUMMARY {
    description
      "Common node of default-vrf, vrfCommon node of
       active, standby, node";
    container summary {
      description
        "LDP summary";
      uses ncs_template_LDP-SUMMARY;
    }
  }

  grouping ncs_template_HA-STATISTICS {
    description
      "Common node of nsr, issu";
    container ha-statistics {
      description
        "LDP NSR Statistics related information";
      container ha-global {
        description
          "LDP NSR Global Statistics information";
        uses ncs_template_LDP-NSR-GBL-STATS-INFO;
      }
      uses ncs_template_HA-NEIGHBOR-TABLE;
    }
  }

  grouping ncs_template_NSR {
    description
      "Common node of default-vrf, vrf";
    container nsr {
      description
        "LDP NSR related information";
      container nsr-pending {
        description
          "LDP NSR Pending related information";
        uses ncs_template_HA-NEIGHBOR-TABLE;
      }
      uses ncs_template_HA-SUMMARY;
      uses ncs_template_HA-STATISTICS;
    }
  }

  grouping ncs_template_GRACEFUL-RESTART {
    description
      "Common node of default-vrf, vrf";
    container graceful-restart {
      description
        "LDP Graceful Restart info";
      uses ncs_template_LDP-GR-GLOBAL-INFO;
    }
  }

  grouping ncs_template_HA-NEIGHBOR-TABLE {
    description
      "Common node of nsr-pending, ha-statistics";
    container ha-neighbors {
      description
        "The LDP HA Neighbors";
      list ha-neighbor {
        // NCS patched for predictable order
        ordered-by user;
        description
          "Information on a particular LDP HA neighbor";
        leaf lsr-id {
          type string;
          description
            "LSR ID of neighbor";
        }
        leaf label-space-id {
          type string;
          description
            "Label space ID of neighbor";
        }
        uses ncs_template_LDP-NSR-STATS-NBR-INFO;
      }
    }
  }

  grouping ncs_template_NEIGHBOR-TABLE {
    description
      "Common node of default-vrf, vrf";
    container neighbors {
      description
        "The LDP Neighbors";
      list neighbor {
        // NCS patched for predictable order
        ordered-by user;
        description
          "Information on a particular LDP neighbor";
        leaf lsr-id {
          type string;
          description
            "LSR ID of neighbor";
        }
        leaf label-space-id {
          type string;
          description
            "Label space ID of neighbor";
        }
        uses ncs_template_LDP-NEIGHBOR-INFO;
      }
    }
  }

  grouping ncs_template_ISSU {
    description
      "Common node of default-vrf, vrf";
    container issu {
      description
        "LDP ISSU related information";
      uses ncs_template_HA-SUMMARY;
      uses ncs_template_HA-STATISTICS;
    }
  }

  grouping ncs_template_BACKOFF-TABLE {
    description
      "Common node of default-vrf, vrf";
    container backoffs {
      description
        "The LDP backoff";
      list backoff {
        // NCS patched for predictable order
        ordered-by user;
        description
          "LDP Backoff Information";
        leaf lsr-id {
          type string;
          description
            "LSR ID of neighbor";
        }
        leaf label-space-id {
          type string;
          description
            "Label space ID of neighbor";
        }
        uses ncs_template_LDP-BACKOFF-ENTRY-INFO;
      }
    }
  }

  grouping ncs_template_AF-TABLE {
    description
      "Common node of default-vrf, vrf";
    container afs {
      description
        "Address Family specific operational data";
      list af {
        // NCS patched for predictable order
        ordered-by user;
        key "af-name";
        description
          "Operational data for given Address Family";
        container interface-summary {
          description
            "IPv4 interface summary information";
          uses ncs_template_LDP-INTF-SUM;
        }
        container bindings {
          description
            "The LDP Bindings";
          list binding {
            // NCS patched for predictable order
            ordered-by user;
            key "prefix";
            description
              "Binding Information";
            leaf prefix {
              type string;
              description
                "The IP Prefix";
            }
            uses ncs_template_LDP-TIB-ENTRY-DETAIL;
          }
        }
        container igp {
          description
            "LDP IGP related information";
          container syncs {
            description
              "LDP IGP Sync related information";
            list sync {
              // NCS patched for predictable order
              ordered-by user;
              key "interface-name";
              description
                "LDP-IGP Synchronization related information
                 for an interface";
              leaf interface-name {
                type xr:ncs_template_Interface-name;
                description
                  "The Interface Name";
              }
              uses ncs_template_LDP-IGP-SYNC-INFO;
            }
          }
          container sync-delay-restart {
            description
              "LDP-IGP Synchronization Delay related
               information";
            uses ncs_template_LDP-IGP-SYNC-DELAY-RESTART-INFO;
          }
        }
        container bindings-summary {
          description
            "Counters for the LDP Label Infomation Base
             (LIB)";
          uses ncs_template_LDP-BINDING-SUMMARY;
        }
        container interfaces {
          description
            "LDP Interface related information";
          list interface {
            // NCS patched for predictable order
            ordered-by user;
            key "interface-name";
            description
              "IPv4 interface information";
            leaf interface-name {
              type xr:ncs_template_Interface-name;
              description
                "The Interface Name";
            }
            uses ncs_template_LDP-INTF;
          }
        }
        container discovery {
          description
            "The LDP Discovery";
          container link-hellos {
            description
              "The LDP Discovery link";
            list link-hello {
              // NCS patched for predictable order
              ordered-by user;
              key "interface-name";
              description
                "Information on LDP link discovery";
              leaf interface-name {
                type xr:ncs_template_Interface-name;
                description
                  "The Interface Name";
              }
              uses ncs_template_LDP-DISCOVERY-LINK-INFO;
            }
          }
          container summary {
            description
              "Summarized information on LDP discovery";
            uses ncs_template_LDP-DISCOVERY-SUMMARY-INFO;
          }
          container targeted-hellos {
            description
              "The LDP Discovery Targeted";
            list targeted-hello {
              // NCS patched for predictable order
              ordered-by user;
              description
                "Information on LDP targeted discovery";
              leaf local-address {
                type string;
                description
                  "Local IP Address";
              }
              leaf target-address {
                type string;
                description
                  "The target IP Address";
              }
              uses ncs_template_LDP-TARGETED-HELLO-INFO;
            }
          }
          container brief {
            description
              "Brief information on LDP discovery";
            container link-hello-briefs {
              description
                "The LDP Discovery link brief information";
              list link-hello-brief {
                // NCS patched for predictable order
                ordered-by user;
                key "interface-name";
                description
                  "Brief information on LDP link discovery";
                leaf interface-name {
                  type xr:ncs_template_Interface-name;
                  description
                    "The Interface Name";
                }
                uses ncs_template_LDP-DISCOVERY-LINK-BRIEF-INFO;
              }
            }
            container targeted-hello-briefs {
              description
                "The LDP Discovery Targeted brief information";
              list targeted-hello-brief {
                // NCS patched for predictable order
                ordered-by user;
                description
                  "Brief information on LDP targeted discovery";
                leaf local-address {
                  type string;
                  description
                    "Local IP Address";
                }
                leaf target-address {
                  type string;
                  description
                    "The target IP Address";
                }
                uses ncs_template_LDP-TARGETED-HELLO-BRIEF-INFO;
              }
            }
          }
          container stats {
            description
              "The LDP Discovery Statistics";
            list stat {
              // NCS patched for predictable order
              ordered-by user;
              description
                "Information on LDP discovery statistics";
              leaf lsr-id {
                type string;
                description
                  "LSR ID of neighbor";
              }
              leaf label-space-id {
                type string;
                description
                  "Label space ID of neighbor";
              }
              uses ncs_template_LDP-DISCOVERY-ADJ-GRP-INFO;
            }
          }
        }
        container forwardings {
          description
            "The LDP Forwarding rewrites";
          list forwarding {
            // NCS patched for predictable order
            ordered-by user;
            key "prefix";
            description
              "Information on a particular LDP forwarding
               rewrite";
            leaf prefix {
              type string;
              description
                "The IP Prefix";
            }
            uses ncs_template_LDP-FWD-PFX-INFO;
          }
        }
        container bindings-advertise-spec {
          description
            "Advertisement Spec (ACL) for LDP Label
             Infomation Base (LIB)";
          uses ncs_template_LDP-BINDING-ADVT-SPEC;
        }
        container forwarding-summary {
          description
            "Summary information regarding LDP forwarding
             setup";
          uses ncs_template_LDP-FWD-SUMM-INFO;
        }
        leaf af-name {
          type ncs_template_Mpls-ldp-oper-af-name;
          description
            "Address Family name";
        }
      }
    }
  }

  grouping ncs_rpc_notif_NSR-SUMMARY-ALL {
    description
      "Common node of active, standby, node";
    container nsr-summary-all {
      description
        "Summary information regarding LDP NSR State";
      uses ncs_rpc_notif_LDP-NSR-SUM;
    }
  }

  grouping ncs_rpc_notif_LDP-ID {
    description
      "Common node of default-vrf, vrf";
    container ldp-id {
      description
        "Local LDP Id";
      uses ncs_rpc_notif_LDP-LDPID-INFO;
    }
  }

  grouping ncs_rpc_notif_CAPABILITY-TABLE {
    description
      "Common node of default-vrf, vrf";
    container capabilities {
      description
        "LDP capability database information";
      list capability {
        key "capability-type";
        description
          "Information on LDP capability";
        leaf capability-type {
          type uint32;
          description
            "The capability type (IANA assigned)";
        }
        uses ncs_rpc_notif_LDP-CAP-INFO;
      }
    }
  }

  grouping ncs_rpc_notif_NEIGHBOR-CAPABILITY-TABLE {
    description
      "Common node of default-vrf, vrf";
    container neighbor-capabilities {
      description
        "LDP Neighbors Capabilities";
      list neighbor-capability {
        description
          "Information on capabilities of a particular LDP
           neighbor";
        leaf lsr-id {
          type inet:ipv4-address-no-zone;
          description
            "LSR ID of neighbor";
        }
        leaf label-space-id {
          type uint32 {
            range "0..65535";
          }
          description
            "Label space ID of neighbor";
        }
        uses ncs_rpc_notif_LDP-NBR-CAP-INFO;
      }
    }
  }

  grouping ncs_rpc_notif_VRF-TABLE {
    description
      "Common node of active, standby, node";
    container vrfs {
      description
        "VRF specific operational data";
      list vrf {
        key "vrf-name";
        description
          "Operational data for given VRF";
        leaf vrf-name {
          type xr:ncs_rpc_notif_Cisco-ios-xr-string;
          description
            "VRF Name";
        }
        uses ncs_rpc_notif_GRACEFUL-RESTART;
        uses ncs_rpc_notif_CAPABILITY-TABLE;
        uses ncs_rpc_notif_SUMMARY;
        uses ncs_rpc_notif_AF-TABLE;
        uses ncs_rpc_notif_NEIGHBOR-BRIEF-TABLE;
        uses ncs_rpc_notif_BACKOFF-PARAMETERS;
        uses ncs_rpc_notif_BACKOFF-TABLE;
        uses ncs_rpc_notif_NSR;
        uses ncs_rpc_notif_PARAMETERS;
        uses ncs_rpc_notif_ISSU;
        uses ncs_rpc_notif_NEIGHBOR-CAPABILITY-TABLE;
        uses ncs_rpc_notif_NEIGHBOR-TABLE;
        uses ncs_rpc_notif_LDP-ID;
        uses ncs_rpc_notif_STATISTICS-TABLE;
      }
    }
  }

  grouping ncs_rpc_notif_BACKOFF-PARAMETERS {
    description
      "Common node of default-vrf, vrf";
    container backoff-parameters {
      description
        "The LDP Backoff Parameters";
      uses ncs_rpc_notif_LDP-BACKOFF-INFO;
    }
  }

  grouping ncs_rpc_notif_HA-SUMMARY {
    description
      "Common node of nsr, issu";
    container ha-summary {
      description
        "LDP HA Summary";
      uses ncs_rpc_notif_LDP-NSR-SUM;
    }
  }

  grouping ncs_rpc_notif_STATISTICS-TABLE {
    description
      "Common node of default-vrf, vrf";
    container statistics {
      description
        "The LDP Statistics";
      list statistic {
        description
          "Statistical Information on a particular LDP
           neighbor";
        leaf lsr-id {
          type inet:ipv4-address-no-zone;
          description
            "LSR ID of neighbor";
        }
        leaf label-space-id {
          type uint32 {
            range "0..65535";
          }
          description
            "Label space ID of neighbor";
        }
        uses ncs_rpc_notif_LDP-STATS-INFO;
      }
    }
  }

  grouping ncs_rpc_notif_DISCOVERY-SUMMARY-ALL {
    description
      "Common node of active, standby, node";
    container discovery-summary-all {
      description
        "Summary information regarding LDP discovery";
      uses ncs_rpc_notif_LDP-DISCOVERY-SUMMARY-INFO;
    }
  }

  grouping ncs_rpc_notif_BINDINGS-SUMMARY-ALL {
    description
      "Common node of active, standby, node";
    container bindings-summary-all {
      description
        "Aggregate VRF counters for the LDP Label
         Infomation Base (LIB)";
      uses ncs_rpc_notif_LDP-BINDING-SUMMARY;
    }
  }

  grouping ncs_rpc_notif_DEFAULT-VRF {
    description
      "Common node of active, standby, node";
    container default-vrf {
      description
        "DefaultVRF specific operational data";
      uses ncs_rpc_notif_GRACEFUL-RESTART;
      uses ncs_rpc_notif_CAPABILITY-TABLE;
      uses ncs_rpc_notif_SUMMARY;
      uses ncs_rpc_notif_AF-TABLE;
      uses ncs_rpc_notif_NEIGHBOR-BRIEF-TABLE;
      uses ncs_rpc_notif_BACKOFF-PARAMETERS;
      uses ncs_rpc_notif_BACKOFF-TABLE;
      uses ncs_rpc_notif_NSR;
      uses ncs_rpc_notif_PARAMETERS;
      uses ncs_rpc_notif_ISSU;
      uses ncs_rpc_notif_NEIGHBOR-CAPABILITY-TABLE;
      uses ncs_rpc_notif_NEIGHBOR-TABLE;
      uses ncs_rpc_notif_LDP-ID;
      uses ncs_rpc_notif_STATISTICS-TABLE;
    }
  }

  grouping ncs_rpc_notif_NEIGHBOR-BRIEF-TABLE {
    description
      "Common node of default-vrf, vrf";
    container neighbor-briefs {
      description
        "The LDP Neighbors (brief)";
      list neighbor-brief {
        description
          "Brief information on a particular LDP neighbor";
        leaf lsr-id {
          type inet:ipv4-address-no-zone;
          description
            "LSR ID of neighbor";
        }
        leaf label-space-id {
          type uint32 {
            range "0..65535";
          }
          description
            "Label space ID of neighbor";
        }
        uses ncs_rpc_notif_LDP-NEIGHBOR-BRIEF-INFO;
      }
    }
  }

  grouping ncs_rpc_notif_ATO-MDB-TABLE {
    description
      "Common node of active, standby, node";
    container ato-mdb-table-entries {
      description
        "AToM DB Table";
      list ato-mdb-table-entry {
        description
          "Entries in AToM DB";
        leaf peer-id {
          type inet:ip-address-no-zone;
          description
            "Peer ID";
        }
        leaf fe-ctype {
          type uint32;
          description
            "FEC Type";
        }
        leaf pw-id {
          type uint32;
          description
            "PW ID";
        }
        leaf agi-type {
          type uint32;
          description
            "AGI Type";
        }
        leaf agi {
          type uint32;
          description
            "AGI";
        }
        leaf saii-type {
          type uint32;
          description
            "SAII Type";
        }
        leaf saii-local-id {
          type inet:ip-address-no-zone;
          description
            "SAII Local ID";
        }
        leaf saii-global-id {
          type uint32;
          description
            "SAII Global ID";
        }
        leaf saii-prefix {
          type xr:ncs_rpc_notif_Hex-integer;
          description
            "SAII Prefix";
        }
        leaf saii-ac-id {
          type uint32;
          description
            "SAII AC ID";
        }
        leaf taii-type {
          type uint32;
          description
            "TAII Type";
        }
        leaf taii-local-id {
          type inet:ip-address-no-zone;
          description
            "TAII Local ID";
        }
        leaf taii-global-id {
          type uint32;
          description
            "TAII Global ID";
        }
        leaf taii-prefix {
          type xr:ncs_rpc_notif_Hex-integer;
          description
            "TAII Prefix";
        }
        leaf taii-ac-id {
          type uint32;
          description
            "TAII AC ID";
        }
        uses ncs_rpc_notif_L2VPN-LDP-ATOM;
      }
    }
  }

  grouping ncs_rpc_notif_PARAMETERS {
    description
      "Common node of default-vrf, vrf";
    container parameters {
      description
        "LDP parameters";
      uses ncs_rpc_notif_LDP-PARAMETERS;
    }
  }

  grouping ncs_rpc_notif_FORWARDING-SUMMARY-ALL {
    description
      "Common node of active, standby, node";
    container forwarding-summary-all {
      description
        "Summary information regarding LDP forwarding
         setup";
      uses ncs_rpc_notif_LDP-FWD-SUMM-INFO;
    }
  }

  grouping ncs_rpc_notif_SUMMARY {
    description
      "Common node of default-vrf, vrf";
    container summary {
      description
        "LDP VRF summary";
      uses ncs_rpc_notif_LDP-SUMMARY-VRF;
    }
  }

  grouping ncs_rpc_notif_MPLS-LDP-OPER-SUMMARY {
    description
      "Common node of default-vrf, vrfCommon node of
       active, standby, node";
    container summary {
      description
        "LDP summary";
      uses ncs_rpc_notif_LDP-SUMMARY;
    }
  }

  grouping ncs_rpc_notif_HA-STATISTICS {
    description
      "Common node of nsr, issu";
    container ha-statistics {
      description
        "LDP NSR Statistics related information";
      container ha-global {
        description
          "LDP NSR Global Statistics information";
        uses ncs_rpc_notif_LDP-NSR-GBL-STATS-INFO;
      }
      uses ncs_rpc_notif_HA-NEIGHBOR-TABLE;
    }
  }

  grouping ncs_rpc_notif_NSR {
    description
      "Common node of default-vrf, vrf";
    container nsr {
      description
        "LDP NSR related information";
      container nsr-pending {
        description
          "LDP NSR Pending related information";
        uses ncs_rpc_notif_HA-NEIGHBOR-TABLE;
      }
      uses ncs_rpc_notif_HA-SUMMARY;
      uses ncs_rpc_notif_HA-STATISTICS;
    }
  }

  grouping ncs_rpc_notif_GRACEFUL-RESTART {
    description
      "Common node of default-vrf, vrf";
    container graceful-restart {
      description
        "LDP Graceful Restart info";
      uses ncs_rpc_notif_LDP-GR-GLOBAL-INFO;
    }
  }

  grouping ncs_rpc_notif_HA-NEIGHBOR-TABLE {
    description
      "Common node of nsr-pending, ha-statistics";
    container ha-neighbors {
      description
        "The LDP HA Neighbors";
      list ha-neighbor {
        description
          "Information on a particular LDP HA neighbor";
        leaf lsr-id {
          type inet:ipv4-address-no-zone;
          description
            "LSR ID of neighbor";
        }
        leaf label-space-id {
          type uint32 {
            range "0..65535";
          }
          description
            "Label space ID of neighbor";
        }
        uses ncs_rpc_notif_LDP-NSR-STATS-NBR-INFO;
      }
    }
  }

  grouping ncs_rpc_notif_NEIGHBOR-TABLE {
    description
      "Common node of default-vrf, vrf";
    container neighbors {
      description
        "The LDP Neighbors";
      list neighbor {
        description
          "Information on a particular LDP neighbor";
        leaf lsr-id {
          type inet:ipv4-address-no-zone;
          description
            "LSR ID of neighbor";
        }
        leaf label-space-id {
          type uint32 {
            range "0..65535";
          }
          description
            "Label space ID of neighbor";
        }
        uses ncs_rpc_notif_LDP-NEIGHBOR-INFO;
      }
    }
  }

  grouping ncs_rpc_notif_ISSU {
    description
      "Common node of default-vrf, vrf";
    container issu {
      description
        "LDP ISSU related information";
      uses ncs_rpc_notif_HA-SUMMARY;
      uses ncs_rpc_notif_HA-STATISTICS;
    }
  }

  grouping ncs_rpc_notif_BACKOFF-TABLE {
    description
      "Common node of default-vrf, vrf";
    container backoffs {
      description
        "The LDP backoff";
      list backoff {
        description
          "LDP Backoff Information";
        leaf lsr-id {
          type inet:ipv4-address-no-zone;
          description
            "LSR ID of neighbor";
        }
        leaf label-space-id {
          type uint32 {
            range "0..65535";
          }
          description
            "Label space ID of neighbor";
        }
        uses ncs_rpc_notif_LDP-BACKOFF-ENTRY-INFO;
      }
    }
  }

  grouping ncs_rpc_notif_AF-TABLE {
    description
      "Common node of default-vrf, vrf";
    container afs {
      description
        "Address Family specific operational data";
      list af {
        key "af-name";
        description
          "Operational data for given Address Family";
        container interface-summary {
          description
            "IPv4 interface summary information";
          uses ncs_rpc_notif_LDP-INTF-SUM;
        }
        container bindings {
          description
            "The LDP Bindings";
          list binding {
            key "prefix";
            description
              "Binding Information";
            leaf prefix {
              type inet:ip-prefix;
              description
                "The IP Prefix";
            }
            uses ncs_rpc_notif_LDP-TIB-ENTRY-DETAIL;
          }
        }
        container igp {
          description
            "LDP IGP related information";
          container syncs {
            description
              "LDP IGP Sync related information";
            list sync {
              key "interface-name";
              description
                "LDP-IGP Synchronization related information
                 for an interface";
              leaf interface-name {
                type xr:ncs_rpc_notif_Interface-name;
                description
                  "The Interface Name";
              }
              uses ncs_rpc_notif_LDP-IGP-SYNC-INFO;
            }
          }
          container sync-delay-restart {
            description
              "LDP-IGP Synchronization Delay related
               information";
            uses ncs_rpc_notif_LDP-IGP-SYNC-DELAY-RESTART-INFO;
          }
        }
        container bindings-summary {
          description
            "Counters for the LDP Label Infomation Base
             (LIB)";
          uses ncs_rpc_notif_LDP-BINDING-SUMMARY;
        }
        container interfaces {
          description
            "LDP Interface related information";
          list interface {
            key "interface-name";
            description
              "IPv4 interface information";
            leaf interface-name {
              type xr:ncs_rpc_notif_Interface-name;
              description
                "The Interface Name";
            }
            uses ncs_rpc_notif_LDP-INTF;
          }
        }
        container discovery {
          description
            "The LDP Discovery";
          container link-hellos {
            description
              "The LDP Discovery link";
            list link-hello {
              key "interface-name";
              description
                "Information on LDP link discovery";
              leaf interface-name {
                type xr:ncs_rpc_notif_Interface-name;
                description
                  "The Interface Name";
              }
              uses ncs_rpc_notif_LDP-DISCOVERY-LINK-INFO;
            }
          }
          container summary {
            description
              "Summarized information on LDP discovery";
            uses ncs_rpc_notif_LDP-DISCOVERY-SUMMARY-INFO;
          }
          container targeted-hellos {
            description
              "The LDP Discovery Targeted";
            list targeted-hello {
              description
                "Information on LDP targeted discovery";
              leaf local-address {
                type inet:ip-address-no-zone;
                description
                  "Local IP Address";
              }
              leaf target-address {
                type inet:ip-address-no-zone;
                description
                  "The target IP Address";
              }
              uses ncs_rpc_notif_LDP-TARGETED-HELLO-INFO;
            }
          }
          container brief {
            description
              "Brief information on LDP discovery";
            container link-hello-briefs {
              description
                "The LDP Discovery link brief information";
              list link-hello-brief {
                key "interface-name";
                description
                  "Brief information on LDP link discovery";
                leaf interface-name {
                  type xr:ncs_rpc_notif_Interface-name;
                  description
                    "The Interface Name";
                }
                uses ncs_rpc_notif_LDP-DISCOVERY-LINK-BRIEF-INFO;
              }
            }
            container targeted-hello-briefs {
              description
                "The LDP Discovery Targeted brief information";
              list targeted-hello-brief {
                description
                  "Brief information on LDP targeted discovery";
                leaf local-address {
                  type inet:ip-address-no-zone;
                  description
                    "Local IP Address";
                }
                leaf target-address {
                  type inet:ip-address-no-zone;
                  description
                    "The target IP Address";
                }
                uses ncs_rpc_notif_LDP-TARGETED-HELLO-BRIEF-INFO;
              }
            }
          }
          container stats {
            description
              "The LDP Discovery Statistics";
            list stat {
              description
                "Information on LDP discovery statistics";
              leaf lsr-id {
                type inet:ipv4-address-no-zone;
                description
                  "LSR ID of neighbor";
              }
              leaf label-space-id {
                type uint32 {
                  range "0..65535";
                }
                description
                  "Label space ID of neighbor";
              }
              uses ncs_rpc_notif_LDP-DISCOVERY-ADJ-GRP-INFO;
            }
          }
        }
        container forwardings {
          description
            "The LDP Forwarding rewrites";
          list forwarding {
            key "prefix";
            description
              "Information on a particular LDP forwarding
               rewrite";
            leaf prefix {
              type inet:ip-prefix;
              description
                "The IP Prefix";
            }
            uses ncs_rpc_notif_LDP-FWD-PFX-INFO;
          }
        }
        container bindings-advertise-spec {
          description
            "Advertisement Spec (ACL) for LDP Label
             Infomation Base (LIB)";
          uses ncs_rpc_notif_LDP-BINDING-ADVT-SPEC;
        }
        container forwarding-summary {
          description
            "Summary information regarding LDP forwarding
             setup";
          uses ncs_rpc_notif_LDP-FWD-SUMM-INFO;
        }
        leaf af-name {
          type ncs_rpc_notif_Mpls-ldp-oper-af-name;
          description
            "Address Family name";
        }
      }
    }
  }

  grouping live_ncs_NSR-SUMMARY-ALL {
    description
      "Common node of active, standby, node";
    container nsr-summary-all {
      description
        "Summary information regarding LDP NSR State";
      uses live_ncs_LDP-NSR-SUM;
    }
  }

  grouping live_ncs_LDP-ID {
    description
      "Common node of default-vrf, vrf";
    container ldp-id {
      description
        "Local LDP Id";
      uses live_ncs_LDP-LDPID-INFO;
    }
  }

  grouping live_ncs_CAPABILITY-TABLE {
    description
      "Common node of default-vrf, vrf";
    container capabilities {
      description
        "LDP capability database information";
      list capability {
        key "capability-type";
        description
          "Information on LDP capability";
        leaf capability-type {
          type uint32;
          description
            "The capability type (IANA assigned)";
        }
        uses live_ncs_LDP-CAP-INFO;
      }
    }
  }

  grouping live_ncs_NEIGHBOR-CAPABILITY-TABLE {
    description
      "Common node of default-vrf, vrf";
    container neighbor-capabilities {
      description
        "LDP Neighbors Capabilities";
      list neighbor-capability {
        description
          "Information on capabilities of a particular LDP
           neighbor";
        leaf lsr-id {
          type inet:ipv4-address-no-zone;
          description
            "LSR ID of neighbor";
        }
        leaf label-space-id {
          type uint32 {
            range "0..65535";
          }
          description
            "Label space ID of neighbor";
        }
        uses live_ncs_LDP-NBR-CAP-INFO;
      }
    }
  }

  grouping live_ncs_VRF-TABLE {
    description
      "Common node of active, standby, node";
    container vrfs {
      description
        "VRF specific operational data";
      list vrf {
        key "vrf-name";
        description
          "Operational data for given VRF";
        leaf vrf-name {
          type xr:live_ncs_Cisco-ios-xr-string;
          description
            "VRF Name";
        }
        uses live_ncs_GRACEFUL-RESTART;
        uses live_ncs_CAPABILITY-TABLE;
        uses live_ncs_SUMMARY;
        uses live_ncs_AF-TABLE;
        uses live_ncs_NEIGHBOR-BRIEF-TABLE;
        uses live_ncs_BACKOFF-PARAMETERS;
        uses live_ncs_BACKOFF-TABLE;
        uses live_ncs_NSR;
        uses live_ncs_PARAMETERS;
        uses live_ncs_ISSU;
        uses live_ncs_NEIGHBOR-CAPABILITY-TABLE;
        uses live_ncs_NEIGHBOR-TABLE;
        uses live_ncs_LDP-ID;
        uses live_ncs_STATISTICS-TABLE;
      }
    }
  }

  grouping live_ncs_BACKOFF-PARAMETERS {
    description
      "Common node of default-vrf, vrf";
    container backoff-parameters {
      description
        "The LDP Backoff Parameters";
      uses live_ncs_LDP-BACKOFF-INFO;
    }
  }

  grouping live_ncs_HA-SUMMARY {
    description
      "Common node of nsr, issu";
    container ha-summary {
      description
        "LDP HA Summary";
      uses live_ncs_LDP-NSR-SUM;
    }
  }

  grouping live_ncs_STATISTICS-TABLE {
    description
      "Common node of default-vrf, vrf";
    container statistics {
      description
        "The LDP Statistics";
      list statistic {
        description
          "Statistical Information on a particular LDP
           neighbor";
        leaf lsr-id {
          type inet:ipv4-address-no-zone;
          description
            "LSR ID of neighbor";
        }
        leaf label-space-id {
          type uint32 {
            range "0..65535";
          }
          description
            "Label space ID of neighbor";
        }
        uses live_ncs_LDP-STATS-INFO;
      }
    }
  }

  grouping live_ncs_DISCOVERY-SUMMARY-ALL {
    description
      "Common node of active, standby, node";
    container discovery-summary-all {
      description
        "Summary information regarding LDP discovery";
      uses live_ncs_LDP-DISCOVERY-SUMMARY-INFO;
    }
  }

  grouping live_ncs_BINDINGS-SUMMARY-ALL {
    description
      "Common node of active, standby, node";
    container bindings-summary-all {
      description
        "Aggregate VRF counters for the LDP Label
         Infomation Base (LIB)";
      uses live_ncs_LDP-BINDING-SUMMARY;
    }
  }

  grouping live_ncs_DEFAULT-VRF {
    description
      "Common node of active, standby, node";
    container default-vrf {
      description
        "DefaultVRF specific operational data";
      uses live_ncs_GRACEFUL-RESTART;
      uses live_ncs_CAPABILITY-TABLE;
      uses live_ncs_SUMMARY;
      uses live_ncs_AF-TABLE;
      uses live_ncs_NEIGHBOR-BRIEF-TABLE;
      uses live_ncs_BACKOFF-PARAMETERS;
      uses live_ncs_BACKOFF-TABLE;
      uses live_ncs_NSR;
      uses live_ncs_PARAMETERS;
      uses live_ncs_ISSU;
      uses live_ncs_NEIGHBOR-CAPABILITY-TABLE;
      uses live_ncs_NEIGHBOR-TABLE;
      uses live_ncs_LDP-ID;
      uses live_ncs_STATISTICS-TABLE;
    }
  }

  grouping live_ncs_NEIGHBOR-BRIEF-TABLE {
    description
      "Common node of default-vrf, vrf";
    container neighbor-briefs {
      description
        "The LDP Neighbors (brief)";
      list neighbor-brief {
        description
          "Brief information on a particular LDP neighbor";
        leaf lsr-id {
          type inet:ipv4-address-no-zone;
          description
            "LSR ID of neighbor";
        }
        leaf label-space-id {
          type uint32 {
            range "0..65535";
          }
          description
            "Label space ID of neighbor";
        }
        uses live_ncs_LDP-NEIGHBOR-BRIEF-INFO;
      }
    }
  }

  grouping live_ncs_ATO-MDB-TABLE {
    description
      "Common node of active, standby, node";
    container ato-mdb-table-entries {
      description
        "AToM DB Table";
      list ato-mdb-table-entry {
        description
          "Entries in AToM DB";
        leaf peer-id {
          type inet:ip-address-no-zone;
          description
            "Peer ID";
        }
        leaf fe-ctype {
          type uint32;
          description
            "FEC Type";
        }
        leaf pw-id {
          type uint32;
          description
            "PW ID";
        }
        leaf agi-type {
          type uint32;
          description
            "AGI Type";
        }
        leaf agi {
          type uint32;
          description
            "AGI";
        }
        leaf saii-type {
          type uint32;
          description
            "SAII Type";
        }
        leaf saii-local-id {
          type inet:ip-address-no-zone;
          description
            "SAII Local ID";
        }
        leaf saii-global-id {
          type uint32;
          description
            "SAII Global ID";
        }
        leaf saii-prefix {
          type xr:live_ncs_Hex-integer;
          description
            "SAII Prefix";
        }
        leaf saii-ac-id {
          type uint32;
          description
            "SAII AC ID";
        }
        leaf taii-type {
          type uint32;
          description
            "TAII Type";
        }
        leaf taii-local-id {
          type inet:ip-address-no-zone;
          description
            "TAII Local ID";
        }
        leaf taii-global-id {
          type uint32;
          description
            "TAII Global ID";
        }
        leaf taii-prefix {
          type xr:live_ncs_Hex-integer;
          description
            "TAII Prefix";
        }
        leaf taii-ac-id {
          type uint32;
          description
            "TAII AC ID";
        }
        uses live_ncs_L2VPN-LDP-ATOM;
      }
    }
  }

  grouping live_ncs_PARAMETERS {
    description
      "Common node of default-vrf, vrf";
    container parameters {
      description
        "LDP parameters";
      uses live_ncs_LDP-PARAMETERS;
    }
  }

  grouping live_ncs_FORWARDING-SUMMARY-ALL {
    description
      "Common node of active, standby, node";
    container forwarding-summary-all {
      description
        "Summary information regarding LDP forwarding
         setup";
      uses live_ncs_LDP-FWD-SUMM-INFO;
    }
  }

  grouping live_ncs_SUMMARY {
    description
      "Common node of default-vrf, vrf";
    container summary {
      description
        "LDP VRF summary";
      uses live_ncs_LDP-SUMMARY-VRF;
    }
  }

  grouping live_ncs_MPLS-LDP-OPER-SUMMARY {
    description
      "Common node of default-vrf, vrfCommon node of
       active, standby, node";
    container summary {
      description
        "LDP summary";
      uses live_ncs_LDP-SUMMARY;
    }
  }

  grouping live_ncs_HA-STATISTICS {
    description
      "Common node of nsr, issu";
    container ha-statistics {
      description
        "LDP NSR Statistics related information";
      container ha-global {
        description
          "LDP NSR Global Statistics information";
        uses live_ncs_LDP-NSR-GBL-STATS-INFO;
      }
      uses live_ncs_HA-NEIGHBOR-TABLE;
    }
  }

  grouping live_ncs_NSR {
    description
      "Common node of default-vrf, vrf";
    container nsr {
      description
        "LDP NSR related information";
      container nsr-pending {
        description
          "LDP NSR Pending related information";
        uses live_ncs_HA-NEIGHBOR-TABLE;
      }
      uses live_ncs_HA-SUMMARY;
      uses live_ncs_HA-STATISTICS;
    }
  }

  grouping live_ncs_GRACEFUL-RESTART {
    description
      "Common node of default-vrf, vrf";
    container graceful-restart {
      description
        "LDP Graceful Restart info";
      uses live_ncs_LDP-GR-GLOBAL-INFO;
    }
  }

  grouping live_ncs_HA-NEIGHBOR-TABLE {
    description
      "Common node of nsr-pending, ha-statistics";
    container ha-neighbors {
      description
        "The LDP HA Neighbors";
      list ha-neighbor {
        description
          "Information on a particular LDP HA neighbor";
        leaf lsr-id {
          type inet:ipv4-address-no-zone;
          description
            "LSR ID of neighbor";
        }
        leaf label-space-id {
          type uint32 {
            range "0..65535";
          }
          description
            "Label space ID of neighbor";
        }
        uses live_ncs_LDP-NSR-STATS-NBR-INFO;
      }
    }
  }

  grouping live_ncs_NEIGHBOR-TABLE {
    description
      "Common node of default-vrf, vrf";
    container neighbors {
      description
        "The LDP Neighbors";
      list neighbor {
        description
          "Information on a particular LDP neighbor";
        leaf lsr-id {
          type inet:ipv4-address-no-zone;
          description
            "LSR ID of neighbor";
        }
        leaf label-space-id {
          type uint32 {
            range "0..65535";
          }
          description
            "Label space ID of neighbor";
        }
        uses live_ncs_LDP-NEIGHBOR-INFO;
      }
    }
  }

  grouping live_ncs_ISSU {
    description
      "Common node of default-vrf, vrf";
    container issu {
      description
        "LDP ISSU related information";
      uses live_ncs_HA-SUMMARY;
      uses live_ncs_HA-STATISTICS;
    }
  }

  grouping live_ncs_BACKOFF-TABLE {
    description
      "Common node of default-vrf, vrf";
    container backoffs {
      description
        "The LDP backoff";
      list backoff {
        description
          "LDP Backoff Information";
        leaf lsr-id {
          type inet:ipv4-address-no-zone;
          description
            "LSR ID of neighbor";
        }
        leaf label-space-id {
          type uint32 {
            range "0..65535";
          }
          description
            "Label space ID of neighbor";
        }
        uses live_ncs_LDP-BACKOFF-ENTRY-INFO;
      }
    }
  }

  grouping live_ncs_AF-TABLE {
    description
      "Common node of default-vrf, vrf";
    container afs {
      description
        "Address Family specific operational data";
      list af {
        key "af-name";
        description
          "Operational data for given Address Family";
        container interface-summary {
          description
            "IPv4 interface summary information";
          uses live_ncs_LDP-INTF-SUM;
        }
        container bindings {
          description
            "The LDP Bindings";
          list binding {
            key "prefix";
            description
              "Binding Information";
            leaf prefix {
              type inet:ip-prefix;
              description
                "The IP Prefix";
            }
            uses live_ncs_LDP-TIB-ENTRY-DETAIL;
          }
        }
        container igp {
          description
            "LDP IGP related information";
          container syncs {
            description
              "LDP IGP Sync related information";
            list sync {
              key "interface-name";
              description
                "LDP-IGP Synchronization related information
                 for an interface";
              leaf interface-name {
                type xr:live_ncs_Interface-name;
                description
                  "The Interface Name";
              }
              uses live_ncs_LDP-IGP-SYNC-INFO;
            }
          }
          container sync-delay-restart {
            description
              "LDP-IGP Synchronization Delay related
               information";
            uses live_ncs_LDP-IGP-SYNC-DELAY-RESTART-INFO;
          }
        }
        container bindings-summary {
          description
            "Counters for the LDP Label Infomation Base
             (LIB)";
          uses live_ncs_LDP-BINDING-SUMMARY;
        }
        container interfaces {
          description
            "LDP Interface related information";
          list interface {
            key "interface-name";
            description
              "IPv4 interface information";
            leaf interface-name {
              type xr:live_ncs_Interface-name;
              description
                "The Interface Name";
            }
            uses live_ncs_LDP-INTF;
          }
        }
        container discovery {
          description
            "The LDP Discovery";
          container link-hellos {
            description
              "The LDP Discovery link";
            list link-hello {
              key "interface-name";
              description
                "Information on LDP link discovery";
              leaf interface-name {
                type xr:live_ncs_Interface-name;
                description
                  "The Interface Name";
              }
              uses live_ncs_LDP-DISCOVERY-LINK-INFO;
            }
          }
          container summary {
            description
              "Summarized information on LDP discovery";
            uses live_ncs_LDP-DISCOVERY-SUMMARY-INFO;
          }
          container targeted-hellos {
            description
              "The LDP Discovery Targeted";
            list targeted-hello {
              description
                "Information on LDP targeted discovery";
              leaf local-address {
                type inet:ip-address-no-zone;
                description
                  "Local IP Address";
              }
              leaf target-address {
                type inet:ip-address-no-zone;
                description
                  "The target IP Address";
              }
              uses live_ncs_LDP-TARGETED-HELLO-INFO;
            }
          }
          container brief {
            description
              "Brief information on LDP discovery";
            container link-hello-briefs {
              description
                "The LDP Discovery link brief information";
              list link-hello-brief {
                key "interface-name";
                description
                  "Brief information on LDP link discovery";
                leaf interface-name {
                  type xr:live_ncs_Interface-name;
                  description
                    "The Interface Name";
                }
                uses live_ncs_LDP-DISCOVERY-LINK-BRIEF-INFO;
              }
            }
            container targeted-hello-briefs {
              description
                "The LDP Discovery Targeted brief information";
              list targeted-hello-brief {
                description
                  "Brief information on LDP targeted discovery";
                leaf local-address {
                  type inet:ip-address-no-zone;
                  description
                    "Local IP Address";
                }
                leaf target-address {
                  type inet:ip-address-no-zone;
                  description
                    "The target IP Address";
                }
                uses live_ncs_LDP-TARGETED-HELLO-BRIEF-INFO;
              }
            }
          }
          container stats {
            description
              "The LDP Discovery Statistics";
            list stat {
              description
                "Information on LDP discovery statistics";
              leaf lsr-id {
                type inet:ipv4-address-no-zone;
                description
                  "LSR ID of neighbor";
              }
              leaf label-space-id {
                type uint32 {
                  range "0..65535";
                }
                description
                  "Label space ID of neighbor";
              }
              uses live_ncs_LDP-DISCOVERY-ADJ-GRP-INFO;
            }
          }
        }
        container forwardings {
          description
            "The LDP Forwarding rewrites";
          list forwarding {
            key "prefix";
            description
              "Information on a particular LDP forwarding
               rewrite";
            leaf prefix {
              type inet:ip-prefix;
              description
                "The IP Prefix";
            }
            uses live_ncs_LDP-FWD-PFX-INFO;
          }
        }
        container bindings-advertise-spec {
          description
            "Advertisement Spec (ACL) for LDP Label
             Infomation Base (LIB)";
          uses live_ncs_LDP-BINDING-ADVT-SPEC;
        }
        container forwarding-summary {
          description
            "Summary information regarding LDP forwarding
             setup";
          uses live_ncs_LDP-FWD-SUMM-INFO;
        }
        leaf af-name {
          type live_ncs_Mpls-ldp-oper-af-name;
          description
            "Address Family name";
        }
      }
    }
  }

  grouping NSR-SUMMARY-ALL {
    description
      "Common node of active, standby, node";
    container nsr-summary-all {
      description
        "Summary information regarding LDP NSR State";
      uses LDP-NSR-SUM;
    }
  }

  grouping LDP-ID {
    description
      "Common node of default-vrf, vrf";
    container ldp-id {
      description
        "Local LDP Id";
      uses LDP-LDPID-INFO;
    }
  }

  grouping CAPABILITY-TABLE {
    description
      "Common node of default-vrf, vrf";
    container capabilities {
      description
        "LDP capability database information";
      list capability {
        key "capability-type";
        description
          "Information on LDP capability";
        leaf capability-type {
          type uint32;
          description
            "The capability type (IANA assigned)";
        }
        uses LDP-CAP-INFO;
      }
    }
  }

  grouping NEIGHBOR-CAPABILITY-TABLE {
    description
      "Common node of default-vrf, vrf";
    container neighbor-capabilities {
      description
        "LDP Neighbors Capabilities";
      list neighbor-capability {
        description
          "Information on capabilities of a particular LDP
           neighbor";
        leaf lsr-id {
          type inet:ipv4-address-no-zone;
          description
            "LSR ID of neighbor";
        }
        leaf label-space-id {
          type uint32 {
            range "0..65535";
          }
          description
            "Label space ID of neighbor";
        }
        uses LDP-NBR-CAP-INFO;
      }
    }
  }

  grouping VRF-TABLE {
    description
      "Common node of active, standby, node";
    container vrfs {
      description
        "VRF specific operational data";
      list vrf {
        key "vrf-name";
        description
          "Operational data for given VRF";
        leaf vrf-name {
          type xr:Cisco-ios-xr-string;
          description
            "VRF Name";
        }
        uses GRACEFUL-RESTART;
        uses CAPABILITY-TABLE;
        uses SUMMARY;
        uses AF-TABLE;
        uses NEIGHBOR-BRIEF-TABLE;
        uses BACKOFF-PARAMETERS;
        uses BACKOFF-TABLE;
        uses NSR;
        uses PARAMETERS;
        uses ISSU;
        uses NEIGHBOR-CAPABILITY-TABLE;
        uses NEIGHBOR-TABLE;
        uses LDP-ID;
        uses STATISTICS-TABLE;
      }
    }
  }

  grouping BACKOFF-PARAMETERS {
    description
      "Common node of default-vrf, vrf";
    container backoff-parameters {
      description
        "The LDP Backoff Parameters";
      uses LDP-BACKOFF-INFO;
    }
  }

  grouping HA-SUMMARY {
    description
      "Common node of nsr, issu";
    container ha-summary {
      description
        "LDP HA Summary";
      uses LDP-NSR-SUM;
    }
  }

  grouping STATISTICS-TABLE {
    description
      "Common node of default-vrf, vrf";
    container statistics {
      description
        "The LDP Statistics";
      list statistic {
        description
          "Statistical Information on a particular LDP
           neighbor";
        leaf lsr-id {
          type inet:ipv4-address-no-zone;
          description
            "LSR ID of neighbor";
        }
        leaf label-space-id {
          type uint32 {
            range "0..65535";
          }
          description
            "Label space ID of neighbor";
        }
        uses LDP-STATS-INFO;
      }
    }
  }

  grouping DISCOVERY-SUMMARY-ALL {
    description
      "Common node of active, standby, node";
    container discovery-summary-all {
      description
        "Summary information regarding LDP discovery";
      uses LDP-DISCOVERY-SUMMARY-INFO;
    }
  }

  grouping BINDINGS-SUMMARY-ALL {
    description
      "Common node of active, standby, node";
    container bindings-summary-all {
      description
        "Aggregate VRF counters for the LDP Label
         Infomation Base (LIB)";
      uses LDP-BINDING-SUMMARY;
    }
  }

  grouping DEFAULT-VRF {
    description
      "Common node of active, standby, node";
    container default-vrf {
      description
        "DefaultVRF specific operational data";
      uses GRACEFUL-RESTART;
      uses CAPABILITY-TABLE;
      uses SUMMARY;
      uses AF-TABLE;
      uses NEIGHBOR-BRIEF-TABLE;
      uses BACKOFF-PARAMETERS;
      uses BACKOFF-TABLE;
      uses NSR;
      uses PARAMETERS;
      uses ISSU;
      uses NEIGHBOR-CAPABILITY-TABLE;
      uses NEIGHBOR-TABLE;
      uses LDP-ID;
      uses STATISTICS-TABLE;
    }
  }

  grouping NEIGHBOR-BRIEF-TABLE {
    description
      "Common node of default-vrf, vrf";
    container neighbor-briefs {
      description
        "The LDP Neighbors (brief)";
      list neighbor-brief {
        description
          "Brief information on a particular LDP neighbor";
        leaf lsr-id {
          type inet:ipv4-address-no-zone;
          description
            "LSR ID of neighbor";
        }
        leaf label-space-id {
          type uint32 {
            range "0..65535";
          }
          description
            "Label space ID of neighbor";
        }
        uses LDP-NEIGHBOR-BRIEF-INFO;
      }
    }
  }

  grouping ATO-MDB-TABLE {
    description
      "Common node of active, standby, node";
    container ato-mdb-table-entries {
      description
        "AToM DB Table";
      list ato-mdb-table-entry {
        description
          "Entries in AToM DB";
        leaf peer-id {
          type inet:ip-address-no-zone;
          description
            "Peer ID";
        }
        leaf fe-ctype {
          type uint32;
          description
            "FEC Type";
        }
        leaf pw-id {
          type uint32;
          description
            "PW ID";
        }
        leaf agi-type {
          type uint32;
          description
            "AGI Type";
        }
        leaf agi {
          type uint32;
          description
            "AGI";
        }
        leaf saii-type {
          type uint32;
          description
            "SAII Type";
        }
        leaf saii-local-id {
          type inet:ip-address-no-zone;
          description
            "SAII Local ID";
        }
        leaf saii-global-id {
          type uint32;
          description
            "SAII Global ID";
        }
        leaf saii-prefix {
          type xr:Hex-integer;
          description
            "SAII Prefix";
        }
        leaf saii-ac-id {
          type uint32;
          description
            "SAII AC ID";
        }
        leaf taii-type {
          type uint32;
          description
            "TAII Type";
        }
        leaf taii-local-id {
          type inet:ip-address-no-zone;
          description
            "TAII Local ID";
        }
        leaf taii-global-id {
          type uint32;
          description
            "TAII Global ID";
        }
        leaf taii-prefix {
          type xr:Hex-integer;
          description
            "TAII Prefix";
        }
        leaf taii-ac-id {
          type uint32;
          description
            "TAII AC ID";
        }
        uses L2VPN-LDP-ATOM;
      }
    }
  }

  grouping PARAMETERS {
    description
      "Common node of default-vrf, vrf";
    container parameters {
      description
        "LDP parameters";
      uses LDP-PARAMETERS;
    }
  }

  grouping FORWARDING-SUMMARY-ALL {
    description
      "Common node of active, standby, node";
    container forwarding-summary-all {
      description
        "Summary information regarding LDP forwarding
         setup";
      uses LDP-FWD-SUMM-INFO;
    }
  }

  grouping SUMMARY {
    description
      "Common node of default-vrf, vrf";
    container summary {
      description
        "LDP VRF summary";
      uses LDP-SUMMARY-VRF;
    }
  }

  grouping MPLS-LDP-OPER-SUMMARY {
    description
      "Common node of default-vrf, vrfCommon node of
       active, standby, node";
    container summary {
      description
        "LDP summary";
      uses LDP-SUMMARY;
    }
  }

  grouping HA-STATISTICS {
    description
      "Common node of nsr, issu";
    container ha-statistics {
      description
        "LDP NSR Statistics related information";
      container ha-global {
        description
          "LDP NSR Global Statistics information";
        uses LDP-NSR-GBL-STATS-INFO;
      }
      uses HA-NEIGHBOR-TABLE;
    }
  }

  grouping NSR {
    description
      "Common node of default-vrf, vrf";
    container nsr {
      description
        "LDP NSR related information";
      container nsr-pending {
        description
          "LDP NSR Pending related information";
        uses HA-NEIGHBOR-TABLE;
      }
      uses HA-SUMMARY;
      uses HA-STATISTICS;
    }
  }

  grouping GRACEFUL-RESTART {
    description
      "Common node of default-vrf, vrf";
    container graceful-restart {
      description
        "LDP Graceful Restart info";
      uses LDP-GR-GLOBAL-INFO;
    }
  }

  grouping HA-NEIGHBOR-TABLE {
    description
      "Common node of nsr-pending, ha-statistics";
    container ha-neighbors {
      description
        "The LDP HA Neighbors";
      list ha-neighbor {
        description
          "Information on a particular LDP HA neighbor";
        leaf lsr-id {
          type inet:ipv4-address-no-zone;
          description
            "LSR ID of neighbor";
        }
        leaf label-space-id {
          type uint32 {
            range "0..65535";
          }
          description
            "Label space ID of neighbor";
        }
        uses LDP-NSR-STATS-NBR-INFO;
      }
    }
  }

  grouping NEIGHBOR-TABLE {
    description
      "Common node of default-vrf, vrf";
    container neighbors {
      description
        "The LDP Neighbors";
      list neighbor {
        description
          "Information on a particular LDP neighbor";
        leaf lsr-id {
          type inet:ipv4-address-no-zone;
          description
            "LSR ID of neighbor";
        }
        leaf label-space-id {
          type uint32 {
            range "0..65535";
          }
          description
            "Label space ID of neighbor";
        }
        uses LDP-NEIGHBOR-INFO;
      }
    }
  }

  grouping ISSU {
    description
      "Common node of default-vrf, vrf";
    container issu {
      description
        "LDP ISSU related information";
      uses HA-SUMMARY;
      uses HA-STATISTICS;
    }
  }

  grouping BACKOFF-TABLE {
    description
      "Common node of default-vrf, vrf";
    container backoffs {
      description
        "The LDP backoff";
      list backoff {
        description
          "LDP Backoff Information";
        leaf lsr-id {
          type inet:ipv4-address-no-zone;
          description
            "LSR ID of neighbor";
        }
        leaf label-space-id {
          type uint32 {
            range "0..65535";
          }
          description
            "Label space ID of neighbor";
        }
        uses LDP-BACKOFF-ENTRY-INFO;
      }
    }
  }

  grouping AF-TABLE {
    description
      "Common node of default-vrf, vrf";
    container afs {
      description
        "Address Family specific operational data";
      list af {
        key "af-name";
        description
          "Operational data for given Address Family";
        container interface-summary {
          description
            "IPv4 interface summary information";
          uses LDP-INTF-SUM;
        }
        container bindings {
          description
            "The LDP Bindings";
          list binding {
            key "prefix";
            description
              "Binding Information";
            leaf prefix {
              type inet:ip-prefix;
              description
                "The IP Prefix";
            }
            uses LDP-TIB-ENTRY-DETAIL;
          }
        }
        container igp {
          description
            "LDP IGP related information";
          container syncs {
            description
              "LDP IGP Sync related information";
            list sync {
              key "interface-name";
              description
                "LDP-IGP Synchronization related information
                 for an interface";
              leaf interface-name {
                type xr:Interface-name;
                description
                  "The Interface Name";
              }
              uses LDP-IGP-SYNC-INFO;
            }
          }
          container sync-delay-restart {
            description
              "LDP-IGP Synchronization Delay related
               information";
            uses LDP-IGP-SYNC-DELAY-RESTART-INFO;
          }
        }
        container bindings-summary {
          description
            "Counters for the LDP Label Infomation Base
             (LIB)";
          uses LDP-BINDING-SUMMARY;
        }
        container interfaces {
          description
            "LDP Interface related information";
          list interface {
            key "interface-name";
            description
              "IPv4 interface information";
            leaf interface-name {
              type xr:Interface-name;
              description
                "The Interface Name";
            }
            uses LDP-INTF;
          }
        }
        container discovery {
          description
            "The LDP Discovery";
          container link-hellos {
            description
              "The LDP Discovery link";
            list link-hello {
              key "interface-name";
              description
                "Information on LDP link discovery";
              leaf interface-name {
                type xr:Interface-name;
                description
                  "The Interface Name";
              }
              uses LDP-DISCOVERY-LINK-INFO;
            }
          }
          container summary {
            description
              "Summarized information on LDP discovery";
            uses LDP-DISCOVERY-SUMMARY-INFO;
          }
          container targeted-hellos {
            description
              "The LDP Discovery Targeted";
            list targeted-hello {
              description
                "Information on LDP targeted discovery";
              leaf local-address {
                type inet:ip-address-no-zone;
                description
                  "Local IP Address";
              }
              leaf target-address {
                type inet:ip-address-no-zone;
                description
                  "The target IP Address";
              }
              uses LDP-TARGETED-HELLO-INFO;
            }
          }
          container brief {
            description
              "Brief information on LDP discovery";
            container link-hello-briefs {
              description
                "The LDP Discovery link brief information";
              list link-hello-brief {
                key "interface-name";
                description
                  "Brief information on LDP link discovery";
                leaf interface-name {
                  type xr:Interface-name;
                  description
                    "The Interface Name";
                }
                uses LDP-DISCOVERY-LINK-BRIEF-INFO;
              }
            }
            container targeted-hello-briefs {
              description
                "The LDP Discovery Targeted brief information";
              list targeted-hello-brief {
                description
                  "Brief information on LDP targeted discovery";
                leaf local-address {
                  type inet:ip-address-no-zone;
                  description
                    "Local IP Address";
                }
                leaf target-address {
                  type inet:ip-address-no-zone;
                  description
                    "The target IP Address";
                }
                uses LDP-TARGETED-HELLO-BRIEF-INFO;
              }
            }
          }
          container stats {
            description
              "The LDP Discovery Statistics";
            list stat {
              description
                "Information on LDP discovery statistics";
              leaf lsr-id {
                type inet:ipv4-address-no-zone;
                description
                  "LSR ID of neighbor";
              }
              leaf label-space-id {
                type uint32 {
                  range "0..65535";
                }
                description
                  "Label space ID of neighbor";
              }
              uses LDP-DISCOVERY-ADJ-GRP-INFO;
            }
          }
        }
        container forwardings {
          description
            "The LDP Forwarding rewrites";
          list forwarding {
            key "prefix";
            description
              "Information on a particular LDP forwarding
               rewrite";
            leaf prefix {
              type inet:ip-prefix;
              description
                "The IP Prefix";
            }
            uses LDP-FWD-PFX-INFO;
          }
        }
        container bindings-advertise-spec {
          description
            "Advertisement Spec (ACL) for LDP Label
             Infomation Base (LIB)";
          uses LDP-BINDING-ADVT-SPEC;
        }
        container forwarding-summary {
          description
            "Summary information regarding LDP forwarding
             setup";
          uses LDP-FWD-SUMM-INFO;
        }
        leaf af-name {
          type Mpls-ldp-oper-af-name;
          description
            "Address Family name";
        }
      }
    }
  }

  augment "/ncs:devices/ncs:device/ncs:config" {
    // NCS drop config false container 'mpls-ldp'
  }
  augment "/ncs:devices/ncs:device/ncs:live-status" {
    container mpls-ldp {
      tailf:ncs-device-type "netconf";
      tailf:display-when "not(../../ncs:module) or ../../ncs:module[ncs:name='Cisco-IOS-XR-mpls-ldp-oper'] or (../../ncs:live-status-protocol[not(ncs:capability)]) or (../../ncs:live-status-protocol/ncs:capability/ncs:module[.='Cisco-IOS-XR-mpls-ldp-oper'])";
      description
        "MPLS LDP operational data";
      container global {
        description
          "Global MPLS LDP operational data";
        container standby {
          description
            "Standby MPLS LDP operational data";
          uses live_ncs_DEFAULT-VRF;
          uses live_ncs_FORWARDING-SUMMARY-ALL;
          uses live_ncs_BINDINGS-SUMMARY-ALL;
          uses live_ncs_ATO-MDB-TABLE;
          uses live_ncs_NSR-SUMMARY-ALL;
          uses live_ncs_MPLS-LDP-OPER-SUMMARY;
          uses live_ncs_VRF-TABLE;
          uses live_ncs_DISCOVERY-SUMMARY-ALL;
        }
        container active {
          description
            "Active MPLS LDP operational data";
          uses live_ncs_DEFAULT-VRF;
          uses live_ncs_FORWARDING-SUMMARY-ALL;
          uses live_ncs_BINDINGS-SUMMARY-ALL;
          uses live_ncs_ATO-MDB-TABLE;
          uses live_ncs_NSR-SUMMARY-ALL;
          uses live_ncs_MPLS-LDP-OPER-SUMMARY;
          uses live_ncs_VRF-TABLE;
          uses live_ncs_DISCOVERY-SUMMARY-ALL;
        }
      }
      container nodes {
        description
          "Location MPLS LDP operational data";
        list node {
          key "node-name";
          description
            "The MPLD LDP operational data for a particular
             node";
          leaf node-name {
            type xr:live_ncs_Node-id;
            description
              "The identifier for the node";
          }
          uses live_ncs_DEFAULT-VRF;
          uses live_ncs_FORWARDING-SUMMARY-ALL;
          uses live_ncs_BINDINGS-SUMMARY-ALL;
          uses live_ncs_ATO-MDB-TABLE;
          uses live_ncs_NSR-SUMMARY-ALL;
          uses live_ncs_MPLS-LDP-OPER-SUMMARY;
          uses live_ncs_VRF-TABLE;
          uses live_ncs_DISCOVERY-SUMMARY-ALL;
        }
      }
    }
  }
  augment "/ncs:devices/ncs:template/ncs:ned-id/ncs:config" {
    // NCS drop config false container 'mpls-ldp'
  }
}

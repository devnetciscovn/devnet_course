module Cisco-IOS-XR-spirit-bfd-hw-offload-cfg {
  // Generated by yanger -t ncs
  tailf:mount-id "cisco-iosxr-nc-7.3:cisco-iosxr-nc-7.3";
  tailf:ncs-device-type "netconf";

  namespace "http://cisco.com/ns/yang/Cisco-IOS-XR-spirit-bfd-hw-offload-cfg";
  prefix spirit-bfd-hw-offload-cfg;

  import Cisco-IOS-XR-types {
    prefix xr;
  }
  import Cisco-IOS-XR-config-mda-cfg {
    prefix node;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR spirit-bfd-hw-offload package configuration.

     This YANG module augments the
       Cisco-IOS-XR-config-mda-cfg
     module with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping ncs_template_NODE-CFG {
    description
      "active/preconfigured nodes configuration";
    container bfd-hardware-offload {
      description
        "Configure BFD offload parameters";
      list node {
        // NCS patched for predictable order
        ordered-by user;
        key "node-name";
        description
          "Node id to filter out trient card";
        leaf enable {
          type empty;
          description
            "Enable BFD HW offload mode";
        }
        leaf node-name {
          type xr:ncs_template_Node-id;
          description
            "NodeName";
        }
      }
    }
  }

  grouping ncs_rpc_notif_NODE-CFG {
    description
      "active/preconfigured nodes configuration";
    container bfd-hardware-offload {
      description
        "Configure BFD offload parameters";
      list node {
        key "node-name";
        description
          "Node id to filter out trient card";
        leaf enable {
          type empty;
          description
            "Enable BFD HW offload mode";
        }
        leaf node-name {
          type xr:ncs_rpc_notif_Node-id;
          description
            "NodeName";
        }
      }
    }
  }

  grouping live_ncs_NODE-CFG {
    description
      "active/preconfigured nodes configuration";
    container bfd-hardware-offload {
      description
        "Configure BFD offload parameters";
      list node {
        key "node-name";
        description
          "Node id to filter out trient card";
        leaf enable {
          type empty;
          description
            "Enable BFD HW offload mode";
        }
        leaf node-name {
          type xr:live_ncs_Node-id;
          description
            "NodeName";
        }
      }
    }
  }

  grouping NODE-CFG {
    description
      "active/preconfigured nodes configuration";
    container bfd-hardware-offload {
      description
        "Configure BFD offload parameters";
      list node {
        key "node-name";
        description
          "Node id to filter out trient card";
        leaf enable {
          type empty;
          description
            "Enable BFD HW offload mode";
        }
        leaf node-name {
          type xr:Node-id;
          description
            "NodeName";
        }
      }
    }
  }

  augment "/ncs:devices/ncs:template/ncs:ned-id/ncs:config/node:active-nodes/node:active-node" {
    description
      "This augment extends active nodes configuration";
    uses ncs_template_NODE-CFG;
  }
  augment "/ncs:devices/ncs:device/ncs:live-status/node:active-nodes/node:active-node" {
    description
      "This augment extends active nodes configuration";
    uses live_ncs_NODE-CFG {
      refine bfd-hardware-offload {
        tailf:ncs-device-type "netconf";
        tailf:display-when "not(../../../../ncs:module) or ../../../../ncs:module[ncs:name='Cisco-IOS-XR-spirit-bfd-hw-offload-cfg'] or (../../../../ncs:live-status-protocol[not(ncs:capability)]) or (../../../../ncs:live-status-protocol/ncs:capability/ncs:module[.='Cisco-IOS-XR-spirit-bfd-hw-offload-cfg'])";
      }
    }
  }
  augment "/ncs:devices/ncs:device/ncs:config/node:active-nodes/node:active-node" {
    description
      "This augment extends active nodes configuration";
    uses NODE-CFG {
      refine bfd-hardware-offload {
        tailf:ncs-device-type "netconf";
        tailf:display-when "not(../../../../ncs:module) or ../../../../ncs:module[ncs:name='Cisco-IOS-XR-spirit-bfd-hw-offload-cfg']";
      }
    }
  }
  augment "/ncs:devices/ncs:template/ncs:ned-id/ncs:config/node:preconfigured-nodes/node:preconfigured-node" {
    description
      "This augment extends preconfigured nodes
       configuration";
    uses ncs_template_NODE-CFG;
  }
  augment "/ncs:devices/ncs:device/ncs:live-status/node:preconfigured-nodes/node:preconfigured-node" {
    description
      "This augment extends preconfigured nodes
       configuration";
    uses live_ncs_NODE-CFG {
      refine bfd-hardware-offload {
        tailf:ncs-device-type "netconf";
        tailf:display-when "not(../../../../ncs:module) or ../../../../ncs:module[ncs:name='Cisco-IOS-XR-spirit-bfd-hw-offload-cfg'] or (../../../../ncs:live-status-protocol[not(ncs:capability)]) or (../../../../ncs:live-status-protocol/ncs:capability/ncs:module[.='Cisco-IOS-XR-spirit-bfd-hw-offload-cfg'])";
      }
    }
  }
  augment "/ncs:devices/ncs:device/ncs:config/node:preconfigured-nodes/node:preconfigured-node" {
    description
      "This augment extends preconfigured nodes
       configuration";
    uses NODE-CFG {
      refine bfd-hardware-offload {
        tailf:ncs-device-type "netconf";
        tailf:display-when "not(../../../../ncs:module) or ../../../../ncs:module[ncs:name='Cisco-IOS-XR-spirit-bfd-hw-offload-cfg']";
      }
    }
  }
}

submodule Cisco-IOS-XR-ncs1k-macsec-ea-oper-sub1 {
  // Generated by yanger -t ncs
  tailf:mount-id "cisco-iosxr-nc-7.3:cisco-iosxr-nc-7.3";

  belongs-to Cisco-IOS-XR-ncs1k-macsec-ea-oper {
    prefix Cisco-IOS-XR-ncs1k-macsec-ea-oper;
  }

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1k-macsec-ea package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Ncs1k-cipher-suit {
    type string;
    description
      "Ncs1k cipher suit";
  }

  typedef ncs_rpc_notif_Ncs1k-cipher-suit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Ncs1k cipher suit";
  }

  typedef live_ncs_Ncs1k-cipher-suit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Ncs1k cipher suit";
  }

  typedef Ncs1k-cipher-suit {
    type enumeration {
      enum "gcm-aes-256" {
        value 0;
        description
          "GCM AES 256";
      }
      enum "gcm-aes-128" {
        value 1;
        description
          "GCM AES 128";
      }
      enum "gcm-aes-xpn-256" {
        value 2;
        description
          "GCM AES XPN 256";
      }
    }
    description
      "Ncs1k cipher suit";
  }

  grouping ncs_template_NCS1K-AN-STATUS {
    description
      "Association Number status";
    leaf association-number {
      type string;
      description
        "Assocition Number";
    }
    leaf device-association-number {
      type string;
      description
        "Devive Association Number";
    }
    leaf short-secure-channel-id {
      type string;
      description
        "Short Secure Channel Id";
    }
    leaf programmed-time {
      type string;
      description
        "Key Programmed Time";
    }
    leaf key-crc {
      type xr:ncs_template_Hex-integer;
      description
        "32bit CRC of Programmed Key";
    }
    leaf-list xpn-salt {
      // NCS patched for predictable order
      ordered-by user;
      type xr:ncs_template_Hex-integer;
      description
        "XPN Salt";
    }
  }

  grouping ncs_template_NCS1K-SC-STATUS {
    description
      "Secure Channel status";
    leaf protection-enabled {
      type string;
      description
        "Protection Enabled";
    }
    leaf secure-channel-id {
      type string;
      description
        "Secure Channel Id";
    }
    leaf confidentiality-offset {
      type string;
      description
        "Confidentiality offset";
    }
    leaf cipher-suite {
      type ncs_template_Ncs1k-cipher-suit;
      description
        "Cipher Suite";
    }
    leaf initial-packet-number {
      type string;
      description
        "Initial Packet Number";
    }
    leaf secure-tag-length {
      type string;
      description
        "Secure Tag Length";
    }
    leaf max-packet-number {
      type string;
      description
        "Maximum Packet Number";
    }
    leaf recent-packet-number {
      type string;
      description
        "Recent Packet Number";
    }
    list active-association {
      // NCS patched for predictable order
      ordered-by user;
      description
        "Active Associations";
      uses ncs_template_NCS1K-AN-STATUS;
    }
  }

  grouping ncs_template_NCS1K-MACSEC-IF-STATUS {
    description
      "Interface Status details";
    container encrypt-sc-status {
      description
        "Encrypt Secure Channel Status";
      uses ncs_template_NCS1K-SC-STATUS;
    }
    container decrypt-sc-status {
      description
        "Decrypt Secure Channel Status";
      uses ncs_template_NCS1K-SC-STATUS;
    }
    leaf replay-window-size {
      type string;
      description
        "Replay Window Size";
    }
    leaf must-secure {
      type string;
      description
        "Must Secure";
    }
    leaf secure-mode {
      type string;
      description
        "Secure Mode";
    }
  }

  grouping ncs_rpc_notif_NCS1K-AN-STATUS {
    description
      "Association Number status";
    leaf association-number {
      type uint8;
      description
        "Assocition Number";
    }
    leaf device-association-number {
      type uint8;
      description
        "Devive Association Number";
    }
    leaf short-secure-channel-id {
      type uint32;
      description
        "Short Secure Channel Id";
    }
    leaf programmed-time {
      type string {
        length "0..30";
      }
      description
        "Key Programmed Time";
    }
    leaf key-crc {
      type xr:ncs_rpc_notif_Hex-integer;
      description
        "32bit CRC of Programmed Key";
    }
    leaf-list xpn-salt {
      type xr:ncs_rpc_notif_Hex-integer;
      description
        "XPN Salt";
    }
  }

  grouping ncs_rpc_notif_NCS1K-SC-STATUS {
    description
      "Secure Channel status";
    leaf protection-enabled {
      type boolean;
      description
        "Protection Enabled";
    }
    leaf secure-channel-id {
      type uint64;
      description
        "Secure Channel Id";
    }
    leaf confidentiality-offset {
      type uint32;
      description
        "Confidentiality offset";
    }
    leaf cipher-suite {
      type ncs_rpc_notif_Ncs1k-cipher-suit;
      description
        "Cipher Suite";
    }
    leaf initial-packet-number {
      type uint64;
      description
        "Initial Packet Number";
    }
    leaf secure-tag-length {
      type uint32;
      description
        "Secure Tag Length";
    }
    leaf max-packet-number {
      type uint64;
      description
        "Maximum Packet Number";
    }
    leaf recent-packet-number {
      type uint64;
      description
        "Recent Packet Number";
    }
    list active-association {
      description
        "Active Associations";
      uses ncs_rpc_notif_NCS1K-AN-STATUS;
    }
  }

  grouping ncs_rpc_notif_NCS1K-MACSEC-IF-STATUS {
    description
      "Interface Status details";
    container encrypt-sc-status {
      description
        "Encrypt Secure Channel Status";
      uses ncs_rpc_notif_NCS1K-SC-STATUS;
    }
    container decrypt-sc-status {
      description
        "Decrypt Secure Channel Status";
      uses ncs_rpc_notif_NCS1K-SC-STATUS;
    }
    leaf replay-window-size {
      type uint32;
      description
        "Replay Window Size";
    }
    leaf must-secure {
      type boolean;
      description
        "Must Secure";
    }
    leaf secure-mode {
      type uint32;
      description
        "Secure Mode";
    }
  }

  grouping live_ncs_NCS1K-AN-STATUS {
    description
      "Association Number status";
    leaf association-number {
      type uint8;
      description
        "Assocition Number";
    }
    leaf device-association-number {
      type uint8;
      description
        "Devive Association Number";
    }
    leaf short-secure-channel-id {
      type uint32;
      description
        "Short Secure Channel Id";
    }
    leaf programmed-time {
      type string {
        length "0..30";
      }
      description
        "Key Programmed Time";
    }
    leaf key-crc {
      type xr:live_ncs_Hex-integer;
      description
        "32bit CRC of Programmed Key";
    }
    leaf-list xpn-salt {
      type xr:live_ncs_Hex-integer;
      description
        "XPN Salt";
    }
  }

  grouping live_ncs_NCS1K-SC-STATUS {
    description
      "Secure Channel status";
    leaf protection-enabled {
      type boolean;
      description
        "Protection Enabled";
    }
    leaf secure-channel-id {
      type uint64;
      description
        "Secure Channel Id";
    }
    leaf confidentiality-offset {
      type uint32;
      description
        "Confidentiality offset";
    }
    leaf cipher-suite {
      type live_ncs_Ncs1k-cipher-suit;
      description
        "Cipher Suite";
    }
    leaf initial-packet-number {
      type uint64;
      description
        "Initial Packet Number";
    }
    leaf secure-tag-length {
      type uint32;
      description
        "Secure Tag Length";
    }
    leaf max-packet-number {
      type uint64;
      description
        "Maximum Packet Number";
    }
    leaf recent-packet-number {
      type uint64;
      description
        "Recent Packet Number";
    }
    list active-association {
      description
        "Active Associations";
      uses live_ncs_NCS1K-AN-STATUS;
    }
  }

  grouping live_ncs_NCS1K-MACSEC-IF-STATUS {
    description
      "Interface Status details";
    container encrypt-sc-status {
      description
        "Encrypt Secure Channel Status";
      uses live_ncs_NCS1K-SC-STATUS;
    }
    container decrypt-sc-status {
      description
        "Decrypt Secure Channel Status";
      uses live_ncs_NCS1K-SC-STATUS;
    }
    leaf replay-window-size {
      type uint32;
      description
        "Replay Window Size";
    }
    leaf must-secure {
      type boolean;
      description
        "Must Secure";
    }
    leaf secure-mode {
      type uint32;
      description
        "Secure Mode";
    }
  }

  grouping NCS1K-AN-STATUS {
    description
      "Association Number status";
    leaf association-number {
      type uint8;
      description
        "Assocition Number";
    }
    leaf device-association-number {
      type uint8;
      description
        "Devive Association Number";
    }
    leaf short-secure-channel-id {
      type uint32;
      description
        "Short Secure Channel Id";
    }
    leaf programmed-time {
      type string {
        length "0..30";
      }
      description
        "Key Programmed Time";
    }
    leaf key-crc {
      type xr:Hex-integer;
      description
        "32bit CRC of Programmed Key";
    }
    leaf-list xpn-salt {
      type xr:Hex-integer;
      description
        "XPN Salt";
    }
  }

  grouping NCS1K-SC-STATUS {
    description
      "Secure Channel status";
    leaf protection-enabled {
      type boolean;
      description
        "Protection Enabled";
    }
    leaf secure-channel-id {
      type uint64;
      description
        "Secure Channel Id";
    }
    leaf confidentiality-offset {
      type uint32;
      description
        "Confidentiality offset";
    }
    leaf cipher-suite {
      type Ncs1k-cipher-suit;
      description
        "Cipher Suite";
    }
    leaf initial-packet-number {
      type uint64;
      description
        "Initial Packet Number";
    }
    leaf secure-tag-length {
      type uint32;
      description
        "Secure Tag Length";
    }
    leaf max-packet-number {
      type uint64;
      description
        "Maximum Packet Number";
    }
    leaf recent-packet-number {
      type uint64;
      description
        "Recent Packet Number";
    }
    list active-association {
      description
        "Active Associations";
      uses NCS1K-AN-STATUS;
    }
  }

  grouping NCS1K-MACSEC-IF-STATUS {
    description
      "Interface Status details";
    container encrypt-sc-status {
      description
        "Encrypt Secure Channel Status";
      uses NCS1K-SC-STATUS;
    }
    container decrypt-sc-status {
      description
        "Decrypt Secure Channel Status";
      uses NCS1K-SC-STATUS;
    }
    leaf replay-window-size {
      type uint32;
      description
        "Replay Window Size";
    }
    leaf must-secure {
      type boolean;
      description
        "Must Secure";
    }
    leaf secure-mode {
      type uint32;
      description
        "Secure Mode";
    }
  }
}

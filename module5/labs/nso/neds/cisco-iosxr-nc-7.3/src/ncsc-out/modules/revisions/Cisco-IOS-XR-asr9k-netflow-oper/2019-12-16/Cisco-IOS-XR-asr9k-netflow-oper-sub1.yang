submodule Cisco-IOS-XR-asr9k-netflow-oper-sub1 {
  // Generated by yanger -t ncs
  tailf:mount-id "cisco-iosxr-nc-7.3:cisco-iosxr-nc-7.3";

  belongs-to Cisco-IOS-XR-asr9k-netflow-oper {
    prefix Cisco-IOS-XR-asr9k-netflow-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-netflow package operational data.

     Copyright (c) 2013-2019 by Cisco Systems, Inc.
     All rights reserved.";

  revision 2019-12-16 {
    description
      "Added map-t logging counters for ingress flows.";
    semver:module-version "1.0.0";
  }
  revision 2019-04-05 {
    description
      "Establish semantic version baseline.";
  }
  revision 2015-11-09 {
    description
      "IOS XR 6.0 revision.";
  }

  typedef ncs_template_Flow-monitor-name {
    type string;
    description
      "Flow monitor name";
  }

  typedef ncs_rpc_notif_Flow-monitor-name {
    type string;
    description
      "Flow monitor name";
  }

  typedef live_ncs_Flow-monitor-name {
    type string;
    description
      "Flow monitor name";
  }

  typedef Flow-monitor-name {
    type string;
    description
      "Flow monitor name";
  }

  grouping ncs_template_NFSVR-COLLECTOR-INFO {
    description
      "Per collector information";
    leaf exporter-state {
      type string;
      description
        "Exporter state";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type string;
      description
        "Destination port number";
    }
    leaf souce-port {
      type string;
      description
        "Source port number";
    }
    leaf transport-protocol {
      type string;
      description
        "Transport protocol";
    }
    leaf packets-sent {
      type string;
      description
        "Packets sent";
    }
    leaf flows-sent {
      type string;
      description
        "Flows sent";
    }
    leaf templates-sent {
      type string;
      description
        "Templates sent";
    }
    leaf option-templates-sent {
      type string;
      description
        "Option templates sent";
    }
    leaf option-data-sent {
      type string;
      description
        "Option data sent";
    }
    leaf bytes-sent {
      type string;
      units "byte";
      description
        "Bytes sent";
    }
    leaf flow-bytes-sent {
      type string;
      units "byte";
      description
        "Flow bytes sent";
    }
    leaf template-bytes-sent {
      type string;
      units "byte";
      description
        "Template bytes sent";
    }
    leaf option-template-bytes-sent {
      type string;
      units "byte";
      description
        "Option template bytes sent";
    }
    leaf option-data-bytes-sent {
      type string;
      units "byte";
      description
        "Option data bytes sent";
    }
    leaf packets-dropped {
      type string;
      description
        "Packets dropped";
    }
    leaf flows-dropped {
      type string;
      description
        "Flows dropped";
    }
    leaf templates-dropped {
      type string;
      description
        "Templates dropped";
    }
    leaf option-templates-dropped {
      type string;
      description
        "Option templates dropped";
    }
    leaf option-data-dropped {
      type string;
      description
        "Option data dropped";
    }
    leaf bytes-dropped {
      type string;
      units "byte";
      description
        "Bytes dropped";
    }
    leaf flow-bytes-dropped {
      type string;
      units "byte";
      description
        "Flow bytes dropped";
    }
    leaf template-bytes-dropped {
      type string;
      units "byte";
      description
        "Template bytes dropped";
    }
    leaf option-template-bytes-dropped {
      type string;
      units "byte";
      description
        "Option template bytes dropped";
    }
    leaf option-data-bytes-dropped {
      type string;
      description
        "Option data dropped";
    }
    leaf last-hour-packest-sent {
      type string;
      description
        "Total packets exported over the last one hour";
    }
    leaf last-hour-bytes-sent {
      type string;
      units "byte";
      description
        "Total bytes exported over the last one hour";
    }
    leaf last-hour-flows-sent {
      type string;
      description
        "Total flows exported over the of last one hour";
    }
    leaf last-minute-packets {
      type string;
      description
        "Total packets exported over the last one minute";
    }
    leaf last-minute-bytes-sent {
      type string;
      units "byte";
      description
        "Total bytes exported over the last one minute";
    }
    leaf last-minute-flows-sent {
      type string;
      description
        "Total flows exported over the last one minute";
    }
    leaf last-second-packets-sent {
      type string;
      description
        "Total packets exported over the last one second";
    }
    leaf last-second-bytes-sent {
      type string;
      units "byte";
      description
        "Total bytes exported over the last one second";
    }
    leaf last-second-flows-sent {
      type string;
      description
        "Total flows exported over the last one second";
    }
  }

  grouping ncs_template_NFSVR-SHOW-FLOW-EXPORTER-RESP-STATS {
    description
      "Flow exporter information";
    leaf name {
      type string;
      description
        "Exporter name";
    }
    leaf protocol {
      type string;
      description
        "Export Protocol Name";
    }
    leaf memory-usage {
      type string;
      description
        "Memory usage";
    }
    leaf-list used-by-flow-monitor {
      // NCS patched for predictable order
      ordered-by user;
      type ncs_template_Flow-monitor-name;
      description
        "List of flow monitors that use the exporter";
    }
    list collector {
      // NCS patched for predictable order
      ordered-by user;
      description
        "Statistics of all collectors";
      uses ncs_template_NFSVR-COLLECTOR-INFO;
    }
  }

  grouping ncs_template_NFSVR-SHOW-FLOW-EXPORTER-RESP-ARRAY {
    description
      "Flow exporter information";
    list statistic {
      // NCS patched for predictable order
      ordered-by user;
      description
        "Array of flow exporters";
      uses ncs_template_NFSVR-SHOW-FLOW-EXPORTER-RESP-STATS;
    }
  }

  grouping ncs_rpc_notif_NFSVR-COLLECTOR-INFO {
    description
      "Per collector information";
    leaf exporter-state {
      type string;
      description
        "Exporter state";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type uint16;
      description
        "Destination port number";
    }
    leaf souce-port {
      type uint16;
      description
        "Source port number";
    }
    leaf transport-protocol {
      type string;
      description
        "Transport protocol";
    }
    leaf packets-sent {
      type uint64;
      description
        "Packets sent";
    }
    leaf flows-sent {
      type uint64;
      description
        "Flows sent";
    }
    leaf templates-sent {
      type uint64;
      description
        "Templates sent";
    }
    leaf option-templates-sent {
      type uint64;
      description
        "Option templates sent";
    }
    leaf option-data-sent {
      type uint64;
      description
        "Option data sent";
    }
    leaf bytes-sent {
      type uint64;
      units "byte";
      description
        "Bytes sent";
    }
    leaf flow-bytes-sent {
      type uint64;
      units "byte";
      description
        "Flow bytes sent";
    }
    leaf template-bytes-sent {
      type uint64;
      units "byte";
      description
        "Template bytes sent";
    }
    leaf option-template-bytes-sent {
      type uint64;
      units "byte";
      description
        "Option template bytes sent";
    }
    leaf option-data-bytes-sent {
      type uint64;
      units "byte";
      description
        "Option data bytes sent";
    }
    leaf packets-dropped {
      type uint64;
      description
        "Packets dropped";
    }
    leaf flows-dropped {
      type uint64;
      description
        "Flows dropped";
    }
    leaf templates-dropped {
      type uint64;
      description
        "Templates dropped";
    }
    leaf option-templates-dropped {
      type uint64;
      description
        "Option templates dropped";
    }
    leaf option-data-dropped {
      type uint64;
      description
        "Option data dropped";
    }
    leaf bytes-dropped {
      type uint64;
      units "byte";
      description
        "Bytes dropped";
    }
    leaf flow-bytes-dropped {
      type uint64;
      units "byte";
      description
        "Flow bytes dropped";
    }
    leaf template-bytes-dropped {
      type uint64;
      units "byte";
      description
        "Template bytes dropped";
    }
    leaf option-template-bytes-dropped {
      type uint64;
      units "byte";
      description
        "Option template bytes dropped";
    }
    leaf option-data-bytes-dropped {
      type uint64;
      description
        "Option data dropped";
    }
    leaf last-hour-packest-sent {
      type uint64;
      description
        "Total packets exported over the last one hour";
    }
    leaf last-hour-bytes-sent {
      type uint64;
      units "byte";
      description
        "Total bytes exported over the last one hour";
    }
    leaf last-hour-flows-sent {
      type uint64;
      description
        "Total flows exported over the of last one hour";
    }
    leaf last-minute-packets {
      type uint64;
      description
        "Total packets exported over the last one minute";
    }
    leaf last-minute-bytes-sent {
      type uint64;
      units "byte";
      description
        "Total bytes exported over the last one minute";
    }
    leaf last-minute-flows-sent {
      type uint64;
      description
        "Total flows exported over the last one minute";
    }
    leaf last-second-packets-sent {
      type uint64;
      description
        "Total packets exported over the last one second";
    }
    leaf last-second-bytes-sent {
      type uint64;
      units "byte";
      description
        "Total bytes exported over the last one second";
    }
    leaf last-second-flows-sent {
      type uint64;
      description
        "Total flows exported over the last one second";
    }
  }

  grouping ncs_rpc_notif_NFSVR-SHOW-FLOW-EXPORTER-RESP-STATS {
    description
      "Flow exporter information";
    leaf name {
      type string;
      description
        "Exporter name";
    }
    leaf protocol {
      type string;
      description
        "Export Protocol Name";
    }
    leaf memory-usage {
      type uint32;
      description
        "Memory usage";
    }
    leaf-list used-by-flow-monitor {
      type ncs_rpc_notif_Flow-monitor-name;
      description
        "List of flow monitors that use the exporter";
    }
    list collector {
      description
        "Statistics of all collectors";
      uses ncs_rpc_notif_NFSVR-COLLECTOR-INFO;
    }
  }

  grouping ncs_rpc_notif_NFSVR-SHOW-FLOW-EXPORTER-RESP-ARRAY {
    description
      "Flow exporter information";
    list statistic {
      description
        "Array of flow exporters";
      uses ncs_rpc_notif_NFSVR-SHOW-FLOW-EXPORTER-RESP-STATS;
    }
  }

  grouping live_ncs_NFSVR-COLLECTOR-INFO {
    description
      "Per collector information";
    leaf exporter-state {
      type string;
      description
        "Exporter state";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type uint16;
      description
        "Destination port number";
    }
    leaf souce-port {
      type uint16;
      description
        "Source port number";
    }
    leaf transport-protocol {
      type string;
      description
        "Transport protocol";
    }
    leaf packets-sent {
      type uint64;
      description
        "Packets sent";
    }
    leaf flows-sent {
      type uint64;
      description
        "Flows sent";
    }
    leaf templates-sent {
      type uint64;
      description
        "Templates sent";
    }
    leaf option-templates-sent {
      type uint64;
      description
        "Option templates sent";
    }
    leaf option-data-sent {
      type uint64;
      description
        "Option data sent";
    }
    leaf bytes-sent {
      type uint64;
      units "byte";
      description
        "Bytes sent";
    }
    leaf flow-bytes-sent {
      type uint64;
      units "byte";
      description
        "Flow bytes sent";
    }
    leaf template-bytes-sent {
      type uint64;
      units "byte";
      description
        "Template bytes sent";
    }
    leaf option-template-bytes-sent {
      type uint64;
      units "byte";
      description
        "Option template bytes sent";
    }
    leaf option-data-bytes-sent {
      type uint64;
      units "byte";
      description
        "Option data bytes sent";
    }
    leaf packets-dropped {
      type uint64;
      description
        "Packets dropped";
    }
    leaf flows-dropped {
      type uint64;
      description
        "Flows dropped";
    }
    leaf templates-dropped {
      type uint64;
      description
        "Templates dropped";
    }
    leaf option-templates-dropped {
      type uint64;
      description
        "Option templates dropped";
    }
    leaf option-data-dropped {
      type uint64;
      description
        "Option data dropped";
    }
    leaf bytes-dropped {
      type uint64;
      units "byte";
      description
        "Bytes dropped";
    }
    leaf flow-bytes-dropped {
      type uint64;
      units "byte";
      description
        "Flow bytes dropped";
    }
    leaf template-bytes-dropped {
      type uint64;
      units "byte";
      description
        "Template bytes dropped";
    }
    leaf option-template-bytes-dropped {
      type uint64;
      units "byte";
      description
        "Option template bytes dropped";
    }
    leaf option-data-bytes-dropped {
      type uint64;
      description
        "Option data dropped";
    }
    leaf last-hour-packest-sent {
      type uint64;
      description
        "Total packets exported over the last one hour";
    }
    leaf last-hour-bytes-sent {
      type uint64;
      units "byte";
      description
        "Total bytes exported over the last one hour";
    }
    leaf last-hour-flows-sent {
      type uint64;
      description
        "Total flows exported over the of last one hour";
    }
    leaf last-minute-packets {
      type uint64;
      description
        "Total packets exported over the last one minute";
    }
    leaf last-minute-bytes-sent {
      type uint64;
      units "byte";
      description
        "Total bytes exported over the last one minute";
    }
    leaf last-minute-flows-sent {
      type uint64;
      description
        "Total flows exported over the last one minute";
    }
    leaf last-second-packets-sent {
      type uint64;
      description
        "Total packets exported over the last one second";
    }
    leaf last-second-bytes-sent {
      type uint64;
      units "byte";
      description
        "Total bytes exported over the last one second";
    }
    leaf last-second-flows-sent {
      type uint64;
      description
        "Total flows exported over the last one second";
    }
  }

  grouping live_ncs_NFSVR-SHOW-FLOW-EXPORTER-RESP-STATS {
    description
      "Flow exporter information";
    leaf name {
      type string;
      description
        "Exporter name";
    }
    leaf protocol {
      type string;
      description
        "Export Protocol Name";
    }
    leaf memory-usage {
      type uint32;
      description
        "Memory usage";
    }
    leaf-list used-by-flow-monitor {
      type live_ncs_Flow-monitor-name;
      description
        "List of flow monitors that use the exporter";
    }
    list collector {
      description
        "Statistics of all collectors";
      uses live_ncs_NFSVR-COLLECTOR-INFO;
    }
  }

  grouping live_ncs_NFSVR-SHOW-FLOW-EXPORTER-RESP-ARRAY {
    description
      "Flow exporter information";
    list statistic {
      description
        "Array of flow exporters";
      uses live_ncs_NFSVR-SHOW-FLOW-EXPORTER-RESP-STATS;
    }
  }

  grouping NFSVR-COLLECTOR-INFO {
    description
      "Per collector information";
    leaf exporter-state {
      type string;
      description
        "Exporter state";
    }
    leaf destination-address {
      type string;
      description
        "Destination IPv4 address in AAA.BBB.CCC.DDD
         format";
    }
    leaf source-address {
      type string;
      description
        "Source IPv4 address in AAA.BBB.CCC.DDD format";
    }
    leaf vrf-name {
      type string;
      description
        "VRF Name";
    }
    leaf destination-port {
      type uint16;
      description
        "Destination port number";
    }
    leaf souce-port {
      type uint16;
      description
        "Source port number";
    }
    leaf transport-protocol {
      type string;
      description
        "Transport protocol";
    }
    leaf packets-sent {
      type uint64;
      description
        "Packets sent";
    }
    leaf flows-sent {
      type uint64;
      description
        "Flows sent";
    }
    leaf templates-sent {
      type uint64;
      description
        "Templates sent";
    }
    leaf option-templates-sent {
      type uint64;
      description
        "Option templates sent";
    }
    leaf option-data-sent {
      type uint64;
      description
        "Option data sent";
    }
    leaf bytes-sent {
      type uint64;
      units "byte";
      description
        "Bytes sent";
    }
    leaf flow-bytes-sent {
      type uint64;
      units "byte";
      description
        "Flow bytes sent";
    }
    leaf template-bytes-sent {
      type uint64;
      units "byte";
      description
        "Template bytes sent";
    }
    leaf option-template-bytes-sent {
      type uint64;
      units "byte";
      description
        "Option template bytes sent";
    }
    leaf option-data-bytes-sent {
      type uint64;
      units "byte";
      description
        "Option data bytes sent";
    }
    leaf packets-dropped {
      type uint64;
      description
        "Packets dropped";
    }
    leaf flows-dropped {
      type uint64;
      description
        "Flows dropped";
    }
    leaf templates-dropped {
      type uint64;
      description
        "Templates dropped";
    }
    leaf option-templates-dropped {
      type uint64;
      description
        "Option templates dropped";
    }
    leaf option-data-dropped {
      type uint64;
      description
        "Option data dropped";
    }
    leaf bytes-dropped {
      type uint64;
      units "byte";
      description
        "Bytes dropped";
    }
    leaf flow-bytes-dropped {
      type uint64;
      units "byte";
      description
        "Flow bytes dropped";
    }
    leaf template-bytes-dropped {
      type uint64;
      units "byte";
      description
        "Template bytes dropped";
    }
    leaf option-template-bytes-dropped {
      type uint64;
      units "byte";
      description
        "Option template bytes dropped";
    }
    leaf option-data-bytes-dropped {
      type uint64;
      description
        "Option data dropped";
    }
    leaf last-hour-packest-sent {
      type uint64;
      description
        "Total packets exported over the last one hour";
    }
    leaf last-hour-bytes-sent {
      type uint64;
      units "byte";
      description
        "Total bytes exported over the last one hour";
    }
    leaf last-hour-flows-sent {
      type uint64;
      description
        "Total flows exported over the of last one hour";
    }
    leaf last-minute-packets {
      type uint64;
      description
        "Total packets exported over the last one minute";
    }
    leaf last-minute-bytes-sent {
      type uint64;
      units "byte";
      description
        "Total bytes exported over the last one minute";
    }
    leaf last-minute-flows-sent {
      type uint64;
      description
        "Total flows exported over the last one minute";
    }
    leaf last-second-packets-sent {
      type uint64;
      description
        "Total packets exported over the last one second";
    }
    leaf last-second-bytes-sent {
      type uint64;
      units "byte";
      description
        "Total bytes exported over the last one second";
    }
    leaf last-second-flows-sent {
      type uint64;
      description
        "Total flows exported over the last one second";
    }
  }

  grouping NFSVR-SHOW-FLOW-EXPORTER-RESP-STATS {
    description
      "Flow exporter information";
    leaf name {
      type string;
      description
        "Exporter name";
    }
    leaf protocol {
      type string;
      description
        "Export Protocol Name";
    }
    leaf memory-usage {
      type uint32;
      description
        "Memory usage";
    }
    leaf-list used-by-flow-monitor {
      type Flow-monitor-name;
      description
        "List of flow monitors that use the exporter";
    }
    list collector {
      description
        "Statistics of all collectors";
      uses NFSVR-COLLECTOR-INFO;
    }
  }

  grouping NFSVR-SHOW-FLOW-EXPORTER-RESP-ARRAY {
    description
      "Flow exporter information";
    list statistic {
      description
        "Array of flow exporters";
      uses NFSVR-SHOW-FLOW-EXPORTER-RESP-STATS;
    }
  }
}

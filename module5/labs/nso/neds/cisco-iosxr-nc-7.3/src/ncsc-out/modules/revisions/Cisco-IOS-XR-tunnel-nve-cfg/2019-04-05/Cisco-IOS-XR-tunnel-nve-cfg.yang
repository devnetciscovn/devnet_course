module Cisco-IOS-XR-tunnel-nve-cfg {
  // Generated by yanger -t ncs
  tailf:mount-id "cisco-iosxr-nc-7.3:cisco-iosxr-nc-7.3";
  tailf:ncs-device-type "netconf";

  namespace "http://cisco.com/ns/yang/Cisco-IOS-XR-tunnel-nve-cfg";
  prefix tunnel-nve-cfg;

  import ietf-inet-types {
    prefix inet;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-nve package configuration.

     This YANG module augments the
       Cisco-IOS-XR-ifmgr-cfg
     module with configuration data.

     Copyright (c) 2013-2019 by Cisco Systems, Inc.
     All rights reserved.";

  revision 2019-04-05 {
    description
      "Establish semantic version baseline.";
    semver:module-version "1.0.1";
  }
  revision 2016-08-30 {
    description
      "Initial Revision.";
  }
  revision 2015-11-09 {
    description
      "IOS XR 6.0 revision.";
  }

  typedef ncs_template_Host-reach-protocol {
    type string;
    description
      "Host reach protocol";
  }

  typedef ncs_template_Vni-range {
    type string;
    description
      "Vni range";
  }

  typedef ncs_template_Vxlan-udp-port-enum {
    type string;
    description
      "Vxlan udp port enum";
  }

  typedef ncs_template_Overlay-encap-enum {
    type string;
    description
      "Overlay encap enum";
  }

  typedef ncs_template_Unknown-unicast-flooding-enum {
    type string;
    description
      "Unknown unicast flooding enum";
  }

  typedef ncs_template_Load-balance-enum {
    type string;
    description
      "Load balance enum";
  }

  typedef ncs_template_Ir-protocol-enum {
    type string;
    description
      "Ir protocol enum";
  }

  typedef ncs_rpc_notif_Host-reach-protocol {
    type enumeration {
      enum "bgp" {
        value 1;
        description
          "Use BGP EVPN for VxLAN tunnel endpoint
           reachability";
      }
    }
    description
      "Host reach protocol";
  }

  typedef ncs_rpc_notif_Vni-range {
    type uint32 {
      range "1..16777215";
    }
    description
      "Vni range";
  }

  typedef ncs_rpc_notif_Vxlan-udp-port-enum {
    type enumeration {
      enum "ietf-udp-port" {
        value 4789;
        description
          "IETF defined UDP port for VxLAN";
      }
      enum "ivx-lan-udp-port" {
        value 48879;
        description
          "UDP port for iVxLAN";
      }
    }
    description
      "Vxlan udp port enum";
  }

  typedef ncs_rpc_notif_Overlay-encap-enum {
    type enumeration {
      enum "vx-lan-encapsulation" {
        value 0;
        description
          "VxLAN Encapsulation";
      }
      enum "soft-gre-encapsulation" {
        value 1;
        description
          "Soft GRE Encapsulation";
      }
    }
    description
      "Overlay encap enum";
  }

  typedef ncs_rpc_notif_Unknown-unicast-flooding-enum {
    type enumeration {
      enum "suppress-uuf" {
        value 1;
        description
          "Suppress unknown unicast flooding";
      }
    }
    description
      "Unknown unicast flooding enum";
  }

  typedef ncs_rpc_notif_Load-balance-enum {
    type enumeration {
      enum "per-evi" {
        value 1;
        description
          "Per evi load balance mode";
      }
    }
    description
      "Load balance enum";
  }

  typedef ncs_rpc_notif_Ir-protocol-enum {
    type enumeration {
      enum "bgp" {
        value 1;
        description
          "Use BGP Protocol for Ingress-Replication";
      }
    }
    description
      "Ir protocol enum";
  }

  typedef live_ncs_Host-reach-protocol {
    type enumeration {
      enum "bgp" {
        value 1;
        description
          "Use BGP EVPN for VxLAN tunnel endpoint
           reachability";
      }
    }
    description
      "Host reach protocol";
  }

  typedef live_ncs_Vni-range {
    type uint32 {
      range "1..16777215";
    }
    description
      "Vni range";
  }

  typedef live_ncs_Vxlan-udp-port-enum {
    type enumeration {
      enum "ietf-udp-port" {
        value 4789;
        description
          "IETF defined UDP port for VxLAN";
      }
      enum "ivx-lan-udp-port" {
        value 48879;
        description
          "UDP port for iVxLAN";
      }
    }
    description
      "Vxlan udp port enum";
  }

  typedef live_ncs_Overlay-encap-enum {
    type enumeration {
      enum "vx-lan-encapsulation" {
        value 0;
        description
          "VxLAN Encapsulation";
      }
      enum "soft-gre-encapsulation" {
        value 1;
        description
          "Soft GRE Encapsulation";
      }
    }
    description
      "Overlay encap enum";
  }

  typedef live_ncs_Unknown-unicast-flooding-enum {
    type enumeration {
      enum "suppress-uuf" {
        value 1;
        description
          "Suppress unknown unicast flooding";
      }
    }
    description
      "Unknown unicast flooding enum";
  }

  typedef live_ncs_Load-balance-enum {
    type enumeration {
      enum "per-evi" {
        value 1;
        description
          "Per evi load balance mode";
      }
    }
    description
      "Load balance enum";
  }

  typedef live_ncs_Ir-protocol-enum {
    type enumeration {
      enum "bgp" {
        value 1;
        description
          "Use BGP Protocol for Ingress-Replication";
      }
    }
    description
      "Ir protocol enum";
  }

  typedef Host-reach-protocol {
    type enumeration {
      enum "bgp" {
        value 1;
        description
          "Use BGP EVPN for VxLAN tunnel endpoint
           reachability";
      }
    }
    description
      "Host reach protocol";
  }

  typedef Vni-range {
    type uint32 {
      range "1..16777215";
    }
    description
      "Vni range";
  }

  typedef Vxlan-udp-port-enum {
    type enumeration {
      enum "ietf-udp-port" {
        value 4789;
        description
          "IETF defined UDP port for VxLAN";
      }
      enum "ivx-lan-udp-port" {
        value 48879;
        description
          "UDP port for iVxLAN";
      }
    }
    description
      "Vxlan udp port enum";
  }

  typedef Overlay-encap-enum {
    type enumeration {
      enum "vx-lan-encapsulation" {
        value 0;
        description
          "VxLAN Encapsulation";
      }
      enum "soft-gre-encapsulation" {
        value 1;
        description
          "Soft GRE Encapsulation";
      }
    }
    description
      "Overlay encap enum";
  }

  typedef Unknown-unicast-flooding-enum {
    type enumeration {
      enum "suppress-uuf" {
        value 1;
        description
          "Suppress unknown unicast flooding";
      }
    }
    description
      "Unknown unicast flooding enum";
  }

  typedef Load-balance-enum {
    type enumeration {
      enum "per-evi" {
        value 1;
        description
          "Per evi load balance mode";
      }
    }
    description
      "Load balance enum";
  }

  typedef Ir-protocol-enum {
    type enumeration {
      enum "bgp" {
        value 1;
        description
          "Use BGP Protocol for Ingress-Replication";
      }
    }
    description
      "Ir protocol enum";
  }

  augment "/ncs:devices/ncs:template/ncs:ned-id/ncs:config/a1:interface-configurations/a1:interface-configuration" {
    description
      "This augment extends the configuration data of
       'Cisco-IOS-XR-ifmgr-cfg'";
    container nve {
      description
        "NVE operational data";
      container anycast {
        description
          "Enable anycast mode for this NVE interface";
        leaf source-interface {
          type string;
          description
            "Name of the Anycast mode source interface";
        }
        leaf sync-group {
          type string;
          description
            "MCast group for syncing between Anycast
             gateways";
        }
      }
      container redundancy {
        description
          "Redundancy configuration for this NVE";
        container backbone-vx-lan {
          description
            "VXLAN backbone";
          leaf enable {
            type empty;
            description
              "Enable Backbone VxLAN";
          }
          leaf backbone-vx-laniccp {
            type string;
            description
              "VxLAN backbone ICCP group";
          }
        }
        container backbone-mpls {
          description
            "MPLS backbone";
          leaf backbone-mplsiccp {
            type string;
            description
              "MPLS backbone ICCP group";
          }
          leaf enable {
            type empty;
            description
              "Enable Backbone MPLS";
          }
        }
        leaf enable {
          type empty;
          description
            "Enable Redundancy";
        }
      }
      container member-vnis {
        description
          "VNI configuration Table for this NVE";
        list member-vni {
          // NCS patched for predictable order
          ordered-by user;
          key "vni-start vni-end";
          description
            "VNI member attributes";
          container multicast {
            presence "enable multicast";
            description
              "Mulitcast core group range associated with
               the VxLAN segment(s)";
            leaf multicast-group-min {
              type string;
              description
                "IPV4 group address of the tunnel source";
            }
            leaf multicast-group-max {
              type string;
              description
                "IPV4 group address MAX";
            }
          }
          leaf host-reachability {
            type ncs_template_Host-reach-protocol;
            description
              "Control protocol for VxLAN tunnel endpoint
               reachability";
          }
          leaf vrf {
            type string;
            description
              "VRF associated with the VxLAN segment";
          }
          leaf unknown-unicast-flooding {
            type ncs_template_Unknown-unicast-flooding-enum;
            description
              "Suppression of unknown unicast flooding";
          }
          leaf load-balance-per-evi {
            type ncs_template_Load-balance-enum;
            description
              "Per-evi load balance mode";
          }
          leaf enable {
            type empty;
            description
              "Enable VNI";
          }
          leaf vni-start {
            type ncs_template_Vni-range;
            description
              "Single VNI or Range Start";
          }
          leaf vni-end {
            type ncs_template_Vni-range;
            description
              "Range End";
          }
        }
      }
      leaf vx-lan-udp-port {
        type ncs_template_Vxlan-udp-port-enum;
        // NCS drop default statement
        description
          "UDP port number in VxLAN encapsulation";
      }
      leaf overlay-encapsulation {
        type ncs_template_Overlay-encap-enum;
        // NCS drop default statement
        description
          "The Overlay Encapsulation for this NVE";
      }
      leaf source-interface {
        type string;
        description
          "Source Interface for this NVE";
      }
      leaf ingress-replication-protocol {
        type ncs_template_Ir-protocol-enum;
        description
          "The Ingress Replication Protocol for this NVE";
      }
    }
  }
  augment "/ncs:devices/ncs:device/ncs:live-status/a1:interface-configurations/a1:interface-configuration" {
    description
      "This augment extends the configuration data of
       'Cisco-IOS-XR-ifmgr-cfg'";
    container nve {
      tailf:ncs-device-type "netconf";
      tailf:display-when "not(../../../../ncs:module) or ../../../../ncs:module[ncs:name='Cisco-IOS-XR-tunnel-nve-cfg'] or (../../../../ncs:live-status-protocol[not(ncs:capability)]) or (../../../../ncs:live-status-protocol/ncs:capability/ncs:module[.='Cisco-IOS-XR-tunnel-nve-cfg'])";
      description
        "NVE operational data";
      container anycast {
        description
          "Enable anycast mode for this NVE interface";
        leaf source-interface {
          type string;
          description
            "Name of the Anycast mode source interface";
        }
        leaf sync-group {
          type inet:ipv4-address-no-zone;
          description
            "MCast group for syncing between Anycast
             gateways";
        }
      }
      container redundancy {
        description
          "Redundancy configuration for this NVE";
        container backbone-vx-lan {
          description
            "VXLAN backbone";
          leaf enable {
            type empty;
            description
              "Enable Backbone VxLAN";
          }
          leaf backbone-vx-laniccp {
            type uint32;
            description
              "VxLAN backbone ICCP group";
          }
        }
        container backbone-mpls {
          description
            "MPLS backbone";
          leaf backbone-mplsiccp {
            type uint32;
            description
              "MPLS backbone ICCP group";
          }
          leaf enable {
            type empty;
            description
              "Enable Backbone MPLS";
          }
        }
        leaf enable {
          type empty;
          description
            "Enable Redundancy";
        }
      }
      container member-vnis {
        description
          "VNI configuration Table for this NVE";
        list member-vni {
          key "vni-start vni-end";
          description
            "VNI member attributes";
          container multicast {
            presence "enable multicast";
            description
              "Mulitcast core group range associated with
               the VxLAN segment(s)";
            leaf multicast-group-min {
              type inet:ipv4-address-no-zone;
              description
                "IPV4 group address of the tunnel source";
            }
            leaf multicast-group-max {
              type inet:ipv4-address-no-zone;
              description
                "IPV4 group address MAX";
            }
          }
          leaf host-reachability {
            type live_ncs_Host-reach-protocol;
            description
              "Control protocol for VxLAN tunnel endpoint
               reachability";
          }
          leaf vrf {
            type string;
            description
              "VRF associated with the VxLAN segment";
          }
          leaf unknown-unicast-flooding {
            type live_ncs_Unknown-unicast-flooding-enum;
            description
              "Suppression of unknown unicast flooding";
          }
          leaf load-balance-per-evi {
            type live_ncs_Load-balance-enum;
            description
              "Per-evi load balance mode";
          }
          leaf enable {
            type empty;
            description
              "Enable VNI";
          }
          leaf vni-start {
            type live_ncs_Vni-range;
            description
              "Single VNI or Range Start";
          }
          leaf vni-end {
            type live_ncs_Vni-range;
            description
              "Range End";
          }
        }
      }
      leaf vx-lan-udp-port {
        type live_ncs_Vxlan-udp-port-enum;
        // NCS drop default statement
        description
          "UDP port number in VxLAN encapsulation";
      }
      leaf overlay-encapsulation {
        type live_ncs_Overlay-encap-enum;
        // NCS drop default statement
        description
          "The Overlay Encapsulation for this NVE";
      }
      leaf source-interface {
        type string;
        description
          "Source Interface for this NVE";
      }
      leaf ingress-replication-protocol {
        type live_ncs_Ir-protocol-enum;
        description
          "The Ingress Replication Protocol for this NVE";
      }
    }
  }
  augment "/ncs:devices/ncs:device/ncs:config/a1:interface-configurations/a1:interface-configuration" {
    description
      "This augment extends the configuration data of
       'Cisco-IOS-XR-ifmgr-cfg'";
    container nve {
      tailf:ncs-device-type "netconf";
      tailf:display-when "not(../../../../ncs:module) or ../../../../ncs:module[ncs:name='Cisco-IOS-XR-tunnel-nve-cfg']";
      description
        "NVE operational data";
      container anycast {
        description
          "Enable anycast mode for this NVE interface";
        leaf source-interface {
          type string;
          description
            "Name of the Anycast mode source interface";
        }
        leaf sync-group {
          type inet:ipv4-address-no-zone;
          description
            "MCast group for syncing between Anycast
             gateways";
        }
      }
      container redundancy {
        description
          "Redundancy configuration for this NVE";
        container backbone-vx-lan {
          description
            "VXLAN backbone";
          leaf enable {
            type empty;
            description
              "Enable Backbone VxLAN";
          }
          leaf backbone-vx-laniccp {
            type uint32;
            description
              "VxLAN backbone ICCP group";
          }
        }
        container backbone-mpls {
          description
            "MPLS backbone";
          leaf backbone-mplsiccp {
            type uint32;
            description
              "MPLS backbone ICCP group";
          }
          leaf enable {
            type empty;
            description
              "Enable Backbone MPLS";
          }
        }
        leaf enable {
          type empty;
          description
            "Enable Redundancy";
        }
      }
      container member-vnis {
        description
          "VNI configuration Table for this NVE";
        list member-vni {
          key "vni-start vni-end";
          description
            "VNI member attributes";
          container multicast {
            presence "enable multicast";
            description
              "Mulitcast core group range associated with
               the VxLAN segment(s)";
            leaf multicast-group-min {
              type inet:ipv4-address-no-zone;
              description
                "IPV4 group address of the tunnel source";
            }
            leaf multicast-group-max {
              type inet:ipv4-address-no-zone;
              description
                "IPV4 group address MAX";
            }
          }
          leaf host-reachability {
            type Host-reach-protocol;
            description
              "Control protocol for VxLAN tunnel endpoint
               reachability";
          }
          leaf vrf {
            type string;
            description
              "VRF associated with the VxLAN segment";
          }
          leaf unknown-unicast-flooding {
            type Unknown-unicast-flooding-enum;
            description
              "Suppression of unknown unicast flooding";
          }
          leaf load-balance-per-evi {
            type Load-balance-enum;
            description
              "Per-evi load balance mode";
          }
          leaf enable {
            type empty;
            description
              "Enable VNI";
          }
          leaf vni-start {
            type Vni-range;
            description
              "Single VNI or Range Start";
          }
          leaf vni-end {
            type Vni-range;
            description
              "Range End";
          }
        }
      }
      leaf vx-lan-udp-port {
        type Vxlan-udp-port-enum;
        default "ietf-udp-port";
        description
          "UDP port number in VxLAN encapsulation";
      }
      leaf overlay-encapsulation {
        type Overlay-encap-enum;
        default "vx-lan-encapsulation";
        description
          "The Overlay Encapsulation for this NVE";
      }
      leaf source-interface {
        type string;
        description
          "Source Interface for this NVE";
      }
      leaf ingress-replication-protocol {
        type Ir-protocol-enum;
        description
          "The Ingress Replication Protocol for this NVE";
      }
    }
  }
}

module Cisco-IOS-XR-ip-ntp-oper {
  // Generated by yanger -t ncs
  tailf:mount-id "cisco-iosxr-nc-7.3:cisco-iosxr-nc-7.3";
  tailf:ncs-device-type "netconf";

  namespace "http://cisco.com/ns/yang/Cisco-IOS-XR-ip-ntp-oper";
  prefix ip-ntp-oper;

  import Cisco-IOS-XR-types {
    prefix xr;
  }
  import cisco-semver {
    prefix semver;
  }
  include Cisco-IOS-XR-ip-ntp-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-ntp package operational data.

     This module contains definitions
     for the following management objects:
       ntp: NTP operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container ntp
  }
  augment "/ncs:devices/ncs:device/ncs:live-status" {
    container ntp {
      tailf:ncs-device-type "netconf";
      tailf:display-when "not(../../ncs:module) or ../../ncs:module[ncs:name='Cisco-IOS-XR-ip-ntp-oper'] or (../../ncs:live-status-protocol[not(ncs:capability)]) or (../../ncs:live-status-protocol/ncs:capability/ncs:module[.='Cisco-IOS-XR-ip-ntp-oper'])";
      description
        "NTP operational data";
      container nodes {
        description
          "Node-specific NTP operational data";
        list node {
          key "node";
          description
            "NTP operational data for a particular node";
          container associations-detail {
            description
              "NTP Associations Detail information";
            uses live_ncs_NTP-EDM-ASSOC-DETAIL-RESULT;
          }
          container status {
            description
              "Status of NTP peer(s)";
            uses live_ncs_NTP-EDM-STATUS-RESULT;
          }
          container associations {
            description
              "NTP Associations information";
            uses live_ncs_NTP-EDM-ASSOC-SUMMARY-RESULT;
          }
          leaf node {
            type xr:live_ncs_Node-id;
            description
              "The node identifier";
          }
        }
      }
    }
  }
  augment "/ncs:devices/ncs:template/ncs:ned-id/ncs:config" {
    // NCS drop config false container ntp
  }
}

module Cisco-IOS-XR-aaa-nacm-oper {
  // Generated by yanger -t ncs
  tailf:mount-id "cisco-iosxr-nc-7.3:cisco-iosxr-nc-7.3";
  tailf:ncs-device-type "netconf";

  namespace "http://cisco.com/ns/yang/Cisco-IOS-XR-aaa-nacm-oper";
  prefix aaa-nacm-oper;

  import Cisco-IOS-XR-types {
    prefix xr;
  }
  import cisco-semver {
    prefix semver;
  }
  include Cisco-IOS-XR-aaa-nacm-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-nacm package operational data.

     This module contains definitions
     for the following management objects:
       aaa-nacm: AAA Nacm Information

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container 'aaa-nacm'
  }
  augment "/ncs:devices/ncs:device/ncs:live-status" {
    container aaa-nacm {
      tailf:ncs-device-type "netconf";
      tailf:display-when "not(../../ncs:module) or ../../ncs:module[ncs:name='Cisco-IOS-XR-aaa-nacm-oper'] or (../../ncs:live-status-protocol[not(ncs:capability)]) or (../../ncs:live-status-protocol/ncs:capability/ncs:module[.='Cisco-IOS-XR-aaa-nacm-oper'])";
      description
        "AAA Nacm Information";
      container counters {
        description
          "AAA NACM summary";
        uses live_ncs_NACM-COUNTERS;
      }
      container users {
        description
          "AAA NACM User summary";
        list user {
          key "user";
          description
            "AAA NACM User detail";
          leaf user {
            type xr:live_ncs_Cisco-ios-xr-string;
            description
              "User";
          }
          uses live_ncs_NACM-USER-DETAIL;
        }
      }
      container summary {
        description
          "AAA NACM summary";
        uses live_ncs_NACM-SUMMARY;
      }
      container rules {
        description
          "AAA NACM Rulelist summary";
        list rule {
          description
            "AAA NACM Rulelist detail";
          container rulelist-rules {
            description
              "AAA NACM Rulelist detail";
            list rulelist-rule {
              key "rule";
              description
                "AAA NACM Rulelist detail";
              leaf rule {
                type xr:live_ncs_Cisco-ios-xr-string;
                description
                  "Rule";
              }
              uses live_ncs_NACM-RULE-DETAIL;
            }
          }
          leaf ordering-index {
            type xr:live_ncs_Cisco-ios-xr-string;
            description
              "Rulelist Ordering Index";
          }
          leaf rulelist-name {
            type xr:live_ncs_Cisco-ios-xr-string;
            description
              "Rulelist Name";
          }
        }
      }
      container groups {
        description
          "AAA NACM Group summary";
        list group {
          key "group";
          description
            "AAA NACM Group detail";
          leaf group {
            type xr:live_ncs_Cisco-ios-xr-string;
            description
              "Group";
          }
          uses live_ncs_NACM-GROUP-DETAIL;
        }
      }
    }
  }
  augment "/ncs:devices/ncs:template/ncs:ned-id/ncs:config" {
    // NCS drop config false container 'aaa-nacm'
  }
}

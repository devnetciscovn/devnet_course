module Cisco-IOS-XR-pbr-bng-cfg {
  // Generated by yanger -t ncs
  tailf:mount-id "cisco-iosxr-nc-7.3:cisco-iosxr-nc-7.3";
  tailf:ncs-device-type "netconf";

  namespace "http://cisco.com/ns/yang/Cisco-IOS-XR-pbr-bng-cfg";
  prefix pbr-bng-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr-bng package configuration.

     This module contains definitions
     for the following management objects:
       bng-pbr: Subscriber PBR configuration

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Bng-pbr-http-enrichment-params {
    type string;
    description
      "Bng pbr http enrichment params";
  }

  typedef ncs_rpc_notif_Bng-pbr-http-enrichment-params {
    type enumeration {
      enum "subscriber-mac" {
        value 1;
        description
          "Subscriber Mac";
      }
      enum "subscriber-ip" {
        value 2;
        description
          "Subscriber IPv4/IPv6 address";
      }
      enum "host-name" {
        value 4;
        description
          "Bng Router Hostname";
      }
      enum "bng-identifier-interface" {
        value 8;
        description
          "Bng Identifier interface";
      }
    }
    description
      "Bng pbr http enrichment params";
  }

  typedef live_ncs_Bng-pbr-http-enrichment-params {
    type enumeration {
      enum "subscriber-mac" {
        value 1;
        description
          "Subscriber Mac";
      }
      enum "subscriber-ip" {
        value 2;
        description
          "Subscriber IPv4/IPv6 address";
      }
      enum "host-name" {
        value 4;
        description
          "Bng Router Hostname";
      }
      enum "bng-identifier-interface" {
        value 8;
        description
          "Bng Identifier interface";
      }
    }
    description
      "Bng pbr http enrichment params";
  }

  typedef Bng-pbr-http-enrichment-params {
    type enumeration {
      enum "subscriber-mac" {
        value 1;
        description
          "Subscriber Mac";
      }
      enum "subscriber-ip" {
        value 2;
        description
          "Subscriber IPv4/IPv6 address";
      }
      enum "host-name" {
        value 4;
        description
          "Bng Router Hostname";
      }
      enum "bng-identifier-interface" {
        value 8;
        description
          "Bng Identifier interface";
      }
    }
    description
      "Bng pbr http enrichment params";
  }

  augment "/ncs:devices/ncs:device/ncs:config" {
    container bng-pbr {
      tailf:ncs-device-type "netconf";
      tailf:display-when "not(../../ncs:module) or ../../ncs:module[ncs:name='Cisco-IOS-XR-pbr-bng-cfg']";
      description
        "Subscriber PBR configuration";
      container http-enrichment {
        description
          "HTTP Enrichment";
        container parameters {
          presence "Indicates a parameters node is configured.";
          description
            "HTTP Enrichment parameters";
          leaf arg1 {
            type Bng-pbr-http-enrichment-params;
            mandatory true;
            description
              "first argument ";
          }
          leaf arg2 {
            type Bng-pbr-http-enrichment-params;
            description
              "second argument ";
          }
          leaf arg3 {
            type Bng-pbr-http-enrichment-params;
            description
              "Third argument ";
          }
          leaf arg4 {
            type Bng-pbr-http-enrichment-params;
            description
              "Fourth argument ";
          }
        }
      }
      leaf bng-interface {
        type xr:Interface-name;
        description
          "Interface for source address";
      }
    }
  }
  augment "/ncs:devices/ncs:device/ncs:live-status" {
    container bng-pbr {
      tailf:ncs-device-type "netconf";
      tailf:display-when "not(../../ncs:module) or ../../ncs:module[ncs:name='Cisco-IOS-XR-pbr-bng-cfg'] or (../../ncs:live-status-protocol[not(ncs:capability)]) or (../../ncs:live-status-protocol/ncs:capability/ncs:module[.='Cisco-IOS-XR-pbr-bng-cfg'])";
      description
        "Subscriber PBR configuration";
      container http-enrichment {
        description
          "HTTP Enrichment";
        container parameters {
          presence "Indicates a parameters node is configured.";
          description
            "HTTP Enrichment parameters";
          leaf arg1 {
            type live_ncs_Bng-pbr-http-enrichment-params;
            // NCS drop mandatory statement
            description
              "first argument ";
          }
          leaf arg2 {
            type live_ncs_Bng-pbr-http-enrichment-params;
            description
              "second argument ";
          }
          leaf arg3 {
            type live_ncs_Bng-pbr-http-enrichment-params;
            description
              "Third argument ";
          }
          leaf arg4 {
            type live_ncs_Bng-pbr-http-enrichment-params;
            description
              "Fourth argument ";
          }
        }
      }
      leaf bng-interface {
        type xr:live_ncs_Interface-name;
        description
          "Interface for source address";
      }
    }
  }
  augment "/ncs:devices/ncs:template/ncs:ned-id/ncs:config" {
    container bng-pbr {
      description
        "Subscriber PBR configuration";
      container http-enrichment {
        description
          "HTTP Enrichment";
        container parameters {
          presence "Indicates a parameters node is configured.";
          description
            "HTTP Enrichment parameters";
          leaf arg1 {
            type ncs_template_Bng-pbr-http-enrichment-params;
            // NCS drop mandatory statement
            description
              "first argument ";
          }
          leaf arg2 {
            type ncs_template_Bng-pbr-http-enrichment-params;
            description
              "second argument ";
          }
          leaf arg3 {
            type ncs_template_Bng-pbr-http-enrichment-params;
            description
              "Third argument ";
          }
          leaf arg4 {
            type ncs_template_Bng-pbr-http-enrichment-params;
            description
              "Fourth argument ";
          }
        }
      }
      leaf bng-interface {
        type xr:ncs_template_Interface-name;
        description
          "Interface for source address";
      }
    }
  }
}

module Cisco-IOS-XR-ipv4-io-oper {
  // Generated by yanger -t ncs
  tailf:mount-id "cisco-iosxr-nc-7.3:cisco-iosxr-nc-7.3";
  tailf:ncs-device-type "netconf";

  namespace "http://cisco.com/ns/yang/Cisco-IOS-XR-ipv4-io-oper";
  prefix ipv4-io-oper;

  import Cisco-IOS-XR-types {
    prefix xr;
  }
  import cisco-semver {
    prefix semver;
  }
  include Cisco-IOS-XR-ipv4-io-oper-sub2 {
    revision-date 2019-10-01;
  }
  include Cisco-IOS-XR-ipv4-io-oper-sub1 {
    revision-date 2019-10-01;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-io package operational data.

     This module contains definitions
     for the following management objects:
       ipv4-network: IPv4 network operational data

     Copyright (c) 2013-2019 by Cisco Systems, Inc.
     All rights reserved.";

  revision 2019-10-01 {
    description
      "Updated brief and detail containers for node related interfaces.";
    semver:module-version "1.1.0";
  }
  revision 2019-04-05 {
    description
      "Establish semantic version baseline.";
    semver:module-version "1.0.1";
  }
  revision 2018-08-01 {
    description
      "Removed empty groupings.";
  }
  revision 2015-10-20 {
    description
      "this schema file has all the latest changes.";
  }
  revision 2015-01-07 {
    description
      "IOS XR 5.3.1 revision.";
  }

  augment "/ncs:devices/ncs:device/ncs:config" {
    // NCS drop config false container 'ipv4-network'
  }
  augment "/ncs:devices/ncs:device/ncs:live-status" {
    container ipv4-network {
      tailf:ncs-device-type "netconf";
      tailf:display-when "not(../../ncs:module) or ../../ncs:module[ncs:name='Cisco-IOS-XR-ipv4-io-oper'] or (../../ncs:live-status-protocol[not(ncs:capability)]) or (../../ncs:live-status-protocol/ncs:capability/ncs:module[.='Cisco-IOS-XR-ipv4-io-oper'])";
      description
        "IPv4 network operational data";
      container nodes {
        description
          "Node-specific IPv4 network operational data";
        list node {
          key "node-name";
          description
            "IPv4 network operational data for a particular
             node";
          container interface-data {
            description
              "IPv4 network operational interface data";
            container vrfs {
              description
                "VRF specific IPv4 network operational
                 interface data";
              list vrf {
                key "vrf-name";
                description
                  "VRF name of an interface belong to";
                container briefs {
                  description
                    "Brief interface IPv4 network operational
                     data for a node";
                  list brief {
                    key "interface-name";
                    description
                      "Brief interface IPv4 network operational
                       data for an interface";
                    leaf interface-name {
                      type xr:live_ncs_Interface-name;
                      description
                        "The name of the interface";
                    }
                    uses live_ncs_IPV4-IF-BRIEF;
                  }
                }
                container details {
                  description
                    "Detail interface IPv4 network operational
                     data for a node";
                  list detail {
                    key "interface-name";
                    description
                      "Detail interface IPv4 network operational
                       data for an interface";
                    leaf interface-name {
                      type xr:live_ncs_Interface-name;
                      description
                        "The name of the interface";
                    }
                    uses live_ncs_IPV4-IF-DETAIL;
                  }
                }
                leaf vrf-name {
                  type xr:live_ncs_Cisco-ios-xr-string;
                  description
                    "The VRF name";
                }
              }
            }
            container summary {
              description
                "Summary of IPv4 network operational interface
                 data on a node";
              uses live_ncs_IPV4-IF-SUMMARY;
            }
            container interfaces {
              description
                "Interface names with VRF";
              list interface {
                key "interface-name";
                description
                  "Interface names with VRF";
                container vrf-names {
                  description
                    "List of VRF on the interface";
                  list vrf-name {
                    key "vrf-name";
                    description
                      "VRF information on the interface";
                    container detail-data {
                      description
                        "Detail IPv4 network operational data for
                         an interface";
                      uses live_ncs_IPV4-IF-DETAIL;
                    }
                    container brief-data {
                      description
                        "Brief IPv4 network operational data for
                         an interface";
                      uses live_ncs_IPV4-IF-BRIEF;
                    }
                    leaf vrf-name {
                      type xr:live_ncs_Cisco-ios-xr-string;
                      description
                        "The VRF name";
                    }
                  }
                }
                leaf interface-name {
                  type xr:live_ncs_Interface-name;
                  description
                    "The name of the interface";
                }
              }
            }
          }
          container statistics {
            description
              "Statistical IPv4 network operational data for
               a node";
            container traffic {
              description
                "Traffic statistics for a node";
              uses live_ncs_IP-TRAFFIC;
            }
          }
          leaf node-name {
            type xr:live_ncs_Node-id;
            description
              "The node name";
          }
        }
      }
    }
  }
  augment "/ncs:devices/ncs:template/ncs:ned-id/ncs:config" {
    // NCS drop config false container 'ipv4-network'
  }
}

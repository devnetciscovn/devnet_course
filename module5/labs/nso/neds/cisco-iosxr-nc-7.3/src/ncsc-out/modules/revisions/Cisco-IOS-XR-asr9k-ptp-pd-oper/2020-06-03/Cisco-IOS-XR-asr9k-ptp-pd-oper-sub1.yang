submodule Cisco-IOS-XR-asr9k-ptp-pd-oper-sub1 {
  // Generated by yanger -t ncs
  tailf:mount-id "cisco-iosxr-nc-7.3:cisco-iosxr-nc-7.3";

  belongs-to Cisco-IOS-XR-asr9k-ptp-pd-oper {
    prefix Cisco-IOS-XR-asr9k-ptp-pd-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-ptp-pd package operational data.

     Copyright (c) 2013-2020 by Cisco Systems, Inc.
     All rights reserved.";

  revision 2020-06-03 {
    description
      "IOS-XR 7.3.1 revision.";
    semver:module-version "1.0.0";
  }
  revision 2019-04-05 {
    description
      "Establish semantic version baseline.";
  }
  revision 2015-11-09 {
    description
      "IOS XR 6.0 revision.";
  }

  grouping ncs_template_PTP-PD-BAG-TIMESTAMP {
    description
      "PTP PD timestamp";
    leaf second {
      type string;
      description
        "value of second";
    }
    leaf nano-second {
      type string;
      description
        "value of nano second";
    }
  }

  grouping ncs_template_PTP-PD-SERVO-INFO {
    description
      "PTP PD servo status";
    container last-set-time {
      description
        "last input of setTime";
      uses ncs_template_PTP-PD-BAG-TIMESTAMP;
    }
    container last-received-t1 {
      description
        "last T1 timestamp reveiced";
      uses ncs_template_PTP-PD-BAG-TIMESTAMP;
    }
    container last-received-t2 {
      description
        "last T2 timestamp reveiced";
      uses ncs_template_PTP-PD-BAG-TIMESTAMP;
    }
    container last-received-t3 {
      description
        "last T3 timestamp reveiced";
      uses ncs_template_PTP-PD-BAG-TIMESTAMP;
    }
    container last-received-t4 {
      description
        "last T4 timestamp reveiced";
      uses ncs_template_PTP-PD-BAG-TIMESTAMP;
    }
    container pre-received-t1 {
      description
        "pre T1 timestamp reveiced";
      uses ncs_template_PTP-PD-BAG-TIMESTAMP;
    }
    container pre-received-t2 {
      description
        "pre T2 timestamp reveiced";
      uses ncs_template_PTP-PD-BAG-TIMESTAMP;
    }
    container pre-received-t3 {
      description
        "pre T3 timestamp reveiced";
      uses ncs_template_PTP-PD-BAG-TIMESTAMP;
    }
    container pre-received-t4 {
      description
        "pre T4 timestamp reveiced";
      uses ncs_template_PTP-PD-BAG-TIMESTAMP;
    }
    leaf lock-status {
      type string;
      description
        "lock status of device";
    }
    leaf running {
      type string;
      description
        "running status of apr";
    }
    leaf device-status {
      type string;
      description
        "status of device";
    }
    leaf log-level {
      type string;
      description
        "log level of apr";
    }
    leaf phase-accuracy-last {
      type string;
      description
        " last phase alignment accuracy";
    }
    leaf num-sync-timestamp {
      type string;
      description
        "number of sync timestamp reveiced";
    }
    leaf num-delay-timestamp {
      type string;
      description
        "number of delay timestamp reveiced";
    }
    leaf num-set-time {
      type string;
      description
        "number of setTime() been called";
    }
    leaf num-step-time {
      type string;
      description
        "number of stepTime() been called";
    }
    leaf num-adjust-freq {
      type string;
      description
        "number of adjustFreq() been called";
    }
    leaf num-adjust-freq-time {
      type string;
      description
        "number of adjustFreqTime() been called";
    }
    leaf last-adjust-freq {
      type string;
      description
        "last input of adjustFreq";
    }
    leaf last-step-time {
      type string;
      description
        "last input of stepTime";
    }
    leaf num-discard-sync-timestamp {
      type string;
      description
        "number of sync timestamp discarded";
    }
    leaf num-discard-delay-timestamp {
      type string;
      description
        "number of delay timestamp discarded";
    }
    leaf flagof-last-set-time {
      type string;
      description
        "last input flag of setTime";
    }
    leaf offset-from-master {
      type string;
      description
        "Time Offset From Master";
    }
    leaf mean-path-delay {
      type string;
      description
        "Mean Path Delay";
    }
    leaf servo-mode {
      type string;
      description
        "Servo Mode";
    }
  }

  grouping ncs_rpc_notif_PTP-PD-BAG-TIMESTAMP {
    description
      "PTP PD timestamp";
    leaf second {
      type uint32;
      description
        "value of second";
    }
    leaf nano-second {
      type uint32;
      description
        "value of nano second";
    }
  }

  grouping ncs_rpc_notif_PTP-PD-SERVO-INFO {
    description
      "PTP PD servo status";
    container last-set-time {
      description
        "last input of setTime";
      uses ncs_rpc_notif_PTP-PD-BAG-TIMESTAMP;
    }
    container last-received-t1 {
      description
        "last T1 timestamp reveiced";
      uses ncs_rpc_notif_PTP-PD-BAG-TIMESTAMP;
    }
    container last-received-t2 {
      description
        "last T2 timestamp reveiced";
      uses ncs_rpc_notif_PTP-PD-BAG-TIMESTAMP;
    }
    container last-received-t3 {
      description
        "last T3 timestamp reveiced";
      uses ncs_rpc_notif_PTP-PD-BAG-TIMESTAMP;
    }
    container last-received-t4 {
      description
        "last T4 timestamp reveiced";
      uses ncs_rpc_notif_PTP-PD-BAG-TIMESTAMP;
    }
    container pre-received-t1 {
      description
        "pre T1 timestamp reveiced";
      uses ncs_rpc_notif_PTP-PD-BAG-TIMESTAMP;
    }
    container pre-received-t2 {
      description
        "pre T2 timestamp reveiced";
      uses ncs_rpc_notif_PTP-PD-BAG-TIMESTAMP;
    }
    container pre-received-t3 {
      description
        "pre T3 timestamp reveiced";
      uses ncs_rpc_notif_PTP-PD-BAG-TIMESTAMP;
    }
    container pre-received-t4 {
      description
        "pre T4 timestamp reveiced";
      uses ncs_rpc_notif_PTP-PD-BAG-TIMESTAMP;
    }
    leaf lock-status {
      type uint16;
      description
        "lock status of device";
    }
    leaf running {
      type boolean;
      description
        "running status of apr";
    }
    leaf device-status {
      type string {
        length "0..50";
      }
      description
        "status of device";
    }
    leaf log-level {
      type uint16;
      description
        "log level of apr";
    }
    leaf phase-accuracy-last {
      type int64;
      description
        " last phase alignment accuracy";
    }
    leaf num-sync-timestamp {
      type uint32;
      description
        "number of sync timestamp reveiced";
    }
    leaf num-delay-timestamp {
      type uint32;
      description
        "number of delay timestamp reveiced";
    }
    leaf num-set-time {
      type uint32;
      description
        "number of setTime() been called";
    }
    leaf num-step-time {
      type uint32;
      description
        "number of stepTime() been called";
    }
    leaf num-adjust-freq {
      type uint32;
      description
        "number of adjustFreq() been called";
    }
    leaf num-adjust-freq-time {
      type uint32;
      description
        "number of adjustFreqTime() been called";
    }
    leaf last-adjust-freq {
      type int32;
      description
        "last input of adjustFreq";
    }
    leaf last-step-time {
      type int32;
      description
        "last input of stepTime";
    }
    leaf num-discard-sync-timestamp {
      type uint32;
      description
        "number of sync timestamp discarded";
    }
    leaf num-discard-delay-timestamp {
      type uint32;
      description
        "number of delay timestamp discarded";
    }
    leaf flagof-last-set-time {
      type boolean;
      description
        "last input flag of setTime";
    }
    leaf offset-from-master {
      type int64;
      description
        "Time Offset From Master";
    }
    leaf mean-path-delay {
      type int64;
      description
        "Mean Path Delay";
    }
    leaf servo-mode {
      type string {
        length "0..50";
      }
      description
        "Servo Mode";
    }
  }

  grouping live_ncs_PTP-PD-BAG-TIMESTAMP {
    description
      "PTP PD timestamp";
    leaf second {
      type uint32;
      description
        "value of second";
    }
    leaf nano-second {
      type uint32;
      description
        "value of nano second";
    }
  }

  grouping live_ncs_PTP-PD-SERVO-INFO {
    description
      "PTP PD servo status";
    container last-set-time {
      description
        "last input of setTime";
      uses live_ncs_PTP-PD-BAG-TIMESTAMP;
    }
    container last-received-t1 {
      description
        "last T1 timestamp reveiced";
      uses live_ncs_PTP-PD-BAG-TIMESTAMP;
    }
    container last-received-t2 {
      description
        "last T2 timestamp reveiced";
      uses live_ncs_PTP-PD-BAG-TIMESTAMP;
    }
    container last-received-t3 {
      description
        "last T3 timestamp reveiced";
      uses live_ncs_PTP-PD-BAG-TIMESTAMP;
    }
    container last-received-t4 {
      description
        "last T4 timestamp reveiced";
      uses live_ncs_PTP-PD-BAG-TIMESTAMP;
    }
    container pre-received-t1 {
      description
        "pre T1 timestamp reveiced";
      uses live_ncs_PTP-PD-BAG-TIMESTAMP;
    }
    container pre-received-t2 {
      description
        "pre T2 timestamp reveiced";
      uses live_ncs_PTP-PD-BAG-TIMESTAMP;
    }
    container pre-received-t3 {
      description
        "pre T3 timestamp reveiced";
      uses live_ncs_PTP-PD-BAG-TIMESTAMP;
    }
    container pre-received-t4 {
      description
        "pre T4 timestamp reveiced";
      uses live_ncs_PTP-PD-BAG-TIMESTAMP;
    }
    leaf lock-status {
      type uint16;
      description
        "lock status of device";
    }
    leaf running {
      type boolean;
      description
        "running status of apr";
    }
    leaf device-status {
      type string {
        length "0..50";
      }
      description
        "status of device";
    }
    leaf log-level {
      type uint16;
      description
        "log level of apr";
    }
    leaf phase-accuracy-last {
      type int64;
      description
        " last phase alignment accuracy";
    }
    leaf num-sync-timestamp {
      type uint32;
      description
        "number of sync timestamp reveiced";
    }
    leaf num-delay-timestamp {
      type uint32;
      description
        "number of delay timestamp reveiced";
    }
    leaf num-set-time {
      type uint32;
      description
        "number of setTime() been called";
    }
    leaf num-step-time {
      type uint32;
      description
        "number of stepTime() been called";
    }
    leaf num-adjust-freq {
      type uint32;
      description
        "number of adjustFreq() been called";
    }
    leaf num-adjust-freq-time {
      type uint32;
      description
        "number of adjustFreqTime() been called";
    }
    leaf last-adjust-freq {
      type int32;
      description
        "last input of adjustFreq";
    }
    leaf last-step-time {
      type int32;
      description
        "last input of stepTime";
    }
    leaf num-discard-sync-timestamp {
      type uint32;
      description
        "number of sync timestamp discarded";
    }
    leaf num-discard-delay-timestamp {
      type uint32;
      description
        "number of delay timestamp discarded";
    }
    leaf flagof-last-set-time {
      type boolean;
      description
        "last input flag of setTime";
    }
    leaf offset-from-master {
      type int64;
      description
        "Time Offset From Master";
    }
    leaf mean-path-delay {
      type int64;
      description
        "Mean Path Delay";
    }
    leaf servo-mode {
      type string {
        length "0..50";
      }
      description
        "Servo Mode";
    }
  }

  grouping PTP-PD-BAG-TIMESTAMP {
    description
      "PTP PD timestamp";
    leaf second {
      type uint32;
      description
        "value of second";
    }
    leaf nano-second {
      type uint32;
      description
        "value of nano second";
    }
  }

  grouping PTP-PD-SERVO-INFO {
    description
      "PTP PD servo status";
    container last-set-time {
      description
        "last input of setTime";
      uses PTP-PD-BAG-TIMESTAMP;
    }
    container last-received-t1 {
      description
        "last T1 timestamp reveiced";
      uses PTP-PD-BAG-TIMESTAMP;
    }
    container last-received-t2 {
      description
        "last T2 timestamp reveiced";
      uses PTP-PD-BAG-TIMESTAMP;
    }
    container last-received-t3 {
      description
        "last T3 timestamp reveiced";
      uses PTP-PD-BAG-TIMESTAMP;
    }
    container last-received-t4 {
      description
        "last T4 timestamp reveiced";
      uses PTP-PD-BAG-TIMESTAMP;
    }
    container pre-received-t1 {
      description
        "pre T1 timestamp reveiced";
      uses PTP-PD-BAG-TIMESTAMP;
    }
    container pre-received-t2 {
      description
        "pre T2 timestamp reveiced";
      uses PTP-PD-BAG-TIMESTAMP;
    }
    container pre-received-t3 {
      description
        "pre T3 timestamp reveiced";
      uses PTP-PD-BAG-TIMESTAMP;
    }
    container pre-received-t4 {
      description
        "pre T4 timestamp reveiced";
      uses PTP-PD-BAG-TIMESTAMP;
    }
    leaf lock-status {
      type uint16;
      description
        "lock status of device";
    }
    leaf running {
      type boolean;
      description
        "running status of apr";
    }
    leaf device-status {
      type string {
        length "0..50";
      }
      description
        "status of device";
    }
    leaf log-level {
      type uint16;
      description
        "log level of apr";
    }
    leaf phase-accuracy-last {
      type int64;
      description
        " last phase alignment accuracy";
    }
    leaf num-sync-timestamp {
      type uint32;
      description
        "number of sync timestamp reveiced";
    }
    leaf num-delay-timestamp {
      type uint32;
      description
        "number of delay timestamp reveiced";
    }
    leaf num-set-time {
      type uint32;
      description
        "number of setTime() been called";
    }
    leaf num-step-time {
      type uint32;
      description
        "number of stepTime() been called";
    }
    leaf num-adjust-freq {
      type uint32;
      description
        "number of adjustFreq() been called";
    }
    leaf num-adjust-freq-time {
      type uint32;
      description
        "number of adjustFreqTime() been called";
    }
    leaf last-adjust-freq {
      type int32;
      description
        "last input of adjustFreq";
    }
    leaf last-step-time {
      type int32;
      description
        "last input of stepTime";
    }
    leaf num-discard-sync-timestamp {
      type uint32;
      description
        "number of sync timestamp discarded";
    }
    leaf num-discard-delay-timestamp {
      type uint32;
      description
        "number of delay timestamp discarded";
    }
    leaf flagof-last-set-time {
      type boolean;
      description
        "last input flag of setTime";
    }
    leaf offset-from-master {
      type int64;
      description
        "Time Offset From Master";
    }
    leaf mean-path-delay {
      type int64;
      description
        "Mean Path Delay";
    }
    leaf servo-mode {
      type string {
        length "0..50";
      }
      description
        "Servo Mode";
    }
  }
}

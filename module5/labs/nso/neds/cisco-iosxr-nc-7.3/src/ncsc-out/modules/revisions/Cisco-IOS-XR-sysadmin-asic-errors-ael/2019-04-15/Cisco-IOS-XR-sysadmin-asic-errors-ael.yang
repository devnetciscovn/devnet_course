module Cisco-IOS-XR-sysadmin-asic-errors-ael {
  // Generated by yanger -t ncs
  tailf:mount-id "cisco-iosxr-nc-7.3:cisco-iosxr-nc-7.3";
  tailf:ncs-device-type "netconf";

  namespace "http://www.cisco.com/ns/yang/Cisco-IOS-XR-sysadmin-asic-errors-ael";
  prefix ael;

  import tailf-common {
    prefix tailf;
  }
  import Cisco-IOS-XR-sysadmin-types {
    prefix calvados;
  }
  import cisco-semver {
    prefix semver;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2019-04-15 {
    description
      "Establish semantic version baseline.";
    semver:module-version "1.0.0";
  }
  revision 2017-07-05 {
    description
      "Namespace change to fix comply with Cisco guidelines on namespace";
  }
  revision 2017-05-01 {
    description
      "Namespace change to comply with Cisco guidelines on namespace";
  }

  grouping ncs_template_clear-asic-errors;

  grouping ncs_template_ael-history-ap-grp {
    container history {
      list location {
        // NCS patched for predictable order
        ordered-by user;
        key "location-name";
        leaf location-name {
          type calvados:ncs_template_location-id;
        }
        uses ncs_template_clear-asic-errors;
      }
    }
  }

  grouping ncs_template_ael-history-grp {
    container history {
      list location {
        // NCS patched for predictable order
        ordered-by user;
        key "location-name";
        leaf location-name {
          type calvados:ncs_template_location-id;
        }
        list log-lst {
          // NCS patched for predictable order
          ordered-by user;
          leaf log-line {
            type string;
          }
        }
      }
    }
  }

  grouping ncs_template_ael-non-history-grp {
    list location {
      // NCS patched for predictable order
      ordered-by user;
      key "location-name";
      leaf location-name {
        type calvados:ncs_template_location-id;
      }
      list log-lst {
        // NCS patched for predictable order
        ordered-by user;
        leaf log-line {
          type string;
        }
      }
    }
  }

  grouping ncs_template_ael-save-option-grp {
    container save-all-inst-asic-errors {
      uses ncs_template_ael-non-history-grp;
    }
  }

  grouping ncs_template_ael-non-history-ap-grp {
    list location {
      // NCS patched for predictable order
      ordered-by user;
      key "location-name";
      leaf location-name {
        type calvados:ncs_template_location-id;
      }
      uses ncs_template_clear-asic-errors;
    }
  }

  grouping ncs_template_ael-all-error-types-grp {
    container sbe {
      uses ncs_template_ael-non-history-grp;
    }
    container mbe {
      uses ncs_template_ael-non-history-grp;
    }
    container parity {
      uses ncs_template_ael-non-history-grp;
    }
    container generic {
      uses ncs_template_ael-non-history-grp;
    }
    container crc {
      uses ncs_template_ael-non-history-grp;
    }
    container reset {
      uses ncs_template_ael-non-history-grp;
    }
    container barrier {
      uses ncs_template_ael-non-history-grp;
    }
    container unexpected {
      uses ncs_template_ael-non-history-grp;
    }
    container link {
      uses ncs_template_ael-non-history-grp;
    }
    container oor-thresh {
      uses ncs_template_ael-non-history-grp;
    }
    container bp {
      uses ncs_template_ael-non-history-grp;
    }
    container io {
      uses ncs_template_ael-non-history-grp;
    }
    container ucode {
      uses ncs_template_ael-non-history-grp;
    }
    container config {
      uses ncs_template_ael-non-history-grp;
    }
    container indirect {
      uses ncs_template_ael-non-history-grp;
    }
    container nonerr {
      uses ncs_template_ael-non-history-grp;
    }
    container summary {
      uses ncs_template_ael-non-history-grp;
    }
    container all {
      uses ncs_template_ael-save-option-grp;
      uses ncs_template_ael-history-grp;
      uses ncs_template_ael-non-history-grp;
    }
  }

  grouping ncs_template_ael-all-error-types-wo-history-grp {
    container sbe {
      uses ncs_template_ael-non-history-grp;
    }
    container mbe {
      uses ncs_template_ael-non-history-grp;
    }
    container parity {
      uses ncs_template_ael-non-history-grp;
    }
    container generic {
      uses ncs_template_ael-non-history-grp;
    }
    container crc {
      uses ncs_template_ael-non-history-grp;
    }
    container reset {
      uses ncs_template_ael-non-history-grp;
    }
    container barrier {
      uses ncs_template_ael-non-history-grp;
    }
    container unexpected {
      uses ncs_template_ael-non-history-grp;
    }
    container link {
      uses ncs_template_ael-non-history-grp;
    }
    container oor-thresh {
      uses ncs_template_ael-non-history-grp;
    }
    container bp {
      uses ncs_template_ael-non-history-grp;
    }
    container io {
      uses ncs_template_ael-non-history-grp;
    }
    container ucode {
      uses ncs_template_ael-non-history-grp;
    }
    container config {
      uses ncs_template_ael-non-history-grp;
    }
    container indirect {
      uses ncs_template_ael-non-history-grp;
    }
    container nonerr {
      uses ncs_template_ael-non-history-grp;
    }
    container summary {
      uses ncs_template_ael-non-history-grp;
    }
    container all {
      uses ncs_template_ael-save-option-grp;
      uses ncs_template_ael-non-history-grp;
    }
  }

  grouping ncs_template_ael-all-error-types-ap-grp {
    container sbe {
      uses ncs_template_ael-non-history-ap-grp;
    }
    container mbe {
      uses ncs_template_ael-non-history-ap-grp;
    }
    container parity {
      uses ncs_template_ael-non-history-ap-grp;
    }
    container generic {
      uses ncs_template_ael-non-history-ap-grp;
    }
    container crc {
      uses ncs_template_ael-non-history-ap-grp;
    }
    container reset {
      uses ncs_template_ael-non-history-ap-grp;
    }
    container barrier {
      uses ncs_template_ael-non-history-ap-grp;
    }
    container unexpected {
      uses ncs_template_ael-non-history-ap-grp;
    }
    container link {
      uses ncs_template_ael-non-history-ap-grp;
    }
    container oor-thresh {
      uses ncs_template_ael-non-history-ap-grp;
    }
    container bp {
      uses ncs_template_ael-non-history-ap-grp;
    }
    container io {
      uses ncs_template_ael-non-history-ap-grp;
    }
    container ucode {
      uses ncs_template_ael-non-history-ap-grp;
    }
    container config {
      uses ncs_template_ael-non-history-ap-grp;
    }
    container indirect {
      uses ncs_template_ael-non-history-ap-grp;
    }
    container nonerr {
      uses ncs_template_ael-non-history-ap-grp;
    }
    container summary {
      uses ncs_template_ael-non-history-ap-grp;
    }
    container all {
      uses ncs_template_ael-save-option-grp;
      uses ncs_template_ael-history-ap-grp;
      uses ncs_template_ael-non-history-ap-grp;
    }
  }

  grouping ncs_template_ael-show-asic-errors-grp {
    // NCS drop config false list 'asic-errors'
  }

  grouping ncs_template_ael-clear-asic-errors-grp {
    container clear-asic-errors-grp {
      // NCS drop config false list 'clear-device'
    }
  }

  grouping ncs_rpc_notif_clear-asic-errors;

  grouping ncs_rpc_notif_ael-history-ap-grp {
    container history {
      list location {
        key "location-name";
        leaf location-name {
          type calvados:ncs_rpc_notif_location-id;
        }
        uses ncs_rpc_notif_clear-asic-errors;
      }
    }
  }

  grouping ncs_rpc_notif_ael-history-grp {
    container history {
      list location {
        key "location-name";
        leaf location-name {
          type calvados:ncs_rpc_notif_location-id;
        }
        list log-lst {
          leaf log-line {
            type string;
          }
        }
      }
    }
  }

  grouping ncs_rpc_notif_ael-non-history-grp {
    list location {
      key "location-name";
      leaf location-name {
        type calvados:ncs_rpc_notif_location-id;
      }
      list log-lst {
        leaf log-line {
          type string;
        }
      }
    }
  }

  grouping ncs_rpc_notif_ael-save-option-grp {
    container save-all-inst-asic-errors {
      uses ncs_rpc_notif_ael-non-history-grp;
    }
  }

  grouping ncs_rpc_notif_ael-non-history-ap-grp {
    list location {
      key "location-name";
      leaf location-name {
        type calvados:ncs_rpc_notif_location-id;
      }
      uses ncs_rpc_notif_clear-asic-errors;
    }
  }

  grouping ncs_rpc_notif_ael-all-error-types-grp {
    container sbe {
      uses ncs_rpc_notif_ael-non-history-grp;
    }
    container mbe {
      uses ncs_rpc_notif_ael-non-history-grp;
    }
    container parity {
      uses ncs_rpc_notif_ael-non-history-grp;
    }
    container generic {
      uses ncs_rpc_notif_ael-non-history-grp;
    }
    container crc {
      uses ncs_rpc_notif_ael-non-history-grp;
    }
    container reset {
      uses ncs_rpc_notif_ael-non-history-grp;
    }
    container barrier {
      uses ncs_rpc_notif_ael-non-history-grp;
    }
    container unexpected {
      uses ncs_rpc_notif_ael-non-history-grp;
    }
    container link {
      uses ncs_rpc_notif_ael-non-history-grp;
    }
    container oor-thresh {
      uses ncs_rpc_notif_ael-non-history-grp;
    }
    container bp {
      uses ncs_rpc_notif_ael-non-history-grp;
    }
    container io {
      uses ncs_rpc_notif_ael-non-history-grp;
    }
    container ucode {
      uses ncs_rpc_notif_ael-non-history-grp;
    }
    container config {
      uses ncs_rpc_notif_ael-non-history-grp;
    }
    container indirect {
      uses ncs_rpc_notif_ael-non-history-grp;
    }
    container nonerr {
      uses ncs_rpc_notif_ael-non-history-grp;
    }
    container summary {
      uses ncs_rpc_notif_ael-non-history-grp;
    }
    container all {
      uses ncs_rpc_notif_ael-save-option-grp;
      uses ncs_rpc_notif_ael-history-grp;
      uses ncs_rpc_notif_ael-non-history-grp;
    }
  }

  grouping ncs_rpc_notif_ael-all-error-types-wo-history-grp {
    container sbe {
      uses ncs_rpc_notif_ael-non-history-grp;
    }
    container mbe {
      uses ncs_rpc_notif_ael-non-history-grp;
    }
    container parity {
      uses ncs_rpc_notif_ael-non-history-grp;
    }
    container generic {
      uses ncs_rpc_notif_ael-non-history-grp;
    }
    container crc {
      uses ncs_rpc_notif_ael-non-history-grp;
    }
    container reset {
      uses ncs_rpc_notif_ael-non-history-grp;
    }
    container barrier {
      uses ncs_rpc_notif_ael-non-history-grp;
    }
    container unexpected {
      uses ncs_rpc_notif_ael-non-history-grp;
    }
    container link {
      uses ncs_rpc_notif_ael-non-history-grp;
    }
    container oor-thresh {
      uses ncs_rpc_notif_ael-non-history-grp;
    }
    container bp {
      uses ncs_rpc_notif_ael-non-history-grp;
    }
    container io {
      uses ncs_rpc_notif_ael-non-history-grp;
    }
    container ucode {
      uses ncs_rpc_notif_ael-non-history-grp;
    }
    container config {
      uses ncs_rpc_notif_ael-non-history-grp;
    }
    container indirect {
      uses ncs_rpc_notif_ael-non-history-grp;
    }
    container nonerr {
      uses ncs_rpc_notif_ael-non-history-grp;
    }
    container summary {
      uses ncs_rpc_notif_ael-non-history-grp;
    }
    container all {
      uses ncs_rpc_notif_ael-save-option-grp;
      uses ncs_rpc_notif_ael-non-history-grp;
    }
  }

  grouping ncs_rpc_notif_ael-all-error-types-ap-grp {
    container sbe {
      uses ncs_rpc_notif_ael-non-history-ap-grp;
    }
    container mbe {
      uses ncs_rpc_notif_ael-non-history-ap-grp;
    }
    container parity {
      uses ncs_rpc_notif_ael-non-history-ap-grp;
    }
    container generic {
      uses ncs_rpc_notif_ael-non-history-ap-grp;
    }
    container crc {
      uses ncs_rpc_notif_ael-non-history-ap-grp;
    }
    container reset {
      uses ncs_rpc_notif_ael-non-history-ap-grp;
    }
    container barrier {
      uses ncs_rpc_notif_ael-non-history-ap-grp;
    }
    container unexpected {
      uses ncs_rpc_notif_ael-non-history-ap-grp;
    }
    container link {
      uses ncs_rpc_notif_ael-non-history-ap-grp;
    }
    container oor-thresh {
      uses ncs_rpc_notif_ael-non-history-ap-grp;
    }
    container bp {
      uses ncs_rpc_notif_ael-non-history-ap-grp;
    }
    container io {
      uses ncs_rpc_notif_ael-non-history-ap-grp;
    }
    container ucode {
      uses ncs_rpc_notif_ael-non-history-ap-grp;
    }
    container config {
      uses ncs_rpc_notif_ael-non-history-ap-grp;
    }
    container indirect {
      uses ncs_rpc_notif_ael-non-history-ap-grp;
    }
    container nonerr {
      uses ncs_rpc_notif_ael-non-history-ap-grp;
    }
    container summary {
      uses ncs_rpc_notif_ael-non-history-ap-grp;
    }
    container all {
      uses ncs_rpc_notif_ael-save-option-grp;
      uses ncs_rpc_notif_ael-history-ap-grp;
      uses ncs_rpc_notif_ael-non-history-ap-grp;
    }
  }

  grouping ncs_rpc_notif_ael-show-asic-errors-grp {
    list asic-errors {
      key "device-name";
      config false;
      leaf device-name {
        type string;
      }
      list instance {
        key "instance-num";
        leaf instance-num {
          type uint32;
        }
        uses ncs_rpc_notif_ael-all-error-types-grp;
      }
      container show-all-instances {
        uses ncs_rpc_notif_ael-all-error-types-wo-history-grp;
      }
    }
  }

  grouping ncs_rpc_notif_ael-clear-asic-errors-grp {
    container clear-asic-errors-grp {
      list clear-device {
        key "device-name";
        config false;
        leaf device-name {
          type string;
        }
        list instance {
          key "instance-num";
          leaf instance-num {
            type uint32;
          }
          uses ncs_rpc_notif_ael-all-error-types-ap-grp;
        }
        container all-instances {
          uses ncs_rpc_notif_ael-all-error-types-ap-grp;
        }
      }
    }
  }

  grouping live_ncs_clear-asic-errors;

  grouping live_ncs_ael-history-ap-grp {
    container history {
      list location {
        key "location-name";
        leaf location-name {
          type calvados:live_ncs_location-id;
        }
        uses live_ncs_clear-asic-errors;
      }
    }
  }

  grouping live_ncs_ael-history-grp {
    container history {
      list location {
        key "location-name";
        leaf location-name {
          type calvados:live_ncs_location-id;
        }
        list log-lst {
          leaf log-line {
            type string;
          }
        }
      }
    }
  }

  grouping live_ncs_ael-non-history-grp {
    list location {
      key "location-name";
      leaf location-name {
        type calvados:live_ncs_location-id;
      }
      list log-lst {
        leaf log-line {
          type string;
        }
      }
    }
  }

  grouping live_ncs_ael-save-option-grp {
    container save-all-inst-asic-errors {
      uses live_ncs_ael-non-history-grp;
    }
  }

  grouping live_ncs_ael-non-history-ap-grp {
    list location {
      key "location-name";
      leaf location-name {
        type calvados:live_ncs_location-id;
      }
      uses live_ncs_clear-asic-errors;
    }
  }

  grouping live_ncs_ael-all-error-types-grp {
    container sbe {
      uses live_ncs_ael-non-history-grp;
    }
    container mbe {
      uses live_ncs_ael-non-history-grp;
    }
    container parity {
      uses live_ncs_ael-non-history-grp;
    }
    container generic {
      uses live_ncs_ael-non-history-grp;
    }
    container crc {
      uses live_ncs_ael-non-history-grp;
    }
    container reset {
      uses live_ncs_ael-non-history-grp;
    }
    container barrier {
      uses live_ncs_ael-non-history-grp;
    }
    container unexpected {
      uses live_ncs_ael-non-history-grp;
    }
    container link {
      uses live_ncs_ael-non-history-grp;
    }
    container oor-thresh {
      uses live_ncs_ael-non-history-grp;
    }
    container bp {
      uses live_ncs_ael-non-history-grp;
    }
    container io {
      uses live_ncs_ael-non-history-grp;
    }
    container ucode {
      uses live_ncs_ael-non-history-grp;
    }
    container config {
      uses live_ncs_ael-non-history-grp;
    }
    container indirect {
      uses live_ncs_ael-non-history-grp;
    }
    container nonerr {
      uses live_ncs_ael-non-history-grp;
    }
    container summary {
      uses live_ncs_ael-non-history-grp;
    }
    container all {
      uses live_ncs_ael-save-option-grp;
      uses live_ncs_ael-history-grp;
      uses live_ncs_ael-non-history-grp;
    }
  }

  grouping live_ncs_ael-all-error-types-wo-history-grp {
    container sbe {
      uses live_ncs_ael-non-history-grp;
    }
    container mbe {
      uses live_ncs_ael-non-history-grp;
    }
    container parity {
      uses live_ncs_ael-non-history-grp;
    }
    container generic {
      uses live_ncs_ael-non-history-grp;
    }
    container crc {
      uses live_ncs_ael-non-history-grp;
    }
    container reset {
      uses live_ncs_ael-non-history-grp;
    }
    container barrier {
      uses live_ncs_ael-non-history-grp;
    }
    container unexpected {
      uses live_ncs_ael-non-history-grp;
    }
    container link {
      uses live_ncs_ael-non-history-grp;
    }
    container oor-thresh {
      uses live_ncs_ael-non-history-grp;
    }
    container bp {
      uses live_ncs_ael-non-history-grp;
    }
    container io {
      uses live_ncs_ael-non-history-grp;
    }
    container ucode {
      uses live_ncs_ael-non-history-grp;
    }
    container config {
      uses live_ncs_ael-non-history-grp;
    }
    container indirect {
      uses live_ncs_ael-non-history-grp;
    }
    container nonerr {
      uses live_ncs_ael-non-history-grp;
    }
    container summary {
      uses live_ncs_ael-non-history-grp;
    }
    container all {
      uses live_ncs_ael-save-option-grp;
      uses live_ncs_ael-non-history-grp;
    }
  }

  grouping live_ncs_ael-all-error-types-ap-grp {
    container sbe {
      uses live_ncs_ael-non-history-ap-grp;
    }
    container mbe {
      uses live_ncs_ael-non-history-ap-grp;
    }
    container parity {
      uses live_ncs_ael-non-history-ap-grp;
    }
    container generic {
      uses live_ncs_ael-non-history-ap-grp;
    }
    container crc {
      uses live_ncs_ael-non-history-ap-grp;
    }
    container reset {
      uses live_ncs_ael-non-history-ap-grp;
    }
    container barrier {
      uses live_ncs_ael-non-history-ap-grp;
    }
    container unexpected {
      uses live_ncs_ael-non-history-ap-grp;
    }
    container link {
      uses live_ncs_ael-non-history-ap-grp;
    }
    container oor-thresh {
      uses live_ncs_ael-non-history-ap-grp;
    }
    container bp {
      uses live_ncs_ael-non-history-ap-grp;
    }
    container io {
      uses live_ncs_ael-non-history-ap-grp;
    }
    container ucode {
      uses live_ncs_ael-non-history-ap-grp;
    }
    container config {
      uses live_ncs_ael-non-history-ap-grp;
    }
    container indirect {
      uses live_ncs_ael-non-history-ap-grp;
    }
    container nonerr {
      uses live_ncs_ael-non-history-ap-grp;
    }
    container summary {
      uses live_ncs_ael-non-history-ap-grp;
    }
    container all {
      uses live_ncs_ael-save-option-grp;
      uses live_ncs_ael-history-ap-grp;
      uses live_ncs_ael-non-history-ap-grp;
    }
  }

  grouping live_ncs_ael-show-asic-errors-grp {
    list asic-errors {
      key "device-name";
      leaf device-name {
        type string;
      }
      list instance {
        key "instance-num";
        leaf instance-num {
          type uint32;
        }
        uses live_ncs_ael-all-error-types-grp;
      }
      container show-all-instances {
        uses live_ncs_ael-all-error-types-wo-history-grp;
      }
    }
  }

  grouping live_ncs_ael-clear-asic-errors-grp {
    container clear-asic-errors-grp {
      list clear-device {
        key "device-name";
        leaf device-name {
          type string;
        }
        list instance {
          key "instance-num";
          leaf instance-num {
            type uint32;
          }
          uses live_ncs_ael-all-error-types-ap-grp;
        }
        container all-instances {
          uses live_ncs_ael-all-error-types-ap-grp;
        }
      }
    }
  }

  grouping clear-asic-errors;

  grouping ael-history-ap-grp {
    container history {
      list location {
        key "location-name";
        leaf location-name {
          type calvados:location-id;
        }
        uses clear-asic-errors;
      }
    }
  }

  grouping ael-history-grp {
    container history {
      list location {
        key "location-name";
        leaf location-name {
          type calvados:location-id;
        }
        list log-lst {
          leaf log-line {
            type string;
          }
        }
      }
    }
  }

  grouping ael-non-history-grp {
    list location {
      key "location-name";
      leaf location-name {
        type calvados:location-id;
      }
      list log-lst {
        leaf log-line {
          type string;
        }
      }
    }
  }

  grouping ael-save-option-grp {
    container save-all-inst-asic-errors {
      uses ael-non-history-grp;
    }
  }

  grouping ael-non-history-ap-grp {
    list location {
      key "location-name";
      leaf location-name {
        type calvados:location-id;
      }
      uses clear-asic-errors;
    }
  }

  grouping ael-all-error-types-grp {
    container sbe {
      uses ael-non-history-grp;
    }
    container mbe {
      uses ael-non-history-grp;
    }
    container parity {
      uses ael-non-history-grp;
    }
    container generic {
      uses ael-non-history-grp;
    }
    container crc {
      uses ael-non-history-grp;
    }
    container reset {
      uses ael-non-history-grp;
    }
    container barrier {
      uses ael-non-history-grp;
    }
    container unexpected {
      uses ael-non-history-grp;
    }
    container link {
      uses ael-non-history-grp;
    }
    container oor-thresh {
      uses ael-non-history-grp;
    }
    container bp {
      uses ael-non-history-grp;
    }
    container io {
      uses ael-non-history-grp;
    }
    container ucode {
      uses ael-non-history-grp;
    }
    container config {
      uses ael-non-history-grp;
    }
    container indirect {
      uses ael-non-history-grp;
    }
    container nonerr {
      uses ael-non-history-grp;
    }
    container summary {
      uses ael-non-history-grp;
    }
    container all {
      uses ael-save-option-grp;
      uses ael-history-grp;
      uses ael-non-history-grp;
    }
  }

  grouping ael-all-error-types-wo-history-grp {
    container sbe {
      uses ael-non-history-grp;
    }
    container mbe {
      uses ael-non-history-grp;
    }
    container parity {
      uses ael-non-history-grp;
    }
    container generic {
      uses ael-non-history-grp;
    }
    container crc {
      uses ael-non-history-grp;
    }
    container reset {
      uses ael-non-history-grp;
    }
    container barrier {
      uses ael-non-history-grp;
    }
    container unexpected {
      uses ael-non-history-grp;
    }
    container link {
      uses ael-non-history-grp;
    }
    container oor-thresh {
      uses ael-non-history-grp;
    }
    container bp {
      uses ael-non-history-grp;
    }
    container io {
      uses ael-non-history-grp;
    }
    container ucode {
      uses ael-non-history-grp;
    }
    container config {
      uses ael-non-history-grp;
    }
    container indirect {
      uses ael-non-history-grp;
    }
    container nonerr {
      uses ael-non-history-grp;
    }
    container summary {
      uses ael-non-history-grp;
    }
    container all {
      uses ael-save-option-grp;
      uses ael-non-history-grp;
    }
  }

  grouping ael-all-error-types-ap-grp {
    container sbe {
      uses ael-non-history-ap-grp;
    }
    container mbe {
      uses ael-non-history-ap-grp;
    }
    container parity {
      uses ael-non-history-ap-grp;
    }
    container generic {
      uses ael-non-history-ap-grp;
    }
    container crc {
      uses ael-non-history-ap-grp;
    }
    container reset {
      uses ael-non-history-ap-grp;
    }
    container barrier {
      uses ael-non-history-ap-grp;
    }
    container unexpected {
      uses ael-non-history-ap-grp;
    }
    container link {
      uses ael-non-history-ap-grp;
    }
    container oor-thresh {
      uses ael-non-history-ap-grp;
    }
    container bp {
      uses ael-non-history-ap-grp;
    }
    container io {
      uses ael-non-history-ap-grp;
    }
    container ucode {
      uses ael-non-history-ap-grp;
    }
    container config {
      uses ael-non-history-ap-grp;
    }
    container indirect {
      uses ael-non-history-ap-grp;
    }
    container nonerr {
      uses ael-non-history-ap-grp;
    }
    container summary {
      uses ael-non-history-ap-grp;
    }
    container all {
      uses ael-save-option-grp;
      uses ael-history-ap-grp;
      uses ael-non-history-ap-grp;
    }
  }

  grouping ael-show-asic-errors-grp {
    // NCS drop config false list 'asic-errors'
  }

  grouping ael-clear-asic-errors-grp {
    container clear-asic-errors-grp {
      // NCS drop config false list 'clear-device'
    }
  }

  augment "/ncs:devices/ncs:device/ncs:config" {
    uses ael-show-asic-errors-grp;
  }
  augment "/ncs:devices/ncs:device/ncs:live-status" {
    uses live_ncs_ael-show-asic-errors-grp {
      refine asic-errors {
        tailf:ncs-device-type "netconf";
        tailf:display-when "not(../ncs:module) or ../ncs:module[ncs:name='Cisco-IOS-XR-sysadmin-asic-errors-ael'] or (../ncs:live-status-protocol[not(ncs:capability)]) or (../ncs:live-status-protocol/ncs:capability/ncs:module[.='Cisco-IOS-XR-sysadmin-asic-errors-ael'])";
      }
    }
  }
  augment "/ncs:devices/ncs:template/ncs:ned-id/ncs:config" {
    uses ncs_template_ael-show-asic-errors-grp;
  }
}

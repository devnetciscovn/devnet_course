module Cisco-IOS-XR-sysadmin-card-mgr {
  // Generated by yanger -t ncs
  tailf:mount-id "cisco-iosxr-nc-7.3:cisco-iosxr-nc-7.3";
  tailf:ncs-device-type "netconf";

  namespace "http://www.cisco.com/ns/yang/Cisco-IOS-XR-sysadmin-card-mgr";
  prefix card_mgr;

  import Cisco-IOS-XR-sysadmin-show-trace {
    prefix show_trace;
  }
  import Cisco-IOS-XR-sysadmin-types {
    prefix calvados;
  }
  import cisco-semver {
    prefix semver;
  }
  import tailf-common {
    prefix tailf;
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "The 'card_mgr' module provides support for access to detail card HW information like power status, card state, inventory info, etc.

     Copyright (c) 2012-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2015-03-29 {
    description
      "Initial revision.";
  }

  typedef ncs_template_startHexOffset {
    type string;
    description
      "Start address in Hex between 0x0 and 0x400";
  }

  typedef ncs_template_endHexOffset {
    type string;
    description
      "End address in Hex between 0x0 and 0x400";
  }

  typedef ncs_template_HexOffset {
    type string;
    description
      "Address in Hex between 0x0 and 0x400";
  }

  typedef ncs_rpc_notif_startHexOffset {
    type string;
    description
      "Start address in Hex between 0x0 and 0x400";
  }

  typedef ncs_rpc_notif_endHexOffset {
    type string;
    description
      "End address in Hex between 0x0 and 0x400";
  }

  typedef ncs_rpc_notif_HexOffset {
    type string;
    description
      "Address in Hex between 0x0 and 0x400";
  }

  typedef live_ncs_startHexOffset {
    type string;
    description
      "Start address in Hex between 0x0 and 0x400";
  }

  typedef live_ncs_endHexOffset {
    type string;
    description
      "End address in Hex between 0x0 and 0x400";
  }

  typedef live_ncs_HexOffset {
    type string;
    description
      "Address in Hex between 0x0 and 0x400";
  }

  typedef startHexOffset {
    type string;
    description
      "Start address in Hex between 0x0 and 0x400";
  }

  typedef endHexOffset {
    type string;
    description
      "End address in Hex between 0x0 and 0x400";
  }

  typedef HexOffset {
    type string;
    description
      "Address in Hex between 0x0 and 0x400";
  }

  grouping ncs_template_card_mgr-group {
    description
      "Card Manager module information";
    container card_mgr {
      description
        "Card Manager module information";
      uses show_trace:ncs_template_traceable;
      uses ncs_template_inventory-group;
      uses ncs_template_event-hist-group;
      uses ncs_template_notif-hist-group;
      uses ncs_template_oir-hist-group;
      uses ncs_template_iofpga-group;
      uses ncs_template_bootldr-group;
    }
  }

  grouping ncs_template_inventory-group {
    description
      "Card inventory Group";
    // NCS drop config false container inventory
  }

  grouping ncs_template_inventory-summary-group {
    description
      "Card Inventory Summary Group";
    // NCS drop config false container summary
  }

  grouping ncs_template_inventory-detail-group {
    description
      "Card Manager Inventory Detail Group";
    // NCS drop config false container detail
  }

  grouping ncs_template_event-hist-group {
    description
      "Card Event History Group";
    // NCS drop config false container 'event-history'
  }

  grouping ncs_template_event-hist-group-brief {
    description
      "Card Event History Group Brief";
    list location {
      // NCS patched for predictable order
      ordered-by user;
      key "location";
      description
        "Select Location";
      leaf location {
        type string;
        description
          "Location";
      }
      container card_event_hist_brief {
        description
          "Card Event History Brief";
        leaf-list card_event_hist_brief_values {
          // NCS patched for predictable order
          ordered-by user;
          type string;
          description
            "Card Event History Brief Values";
        }
      }
    }
  }

  grouping ncs_template_event-hist-group-detail {
    description
      "Card Event History Group Detail";
    list location {
      // NCS patched for predictable order
      ordered-by user;
      key "location";
      description
        "Select Location";
      leaf location {
        type string;
        description
          "Location";
      }
      container card_event_hist_detail {
        description
          "Card Event History Detail";
        leaf-list card_event_hist_detail_values {
          // NCS patched for predictable order
          ordered-by user;
          type string;
          description
            "Card Event History Detail Values";
        }
      }
    }
  }

  grouping ncs_template_notif-hist-group {
    description
      "Card State Notification History Group";
    // NCS drop config false container 'notif-history'
  }

  grouping ncs_template_notif-hist-group-brief {
    description
      "Notify Histroy Group Brief";
    list location {
      // NCS patched for predictable order
      ordered-by user;
      key "location";
      description
        "Select Location";
      leaf location {
        type string;
        description
          "Location";
      }
      container card_notif_hist_brief {
        description
          "Notify Histroy Brief";
        leaf-list card_notif_hist_brief_values {
          // NCS patched for predictable order
          ordered-by user;
          type string;
          description
            "Notify Histroy Brief Values";
        }
      }
    }
  }

  grouping ncs_template_notif-hist-group-detail {
    description
      "Notify Histroy Group Detail";
    list location {
      // NCS patched for predictable order
      ordered-by user;
      key "location";
      description
        "Select Location";
      leaf location {
        type string;
        description
          "Location";
      }
      container card_notif_hist_detail {
        description
          "Notify Histroy Detail";
        leaf-list card_notif_hist_detail_values {
          // NCS patched for predictable order
          ordered-by user;
          type string;
          description
            "Notify Histroy Detail Values";
        }
      }
    }
  }

  grouping ncs_template_oir-hist-group {
    description
      "Cards OIR History Group";
    // NCS drop config false container 'oir-history'
  }

  grouping ncs_template_iofpga-group {
    description
      "IOFPGA Information Group";
    // NCS drop config false container iofpga
  }

  grouping ncs_template_iofpga-register-group {
    description
      "IOFPGA Register Information Group";
    // NCS drop config false container register
  }

  grouping ncs_template_cpu-register-group {
    description
      "CPU-IOFPGA Register Information Group";
    // NCS drop config false container cpu
  }

  grouping ncs_template_mb-register-group {
    description
      "Mother Board(MB)-IOFPGA Register Information Group";
    // NCS drop config false container mb
  }

  grouping ncs_template_dc-register-group {
    description
      "Daughter Card(DC)-IOFPGA Register Information Group";
    // NCS drop config false container dc
  }

  grouping ncs_template_iofpga-block-number-group {
    description
      "IOFPGA Block Number Group";
    // NCS drop config false list iofpga_block_number
  }

  grouping ncs_template_iofpga-offset-group {
    description
      "IOFPGA Offset Group";
    // NCS drop config false list iofpga_offset
  }

  grouping ncs_template_iofpga-address-group {
    description
      "IOFPGA Address Group";
    // NCS drop config false list iofpga_address
  }

  grouping ncs_template_iofpga-flash-group {
    description
      "IOFPGA SPI Flash Group";
    // NCS drop config false container flash
  }

  grouping ncs_template_iofpga-flash-info-group {
    description
      "IOFPGA SPI Flash Information Group";
    // NCS drop config false container info
  }

  grouping ncs_template_iofpga-flash-status-group {
    description
      "IOFPGA SPI Flash Status Group";
    // NCS drop config false container status
  }

  grouping ncs_template_bootldr-group {
    description
      "Bootloader Group";
    // NCS drop config false container bootloader
  }

  grouping ncs_template_bootldr-flash-group {
    description
      "Bootloader SPI Flash Group";
    // NCS drop config false container flash
  }

  grouping ncs_template_bootldr-flash-info-group {
    description
      "Bootloader SPI Flash Information Group";
    // NCS drop config false container info
  }

  grouping ncs_template_bootldr-flash-status-group {
    description
      "Bootloader SPI Flash Group";
    // NCS drop config false container status
  }

  grouping ncs_rpc_notif_card_mgr-group {
    description
      "Card Manager module information";
    container card_mgr {
      description
        "Card Manager module information";
      uses show_trace:ncs_rpc_notif_traceable;
      uses ncs_rpc_notif_inventory-group;
      uses ncs_rpc_notif_event-hist-group;
      uses ncs_rpc_notif_notif-hist-group;
      uses ncs_rpc_notif_oir-hist-group;
      uses ncs_rpc_notif_iofpga-group;
      uses ncs_rpc_notif_bootldr-group;
    }
  }

  grouping ncs_rpc_notif_inventory-group {
    description
      "Card inventory Group";
    container inventory {
      config false;
      description
        "Card inventory information";
      uses ncs_rpc_notif_inventory-summary-group;
      uses ncs_rpc_notif_inventory-detail-group;
    }
  }

  grouping ncs_rpc_notif_inventory-summary-group {
    description
      "Card Inventory Summary Group";
    container summary {
      config false;
      description
        "Card inventory summary";
      list card_mgr_inv_summary {
        key "location";
        description
          "Card Manager Inventory Summary";
        leaf location {
          type string;
          mandatory true;
          description
            "Card location";
        }
        leaf card_mgr_inv_PID_string {
          type string;
          description
            "Card inventory PID";
        }
        leaf card_mgr_inv_slot_number {
          type uint32;
          description
            "Card inventory BP ID";
        }
        leaf card_mgr_inv_serial_number {
          type string;
          description
            "Card inventory Serial Number";
        }
        leaf card_mgr_inv_hw_version {
          type string;
          description
            "Card inventory HW Ver";
        }
        leaf card_mgr_inv_card_state {
          type string;
          description
            "Card inventory Card State";
        }
      }
    }
  }

  grouping ncs_rpc_notif_inventory-detail-group {
    description
      "Card Manager Inventory Detail Group";
    container detail {
      config false;
      description
        "Card Manager inventory detail information";
      list card_mgr_inv_detail {
        key "location";
        description
          "Card location";
        leaf location {
          type string;
          description
            "Card location";
        }
        container card_mgr_inv_detail_list {
          description
            "card_mgr inventory detail list";
          leaf-list card_mgr_inv_detail_values {
            type string;
            description
              "card_mgr inventory detail value";
          }
        }
      }
    }
  }

  grouping ncs_rpc_notif_event-hist-group {
    description
      "Card Event History Group";
    container event-history {
      config false;
      description
        "Card Event History";
      container brief {
        config false;
        description
          "Show all events in brief format";
        uses ncs_rpc_notif_event-hist-group-brief;
      }
      container detail {
        config false;
        description
          "Show all events with additional detail information";
        uses ncs_rpc_notif_event-hist-group-detail;
      }
    }
  }

  grouping ncs_rpc_notif_event-hist-group-brief {
    description
      "Card Event History Group Brief";
    list location {
      key "location";
      description
        "Select Location";
      leaf location {
        type string;
        description
          "Location";
      }
      container card_event_hist_brief {
        description
          "Card Event History Brief";
        leaf-list card_event_hist_brief_values {
          type string;
          description
            "Card Event History Brief Values";
        }
      }
    }
  }

  grouping ncs_rpc_notif_event-hist-group-detail {
    description
      "Card Event History Group Detail";
    list location {
      key "location";
      description
        "Select Location";
      leaf location {
        type string;
        description
          "Location";
      }
      container card_event_hist_detail {
        description
          "Card Event History Detail";
        leaf-list card_event_hist_detail_values {
          type string;
          description
            "Card Event History Detail Values";
        }
      }
    }
  }

  grouping ncs_rpc_notif_notif-hist-group {
    description
      "Card State Notification History Group";
    container notif-history {
      config false;
      description
        "Card State Notification History";
      container brief {
        config false;
        description
          "Show all state notifications in brief format";
        uses ncs_rpc_notif_notif-hist-group-brief;
      }
      container detail {
        config false;
        description
          "Show all state notifications with additional detail information";
        uses ncs_rpc_notif_notif-hist-group-detail;
      }
    }
  }

  grouping ncs_rpc_notif_notif-hist-group-brief {
    description
      "Notify Histroy Group Brief";
    list location {
      key "location";
      description
        "Select Location";
      leaf location {
        type string;
        description
          "Location";
      }
      container card_notif_hist_brief {
        description
          "Notify Histroy Brief";
        leaf-list card_notif_hist_brief_values {
          type string;
          description
            "Notify Histroy Brief Values";
        }
      }
    }
  }

  grouping ncs_rpc_notif_notif-hist-group-detail {
    description
      "Notify Histroy Group Detail";
    list location {
      key "location";
      description
        "Select Location";
      leaf location {
        type string;
        description
          "Location";
      }
      container card_notif_hist_detail {
        description
          "Notify Histroy Detail";
        leaf-list card_notif_hist_detail_values {
          type string;
          description
            "Notify Histroy Detail Values";
        }
      }
    }
  }

  grouping ncs_rpc_notif_oir-hist-group {
    description
      "Cards OIR History Group";
    container oir-history {
      config false;
      description
        "Cards OIR History";
      list rack {
        key "rack";
        description
          "Select Rack";
        leaf rack {
          type string;
          description
            "Rack";
        }
        container card_oir_hist {
          description
            "Cards OIR History";
          leaf-list card_oir_events {
            type string;
            description
              "Cards OIR Events";
          }
        }
      }
    }
  }

  grouping ncs_rpc_notif_iofpga-group {
    description
      "IOFPGA Information Group";
    container iofpga {
      config false;
      description
        "IOFPGA information";
      uses ncs_rpc_notif_iofpga-register-group;
      uses ncs_rpc_notif_iofpga-flash-group;
    }
  }

  grouping ncs_rpc_notif_iofpga-register-group {
    description
      "IOFPGA Register Information Group";
    container register {
      config false;
      description
        "IOFPGA Register information";
      uses ncs_rpc_notif_cpu-register-group;
      uses ncs_rpc_notif_mb-register-group;
      uses ncs_rpc_notif_dc-register-group;
    }
  }

  grouping ncs_rpc_notif_cpu-register-group {
    description
      "CPU-IOFPGA Register Information Group";
    container cpu {
      config false;
      description
        "CPU-IOFPGA Register information";
      list register_location {
        key "register_location";
        config false;
        description
          "Card location";
        leaf register_location {
          type string;
          description
            "Location";
        }
        uses ncs_rpc_notif_iofpga-block-number-group;
        uses ncs_rpc_notif_iofpga-offset-group;
        uses ncs_rpc_notif_iofpga-address-group;
      }
    }
  }

  grouping ncs_rpc_notif_mb-register-group {
    description
      "Mother Board(MB)-IOFPGA Register Information Group";
    container mb {
      config false;
      description
        "Mother Board(MB)-IOFPGA Register information";
      list register_location {
        key "register_location";
        config false;
        description
          "Card location";
        leaf register_location {
          type string;
          description
            "Location";
        }
        uses ncs_rpc_notif_iofpga-block-number-group;
        uses ncs_rpc_notif_iofpga-offset-group;
        uses ncs_rpc_notif_iofpga-address-group;
      }
    }
  }

  grouping ncs_rpc_notif_dc-register-group {
    description
      "Daughter Card(DC)-IOFPGA Register Information Group";
    container dc {
      config false;
      description
        "Daughter Card(DC)-IOFPGA Register information";
      list register_location {
        key "register_location";
        config false;
        description
          "Card location";
        leaf register_location {
          type string;
          description
            "Location";
        }
        uses ncs_rpc_notif_iofpga-block-number-group;
        uses ncs_rpc_notif_iofpga-offset-group;
        uses ncs_rpc_notif_iofpga-address-group;
      }
    }
  }

  grouping ncs_rpc_notif_iofpga-block-number-group {
    description
      "IOFPGA Block Number Group";
    list iofpga_block_number {
      key "iofpga_block_num";
      config false;
      description
        "Register Group ID";
      leaf iofpga_block_num {
        type uint32;
        description
          "GP";
      }
      leaf block_location {
        type string;
        description
          "Location";
      }
      leaf iofpga_block_nm {
        type string;
        description
          "Block NM";
      }
      list iofpga_register_number {
        key "index";
        description
          "Register Number";
        leaf index {
          type uint32;
          description
            "Register IDX";
        }
        leaf iofpga_register_name {
          type string;
          description
            "Register Name";
        }
        list iofpga_data {
          description
            "IOFPGA DATA";
          leaf name {
            type string;
            description
              "Register Name";
          }
          leaf offset {
            type uint32;
            description
              "Register Offset";
          }
          leaf value {
            type uint32;
            description
              "Register Value";
          }
        }
      }
    }
  }

  grouping ncs_rpc_notif_iofpga-offset-group {
    description
      "IOFPGA Offset Group";
    list iofpga_offset {
      key "hex_offset";
      config false;
      description
        "Register Offset Address";
      leaf hex_offset {
        type ncs_rpc_notif_HexOffset;
        description
          "Register Hex Offset";
      }
      list iofpga_reg_offset_data {
        description
          "Register Offset Data";
        leaf iofpga_reg_off_addr {
          type uint32;
          description
            "Register Offset Address";
        }
        leaf reg_off_value {
          type string;
          description
            "Register Offset Value";
        }
      }
    }
  }

  grouping ncs_rpc_notif_iofpga-address-group {
    description
      "IOFPGA Address Group";
    list iofpga_address {
      key "start_hex_addr end_hex_addr";
      config false;
      description
        "Register Range to fetch data";
      leaf start_hex_addr {
        type ncs_rpc_notif_startHexOffset;
        description
          "Register Start Hex Address";
      }
      leaf end_hex_addr {
        type ncs_rpc_notif_endHexOffset;
        description
          "Register End Hex Address";
      }
      list iofpga_reg_range_addr_list {
        key "iofpga_reg_range_addr";
        description
          "Register Range Hex Address";
        leaf iofpga_reg_range_addr {
          type uint32;
          description
            "Register Offset";
        }
        list iofpga_reg_data {
          description
            "Register Data";
          leaf iofpga_reg_addr {
            type uint32;
            description
              "Register Address";
          }
          leaf reg_value {
            type string;
            description
              "Register Value";
          }
        }
      }
    }
  }

  grouping ncs_rpc_notif_iofpga-flash-group {
    description
      "IOFPGA SPI Flash Group";
    container flash {
      config false;
      description
        "IOFPGA SPI flash information";
      uses ncs_rpc_notif_iofpga-flash-info-group;
      uses ncs_rpc_notif_iofpga-flash-status-group;
    }
  }

  grouping ncs_rpc_notif_iofpga-flash-info-group {
    description
      "IOFPGA SPI Flash Information Group";
    container info {
      config false;
      description
        "IOFPGA SPI flash content";
      list flash_location {
        key "flash_location";
        description
          "Select Location";
        leaf flash_location {
          type calvados:ncs_rpc_notif_location-id;
          description
            "IOFPGA Flash Location";
        }
        container iofpga_flash_info {
          description
            "IOFPGA Flash Information";
          leaf-list iofpga_flash_info_values {
            type string;
            description
              "IOFPGA Flash Information Values";
          }
        }
      }
    }
  }

  grouping ncs_rpc_notif_iofpga-flash-status-group {
    description
      "IOFPGA SPI Flash Status Group";
    container status {
      config false;
      description
        "IOFPGA SPI flash status";
      list flash_location {
        key "flash_location";
        description
          "IOFPGA Flash Location";
        leaf flash_location {
          type calvados:ncs_rpc_notif_location-id;
          description
            "IOFPGA Flash Location ID";
        }
        container iofpga_flash_status {
          description
            "IOFPGA Flash Status";
          leaf-list iofpga_flash_status_values {
            type string;
            description
              "IOFPGA Flash Status Values";
          }
        }
      }
    }
  }

  grouping ncs_rpc_notif_bootldr-group {
    description
      "Bootloader Group";
    container bootloader {
      config false;
      description
        "Bootloader information";
      uses ncs_rpc_notif_bootldr-flash-group;
    }
  }

  grouping ncs_rpc_notif_bootldr-flash-group {
    description
      "Bootloader SPI Flash Group";
    container flash {
      config false;
      description
        "Bootloader SPI flash information";
      uses ncs_rpc_notif_bootldr-flash-info-group;
      uses ncs_rpc_notif_bootldr-flash-status-group;
    }
  }

  grouping ncs_rpc_notif_bootldr-flash-info-group {
    description
      "Bootloader SPI Flash Information Group";
    container info {
      config false;
      description
        "Bootloader SPI flash content";
      list flash_location {
        key "flash_location";
        description
          "Select Location";
        leaf flash_location {
          type calvados:ncs_rpc_notif_location-id;
          description
            "Location ID";
        }
        container bootldr_flash_info {
          description
            "Bootloader Flash Information";
          leaf-list bootldr_flash_info_values {
            type string;
            description
              "Bootloader Flash Information Values";
          }
        }
      }
    }
  }

  grouping ncs_rpc_notif_bootldr-flash-status-group {
    description
      "Bootloader SPI Flash Group";
    container status {
      config false;
      description
        "Bootloader SPI flash status";
      list flash_location {
        key "flash_location";
        description
          "Select Location";
        leaf flash_location {
          type calvados:ncs_rpc_notif_location-id;
          description
            "Location ID";
        }
        container bootldr_flash_status {
          description
            "Bootloader flash status";
          leaf-list bootldr_flash_status_values {
            type string;
            description
              "Bootloader Flash Status Values";
          }
        }
      }
    }
  }

  grouping live_ncs_card_mgr-group {
    description
      "Card Manager module information";
    container card_mgr {
      description
        "Card Manager module information";
      uses show_trace:live_ncs_traceable;
      uses live_ncs_inventory-group;
      uses live_ncs_event-hist-group;
      uses live_ncs_notif-hist-group;
      uses live_ncs_oir-hist-group;
      uses live_ncs_iofpga-group;
      uses live_ncs_bootldr-group;
    }
  }

  grouping live_ncs_inventory-group {
    description
      "Card inventory Group";
    container inventory {
      description
        "Card inventory information";
      uses live_ncs_inventory-summary-group;
      uses live_ncs_inventory-detail-group;
    }
  }

  grouping live_ncs_inventory-summary-group {
    description
      "Card Inventory Summary Group";
    container summary {
      description
        "Card inventory summary";
      list card_mgr_inv_summary {
        key "location";
        description
          "Card Manager Inventory Summary";
        leaf location {
          type string;
          // NCS drop mandatory statement
          description
            "Card location";
        }
        leaf card_mgr_inv_PID_string {
          type string;
          description
            "Card inventory PID";
        }
        leaf card_mgr_inv_slot_number {
          type uint32;
          description
            "Card inventory BP ID";
        }
        leaf card_mgr_inv_serial_number {
          type string;
          description
            "Card inventory Serial Number";
        }
        leaf card_mgr_inv_hw_version {
          type string;
          description
            "Card inventory HW Ver";
        }
        leaf card_mgr_inv_card_state {
          type string;
          description
            "Card inventory Card State";
        }
      }
    }
  }

  grouping live_ncs_inventory-detail-group {
    description
      "Card Manager Inventory Detail Group";
    container detail {
      description
        "Card Manager inventory detail information";
      list card_mgr_inv_detail {
        key "location";
        description
          "Card location";
        leaf location {
          type string;
          description
            "Card location";
        }
        container card_mgr_inv_detail_list {
          description
            "card_mgr inventory detail list";
          leaf-list card_mgr_inv_detail_values {
            type string;
            description
              "card_mgr inventory detail value";
          }
        }
      }
    }
  }

  grouping live_ncs_event-hist-group {
    description
      "Card Event History Group";
    container event-history {
      description
        "Card Event History";
      container brief {
        description
          "Show all events in brief format";
        uses live_ncs_event-hist-group-brief;
      }
      container detail {
        description
          "Show all events with additional detail information";
        uses live_ncs_event-hist-group-detail;
      }
    }
  }

  grouping live_ncs_event-hist-group-brief {
    description
      "Card Event History Group Brief";
    list location {
      key "location";
      description
        "Select Location";
      leaf location {
        type string;
        description
          "Location";
      }
      container card_event_hist_brief {
        description
          "Card Event History Brief";
        leaf-list card_event_hist_brief_values {
          type string;
          description
            "Card Event History Brief Values";
        }
      }
    }
  }

  grouping live_ncs_event-hist-group-detail {
    description
      "Card Event History Group Detail";
    list location {
      key "location";
      description
        "Select Location";
      leaf location {
        type string;
        description
          "Location";
      }
      container card_event_hist_detail {
        description
          "Card Event History Detail";
        leaf-list card_event_hist_detail_values {
          type string;
          description
            "Card Event History Detail Values";
        }
      }
    }
  }

  grouping live_ncs_notif-hist-group {
    description
      "Card State Notification History Group";
    container notif-history {
      description
        "Card State Notification History";
      container brief {
        description
          "Show all state notifications in brief format";
        uses live_ncs_notif-hist-group-brief;
      }
      container detail {
        description
          "Show all state notifications with additional detail information";
        uses live_ncs_notif-hist-group-detail;
      }
    }
  }

  grouping live_ncs_notif-hist-group-brief {
    description
      "Notify Histroy Group Brief";
    list location {
      key "location";
      description
        "Select Location";
      leaf location {
        type string;
        description
          "Location";
      }
      container card_notif_hist_brief {
        description
          "Notify Histroy Brief";
        leaf-list card_notif_hist_brief_values {
          type string;
          description
            "Notify Histroy Brief Values";
        }
      }
    }
  }

  grouping live_ncs_notif-hist-group-detail {
    description
      "Notify Histroy Group Detail";
    list location {
      key "location";
      description
        "Select Location";
      leaf location {
        type string;
        description
          "Location";
      }
      container card_notif_hist_detail {
        description
          "Notify Histroy Detail";
        leaf-list card_notif_hist_detail_values {
          type string;
          description
            "Notify Histroy Detail Values";
        }
      }
    }
  }

  grouping live_ncs_oir-hist-group {
    description
      "Cards OIR History Group";
    container oir-history {
      description
        "Cards OIR History";
      list rack {
        key "rack";
        description
          "Select Rack";
        leaf rack {
          type string;
          description
            "Rack";
        }
        container card_oir_hist {
          description
            "Cards OIR History";
          leaf-list card_oir_events {
            type string;
            description
              "Cards OIR Events";
          }
        }
      }
    }
  }

  grouping live_ncs_iofpga-group {
    description
      "IOFPGA Information Group";
    container iofpga {
      description
        "IOFPGA information";
      uses live_ncs_iofpga-register-group;
      uses live_ncs_iofpga-flash-group;
    }
  }

  grouping live_ncs_iofpga-register-group {
    description
      "IOFPGA Register Information Group";
    container register {
      description
        "IOFPGA Register information";
      uses live_ncs_cpu-register-group;
      uses live_ncs_mb-register-group;
      uses live_ncs_dc-register-group;
    }
  }

  grouping live_ncs_cpu-register-group {
    description
      "CPU-IOFPGA Register Information Group";
    container cpu {
      description
        "CPU-IOFPGA Register information";
      list register_location {
        key "register_location";
        description
          "Card location";
        leaf register_location {
          type string;
          description
            "Location";
        }
        uses live_ncs_iofpga-block-number-group;
        uses live_ncs_iofpga-offset-group;
        uses live_ncs_iofpga-address-group;
      }
    }
  }

  grouping live_ncs_mb-register-group {
    description
      "Mother Board(MB)-IOFPGA Register Information Group";
    container mb {
      description
        "Mother Board(MB)-IOFPGA Register information";
      list register_location {
        key "register_location";
        description
          "Card location";
        leaf register_location {
          type string;
          description
            "Location";
        }
        uses live_ncs_iofpga-block-number-group;
        uses live_ncs_iofpga-offset-group;
        uses live_ncs_iofpga-address-group;
      }
    }
  }

  grouping live_ncs_dc-register-group {
    description
      "Daughter Card(DC)-IOFPGA Register Information Group";
    container dc {
      description
        "Daughter Card(DC)-IOFPGA Register information";
      list register_location {
        key "register_location";
        description
          "Card location";
        leaf register_location {
          type string;
          description
            "Location";
        }
        uses live_ncs_iofpga-block-number-group;
        uses live_ncs_iofpga-offset-group;
        uses live_ncs_iofpga-address-group;
      }
    }
  }

  grouping live_ncs_iofpga-block-number-group {
    description
      "IOFPGA Block Number Group";
    list iofpga_block_number {
      key "iofpga_block_num";
      description
        "Register Group ID";
      leaf iofpga_block_num {
        type uint32;
        description
          "GP";
      }
      leaf block_location {
        type string;
        description
          "Location";
      }
      leaf iofpga_block_nm {
        type string;
        description
          "Block NM";
      }
      list iofpga_register_number {
        key "index";
        description
          "Register Number";
        leaf index {
          type uint32;
          description
            "Register IDX";
        }
        leaf iofpga_register_name {
          type string;
          description
            "Register Name";
        }
        list iofpga_data {
          description
            "IOFPGA DATA";
          leaf name {
            type string;
            description
              "Register Name";
          }
          leaf offset {
            type uint32;
            description
              "Register Offset";
          }
          leaf value {
            type uint32;
            description
              "Register Value";
          }
        }
      }
    }
  }

  grouping live_ncs_iofpga-offset-group {
    description
      "IOFPGA Offset Group";
    list iofpga_offset {
      key "hex_offset";
      description
        "Register Offset Address";
      leaf hex_offset {
        type live_ncs_HexOffset;
        description
          "Register Hex Offset";
      }
      list iofpga_reg_offset_data {
        description
          "Register Offset Data";
        leaf iofpga_reg_off_addr {
          type uint32;
          description
            "Register Offset Address";
        }
        leaf reg_off_value {
          type string;
          description
            "Register Offset Value";
        }
      }
    }
  }

  grouping live_ncs_iofpga-address-group {
    description
      "IOFPGA Address Group";
    list iofpga_address {
      key "start_hex_addr end_hex_addr";
      description
        "Register Range to fetch data";
      leaf start_hex_addr {
        type live_ncs_startHexOffset;
        description
          "Register Start Hex Address";
      }
      leaf end_hex_addr {
        type live_ncs_endHexOffset;
        description
          "Register End Hex Address";
      }
      list iofpga_reg_range_addr_list {
        key "iofpga_reg_range_addr";
        description
          "Register Range Hex Address";
        leaf iofpga_reg_range_addr {
          type uint32;
          description
            "Register Offset";
        }
        list iofpga_reg_data {
          description
            "Register Data";
          leaf iofpga_reg_addr {
            type uint32;
            description
              "Register Address";
          }
          leaf reg_value {
            type string;
            description
              "Register Value";
          }
        }
      }
    }
  }

  grouping live_ncs_iofpga-flash-group {
    description
      "IOFPGA SPI Flash Group";
    container flash {
      description
        "IOFPGA SPI flash information";
      uses live_ncs_iofpga-flash-info-group;
      uses live_ncs_iofpga-flash-status-group;
    }
  }

  grouping live_ncs_iofpga-flash-info-group {
    description
      "IOFPGA SPI Flash Information Group";
    container info {
      description
        "IOFPGA SPI flash content";
      list flash_location {
        key "flash_location";
        description
          "Select Location";
        leaf flash_location {
          type calvados:live_ncs_location-id;
          description
            "IOFPGA Flash Location";
        }
        container iofpga_flash_info {
          description
            "IOFPGA Flash Information";
          leaf-list iofpga_flash_info_values {
            type string;
            description
              "IOFPGA Flash Information Values";
          }
        }
      }
    }
  }

  grouping live_ncs_iofpga-flash-status-group {
    description
      "IOFPGA SPI Flash Status Group";
    container status {
      description
        "IOFPGA SPI flash status";
      list flash_location {
        key "flash_location";
        description
          "IOFPGA Flash Location";
        leaf flash_location {
          type calvados:live_ncs_location-id;
          description
            "IOFPGA Flash Location ID";
        }
        container iofpga_flash_status {
          description
            "IOFPGA Flash Status";
          leaf-list iofpga_flash_status_values {
            type string;
            description
              "IOFPGA Flash Status Values";
          }
        }
      }
    }
  }

  grouping live_ncs_bootldr-group {
    description
      "Bootloader Group";
    container bootloader {
      description
        "Bootloader information";
      uses live_ncs_bootldr-flash-group;
    }
  }

  grouping live_ncs_bootldr-flash-group {
    description
      "Bootloader SPI Flash Group";
    container flash {
      description
        "Bootloader SPI flash information";
      uses live_ncs_bootldr-flash-info-group;
      uses live_ncs_bootldr-flash-status-group;
    }
  }

  grouping live_ncs_bootldr-flash-info-group {
    description
      "Bootloader SPI Flash Information Group";
    container info {
      description
        "Bootloader SPI flash content";
      list flash_location {
        key "flash_location";
        description
          "Select Location";
        leaf flash_location {
          type calvados:live_ncs_location-id;
          description
            "Location ID";
        }
        container bootldr_flash_info {
          description
            "Bootloader Flash Information";
          leaf-list bootldr_flash_info_values {
            type string;
            description
              "Bootloader Flash Information Values";
          }
        }
      }
    }
  }

  grouping live_ncs_bootldr-flash-status-group {
    description
      "Bootloader SPI Flash Group";
    container status {
      description
        "Bootloader SPI flash status";
      list flash_location {
        key "flash_location";
        description
          "Select Location";
        leaf flash_location {
          type calvados:live_ncs_location-id;
          description
            "Location ID";
        }
        container bootldr_flash_status {
          description
            "Bootloader flash status";
          leaf-list bootldr_flash_status_values {
            type string;
            description
              "Bootloader Flash Status Values";
          }
        }
      }
    }
  }

  grouping card_mgr-group {
    description
      "Card Manager module information";
    container card_mgr {
      description
        "Card Manager module information";
      uses show_trace:traceable;
      uses inventory-group;
      uses event-hist-group;
      uses notif-hist-group;
      uses oir-hist-group;
      uses iofpga-group;
      uses bootldr-group;
    }
  }

  grouping inventory-group {
    description
      "Card inventory Group";
    // NCS drop config false container inventory
  }

  grouping inventory-summary-group {
    description
      "Card Inventory Summary Group";
    // NCS drop config false container summary
  }

  grouping inventory-detail-group {
    description
      "Card Manager Inventory Detail Group";
    // NCS drop config false container detail
  }

  grouping event-hist-group {
    description
      "Card Event History Group";
    // NCS drop config false container 'event-history'
  }

  grouping event-hist-group-brief {
    description
      "Card Event History Group Brief";
    list location {
      key "location";
      description
        "Select Location";
      leaf location {
        type string;
        description
          "Location";
      }
      container card_event_hist_brief {
        description
          "Card Event History Brief";
        leaf-list card_event_hist_brief_values {
          type string;
          description
            "Card Event History Brief Values";
        }
      }
    }
  }

  grouping event-hist-group-detail {
    description
      "Card Event History Group Detail";
    list location {
      key "location";
      description
        "Select Location";
      leaf location {
        type string;
        description
          "Location";
      }
      container card_event_hist_detail {
        description
          "Card Event History Detail";
        leaf-list card_event_hist_detail_values {
          type string;
          description
            "Card Event History Detail Values";
        }
      }
    }
  }

  grouping notif-hist-group {
    description
      "Card State Notification History Group";
    // NCS drop config false container 'notif-history'
  }

  grouping notif-hist-group-brief {
    description
      "Notify Histroy Group Brief";
    list location {
      key "location";
      description
        "Select Location";
      leaf location {
        type string;
        description
          "Location";
      }
      container card_notif_hist_brief {
        description
          "Notify Histroy Brief";
        leaf-list card_notif_hist_brief_values {
          type string;
          description
            "Notify Histroy Brief Values";
        }
      }
    }
  }

  grouping notif-hist-group-detail {
    description
      "Notify Histroy Group Detail";
    list location {
      key "location";
      description
        "Select Location";
      leaf location {
        type string;
        description
          "Location";
      }
      container card_notif_hist_detail {
        description
          "Notify Histroy Detail";
        leaf-list card_notif_hist_detail_values {
          type string;
          description
            "Notify Histroy Detail Values";
        }
      }
    }
  }

  grouping oir-hist-group {
    description
      "Cards OIR History Group";
    // NCS drop config false container 'oir-history'
  }

  grouping iofpga-group {
    description
      "IOFPGA Information Group";
    // NCS drop config false container iofpga
  }

  grouping iofpga-register-group {
    description
      "IOFPGA Register Information Group";
    // NCS drop config false container register
  }

  grouping cpu-register-group {
    description
      "CPU-IOFPGA Register Information Group";
    // NCS drop config false container cpu
  }

  grouping mb-register-group {
    description
      "Mother Board(MB)-IOFPGA Register Information Group";
    // NCS drop config false container mb
  }

  grouping dc-register-group {
    description
      "Daughter Card(DC)-IOFPGA Register Information Group";
    // NCS drop config false container dc
  }

  grouping iofpga-block-number-group {
    description
      "IOFPGA Block Number Group";
    // NCS drop config false list iofpga_block_number
  }

  grouping iofpga-offset-group {
    description
      "IOFPGA Offset Group";
    // NCS drop config false list iofpga_offset
  }

  grouping iofpga-address-group {
    description
      "IOFPGA Address Group";
    // NCS drop config false list iofpga_address
  }

  grouping iofpga-flash-group {
    description
      "IOFPGA SPI Flash Group";
    // NCS drop config false container flash
  }

  grouping iofpga-flash-info-group {
    description
      "IOFPGA SPI Flash Information Group";
    // NCS drop config false container info
  }

  grouping iofpga-flash-status-group {
    description
      "IOFPGA SPI Flash Status Group";
    // NCS drop config false container status
  }

  grouping bootldr-group {
    description
      "Bootloader Group";
    // NCS drop config false container bootloader
  }

  grouping bootldr-flash-group {
    description
      "Bootloader SPI Flash Group";
    // NCS drop config false container flash
  }

  grouping bootldr-flash-info-group {
    description
      "Bootloader SPI Flash Information Group";
    // NCS drop config false container info
  }

  grouping bootldr-flash-status-group {
    description
      "Bootloader SPI Flash Group";
    // NCS drop config false container status
  }
}

submodule Cisco-IOS-XR-adt-oper-sub1 {
  // Generated by yanger -t ncs
  tailf:mount-id "cisco-iosxr-nc-7.3:cisco-iosxr-nc-7.3";

  belongs-to Cisco-IOS-XR-adt-oper {
    prefix Cisco-IOS-XR-adt-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR adt package operational data.

     Copyright (c) 2013-2020 by Cisco Systems, Inc.
     All rights reserved.";

  revision 2020-05-05 {
    description
      "IOS XR 7.3.1 Initial version.";
    semver:module-version "1.0.0";
  }
  revision 2019-04-05 {
    description
      "Establish semantic version baseline.";
  }
  revision 2015-11-09 {
    description
      "IOS XR 6.0 revision.";
  }

  grouping ncs_template_ADT-SENSOR-PATHS {
    description
      "Sensor paths";
    leaf sensor-path {
      type string;
      description
        "Sensor path ";
    }
    leaf cadence {
      type string;
      units "second";
      description
        "Cadence in seconds";
    }
    leaf is-implicitly-added {
      type string;
      description
        "Is implicity added sensor-path";
    }
    leaf subscription-id {
      type string;
      description
        "Subscription Id ";
    }
  }

  grouping ncs_template_ADT-SENSOR-GROUPS {
    description
      "Sensor groups";
    leaf sensor-group-name {
      type string;
      description
        "Sensor group name ";
    }
    list sensor-path {
      // NCS patched for predictable order
      ordered-by user;
      description
        "Sensor paths";
      uses ncs_template_ADT-SENSOR-PATHS;
    }
  }

  grouping ncs_template_ADT-SUBSCRIPTION-INFO {
    description
      "ADT subscription details";
    list sensor-group {
      // NCS patched for predictable order
      ordered-by user;
      description
        "Subscribed sensor groups";
      uses ncs_template_ADT-SENSOR-GROUPS;
    }
    list missed-collection {
      // NCS patched for predictable order
      ordered-by user;
      description
        "Missed sensor group collections ";
      uses ncs_template_ADT-SENSOR-GROUPS;
    }
  }

  grouping ncs_template_DETECTOR-STATISTICS {
    description
      "ADT detector statistics";
    leaf-list detector-state {
      // NCS patched for predictable order
      ordered-by user;
      type string;
      // NCS drop max-elements statement
      description
        "detector state";
    }
  }

  grouping ncs_template_TUNER-STATISTICS {
    description
      "ADT tuner statistics";
    leaf tuner-state {
      type string;
      description
        "Current tuner state";
    }
    leaf sys-cpu-state {
      type string;
      description
        "system CPU state 1:OK 0:NOK";
    }
    leaf sys-mem-state {
      type string;
      description
        "system memory state 1:OK 0:NOK";
    }
    leaf proc-cpu-state {
      type string;
      description
        "adt process CPU state 1:OK 0:NOK";
    }
    leaf proc-soft-limit {
      type string;
      description
        "adt proc soft limit";
    }
    leaf proc-mem-state {
      type string;
      description
        "adt process  memory state 1:OK 0:NOK";
    }
    leaf default-path-collection-total {
      type string;
      description
        "total default path collections";
    }
    leaf default-path-collection-status {
      type string;
      description
        "status of default path collections 1:OK 0:NOK";
    }
    leaf user-path-collection-total {
      type string;
      description
        "total user path collections";
    }
    leaf user-path-collection-status {
      type string;
      description
        "status of user path collections 1:OK 0:NOK";
    }
    leaf time-in-curr-state {
      type string;
      units "second";
      description
        "time :seconds: spend in current state";
    }
    leaf sysdb-path-count {
      type string;
      description
        "count of sysdb paths collected by ADT";
    }
    leaf item-count {
      type string;
      description
        "item count collected by ADT";
    }
    leaf-list sys-cpu-stae {
      // NCS patched for predictable order
      ordered-by user;
      type string;
      // NCS drop max-elements statement
      description
        "last 4 samples of system cpu";
    }
    leaf-list sys-mem-data {
      // NCS patched for predictable order
      ordered-by user;
      type string;
      // NCS drop max-elements statement
      description
        "last 4 samples of system memory data";
    }
    leaf-list proc-cpu-stae {
      // NCS patched for predictable order
      ordered-by user;
      type string;
      // NCS drop max-elements statement
      description
        "last 4 samples of adt process cpu";
    }
    leaf-list proc-mem-data {
      // NCS patched for predictable order
      ordered-by user;
      type string;
      // NCS drop max-elements statement
      description
        "last 4 samples of adt process memory data";
    }
    leaf-list default-path-collection-missed-data {
      // NCS patched for predictable order
      ordered-by user;
      type string;
      // NCS drop max-elements statement
      description
        "last 4 samples of missed collection for default
         paths";
    }
    leaf-list user-path-collection-missed-data {
      // NCS patched for predictable order
      ordered-by user;
      type string;
      // NCS drop max-elements statement
      description
        "last 4 samples of missed collection for user
         paths";
    }
  }

  grouping ncs_template_MEMORY-STATISTICS {
    description
      "ADT memory statistics";
    leaf current-memory-total {
      type string;
      units "byte";
      description
        "Current memory usage Total in bytes";
    }
    leaf current-memory-py {
      type string;
      units "byte";
      description
        "Current memory usage Py in bytes";
    }
    leaf peak-memory-total {
      type string;
      units "byte";
      description
        "Peak memory usage Total in bytes";
    }
    leaf peak-memory-py {
      type string;
      units "byte";
      description
        "Peak memory usage Py in bytes";
    }
  }

  grouping ncs_template_OUTPUT-STATISTICS {
    description
      "ADT output statistics";
    leaf total-output-messages {
      type string;
      description
        "Total output messages from selector";
    }
    leaf total-notify {
      type string;
      description
        "Total ADT notifies";
    }
    leaf total-hints {
      type string;
      description
        "Total Hints";
    }
    leaf total-pending-selector-messages {
      type string;
      description
        "Total pending selector messages not pushed to
         MDT";
    }
    leaf total-mdt-reads {
      type string;
      description
        "Total MDT reads";
    }
    leaf total-edt-events {
      type string;
      description
        "Total EDT events";
    }
  }

  grouping ncs_template_INPUT-STATISTICS {
    description
      "ADT input statistics";
    leaf total-input-messages {
      type string;
      description
        "Total input messages received by pal";
    }
    leaf total-output-messages {
      type string;
      description
        "Total output messages send to collector";
    }
    leaf total-collection-errors {
      type string;
      description
        "Total Collection errors";
    }
    leaf total-decode-errors {
      type string;
      description
        "Total decode errors";
    }
    leaf total-bytes-received {
      type string;
      units "byte";
      description
        "Total bytes received from MDT sensor";
    }
    leaf total-bytes-sent {
      type string;
      units "byte";
      description
        "Total bytes sent to collector ";
    }
  }

  grouping ncs_template_ADT-STATISTICS {
    description
      "ADT statistics";
    container input-stats {
      description
        "Input statistics";
      uses ncs_template_INPUT-STATISTICS;
    }
    container output-stats {
      description
        "Output statistics";
      uses ncs_template_OUTPUT-STATISTICS;
    }
    container memory-stats {
      description
        "Memory statistics";
      uses ncs_template_MEMORY-STATISTICS;
    }
    container tuner-stats {
      description
        "Tuner statistics";
      uses ncs_template_TUNER-STATISTICS;
    }
    container detector-stats {
      description
        "Detector statistics";
      uses ncs_template_DETECTOR-STATISTICS;
    }
    leaf last-telemetry-message-timestamp {
      type string;
      description
        "Timestamp of last telemetry message received";
    }
    leaf last-selector-output-timestamp {
      type string;
      description
        "Timestanmp of last selector output";
    }
  }

  grouping ncs_rpc_notif_ADT-SENSOR-PATHS {
    description
      "Sensor paths";
    leaf sensor-path {
      type string;
      description
        "Sensor path ";
    }
    leaf cadence {
      type uint32;
      units "second";
      description
        "Cadence in seconds";
    }
    leaf is-implicitly-added {
      type uint8;
      description
        "Is implicity added sensor-path";
    }
    leaf subscription-id {
      type uint64;
      description
        "Subscription Id ";
    }
  }

  grouping ncs_rpc_notif_ADT-SENSOR-GROUPS {
    description
      "Sensor groups";
    leaf sensor-group-name {
      type string;
      description
        "Sensor group name ";
    }
    list sensor-path {
      description
        "Sensor paths";
      uses ncs_rpc_notif_ADT-SENSOR-PATHS;
    }
  }

  grouping ncs_rpc_notif_ADT-SUBSCRIPTION-INFO {
    description
      "ADT subscription details";
    list sensor-group {
      description
        "Subscribed sensor groups";
      uses ncs_rpc_notif_ADT-SENSOR-GROUPS;
    }
    list missed-collection {
      description
        "Missed sensor group collections ";
      uses ncs_rpc_notif_ADT-SENSOR-GROUPS;
    }
  }

  grouping ncs_rpc_notif_DETECTOR-STATISTICS {
    description
      "ADT detector statistics";
    leaf-list detector-state {
      type uint32;
      max-elements 4;
      description
        "detector state";
    }
  }

  grouping ncs_rpc_notif_TUNER-STATISTICS {
    description
      "ADT tuner statistics";
    leaf tuner-state {
      type uint8;
      description
        "Current tuner state";
    }
    leaf sys-cpu-state {
      type uint8;
      description
        "system CPU state 1:OK 0:NOK";
    }
    leaf sys-mem-state {
      type uint8;
      description
        "system memory state 1:OK 0:NOK";
    }
    leaf proc-cpu-state {
      type uint8;
      description
        "adt process CPU state 1:OK 0:NOK";
    }
    leaf proc-soft-limit {
      type uint32;
      description
        "adt proc soft limit";
    }
    leaf proc-mem-state {
      type uint8;
      description
        "adt process  memory state 1:OK 0:NOK";
    }
    leaf default-path-collection-total {
      type uint64;
      description
        "total default path collections";
    }
    leaf default-path-collection-status {
      type uint8;
      description
        "status of default path collections 1:OK 0:NOK";
    }
    leaf user-path-collection-total {
      type uint64;
      description
        "total user path collections";
    }
    leaf user-path-collection-status {
      type uint8;
      description
        "status of user path collections 1:OK 0:NOK";
    }
    leaf time-in-curr-state {
      type uint64;
      units "second";
      description
        "time :seconds: spend in current state";
    }
    leaf sysdb-path-count {
      type uint64;
      description
        "count of sysdb paths collected by ADT";
    }
    leaf item-count {
      type uint64;
      description
        "item count collected by ADT";
    }
    leaf-list sys-cpu-stae {
      type uint32;
      max-elements 4;
      description
        "last 4 samples of system cpu";
    }
    leaf-list sys-mem-data {
      type uint32;
      max-elements 4;
      description
        "last 4 samples of system memory data";
    }
    leaf-list proc-cpu-stae {
      type uint32;
      max-elements 4;
      description
        "last 4 samples of adt process cpu";
    }
    leaf-list proc-mem-data {
      type uint32;
      max-elements 4;
      description
        "last 4 samples of adt process memory data";
    }
    leaf-list default-path-collection-missed-data {
      type uint32;
      max-elements 4;
      description
        "last 4 samples of missed collection for default
         paths";
    }
    leaf-list user-path-collection-missed-data {
      type uint32;
      max-elements 4;
      description
        "last 4 samples of missed collection for user
         paths";
    }
  }

  grouping ncs_rpc_notif_MEMORY-STATISTICS {
    description
      "ADT memory statistics";
    leaf current-memory-total {
      type uint32;
      units "byte";
      description
        "Current memory usage Total in bytes";
    }
    leaf current-memory-py {
      type uint32;
      units "byte";
      description
        "Current memory usage Py in bytes";
    }
    leaf peak-memory-total {
      type uint32;
      units "byte";
      description
        "Peak memory usage Total in bytes";
    }
    leaf peak-memory-py {
      type uint32;
      units "byte";
      description
        "Peak memory usage Py in bytes";
    }
  }

  grouping ncs_rpc_notif_OUTPUT-STATISTICS {
    description
      "ADT output statistics";
    leaf total-output-messages {
      type uint32;
      description
        "Total output messages from selector";
    }
    leaf total-notify {
      type uint32;
      description
        "Total ADT notifies";
    }
    leaf total-hints {
      type uint32;
      description
        "Total Hints";
    }
    leaf total-pending-selector-messages {
      type uint32;
      description
        "Total pending selector messages not pushed to
         MDT";
    }
    leaf total-mdt-reads {
      type uint32;
      description
        "Total MDT reads";
    }
    leaf total-edt-events {
      type uint32;
      description
        "Total EDT events";
    }
  }

  grouping ncs_rpc_notif_INPUT-STATISTICS {
    description
      "ADT input statistics";
    leaf total-input-messages {
      type uint32;
      description
        "Total input messages received by pal";
    }
    leaf total-output-messages {
      type uint32;
      description
        "Total output messages send to collector";
    }
    leaf total-collection-errors {
      type uint32;
      description
        "Total Collection errors";
    }
    leaf total-decode-errors {
      type uint32;
      description
        "Total decode errors";
    }
    leaf total-bytes-received {
      type uint64;
      units "byte";
      description
        "Total bytes received from MDT sensor";
    }
    leaf total-bytes-sent {
      type uint64;
      units "byte";
      description
        "Total bytes sent to collector ";
    }
  }

  grouping ncs_rpc_notif_ADT-STATISTICS {
    description
      "ADT statistics";
    container input-stats {
      description
        "Input statistics";
      uses ncs_rpc_notif_INPUT-STATISTICS;
    }
    container output-stats {
      description
        "Output statistics";
      uses ncs_rpc_notif_OUTPUT-STATISTICS;
    }
    container memory-stats {
      description
        "Memory statistics";
      uses ncs_rpc_notif_MEMORY-STATISTICS;
    }
    container tuner-stats {
      description
        "Tuner statistics";
      uses ncs_rpc_notif_TUNER-STATISTICS;
    }
    container detector-stats {
      description
        "Detector statistics";
      uses ncs_rpc_notif_DETECTOR-STATISTICS;
    }
    leaf last-telemetry-message-timestamp {
      type uint64;
      description
        "Timestamp of last telemetry message received";
    }
    leaf last-selector-output-timestamp {
      type uint64;
      description
        "Timestanmp of last selector output";
    }
  }

  grouping live_ncs_ADT-SENSOR-PATHS {
    description
      "Sensor paths";
    leaf sensor-path {
      type string;
      description
        "Sensor path ";
    }
    leaf cadence {
      type uint32;
      units "second";
      description
        "Cadence in seconds";
    }
    leaf is-implicitly-added {
      type uint8;
      description
        "Is implicity added sensor-path";
    }
    leaf subscription-id {
      type uint64;
      description
        "Subscription Id ";
    }
  }

  grouping live_ncs_ADT-SENSOR-GROUPS {
    description
      "Sensor groups";
    leaf sensor-group-name {
      type string;
      description
        "Sensor group name ";
    }
    list sensor-path {
      description
        "Sensor paths";
      uses live_ncs_ADT-SENSOR-PATHS;
    }
  }

  grouping live_ncs_ADT-SUBSCRIPTION-INFO {
    description
      "ADT subscription details";
    list sensor-group {
      description
        "Subscribed sensor groups";
      uses live_ncs_ADT-SENSOR-GROUPS;
    }
    list missed-collection {
      description
        "Missed sensor group collections ";
      uses live_ncs_ADT-SENSOR-GROUPS;
    }
  }

  grouping live_ncs_DETECTOR-STATISTICS {
    description
      "ADT detector statistics";
    leaf-list detector-state {
      type uint32;
      // NCS drop max-elements statement
      description
        "detector state";
    }
  }

  grouping live_ncs_TUNER-STATISTICS {
    description
      "ADT tuner statistics";
    leaf tuner-state {
      type uint8;
      description
        "Current tuner state";
    }
    leaf sys-cpu-state {
      type uint8;
      description
        "system CPU state 1:OK 0:NOK";
    }
    leaf sys-mem-state {
      type uint8;
      description
        "system memory state 1:OK 0:NOK";
    }
    leaf proc-cpu-state {
      type uint8;
      description
        "adt process CPU state 1:OK 0:NOK";
    }
    leaf proc-soft-limit {
      type uint32;
      description
        "adt proc soft limit";
    }
    leaf proc-mem-state {
      type uint8;
      description
        "adt process  memory state 1:OK 0:NOK";
    }
    leaf default-path-collection-total {
      type uint64;
      description
        "total default path collections";
    }
    leaf default-path-collection-status {
      type uint8;
      description
        "status of default path collections 1:OK 0:NOK";
    }
    leaf user-path-collection-total {
      type uint64;
      description
        "total user path collections";
    }
    leaf user-path-collection-status {
      type uint8;
      description
        "status of user path collections 1:OK 0:NOK";
    }
    leaf time-in-curr-state {
      type uint64;
      units "second";
      description
        "time :seconds: spend in current state";
    }
    leaf sysdb-path-count {
      type uint64;
      description
        "count of sysdb paths collected by ADT";
    }
    leaf item-count {
      type uint64;
      description
        "item count collected by ADT";
    }
    leaf-list sys-cpu-stae {
      type uint32;
      // NCS drop max-elements statement
      description
        "last 4 samples of system cpu";
    }
    leaf-list sys-mem-data {
      type uint32;
      // NCS drop max-elements statement
      description
        "last 4 samples of system memory data";
    }
    leaf-list proc-cpu-stae {
      type uint32;
      // NCS drop max-elements statement
      description
        "last 4 samples of adt process cpu";
    }
    leaf-list proc-mem-data {
      type uint32;
      // NCS drop max-elements statement
      description
        "last 4 samples of adt process memory data";
    }
    leaf-list default-path-collection-missed-data {
      type uint32;
      // NCS drop max-elements statement
      description
        "last 4 samples of missed collection for default
         paths";
    }
    leaf-list user-path-collection-missed-data {
      type uint32;
      // NCS drop max-elements statement
      description
        "last 4 samples of missed collection for user
         paths";
    }
  }

  grouping live_ncs_MEMORY-STATISTICS {
    description
      "ADT memory statistics";
    leaf current-memory-total {
      type uint32;
      units "byte";
      description
        "Current memory usage Total in bytes";
    }
    leaf current-memory-py {
      type uint32;
      units "byte";
      description
        "Current memory usage Py in bytes";
    }
    leaf peak-memory-total {
      type uint32;
      units "byte";
      description
        "Peak memory usage Total in bytes";
    }
    leaf peak-memory-py {
      type uint32;
      units "byte";
      description
        "Peak memory usage Py in bytes";
    }
  }

  grouping live_ncs_OUTPUT-STATISTICS {
    description
      "ADT output statistics";
    leaf total-output-messages {
      type uint32;
      description
        "Total output messages from selector";
    }
    leaf total-notify {
      type uint32;
      description
        "Total ADT notifies";
    }
    leaf total-hints {
      type uint32;
      description
        "Total Hints";
    }
    leaf total-pending-selector-messages {
      type uint32;
      description
        "Total pending selector messages not pushed to
         MDT";
    }
    leaf total-mdt-reads {
      type uint32;
      description
        "Total MDT reads";
    }
    leaf total-edt-events {
      type uint32;
      description
        "Total EDT events";
    }
  }

  grouping live_ncs_INPUT-STATISTICS {
    description
      "ADT input statistics";
    leaf total-input-messages {
      type uint32;
      description
        "Total input messages received by pal";
    }
    leaf total-output-messages {
      type uint32;
      description
        "Total output messages send to collector";
    }
    leaf total-collection-errors {
      type uint32;
      description
        "Total Collection errors";
    }
    leaf total-decode-errors {
      type uint32;
      description
        "Total decode errors";
    }
    leaf total-bytes-received {
      type uint64;
      units "byte";
      description
        "Total bytes received from MDT sensor";
    }
    leaf total-bytes-sent {
      type uint64;
      units "byte";
      description
        "Total bytes sent to collector ";
    }
  }

  grouping live_ncs_ADT-STATISTICS {
    description
      "ADT statistics";
    container input-stats {
      description
        "Input statistics";
      uses live_ncs_INPUT-STATISTICS;
    }
    container output-stats {
      description
        "Output statistics";
      uses live_ncs_OUTPUT-STATISTICS;
    }
    container memory-stats {
      description
        "Memory statistics";
      uses live_ncs_MEMORY-STATISTICS;
    }
    container tuner-stats {
      description
        "Tuner statistics";
      uses live_ncs_TUNER-STATISTICS;
    }
    container detector-stats {
      description
        "Detector statistics";
      uses live_ncs_DETECTOR-STATISTICS;
    }
    leaf last-telemetry-message-timestamp {
      type uint64;
      description
        "Timestamp of last telemetry message received";
    }
    leaf last-selector-output-timestamp {
      type uint64;
      description
        "Timestanmp of last selector output";
    }
  }

  grouping ADT-SENSOR-PATHS {
    description
      "Sensor paths";
    leaf sensor-path {
      type string;
      description
        "Sensor path ";
    }
    leaf cadence {
      type uint32;
      units "second";
      description
        "Cadence in seconds";
    }
    leaf is-implicitly-added {
      type uint8;
      description
        "Is implicity added sensor-path";
    }
    leaf subscription-id {
      type uint64;
      description
        "Subscription Id ";
    }
  }

  grouping ADT-SENSOR-GROUPS {
    description
      "Sensor groups";
    leaf sensor-group-name {
      type string;
      description
        "Sensor group name ";
    }
    list sensor-path {
      description
        "Sensor paths";
      uses ADT-SENSOR-PATHS;
    }
  }

  grouping ADT-SUBSCRIPTION-INFO {
    description
      "ADT subscription details";
    list sensor-group {
      description
        "Subscribed sensor groups";
      uses ADT-SENSOR-GROUPS;
    }
    list missed-collection {
      description
        "Missed sensor group collections ";
      uses ADT-SENSOR-GROUPS;
    }
  }

  grouping DETECTOR-STATISTICS {
    description
      "ADT detector statistics";
    leaf-list detector-state {
      type uint32;
      max-elements 4;
      description
        "detector state";
    }
  }

  grouping TUNER-STATISTICS {
    description
      "ADT tuner statistics";
    leaf tuner-state {
      type uint8;
      description
        "Current tuner state";
    }
    leaf sys-cpu-state {
      type uint8;
      description
        "system CPU state 1:OK 0:NOK";
    }
    leaf sys-mem-state {
      type uint8;
      description
        "system memory state 1:OK 0:NOK";
    }
    leaf proc-cpu-state {
      type uint8;
      description
        "adt process CPU state 1:OK 0:NOK";
    }
    leaf proc-soft-limit {
      type uint32;
      description
        "adt proc soft limit";
    }
    leaf proc-mem-state {
      type uint8;
      description
        "adt process  memory state 1:OK 0:NOK";
    }
    leaf default-path-collection-total {
      type uint64;
      description
        "total default path collections";
    }
    leaf default-path-collection-status {
      type uint8;
      description
        "status of default path collections 1:OK 0:NOK";
    }
    leaf user-path-collection-total {
      type uint64;
      description
        "total user path collections";
    }
    leaf user-path-collection-status {
      type uint8;
      description
        "status of user path collections 1:OK 0:NOK";
    }
    leaf time-in-curr-state {
      type uint64;
      units "second";
      description
        "time :seconds: spend in current state";
    }
    leaf sysdb-path-count {
      type uint64;
      description
        "count of sysdb paths collected by ADT";
    }
    leaf item-count {
      type uint64;
      description
        "item count collected by ADT";
    }
    leaf-list sys-cpu-stae {
      type uint32;
      max-elements 4;
      description
        "last 4 samples of system cpu";
    }
    leaf-list sys-mem-data {
      type uint32;
      max-elements 4;
      description
        "last 4 samples of system memory data";
    }
    leaf-list proc-cpu-stae {
      type uint32;
      max-elements 4;
      description
        "last 4 samples of adt process cpu";
    }
    leaf-list proc-mem-data {
      type uint32;
      max-elements 4;
      description
        "last 4 samples of adt process memory data";
    }
    leaf-list default-path-collection-missed-data {
      type uint32;
      max-elements 4;
      description
        "last 4 samples of missed collection for default
         paths";
    }
    leaf-list user-path-collection-missed-data {
      type uint32;
      max-elements 4;
      description
        "last 4 samples of missed collection for user
         paths";
    }
  }

  grouping MEMORY-STATISTICS {
    description
      "ADT memory statistics";
    leaf current-memory-total {
      type uint32;
      units "byte";
      description
        "Current memory usage Total in bytes";
    }
    leaf current-memory-py {
      type uint32;
      units "byte";
      description
        "Current memory usage Py in bytes";
    }
    leaf peak-memory-total {
      type uint32;
      units "byte";
      description
        "Peak memory usage Total in bytes";
    }
    leaf peak-memory-py {
      type uint32;
      units "byte";
      description
        "Peak memory usage Py in bytes";
    }
  }

  grouping OUTPUT-STATISTICS {
    description
      "ADT output statistics";
    leaf total-output-messages {
      type uint32;
      description
        "Total output messages from selector";
    }
    leaf total-notify {
      type uint32;
      description
        "Total ADT notifies";
    }
    leaf total-hints {
      type uint32;
      description
        "Total Hints";
    }
    leaf total-pending-selector-messages {
      type uint32;
      description
        "Total pending selector messages not pushed to
         MDT";
    }
    leaf total-mdt-reads {
      type uint32;
      description
        "Total MDT reads";
    }
    leaf total-edt-events {
      type uint32;
      description
        "Total EDT events";
    }
  }

  grouping INPUT-STATISTICS {
    description
      "ADT input statistics";
    leaf total-input-messages {
      type uint32;
      description
        "Total input messages received by pal";
    }
    leaf total-output-messages {
      type uint32;
      description
        "Total output messages send to collector";
    }
    leaf total-collection-errors {
      type uint32;
      description
        "Total Collection errors";
    }
    leaf total-decode-errors {
      type uint32;
      description
        "Total decode errors";
    }
    leaf total-bytes-received {
      type uint64;
      units "byte";
      description
        "Total bytes received from MDT sensor";
    }
    leaf total-bytes-sent {
      type uint64;
      units "byte";
      description
        "Total bytes sent to collector ";
    }
  }

  grouping ADT-STATISTICS {
    description
      "ADT statistics";
    container input-stats {
      description
        "Input statistics";
      uses INPUT-STATISTICS;
    }
    container output-stats {
      description
        "Output statistics";
      uses OUTPUT-STATISTICS;
    }
    container memory-stats {
      description
        "Memory statistics";
      uses MEMORY-STATISTICS;
    }
    container tuner-stats {
      description
        "Tuner statistics";
      uses TUNER-STATISTICS;
    }
    container detector-stats {
      description
        "Detector statistics";
      uses DETECTOR-STATISTICS;
    }
    leaf last-telemetry-message-timestamp {
      type uint64;
      description
        "Timestamp of last telemetry message received";
    }
    leaf last-selector-output-timestamp {
      type uint64;
      description
        "Timestanmp of last selector output";
    }
  }
}

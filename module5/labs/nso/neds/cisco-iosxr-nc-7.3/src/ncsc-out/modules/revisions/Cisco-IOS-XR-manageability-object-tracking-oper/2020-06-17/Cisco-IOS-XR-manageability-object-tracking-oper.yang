module Cisco-IOS-XR-manageability-object-tracking-oper {
  // Generated by yanger -t ncs
  tailf:mount-id "cisco-iosxr-nc-7.3:cisco-iosxr-nc-7.3";
  tailf:ncs-device-type "netconf";

  namespace "http://cisco.com/ns/yang/Cisco-IOS-XR-manageability-object-tracking-oper";
  prefix manageability-object-tracking-oper;

  import cisco-semver {
    prefix semver;
  }
  import Cisco-IOS-XR-manageability-object-tracking-datatypes {
    prefix dt1;
  }
  include Cisco-IOS-XR-manageability-object-tracking-oper-sub1 {
    revision-date 2020-06-17;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR manageability-object-tracking package operational data.

     This module contains definitions
     for the following management objects:
       object-tracking: Object Tracking operational data

     Copyright (c) 2013-2020 by Cisco Systems, Inc.
     All rights reserved.";

  revision 2020-06-17 {
    description
      "Added support to display delay up/down values in show track.";
    semver:module-version "2.2.0";
  }
  revision 2019-10-07 {
    description
      "Added support for track type bgp nbr af.";
    semver:module-version "2.1.0";
  }
  revision 2019-09-07 {
    description
      "Removed IPv4 Route type nodes and added generic node for both IPv4 and IPv6.";
    semver:module-version "2.0.0";
  }
  revision 2019-04-05 {
    description
      "Establish semantic version baseline.";
    semver:module-version "1.0.0";
  }
  revision 2015-11-09 {
    description
      "IOS XR 6.0 revision.";
  }

  augment "/ncs:devices/ncs:device/ncs:config" {
    // NCS drop config false container 'object-tracking'
  }
  augment "/ncs:devices/ncs:device/ncs:live-status" {
    container object-tracking {
      tailf:ncs-device-type "netconf";
      tailf:display-when "not(../../ncs:module) or ../../ncs:module[ncs:name='Cisco-IOS-XR-manageability-object-tracking-oper'] or (../../ncs:live-status-protocol[not(ncs:capability)]) or (../../ncs:live-status-protocol/ncs:capability/ncs:module[.='Cisco-IOS-XR-manageability-object-tracking-oper'])";
      description
        "Object Tracking operational data";
      container track-type-interface {
        description
          "Object Tracking Type interface info";
        uses live_ncs_TRACK-INFO;
      }
      container track-briefs {
        description
          "Object Tracking Track table brief";
        list track-brief {
          key "track-name";
          description
            "Track name - maximum 32 characters";
          leaf track-name {
            type dt1:live_ncs_Object-tracking-name-string;
            description
              "Track name";
          }
          uses live_ncs_TRACK-INFO-BRIEF;
        }
      }
      container track-type-rtr-reachability {
        description
          "Object Tracking Type RTR Reachability info";
        uses live_ncs_TRACK-INFO;
      }
      container track-type-rtr-reachability-brief {
        description
          "Object Tracking Type RTR Reachability brief info";
        uses live_ncs_TRACK-INFO-BRIEF;
      }
      container tracks {
        description
          "Object Tracking Track table";
        list track {
          key "track-name";
          description
            "Track name - maximum 32 characters";
          leaf track-name {
            type dt1:live_ncs_Object-tracking-name-string;
            description
              "Track name";
          }
          uses live_ncs_TRACK-INFO;
        }
      }
      container track-type-route {
        description
          "Object Tracking Type Route info";
        uses live_ncs_TRACK-INFO;
      }
      container track-type-route-brief {
        description
          "Object Tracking Type Route brief info";
        uses live_ncs_TRACK-INFO-BRIEF;
      }
      container track-type-interface-brief {
        description
          "Object Tracking Type Interface brief info";
        uses live_ncs_TRACK-INFO-BRIEF;
      }
    }
  }
  augment "/ncs:devices/ncs:template/ncs:ned-id/ncs:config" {
    // NCS drop config false container 'object-tracking'
  }
}

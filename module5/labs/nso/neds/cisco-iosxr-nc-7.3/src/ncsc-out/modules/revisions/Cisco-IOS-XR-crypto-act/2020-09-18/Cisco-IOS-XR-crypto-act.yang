module Cisco-IOS-XR-crypto-act {
  // Generated by yanger -t ncs
  tailf:mount-id "cisco-iosxr-nc-7.3:cisco-iosxr-nc-7.3";
  tailf:ncs-device-type "netconf";

  namespace "http://cisco.com/ns/yang/Cisco-IOS-XR-crypto-act";
  prefix crypto-act;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2020 by Cisco Systems, Inc.
     All rights reserved.";

  revision 2020-09-18 {
    description
      "Change user task for ca-crl-request from cisco-support to crypto";
    semver:module-version "1.2.0";
  }
  revision 2019-10-01 {
    description
      "Made changes to be RFC6087 compliant";
    semver:module-version "1.1.0";
  }
  revision 2019-06-18 {
    description
      "IOS XR 7.0.1 revision.";
    semver:module-version "1.0.0";
  }
  revision 2019-04-05 {
    description
      "Establish semantic version baseline.";
  }
  revision 2016-04-17 {
    description
      "IOS XR 6.1.1 revision.";
  }

  grouping ncs_template_KEY-MODULUS {
    description
      "Key modulus grouping";
    leaf key-label {
      type string;
      description
        "RSA keypair label";
    }
    leaf key-modulus {
      type string;
      // NCS drop mandatory statement
      description
        "Key modulus in the range of 512 to 4096 for your General Purpose Keypair. Choosing a key modulus greater than 512 may take a few minutes";
    }
  }

  grouping ncs_rpc_notif_KEY-MODULUS {
    description
      "Key modulus grouping";
    leaf key-label {
      type string;
      description
        "RSA keypair label";
    }
    leaf key-modulus {
      type int32 {
        range "512..4096";
      }
      mandatory true;
      description
        "Key modulus in the range of 512 to 4096 for your General Purpose Keypair. Choosing a key modulus greater than 512 may take a few minutes";
    }
  }

  grouping live_ncs_KEY-MODULUS {
    description
      "Key modulus grouping";
    leaf key-label {
      type string;
      description
        "RSA keypair label";
    }
    leaf key-modulus {
      type int32 {
        range "512..4096";
      }
      // NCS drop mandatory statement
      description
        "Key modulus in the range of 512 to 4096 for your General Purpose Keypair. Choosing a key modulus greater than 512 may take a few minutes";
    }
  }

  grouping KEY-MODULUS {
    description
      "Key modulus grouping";
    leaf key-label {
      type string;
      description
        "RSA keypair label";
    }
    leaf key-modulus {
      type int32 {
        range "512..4096";
      }
      mandatory true;
      description
        "Key modulus in the range of 512 to 4096 for your General Purpose Keypair. Choosing a key modulus greater than 512 may take a few minutes";
    }
  }

  augment "/ncs:devices/ncs:device/ncs:rpc" {
    container rpc-ca-trustpool-import-url-clean {
      tailf:ncs-device-type "netconf";
      tailf:display-when "not(../../ncs:module) or ../../ncs:module[ncs:name='Cisco-IOS-XR-crypto-act']";
      tailf:action ca-trustpool-import-url-clean {
        tailf:actionpoint ncsproxy {
          tailf:internal;
        }
        description
          "Remove downloaded certificates in trustpool";
        input {
          leaf url {
            type string;
            description
              "in URL format";
          }
        }
      }
    }
  }
  augment "/ncs:devices/ncs:device-group/ncs:ned-id/ncs:rpc" {
    container rpc-ca-trustpool-import-url-clean {
      tailf:ncs-device-type "netconf";
      tailf:display-when "/ncs:devices/ncs:device[ncs:name=current()/../../../ncs:member]/ncs:module[ncs:name='Cisco-IOS-XR-crypto-act']";
      tailf:action ca-trustpool-import-url-clean {
        tailf:actionpoint ncsproxy {
          tailf:internal;
        }
        description
          "Remove downloaded certificates in trustpool";
        input {
          leaf url {
            type string;
            description
              "in URL format";
          }
        }
      }
    }
  }
  augment "/ncs:devices/ncs:device/ncs:rpc" {
    container rpc-ca-trustpool-import-url {
      tailf:ncs-device-type "netconf";
      tailf:display-when "not(../../ncs:module) or ../../ncs:module[ncs:name='Cisco-IOS-XR-crypto-act']";
      tailf:action ca-trustpool-import-url {
        tailf:actionpoint ncsproxy {
          tailf:internal;
        }
        description
          "Manual import trustpool certificates from URL";
        input {
          leaf url {
            type string;
            description
              "in URL format";
          }
        }
      }
    }
  }
  augment "/ncs:devices/ncs:device-group/ncs:ned-id/ncs:rpc" {
    container rpc-ca-trustpool-import-url {
      tailf:ncs-device-type "netconf";
      tailf:display-when "/ncs:devices/ncs:device[ncs:name=current()/../../../ncs:member]/ncs:module[ncs:name='Cisco-IOS-XR-crypto-act']";
      tailf:action ca-trustpool-import-url {
        tailf:actionpoint ncsproxy {
          tailf:internal;
        }
        description
          "Manual import trustpool certificates from URL";
        input {
          leaf url {
            type string;
            description
              "in URL format";
          }
        }
      }
    }
  }
  augment "/ncs:devices/ncs:device/ncs:rpc" {
    container rpc-ca-crl-request {
      tailf:ncs-device-type "netconf";
      tailf:display-when "not(../../ncs:module) or ../../ncs:module[ncs:name='Cisco-IOS-XR-crypto-act']";
      tailf:action ca-crl-request {
        tailf:actionpoint ncsproxy {
          tailf:internal;
        }
        description
          "Actions on certificate revocation lists";
        input {
          leaf uri {
            type string;
            mandatory true;
            description
              "CRL Distribution Point in URI format";
          }
        }
        output {
          leaf certificate {
            type string;
            mandatory true;
            description
              "Certificate returned";
          }
        }
      }
    }
  }
  augment "/ncs:devices/ncs:device-group/ncs:ned-id/ncs:rpc" {
    container rpc-ca-crl-request {
      tailf:ncs-device-type "netconf";
      tailf:display-when "/ncs:devices/ncs:device[ncs:name=current()/../../../ncs:member]/ncs:module[ncs:name='Cisco-IOS-XR-crypto-act']";
      tailf:action ca-crl-request {
        tailf:actionpoint ncsproxy {
          tailf:internal;
        }
        description
          "Actions on certificate revocation lists";
        input {
          leaf uri {
            type string;
            mandatory true;
            description
              "CRL Distribution Point in URI format";
          }
        }
        output {
          container "device" {
            leaf "name" {
              type string;
            }
            leaf "info" {
              type string;
            }
            container "result" {
              leaf certificate {
                type string;
                mandatory true;
                description
                  "Certificate returned";
              }
            }
          }
        }
      }
    }
  }
  augment "/ncs:devices/ncs:device/ncs:rpc" {
    container rpc-ca-cancel-enroll {
      tailf:ncs-device-type "netconf";
      tailf:display-when "not(../../ncs:module) or ../../ncs:module[ncs:name='Cisco-IOS-XR-crypto-act']";
      tailf:action ca-cancel-enroll {
        tailf:actionpoint ncsproxy {
          tailf:internal;
        }
        description
          "Cancel enrollment from a CA";
        input {
          leaf server-name {
            type string;
            mandatory true;
            description
              "CA Server Name";
          }
        }
      }
    }
  }
  augment "/ncs:devices/ncs:device-group/ncs:ned-id/ncs:rpc" {
    container rpc-ca-cancel-enroll {
      tailf:ncs-device-type "netconf";
      tailf:display-when "/ncs:devices/ncs:device[ncs:name=current()/../../../ncs:member]/ncs:module[ncs:name='Cisco-IOS-XR-crypto-act']";
      tailf:action ca-cancel-enroll {
        tailf:actionpoint ncsproxy {
          tailf:internal;
        }
        description
          "Cancel enrollment from a CA";
        input {
          leaf server-name {
            type string;
            mandatory true;
            description
              "CA Server Name";
          }
        }
      }
    }
  }
  augment "/ncs:devices/ncs:device/ncs:rpc" {
    container rpc-ca-import-certificate {
      tailf:ncs-device-type "netconf";
      tailf:display-when "not(../../ncs:module) or ../../ncs:module[ncs:name='Cisco-IOS-XR-crypto-act']";
      tailf:action ca-import-certificate {
        tailf:actionpoint ncsproxy {
          tailf:internal;
        }
        description
          "Import a certificate from a s/tftp server or the terminal";
        input {
          leaf server-name {
            type string;
            mandatory true;
            description
              "CA Server Name";
          }
        }
      }
    }
  }
  augment "/ncs:devices/ncs:device-group/ncs:ned-id/ncs:rpc" {
    container rpc-ca-import-certificate {
      tailf:ncs-device-type "netconf";
      tailf:display-when "/ncs:devices/ncs:device[ncs:name=current()/../../../ncs:member]/ncs:module[ncs:name='Cisco-IOS-XR-crypto-act']";
      tailf:action ca-import-certificate {
        tailf:actionpoint ncsproxy {
          tailf:internal;
        }
        description
          "Import a certificate from a s/tftp server or the terminal";
        input {
          leaf server-name {
            type string;
            mandatory true;
            description
              "CA Server Name";
          }
        }
      }
    }
  }
  augment "/ncs:devices/ncs:device/ncs:rpc" {
    container rpc-ca-enroll {
      tailf:ncs-device-type "netconf";
      tailf:display-when "not(../../ncs:module) or ../../ncs:module[ncs:name='Cisco-IOS-XR-crypto-act']";
      tailf:action ca-enroll {
        tailf:actionpoint ncsproxy {
          tailf:internal;
        }
        description
          "Request a certificate from a CA";
        input {
          leaf server-name {
            type string;
            mandatory true;
            description
              "CA Server Name";
          }
        }
      }
    }
  }
  augment "/ncs:devices/ncs:device-group/ncs:ned-id/ncs:rpc" {
    container rpc-ca-enroll {
      tailf:ncs-device-type "netconf";
      tailf:display-when "/ncs:devices/ncs:device[ncs:name=current()/../../../ncs:member]/ncs:module[ncs:name='Cisco-IOS-XR-crypto-act']";
      tailf:action ca-enroll {
        tailf:actionpoint ncsproxy {
          tailf:internal;
        }
        description
          "Request a certificate from a CA";
        input {
          leaf server-name {
            type string;
            mandatory true;
            description
              "CA Server Name";
          }
        }
      }
    }
  }
  augment "/ncs:devices/ncs:device/ncs:rpc" {
    container rpc-ca-authenticate {
      tailf:ncs-device-type "netconf";
      tailf:display-when "not(../../ncs:module) or ../../ncs:module[ncs:name='Cisco-IOS-XR-crypto-act']";
      tailf:action ca-authenticate {
        tailf:actionpoint ncsproxy {
          tailf:internal;
        }
        description
          "Get the certification authority certificate";
        input {
          leaf server-name {
            type string;
            mandatory true;
            description
              "CA Server Name";
          }
        }
      }
    }
  }
  augment "/ncs:devices/ncs:device-group/ncs:ned-id/ncs:rpc" {
    container rpc-ca-authenticate {
      tailf:ncs-device-type "netconf";
      tailf:display-when "/ncs:devices/ncs:device[ncs:name=current()/../../../ncs:member]/ncs:module[ncs:name='Cisco-IOS-XR-crypto-act']";
      tailf:action ca-authenticate {
        tailf:actionpoint ncsproxy {
          tailf:internal;
        }
        description
          "Get the certification authority certificate";
        input {
          leaf server-name {
            type string;
            mandatory true;
            description
              "CA Server Name";
          }
        }
      }
    }
  }
  augment "/ncs:devices/ncs:device/ncs:rpc" {
    container rpc-key-import-authentication-rsa-username {
      tailf:ncs-device-type "netconf";
      tailf:display-when "not(../../ncs:module) or ../../ncs:module[ncs:name='Cisco-IOS-XR-crypto-act']";
      tailf:action key-import-authentication-rsa-username {
        tailf:actionpoint ncsproxy {
          tailf:internal;
        }
        description
          "RSA authentication key for user";
        input {
          leaf path {
            type string;
            mandatory true;
            description
              "Path to RSA pubkey file";
          }
          leaf username {
            type string;
            mandatory true;
            description
              "Username";
          }
        }
      }
    }
  }
  augment "/ncs:devices/ncs:device-group/ncs:ned-id/ncs:rpc" {
    container rpc-key-import-authentication-rsa-username {
      tailf:ncs-device-type "netconf";
      tailf:display-when "/ncs:devices/ncs:device[ncs:name=current()/../../../ncs:member]/ncs:module[ncs:name='Cisco-IOS-XR-crypto-act']";
      tailf:action key-import-authentication-rsa-username {
        tailf:actionpoint ncsproxy {
          tailf:internal;
        }
        description
          "RSA authentication key for user";
        input {
          leaf path {
            type string;
            mandatory true;
            description
              "Path to RSA pubkey file";
          }
          leaf username {
            type string;
            mandatory true;
            description
              "Username";
          }
        }
      }
    }
  }
  augment "/ncs:devices/ncs:device/ncs:rpc" {
    container rpc-key-import-authentication-rsa {
      tailf:ncs-device-type "netconf";
      tailf:display-when "not(../../ncs:module) or ../../ncs:module[ncs:name='Cisco-IOS-XR-crypto-act']";
      tailf:action key-import-authentication-rsa {
        tailf:actionpoint ncsproxy {
          tailf:internal;
        }
        description
          "Remove RSA authentication key";
        input {
          leaf path {
            type string;
            mandatory true;
            description
              "Path to RSA pubkey file";
          }
        }
      }
    }
  }
  augment "/ncs:devices/ncs:device-group/ncs:ned-id/ncs:rpc" {
    container rpc-key-import-authentication-rsa {
      tailf:ncs-device-type "netconf";
      tailf:display-when "/ncs:devices/ncs:device[ncs:name=current()/../../../ncs:member]/ncs:module[ncs:name='Cisco-IOS-XR-crypto-act']";
      tailf:action key-import-authentication-rsa {
        tailf:actionpoint ncsproxy {
          tailf:internal;
        }
        description
          "Remove RSA authentication key";
        input {
          leaf path {
            type string;
            mandatory true;
            description
              "Path to RSA pubkey file";
          }
        }
      }
    }
  }
  augment "/ncs:devices/ncs:device/ncs:rpc" {
    container rpc-key-zeroize-ed25519 {
      tailf:ncs-device-type "netconf";
      tailf:display-when "not(../../ncs:module) or ../../ncs:module[ncs:name='Cisco-IOS-XR-crypto-act']";
      tailf:action key-zeroize-ed25519 {
        tailf:actionpoint ncsproxy {
          tailf:internal;
        }
        description
          "Remove ed25519 keys";
        input {
          leaf key-label {
            type string;
            description
              "Ed25519 key label";
          }
        }
      }
    }
  }
  augment "/ncs:devices/ncs:device-group/ncs:ned-id/ncs:rpc" {
    container rpc-key-zeroize-ed25519 {
      tailf:ncs-device-type "netconf";
      tailf:display-when "/ncs:devices/ncs:device[ncs:name=current()/../../../ncs:member]/ncs:module[ncs:name='Cisco-IOS-XR-crypto-act']";
      tailf:action key-zeroize-ed25519 {
        tailf:actionpoint ncsproxy {
          tailf:internal;
        }
        description
          "Remove ed25519 keys";
        input {
          leaf key-label {
            type string;
            description
              "Ed25519 key label";
          }
        }
      }
    }
  }
  augment "/ncs:devices/ncs:device/ncs:rpc" {
    container rpc-key-zeroize-authentication-rsa-all {
      tailf:ncs-device-type "netconf";
      tailf:display-when "not(../../ncs:module) or ../../ncs:module[ncs:name='Cisco-IOS-XR-crypto-act']";
      tailf:action key-zeroize-authentication-rsa-all {
        tailf:actionpoint ncsproxy {
          tailf:internal;
        }
        description
          "Remove RSA authentication key";
      }
    }
  }
  augment "/ncs:devices/ncs:device-group/ncs:ned-id/ncs:rpc" {
    container rpc-key-zeroize-authentication-rsa-all {
      tailf:ncs-device-type "netconf";
      tailf:display-when "/ncs:devices/ncs:device[ncs:name=current()/../../../ncs:member]/ncs:module[ncs:name='Cisco-IOS-XR-crypto-act']";
      tailf:action key-zeroize-authentication-rsa-all {
        tailf:actionpoint ncsproxy {
          tailf:internal;
        }
        description
          "Remove RSA authentication key";
      }
    }
  }
  augment "/ncs:devices/ncs:device/ncs:rpc" {
    container rpc-key-zeroize-authentication-rsa-username {
      tailf:ncs-device-type "netconf";
      tailf:display-when "not(../../ncs:module) or ../../ncs:module[ncs:name='Cisco-IOS-XR-crypto-act']";
      tailf:action key-zeroize-authentication-rsa-username {
        tailf:actionpoint ncsproxy {
          tailf:internal;
        }
        description
          "Remove RSA authentication key";
        input {
          leaf username {
            type string;
            mandatory true;
            description
              "Username";
          }
        }
      }
    }
  }
  augment "/ncs:devices/ncs:device-group/ncs:ned-id/ncs:rpc" {
    container rpc-key-zeroize-authentication-rsa-username {
      tailf:ncs-device-type "netconf";
      tailf:display-when "/ncs:devices/ncs:device[ncs:name=current()/../../../ncs:member]/ncs:module[ncs:name='Cisco-IOS-XR-crypto-act']";
      tailf:action key-zeroize-authentication-rsa-username {
        tailf:actionpoint ncsproxy {
          tailf:internal;
        }
        description
          "Remove RSA authentication key";
        input {
          leaf username {
            type string;
            mandatory true;
            description
              "Username";
          }
        }
      }
    }
  }
  augment "/ncs:devices/ncs:device/ncs:rpc" {
    container rpc-key-zeroize-authentication-rsa {
      tailf:ncs-device-type "netconf";
      tailf:display-when "not(../../ncs:module) or ../../ncs:module[ncs:name='Cisco-IOS-XR-crypto-act']";
      tailf:action key-zeroize-authentication-rsa {
        tailf:actionpoint ncsproxy {
          tailf:internal;
        }
        description
          "Remove RSA authentication key";
      }
    }
  }
  augment "/ncs:devices/ncs:device-group/ncs:ned-id/ncs:rpc" {
    container rpc-key-zeroize-authentication-rsa {
      tailf:ncs-device-type "netconf";
      tailf:display-when "/ncs:devices/ncs:device[ncs:name=current()/../../../ncs:member]/ncs:module[ncs:name='Cisco-IOS-XR-crypto-act']";
      tailf:action key-zeroize-authentication-rsa {
        tailf:actionpoint ncsproxy {
          tailf:internal;
        }
        description
          "Remove RSA authentication key";
      }
    }
  }
  augment "/ncs:devices/ncs:device/ncs:rpc" {
    container rpc-key-zeroize-ecdsa {
      tailf:ncs-device-type "netconf";
      tailf:display-when "not(../../ncs:module) or ../../ncs:module[ncs:name='Cisco-IOS-XR-crypto-act']";
      tailf:action key-zeroize-ecdsa {
        tailf:actionpoint ncsproxy {
          tailf:internal;
        }
        description
          "Remove ECDSA key of curve type nistp256 | nistp384 | nistp521";
        input {
          leaf key-modulus {
            type enumeration {
              enum "nistp256" {
                value 0;
                description
                  "nistp256";
              }
              enum "nistp384" {
                value 1;
                description
                  "nistp384";
              }
              enum "nistp521" {
                value 2;
                description
                  "nistp521";
              }
            }
            mandatory true;
            description
              "Key modulus";
          }
          leaf key-label {
            type string;
            description
              "ECDSA key label";
          }
        }
      }
    }
  }
  augment "/ncs:devices/ncs:device-group/ncs:ned-id/ncs:rpc" {
    container rpc-key-zeroize-ecdsa {
      tailf:ncs-device-type "netconf";
      tailf:display-when "/ncs:devices/ncs:device[ncs:name=current()/../../../ncs:member]/ncs:module[ncs:name='Cisco-IOS-XR-crypto-act']";
      tailf:action key-zeroize-ecdsa {
        tailf:actionpoint ncsproxy {
          tailf:internal;
        }
        description
          "Remove ECDSA key of curve type nistp256 | nistp384 | nistp521";
        input {
          leaf key-modulus {
            type enumeration {
              enum "nistp256" {
                value 0;
                description
                  "nistp256";
              }
              enum "nistp384" {
                value 1;
                description
                  "nistp384";
              }
              enum "nistp521" {
                value 2;
                description
                  "nistp521";
              }
            }
            mandatory true;
            description
              "Key modulus";
          }
          leaf key-label {
            type string;
            description
              "ECDSA key label";
          }
        }
      }
    }
  }
  augment "/ncs:devices/ncs:device/ncs:rpc" {
    container rpc-key-zeroize-dsa {
      tailf:ncs-device-type "netconf";
      tailf:display-when "not(../../ncs:module) or ../../ncs:module[ncs:name='Cisco-IOS-XR-crypto-act']";
      tailf:action key-zeroize-dsa {
        tailf:actionpoint ncsproxy {
          tailf:internal;
        }
        description
          "Remove DSA keys";
      }
    }
  }
  augment "/ncs:devices/ncs:device-group/ncs:ned-id/ncs:rpc" {
    container rpc-key-zeroize-dsa {
      tailf:ncs-device-type "netconf";
      tailf:display-when "/ncs:devices/ncs:device[ncs:name=current()/../../../ncs:member]/ncs:module[ncs:name='Cisco-IOS-XR-crypto-act']";
      tailf:action key-zeroize-dsa {
        tailf:actionpoint ncsproxy {
          tailf:internal;
        }
        description
          "Remove DSA keys";
      }
    }
  }
  augment "/ncs:devices/ncs:device/ncs:rpc" {
    container rpc-key-zeroize-rsa {
      tailf:ncs-device-type "netconf";
      tailf:display-when "not(../../ncs:module) or ../../ncs:module[ncs:name='Cisco-IOS-XR-crypto-act']";
      tailf:action key-zeroize-rsa {
        tailf:actionpoint ncsproxy {
          tailf:internal;
        }
        description
          "Remove RSA keys";
        input {
          leaf key-label {
            type string;
            description
              "RSA key label";
          }
        }
      }
    }
  }
  augment "/ncs:devices/ncs:device-group/ncs:ned-id/ncs:rpc" {
    container rpc-key-zeroize-rsa {
      tailf:ncs-device-type "netconf";
      tailf:display-when "/ncs:devices/ncs:device[ncs:name=current()/../../../ncs:member]/ncs:module[ncs:name='Cisco-IOS-XR-crypto-act']";
      tailf:action key-zeroize-rsa {
        tailf:actionpoint ncsproxy {
          tailf:internal;
        }
        description
          "Remove RSA keys";
        input {
          leaf key-label {
            type string;
            description
              "RSA key label";
          }
        }
      }
    }
  }
  augment "/ncs:devices/ncs:device/ncs:rpc" {
    container rpc-key-generate-ed25519 {
      tailf:ncs-device-type "netconf";
      tailf:display-when "not(../../ncs:module) or ../../ncs:module[ncs:name='Cisco-IOS-XR-crypto-act']";
      tailf:action key-generate-ed25519 {
        tailf:actionpoint ncsproxy {
          tailf:internal;
        }
        description
          "Generate a Ed25519 key-pair";
        input {
          leaf key-label {
            type string;
            description
              "Ed25519 key label";
          }
        }
      }
    }
  }
  augment "/ncs:devices/ncs:device-group/ncs:ned-id/ncs:rpc" {
    container rpc-key-generate-ed25519 {
      tailf:ncs-device-type "netconf";
      tailf:display-when "/ncs:devices/ncs:device[ncs:name=current()/../../../ncs:member]/ncs:module[ncs:name='Cisco-IOS-XR-crypto-act']";
      tailf:action key-generate-ed25519 {
        tailf:actionpoint ncsproxy {
          tailf:internal;
        }
        description
          "Generate a Ed25519 key-pair";
        input {
          leaf key-label {
            type string;
            description
              "Ed25519 key label";
          }
        }
      }
    }
  }
  augment "/ncs:devices/ncs:device/ncs:rpc" {
    container rpc-key-generate-ecdsa {
      tailf:ncs-device-type "netconf";
      tailf:display-when "not(../../ncs:module) or ../../ncs:module[ncs:name='Cisco-IOS-XR-crypto-act']";
      tailf:action key-generate-ecdsa {
        tailf:actionpoint ncsproxy {
          tailf:internal;
        }
        description
          "Generate a ECDSA key of curve type nistp256 | nistp384 | nistp521";
        input {
          leaf key-modulus {
            type enumeration {
              enum "nistp256" {
                value 0;
                description
                  "nistp256";
              }
              enum "nistp384" {
                value 1;
                description
                  "nistp384";
              }
              enum "nistp521" {
                value 2;
                description
                  "nistp521";
              }
            }
            mandatory true;
            description
              "Key modulus";
          }
          leaf key-label {
            type string;
            description
              "ECDSA key label";
          }
        }
      }
    }
  }
  augment "/ncs:devices/ncs:device-group/ncs:ned-id/ncs:rpc" {
    container rpc-key-generate-ecdsa {
      tailf:ncs-device-type "netconf";
      tailf:display-when "/ncs:devices/ncs:device[ncs:name=current()/../../../ncs:member]/ncs:module[ncs:name='Cisco-IOS-XR-crypto-act']";
      tailf:action key-generate-ecdsa {
        tailf:actionpoint ncsproxy {
          tailf:internal;
        }
        description
          "Generate a ECDSA key of curve type nistp256 | nistp384 | nistp521";
        input {
          leaf key-modulus {
            type enumeration {
              enum "nistp256" {
                value 0;
                description
                  "nistp256";
              }
              enum "nistp384" {
                value 1;
                description
                  "nistp384";
              }
              enum "nistp521" {
                value 2;
                description
                  "nistp521";
              }
            }
            mandatory true;
            description
              "Key modulus";
          }
          leaf key-label {
            type string;
            description
              "ECDSA key label";
          }
        }
      }
    }
  }
  augment "/ncs:devices/ncs:device/ncs:rpc" {
    container rpc-key-generate-dsa {
      tailf:ncs-device-type "netconf";
      tailf:display-when "not(../../ncs:module) or ../../ncs:module[ncs:name='Cisco-IOS-XR-crypto-act']";
      tailf:action key-generate-dsa {
        tailf:actionpoint ncsproxy {
          tailf:internal;
        }
        description
          "Generate DSA keys";
        input {
          leaf key-modulus {
            type int32 {
              range "512|768|1024";
            }
            mandatory true;
            description
              "Key modulus size can be 512, 768 or 1024 bits.";
          }
        }
      }
    }
  }
  augment "/ncs:devices/ncs:device-group/ncs:ned-id/ncs:rpc" {
    container rpc-key-generate-dsa {
      tailf:ncs-device-type "netconf";
      tailf:display-when "/ncs:devices/ncs:device[ncs:name=current()/../../../ncs:member]/ncs:module[ncs:name='Cisco-IOS-XR-crypto-act']";
      tailf:action key-generate-dsa {
        tailf:actionpoint ncsproxy {
          tailf:internal;
        }
        description
          "Generate DSA keys";
        input {
          leaf key-modulus {
            type int32 {
              range "512|768|1024";
            }
            mandatory true;
            description
              "Key modulus size can be 512, 768 or 1024 bits.";
          }
        }
      }
    }
  }
  augment "/ncs:devices/ncs:device/ncs:rpc" {
    container rpc-key-generate-rsa {
      tailf:ncs-device-type "netconf";
      tailf:display-when "not(../../ncs:module) or ../../ncs:module[ncs:name='Cisco-IOS-XR-crypto-act']";
      tailf:action key-generate-rsa {
        tailf:actionpoint ncsproxy {
          tailf:internal;
        }
        description
          "Generate seperate RSA key pairs for signing and encryption";
        input {
          uses ncs_rpc_notif_KEY-MODULUS;
        }
      }
    }
  }
  augment "/ncs:devices/ncs:device-group/ncs:ned-id/ncs:rpc" {
    container rpc-key-generate-rsa {
      tailf:ncs-device-type "netconf";
      tailf:display-when "/ncs:devices/ncs:device[ncs:name=current()/../../../ncs:member]/ncs:module[ncs:name='Cisco-IOS-XR-crypto-act']";
      tailf:action key-generate-rsa {
        tailf:actionpoint ncsproxy {
          tailf:internal;
        }
        description
          "Generate seperate RSA key pairs for signing and encryption";
        input {
          uses ncs_rpc_notif_KEY-MODULUS;
        }
      }
    }
  }
  augment "/ncs:devices/ncs:device/ncs:rpc" {
    container rpc-key-generate-rsa-usage-keys {
      tailf:ncs-device-type "netconf";
      tailf:display-when "not(../../ncs:module) or ../../ncs:module[ncs:name='Cisco-IOS-XR-crypto-act']";
      tailf:action key-generate-rsa-usage-keys {
        tailf:actionpoint ncsproxy {
          tailf:internal;
        }
        description
          "Generate seperate RSA key pairs for signing and encryption";
        input {
          uses ncs_rpc_notif_KEY-MODULUS;
        }
      }
    }
  }
  augment "/ncs:devices/ncs:device-group/ncs:ned-id/ncs:rpc" {
    container rpc-key-generate-rsa-usage-keys {
      tailf:ncs-device-type "netconf";
      tailf:display-when "/ncs:devices/ncs:device[ncs:name=current()/../../../ncs:member]/ncs:module[ncs:name='Cisco-IOS-XR-crypto-act']";
      tailf:action key-generate-rsa-usage-keys {
        tailf:actionpoint ncsproxy {
          tailf:internal;
        }
        description
          "Generate seperate RSA key pairs for signing and encryption";
        input {
          uses ncs_rpc_notif_KEY-MODULUS;
        }
      }
    }
  }
  augment "/ncs:devices/ncs:device/ncs:rpc" {
    container rpc-key-generate-rsa-general-keys {
      tailf:ncs-device-type "netconf";
      tailf:display-when "not(../../ncs:module) or ../../ncs:module[ncs:name='Cisco-IOS-XR-crypto-act']";
      tailf:action key-generate-rsa-general-keys {
        tailf:actionpoint ncsproxy {
          tailf:internal;
        }
        description
          "Generate a general purpose RSA key pair for signing and encryption";
        input {
          uses ncs_rpc_notif_KEY-MODULUS;
        }
      }
    }
  }
  augment "/ncs:devices/ncs:device-group/ncs:ned-id/ncs:rpc" {
    container rpc-key-generate-rsa-general-keys {
      tailf:ncs-device-type "netconf";
      tailf:display-when "/ncs:devices/ncs:device[ncs:name=current()/../../../ncs:member]/ncs:module[ncs:name='Cisco-IOS-XR-crypto-act']";
      tailf:action key-generate-rsa-general-keys {
        tailf:actionpoint ncsproxy {
          tailf:internal;
        }
        description
          "Generate a general purpose RSA key pair for signing and encryption";
        input {
          uses ncs_rpc_notif_KEY-MODULUS;
        }
      }
    }
  }
}

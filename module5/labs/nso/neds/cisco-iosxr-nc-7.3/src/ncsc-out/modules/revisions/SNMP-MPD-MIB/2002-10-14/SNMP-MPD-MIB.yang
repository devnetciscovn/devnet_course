module SNMP-MPD-MIB {
  // Generated by yanger -t ncs
  tailf:mount-id "cisco-iosxr-nc-7.3:cisco-iosxr-nc-7.3";
  tailf:ncs-device-type "netconf";

  namespace "http://tail-f.com/ns/mibs/SNMP-MPD-MIB/200210140000Z";
  prefix SNMP_MPD_MIB;

  import ietf-yang-types {
    prefix yang;
  }
  import tailf-common {
    prefix tailf;
  }
  import tailf-ncs {
    prefix ncs;
  }

  revision 2002-10-14 {
    description
      "";
  }

  augment "/ncs:devices/ncs:device/ncs:config" {
    // NCS drop config false container 'SNMP-MPD-MIB'
  }
  augment "/ncs:devices/ncs:device/ncs:live-status" {
    container SNMP-MPD-MIB {
      tailf:ncs-device-type "netconf";
      tailf:display-when "not(../../ncs:module) or ../../ncs:module[ncs:name='SNMP-MPD-MIB'] or (../../ncs:live-status-protocol[not(ncs:capability)]) or (../../ncs:live-status-protocol/ncs:capability/ncs:module[.='SNMP-MPD-MIB'])";
      container snmpMPDStats {
        leaf snmpUnknownSecurityModels {
          type yang:counter32;
        }
        leaf snmpInvalidMsgs {
          type yang:counter32;
        }
        leaf snmpUnknownPDUHandlers {
          type yang:counter32;
        }
      }
    }
  }
  augment "/ncs:devices/ncs:template/ncs:ned-id/ncs:config" {
    // NCS drop config false container 'SNMP-MPD-MIB'
  }
}

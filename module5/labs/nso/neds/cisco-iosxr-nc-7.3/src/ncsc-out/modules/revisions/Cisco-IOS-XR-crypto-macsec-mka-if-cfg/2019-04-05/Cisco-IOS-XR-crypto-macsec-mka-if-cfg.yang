module Cisco-IOS-XR-crypto-macsec-mka-if-cfg {
  // Generated by yanger -t ncs
  tailf:mount-id "cisco-iosxr-nc-7.3:cisco-iosxr-nc-7.3";
  tailf:ncs-device-type "netconf";

  namespace "http://cisco.com/ns/yang/Cisco-IOS-XR-crypto-macsec-mka-if-cfg";
  prefix crypto-macsec-mka-if-cfg;

  import Cisco-IOS-XR-types {
    prefix xr;
  }
  import cisco-semver {
    prefix semver;
  }
  import Cisco-IOS-XR-ifmgr-cfg {
    prefix a1;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-macsec-mka-if package configuration.

     This YANG module augments the
       Cisco-IOS-XR-ifmgr-cfg
     module with configuration data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Eap-list {
    type string;
    description
      "eap: eap config";
  }

  typedef ncs_rpc_notif_Eap-list {
    type string {
      pattern '(eap)';
    }
    description
      "eap: eap config";
  }

  typedef live_ncs_Eap-list {
    type string {
      pattern '(eap)';
    }
    description
      "eap: eap config";
  }

  typedef Eap-list {
    type string {
      pattern '(eap)';
    }
    description
      "eap: eap config";
  }

  augment "/ncs:devices/ncs:template/ncs:ned-id/ncs:config/a1:interface-configurations/a1:interface-configuration" {
    description
      "This augment extends the configuration data of
       'Cisco-IOS-XR-ifmgr-cfg'";
    container macsec {
      description
        "MACSec service for an interface";
      container macsec-service {
        presence "Indicates a macsec-service node is configured.";
        description
          "macsec-service configuration on interface";
        leaf decrypt-port {
          type xr:ncs_template_Interface-name;
          // NCS drop mandatory statement
          description
            "macsec service decryption port";
        }
        leaf key-chain {
          type string;
          // NCS drop mandatory statement
          description
            "name of keychain";
        }
        leaf policy {
          type string;
          description
            "name of policy";
        }
      }
      container eap {
        description
          "Enabling MACSec eap Configuration on Interface";
        leaf eap-config {
          type ncs_template_Eap-list;
          description
            "Eap config";
        }
        leaf policy-name {
          type xr:ncs_template_Cisco-ios-xr-string;
          description
            "Name of Policy";
        }
      }
      container psk-key-chain {
        presence "Indicates a psk-key-chain node is configured.";
        description
          "MACSec MKA Configuration on Interface";
        leaf key-chain-name {
          type xr:ncs_template_Cisco-ios-xr-string;
          // NCS drop mandatory statement
          description
            "Name of KeyChainName";
        }
        leaf policy-name {
          type xr:ncs_template_Cisco-ios-xr-string;
          description
            "Name of Policy";
        }
        leaf fallback-key-chain {
          type string;
          description
            "name of fallback keychain";
        }
      }
    }
  }
  augment "/ncs:devices/ncs:device/ncs:live-status/a1:interface-configurations/a1:interface-configuration" {
    description
      "This augment extends the configuration data of
       'Cisco-IOS-XR-ifmgr-cfg'";
    container macsec {
      tailf:ncs-device-type "netconf";
      tailf:display-when "not(../../../../ncs:module) or ../../../../ncs:module[ncs:name='Cisco-IOS-XR-crypto-macsec-mka-if-cfg'] or (../../../../ncs:live-status-protocol[not(ncs:capability)]) or (../../../../ncs:live-status-protocol/ncs:capability/ncs:module[.='Cisco-IOS-XR-crypto-macsec-mka-if-cfg'])";
      description
        "MACSec service for an interface";
      container macsec-service {
        presence "Indicates a macsec-service node is configured.";
        description
          "macsec-service configuration on interface";
        leaf decrypt-port {
          type xr:live_ncs_Interface-name;
          // NCS drop mandatory statement
          description
            "macsec service decryption port";
        }
        leaf key-chain {
          type string {
            length "1..32";
          }
          // NCS drop mandatory statement
          description
            "name of keychain";
        }
        leaf policy {
          type string {
            length "1..16";
          }
          description
            "name of policy";
        }
      }
      container eap {
        description
          "Enabling MACSec eap Configuration on Interface";
        leaf eap-config {
          type live_ncs_Eap-list;
          description
            "Eap config";
        }
        leaf policy-name {
          type xr:live_ncs_Cisco-ios-xr-string;
          description
            "Name of Policy";
        }
      }
      container psk-key-chain {
        presence "Indicates a psk-key-chain node is configured.";
        description
          "MACSec MKA Configuration on Interface";
        leaf key-chain-name {
          type xr:live_ncs_Cisco-ios-xr-string;
          // NCS drop mandatory statement
          description
            "Name of KeyChainName";
        }
        leaf policy-name {
          type xr:live_ncs_Cisco-ios-xr-string;
          description
            "Name of Policy";
        }
        leaf fallback-key-chain {
          type string {
            length "1..32";
          }
          description
            "name of fallback keychain";
        }
      }
    }
  }
  augment "/ncs:devices/ncs:device/ncs:config/a1:interface-configurations/a1:interface-configuration" {
    description
      "This augment extends the configuration data of
       'Cisco-IOS-XR-ifmgr-cfg'";
    container macsec {
      tailf:ncs-device-type "netconf";
      tailf:display-when "not(../../../../ncs:module) or ../../../../ncs:module[ncs:name='Cisco-IOS-XR-crypto-macsec-mka-if-cfg']";
      description
        "MACSec service for an interface";
      container macsec-service {
        presence "Indicates a macsec-service node is configured.";
        description
          "macsec-service configuration on interface";
        leaf decrypt-port {
          type xr:Interface-name;
          mandatory true;
          description
            "macsec service decryption port";
        }
        leaf key-chain {
          type string {
            length "1..32";
          }
          mandatory true;
          description
            "name of keychain";
        }
        leaf policy {
          type string {
            length "1..16";
          }
          description
            "name of policy";
        }
      }
      container eap {
        description
          "Enabling MACSec eap Configuration on Interface";
        leaf eap-config {
          type Eap-list;
          description
            "Eap config";
        }
        leaf policy-name {
          type xr:Cisco-ios-xr-string {
            length "1..16";
          }
          description
            "Name of Policy";
        }
      }
      container psk-key-chain {
        presence "Indicates a psk-key-chain node is configured.";
        description
          "MACSec MKA Configuration on Interface";
        leaf key-chain-name {
          type xr:Cisco-ios-xr-string {
            length "1..32";
          }
          mandatory true;
          description
            "Name of KeyChainName";
        }
        leaf policy-name {
          type xr:Cisco-ios-xr-string {
            length "1..16";
          }
          description
            "Name of Policy";
        }
        leaf fallback-key-chain {
          type string {
            length "1..32";
          }
          description
            "name of fallback keychain";
        }
      }
    }
  }
}

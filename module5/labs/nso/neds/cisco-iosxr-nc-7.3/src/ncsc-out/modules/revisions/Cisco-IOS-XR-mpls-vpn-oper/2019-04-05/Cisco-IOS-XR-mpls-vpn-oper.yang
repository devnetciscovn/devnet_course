module Cisco-IOS-XR-mpls-vpn-oper {
  // Generated by yanger -t ncs
  tailf:mount-id "cisco-iosxr-nc-7.3:cisco-iosxr-nc-7.3";
  tailf:ncs-device-type "netconf";

  namespace "http://cisco.com/ns/yang/Cisco-IOS-XR-mpls-vpn-oper";
  prefix mpls-vpn-oper;

  import cisco-semver {
    prefix semver;
  }
  include Cisco-IOS-XR-mpls-vpn-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-vpn package operational data.

     This module contains definitions
     for the following management objects:
       l3vpn: L3VPN operational data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container l3vpn
  }
  augment "/ncs:devices/ncs:device/ncs:live-status" {
    container l3vpn {
      tailf:ncs-device-type "netconf";
      tailf:display-when "not(../../ncs:module) or ../../ncs:module[ncs:name='Cisco-IOS-XR-mpls-vpn-oper'] or (../../ncs:live-status-protocol[not(ncs:capability)]) or (../../ncs:live-status-protocol/ncs:capability/ncs:module[.='Cisco-IOS-XR-mpls-vpn-oper'])";
      description
        "L3VPN operational data";
      container invalid-vrfs {
        description
          "Invalid VRF Table (VRFs that are forward
           referenced)";
        list invalid-vrf {
          key "vrf-name";
          description
            "Invalid VRF (VRF that is forward referenced)";
          leaf vrf-name {
            type string {
              length "1..33";
            }
            description
              "Name of the referenced VRF which is invalid";
          }
          uses live_ncs_MPLS-VPN-VRF;
        }
      }
      container vrfs {
        description
          "VRF Table";
        list vrf {
          key "vrf-name";
          description
            "VRF";
          leaf vrf-name {
            type string {
              length "1..33";
            }
            description
              "Name of the referenced VRF";
          }
          uses live_ncs_MPLS-VPN-VRF;
        }
      }
    }
  }
  augment "/ncs:devices/ncs:template/ncs:ned-id/ncs:config" {
    // NCS drop config false container l3vpn
  }
}

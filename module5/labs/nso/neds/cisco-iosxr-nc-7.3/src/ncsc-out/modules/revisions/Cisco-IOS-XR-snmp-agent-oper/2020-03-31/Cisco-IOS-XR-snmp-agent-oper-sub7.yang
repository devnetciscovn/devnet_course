submodule Cisco-IOS-XR-snmp-agent-oper-sub7 {
  // Generated by yanger -t ncs
  tailf:mount-id "cisco-iosxr-nc-7.3:cisco-iosxr-nc-7.3";

  belongs-to Cisco-IOS-XR-snmp-agent-oper {
    prefix Cisco-IOS-XR-snmp-agent-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR snmp-agent package operational data.

     Copyright (c) 2013-2020 by Cisco Systems, Inc.
     All rights reserved.";

  revision 2020-03-31 {
    description
      "Fixing backward compatibility error in module.";
    semver:module-version "1.1.0";
  }
  revision 2019-04-05 {
    description
      "Establish semantic version baseline.";
    semver:module-version "1.0.1";
  }
  revision 2018-07-20 {
    description
      "Fixed English plural name transformation error.";
  }
  revision 2017-09-07 {
    description
      "Fixed type translation error.";
  }
  revision 2017-05-01 {
    description
      "Fixing backward compatibility error in module.";
  }
  revision 2016-06-01 {
    description
      "IOS XR 6.0.1 revision.";
  }
  revision 2015-01-07 {
    description
      "IOS XR 5.3.1 revision.";
  }

  grouping ncs_template_SNMP-TRAP-STATS {
    description
      "SNMP Trap statistics";
    leaf number-of-pkts-in-trap-q {
      type string;
      description
        "No. of trap packets in trapQ";
    }
    leaf max-q-length-of-trap-q {
      type string;
      description
        "Maximum Queue length of trapQ";
    }
    leaf number-of-pkts-sent {
      type string;
      description
        "No. of trap packets sent";
    }
    leaf number-of-pkts-dropped {
      type string;
      description
        "No. of trap packets dropped";
    }
  }

  grouping ncs_rpc_notif_SNMP-TRAP-STATS {
    description
      "SNMP Trap statistics";
    leaf number-of-pkts-in-trap-q {
      type uint32;
      description
        "No. of trap packets in trapQ";
    }
    leaf max-q-length-of-trap-q {
      type uint32;
      description
        "Maximum Queue length of trapQ";
    }
    leaf number-of-pkts-sent {
      type uint32;
      description
        "No. of trap packets sent";
    }
    leaf number-of-pkts-dropped {
      type uint32;
      description
        "No. of trap packets dropped";
    }
  }

  grouping live_ncs_SNMP-TRAP-STATS {
    description
      "SNMP Trap statistics";
    leaf number-of-pkts-in-trap-q {
      type uint32;
      description
        "No. of trap packets in trapQ";
    }
    leaf max-q-length-of-trap-q {
      type uint32;
      description
        "Maximum Queue length of trapQ";
    }
    leaf number-of-pkts-sent {
      type uint32;
      description
        "No. of trap packets sent";
    }
    leaf number-of-pkts-dropped {
      type uint32;
      description
        "No. of trap packets dropped";
    }
  }

  grouping SNMP-TRAP-STATS {
    description
      "SNMP Trap statistics";
    leaf number-of-pkts-in-trap-q {
      type uint32;
      description
        "No. of trap packets in trapQ";
    }
    leaf max-q-length-of-trap-q {
      type uint32;
      description
        "Maximum Queue length of trapQ";
    }
    leaf number-of-pkts-sent {
      type uint32;
      description
        "No. of trap packets sent";
    }
    leaf number-of-pkts-dropped {
      type uint32;
      description
        "No. of trap packets dropped";
    }
  }
}

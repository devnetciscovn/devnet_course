submodule Cisco-IOS-XR-mirror-oper-sub1 {
  // Generated by yanger -t ncs
  tailf:mount-id "cisco-iosxr-nc-7.3:cisco-iosxr-nc-7.3";

  belongs-to Cisco-IOS-XR-mirror-oper {
    prefix Cisco-IOS-XR-mirror-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mirror package operational data.

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef ncs_template_Change-bag-reason {
    type string;
    description
      "ChangeReason";
  }

  typedef ncs_template_File-bag {
    type string;
    description
      "ItemType";
  }

  typedef ncs_template_Update-bag {
    type string;
    description
      "Update";
  }

  typedef ncs_template_Mirror-bag-state {
    type string;
    description
      "MirrorState";
  }

  typedef ncs_rpc_notif_Change-bag-reason {
    type enumeration {
      enum "checksum" {
        description
          "Checksum";
      }
      enum "size" {
        description
          "Size";
      }
      enum "mod-time" {
        description
          "Modification time";
      }
      enum "permissions" {
        description
          "Permissions changed";
      }
      enum "owner" {
        description
          "Owner changed";
      }
      enum "group" {
        description
          "Group changed";
      }
      enum "reserved" {
        description
          "<reserved>";
      }
      enum "acl" {
        description
          "ACL changed";
      }
      enum "xattr" {
        description
          "Extended attributes changed";
      }
      enum "none" {
        description
          "Unknown or no mismatch. When UT_UNKNOWN or
           UT_NONE.";
      }
      enum "sub-item" {
        description
          "Sub item of this dir has a change";
      }
      enum "new-item" {
        description
          "This item is newly created";
      }
    }
    description
      "ChangeReason";
  }

  typedef ncs_rpc_notif_File-bag {
    type enumeration {
      enum "file" {
        description
          "File";
      }
      enum "directory" {
        description
          "Directory";
      }
      enum "symlink" {
        description
          "Symlink";
      }
      enum "device" {
        description
          "Device";
      }
      enum "special" {
        description
          "Special";
      }
      enum "unknown" {
        description
          "<unknown>";
      }
    }
    description
      "ItemType";
  }

  typedef ncs_rpc_notif_Update-bag {
    type enumeration {
      enum "send" {
        description
          "Send changes to standby";
      }
      enum "recv" {
        description
          "Receive changes from standby";
      }
      enum "create" {
        description
          "Create on standby";
      }
      enum "hardlink" {
        description
          "Hardlink";
      }
      enum "unknown" {
        description
          "Unexpected reason, use update_msg field";
      }
      enum "none" {
        description
          "In sync on both active and standby";
      }
      enum "delete" {
        description
          "Delete on standby";
      }
      enum "sub-item" {
        description
          "Sub item of this dir needs a change";
      }
    }
    description
      "Update";
  }

  typedef ncs_rpc_notif_Mirror-bag-state {
    type enumeration {
      enum "no" {
        description
          "Not mirrored, and no sync in progress";
      }
      enum "yes" {
        description
          "Mirrored";
      }
      enum "in-progress" {
        description
          "Not mirrored, but sync in progress";
      }
    }
    description
      "MirrorState";
  }

  typedef live_ncs_Change-bag-reason {
    type enumeration {
      enum "checksum" {
        description
          "Checksum";
      }
      enum "size" {
        description
          "Size";
      }
      enum "mod-time" {
        description
          "Modification time";
      }
      enum "permissions" {
        description
          "Permissions changed";
      }
      enum "owner" {
        description
          "Owner changed";
      }
      enum "group" {
        description
          "Group changed";
      }
      enum "reserved" {
        description
          "<reserved>";
      }
      enum "acl" {
        description
          "ACL changed";
      }
      enum "xattr" {
        description
          "Extended attributes changed";
      }
      enum "none" {
        description
          "Unknown or no mismatch. When UT_UNKNOWN or
           UT_NONE.";
      }
      enum "sub-item" {
        description
          "Sub item of this dir has a change";
      }
      enum "new-item" {
        description
          "This item is newly created";
      }
    }
    description
      "ChangeReason";
  }

  typedef live_ncs_File-bag {
    type enumeration {
      enum "file" {
        description
          "File";
      }
      enum "directory" {
        description
          "Directory";
      }
      enum "symlink" {
        description
          "Symlink";
      }
      enum "device" {
        description
          "Device";
      }
      enum "special" {
        description
          "Special";
      }
      enum "unknown" {
        description
          "<unknown>";
      }
    }
    description
      "ItemType";
  }

  typedef live_ncs_Update-bag {
    type enumeration {
      enum "send" {
        description
          "Send changes to standby";
      }
      enum "recv" {
        description
          "Receive changes from standby";
      }
      enum "create" {
        description
          "Create on standby";
      }
      enum "hardlink" {
        description
          "Hardlink";
      }
      enum "unknown" {
        description
          "Unexpected reason, use update_msg field";
      }
      enum "none" {
        description
          "In sync on both active and standby";
      }
      enum "delete" {
        description
          "Delete on standby";
      }
      enum "sub-item" {
        description
          "Sub item of this dir needs a change";
      }
    }
    description
      "Update";
  }

  typedef live_ncs_Mirror-bag-state {
    type enumeration {
      enum "no" {
        description
          "Not mirrored, and no sync in progress";
      }
      enum "yes" {
        description
          "Mirrored";
      }
      enum "in-progress" {
        description
          "Not mirrored, but sync in progress";
      }
    }
    description
      "MirrorState";
  }

  typedef Change-bag-reason {
    type enumeration {
      enum "checksum" {
        description
          "Checksum";
      }
      enum "size" {
        description
          "Size";
      }
      enum "mod-time" {
        description
          "Modification time";
      }
      enum "permissions" {
        description
          "Permissions changed";
      }
      enum "owner" {
        description
          "Owner changed";
      }
      enum "group" {
        description
          "Group changed";
      }
      enum "reserved" {
        description
          "<reserved>";
      }
      enum "acl" {
        description
          "ACL changed";
      }
      enum "xattr" {
        description
          "Extended attributes changed";
      }
      enum "none" {
        description
          "Unknown or no mismatch. When UT_UNKNOWN or
           UT_NONE.";
      }
      enum "sub-item" {
        description
          "Sub item of this dir has a change";
      }
      enum "new-item" {
        description
          "This item is newly created";
      }
    }
    description
      "ChangeReason";
  }

  typedef File-bag {
    type enumeration {
      enum "file" {
        description
          "File";
      }
      enum "directory" {
        description
          "Directory";
      }
      enum "symlink" {
        description
          "Symlink";
      }
      enum "device" {
        description
          "Device";
      }
      enum "special" {
        description
          "Special";
      }
      enum "unknown" {
        description
          "<unknown>";
      }
    }
    description
      "ItemType";
  }

  typedef Update-bag {
    type enumeration {
      enum "send" {
        description
          "Send changes to standby";
      }
      enum "recv" {
        description
          "Receive changes from standby";
      }
      enum "create" {
        description
          "Create on standby";
      }
      enum "hardlink" {
        description
          "Hardlink";
      }
      enum "unknown" {
        description
          "Unexpected reason, use update_msg field";
      }
      enum "none" {
        description
          "In sync on both active and standby";
      }
      enum "delete" {
        description
          "Delete on standby";
      }
      enum "sub-item" {
        description
          "Sub item of this dir needs a change";
      }
    }
    description
      "Update";
  }

  typedef Mirror-bag-state {
    type enumeration {
      enum "no" {
        description
          "Not mirrored, and no sync in progress";
      }
      enum "yes" {
        description
          "Mirrored";
      }
      enum "in-progress" {
        description
          "Not mirrored, but sync in progress";
      }
    }
    description
      "MirrorState";
  }

  grouping ncs_template_MIRROR-FILE-ENTRY {
    description
      "One item in the mirror dir";
    leaf path-xr {
      type string;
      description
        "Path item";
    }
    leaf state {
      type ncs_template_Mirror-bag-state;
      description
        "What sync state item is in";
    }
    leaf update {
      type ncs_template_Update-bag;
      description
        "What update should be done";
    }
    leaf update-msg {
      type string;
      description
        "In case of unknown update";
    }
    leaf type {
      type ncs_template_File-bag;
      description
        "Item type";
    }
    leaf reason {
      type ncs_template_Change-bag-reason;
      description
        "Reason for mismatch";
    }
    leaf checksum {
      type string;
      description
        "MD5 checksum for mirrored files";
    }
    leaf mod-time {
      type string;
      description
        "Mod time for mirrored files";
    }
  }

  grouping ncs_template_MIRROR-SYNC-ENTRY {
    description
      "One sync dir status";
    leaf directory-xr {
      type string;
      description
        "Directory being synced";
    }
    leaf sync-in-progress {
      type string;
      description
        "True if sync is in progress";
    }
    leaf start-time {
      type string;
      description
        "Unix Epoch of when sync started";
    }
    leaf scan-error {
      type string;
      description
        "Empty if no error, else the dir scanning error
         which prevents mirroring on this dir";
    }
    leaf standby-up {
      type string;
      description
        "If false, standby is not syncable";
    }
  }

  grouping ncs_rpc_notif_MIRROR-FILE-ENTRY {
    description
      "One item in the mirror dir";
    leaf path-xr {
      type string;
      description
        "Path item";
    }
    leaf state {
      type ncs_rpc_notif_Mirror-bag-state;
      description
        "What sync state item is in";
    }
    leaf update {
      type ncs_rpc_notif_Update-bag;
      description
        "What update should be done";
    }
    leaf update-msg {
      type string;
      description
        "In case of unknown update";
    }
    leaf type {
      type ncs_rpc_notif_File-bag;
      description
        "Item type";
    }
    leaf reason {
      type ncs_rpc_notif_Change-bag-reason;
      description
        "Reason for mismatch";
    }
    leaf checksum {
      type string;
      description
        "MD5 checksum for mirrored files";
    }
    leaf mod-time {
      type uint64;
      description
        "Mod time for mirrored files";
    }
  }

  grouping ncs_rpc_notif_MIRROR-SYNC-ENTRY {
    description
      "One sync dir status";
    leaf directory-xr {
      type string;
      description
        "Directory being synced";
    }
    leaf sync-in-progress {
      type boolean;
      description
        "True if sync is in progress";
    }
    leaf start-time {
      type uint64;
      description
        "Unix Epoch of when sync started";
    }
    leaf scan-error {
      type string;
      description
        "Empty if no error, else the dir scanning error
         which prevents mirroring on this dir";
    }
    leaf standby-up {
      type boolean;
      description
        "If false, standby is not syncable";
    }
  }

  grouping live_ncs_MIRROR-FILE-ENTRY {
    description
      "One item in the mirror dir";
    leaf path-xr {
      type string;
      description
        "Path item";
    }
    leaf state {
      type live_ncs_Mirror-bag-state;
      description
        "What sync state item is in";
    }
    leaf update {
      type live_ncs_Update-bag;
      description
        "What update should be done";
    }
    leaf update-msg {
      type string;
      description
        "In case of unknown update";
    }
    leaf type {
      type live_ncs_File-bag;
      description
        "Item type";
    }
    leaf reason {
      type live_ncs_Change-bag-reason;
      description
        "Reason for mismatch";
    }
    leaf checksum {
      type string;
      description
        "MD5 checksum for mirrored files";
    }
    leaf mod-time {
      type uint64;
      description
        "Mod time for mirrored files";
    }
  }

  grouping live_ncs_MIRROR-SYNC-ENTRY {
    description
      "One sync dir status";
    leaf directory-xr {
      type string;
      description
        "Directory being synced";
    }
    leaf sync-in-progress {
      type boolean;
      description
        "True if sync is in progress";
    }
    leaf start-time {
      type uint64;
      description
        "Unix Epoch of when sync started";
    }
    leaf scan-error {
      type string;
      description
        "Empty if no error, else the dir scanning error
         which prevents mirroring on this dir";
    }
    leaf standby-up {
      type boolean;
      description
        "If false, standby is not syncable";
    }
  }

  grouping MIRROR-FILE-ENTRY {
    description
      "One item in the mirror dir";
    leaf path-xr {
      type string;
      description
        "Path item";
    }
    leaf state {
      type Mirror-bag-state;
      description
        "What sync state item is in";
    }
    leaf update {
      type Update-bag;
      description
        "What update should be done";
    }
    leaf update-msg {
      type string;
      description
        "In case of unknown update";
    }
    leaf type {
      type File-bag;
      description
        "Item type";
    }
    leaf reason {
      type Change-bag-reason;
      description
        "Reason for mismatch";
    }
    leaf checksum {
      type string;
      description
        "MD5 checksum for mirrored files";
    }
    leaf mod-time {
      type uint64;
      description
        "Mod time for mirrored files";
    }
  }

  grouping MIRROR-SYNC-ENTRY {
    description
      "One sync dir status";
    leaf directory-xr {
      type string;
      description
        "Directory being synced";
    }
    leaf sync-in-progress {
      type boolean;
      description
        "True if sync is in progress";
    }
    leaf start-time {
      type uint64;
      description
        "Unix Epoch of when sync started";
    }
    leaf scan-error {
      type string;
      description
        "Empty if no error, else the dir scanning error
         which prevents mirroring on this dir";
    }
    leaf standby-up {
      type boolean;
      description
        "If false, standby is not syncable";
    }
  }
}

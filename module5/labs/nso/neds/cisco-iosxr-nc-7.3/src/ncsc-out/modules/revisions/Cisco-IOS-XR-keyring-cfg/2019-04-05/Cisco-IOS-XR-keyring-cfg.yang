module Cisco-IOS-XR-keyring-cfg {
  // Generated by yanger -t ncs
  tailf:mount-id "cisco-iosxr-nc-7.3:cisco-iosxr-nc-7.3";
  tailf:ncs-device-type "netconf";

  namespace "http://cisco.com/ns/yang/Cisco-IOS-XR-keyring-cfg";
  prefix keyring-cfg;

  import ietf-inet-types {
    prefix inet;
  }
  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR keyring package configuration.

     This module contains definitions
     for the following management objects:
       keyring: Keyring config commands

     Copyright (c) 2013-2019 by Cisco Systems, Inc.
     All rights reserved.";

  revision 2019-04-05 {
    description
      "Establish semantic version baseline.";
    semver:module-version "1.1.0";
  }
  revision 2019-02-04 {
    description
      "Keyring Configuration Yang Support";
  }
  revision 2015-11-09 {
    description
      "IOS XR 6.0 revision.";
  }

  typedef ncs_template_Keyring-encryption {
    type string;
    description
      "Keyring encryption";
  }

  typedef ncs_rpc_notif_Keyring-encryption {
    type enumeration {
      enum "type7" {
        value 1;
        description
          "Type 7 encryption";
      }
    }
    description
      "Keyring encryption";
  }

  typedef live_ncs_Keyring-encryption {
    type enumeration {
      enum "type7" {
        value 1;
        description
          "Type 7 encryption";
      }
    }
    description
      "Keyring encryption";
  }

  typedef Keyring-encryption {
    type enumeration {
      enum "type7" {
        value 1;
        description
          "Type 7 encryption";
      }
    }
    description
      "Keyring encryption";
  }

  augment "/ncs:devices/ncs:device/ncs:config" {
    container keyring {
      tailf:ncs-device-type "netconf";
      tailf:display-when "not(../../ncs:module) or ../../ncs:module[ncs:name='Cisco-IOS-XR-keyring-cfg']";
      description
        "Keyring config commands";
      list keyring-name {
        key "name";
        description
          "Keyring name";
        container peer-names {
          description
            "Keyring peer config commands";
          list peer-name {
            key "name";
            description
              "Keyring peer name";
            container address {
              presence "enable address";
              description
                "IP Address to identify the peer";
              leaf ip {
                type inet:ipv4-address-no-zone;
                description
                  "IP Address";
              }
              leaf subnet {
                type inet:ipv4-address-no-zone;
                description
                  "Subnet";
              }
            }
            container psk {
              description
                "Pre-shared key for peer";
              container local-remote-key {
                description
                  "Local/Remote pre-shared key for the peer";
                leaf local {
                  type xr:Proprietary-password;
                  description
                    "Local pre-shared key";
                }
                leaf remote {
                  type xr:Proprietary-password;
                  description
                    "Remote pre-shared key";
                }
                leaf encryption-type {
                  type Keyring-encryption;
                  default "type7";
                  description
                    "encryption type used to store key";
                }
              }
              container both-key {
                description
                  "Both pre-shared key for the peer";
                leaf string {
                  type xr:Proprietary-password;
                  description
                    "Both pre-shared key";
                }
                leaf encryption-type {
                  type Keyring-encryption;
                  default "type7";
                  description
                    "encryption type used to store key";
                }
              }
            }
            leaf peer-sub {
              type empty;
              mandatory true;
              description
                "This indicates existence of keyring-peer";
            }
            leaf name {
              type xr:Cisco-ios-xr-string {
                length "1..32";
              }
              description
                "Name of the keyring-peer";
            }
          }
        }
        leaf keyring-sub {
          type empty;
          mandatory true;
          description
            "This indicated existence of keyring";
        }
        leaf name {
          type xr:Cisco-ios-xr-string {
            length "1..32";
          }
          description
            "Name of the keyring";
        }
      }
    }
  }
  augment "/ncs:devices/ncs:device/ncs:live-status" {
    container keyring {
      tailf:ncs-device-type "netconf";
      tailf:display-when "not(../../ncs:module) or ../../ncs:module[ncs:name='Cisco-IOS-XR-keyring-cfg'] or (../../ncs:live-status-protocol[not(ncs:capability)]) or (../../ncs:live-status-protocol/ncs:capability/ncs:module[.='Cisco-IOS-XR-keyring-cfg'])";
      description
        "Keyring config commands";
      list keyring-name {
        key "name";
        description
          "Keyring name";
        container peer-names {
          description
            "Keyring peer config commands";
          list peer-name {
            key "name";
            description
              "Keyring peer name";
            container address {
              presence "enable address";
              description
                "IP Address to identify the peer";
              leaf ip {
                type inet:ipv4-address-no-zone;
                description
                  "IP Address";
              }
              leaf subnet {
                type inet:ipv4-address-no-zone;
                description
                  "Subnet";
              }
            }
            container psk {
              description
                "Pre-shared key for peer";
              container local-remote-key {
                description
                  "Local/Remote pre-shared key for the peer";
                leaf local {
                  type xr:live_ncs_Proprietary-password;
                  description
                    "Local pre-shared key";
                }
                leaf remote {
                  type xr:live_ncs_Proprietary-password;
                  description
                    "Remote pre-shared key";
                }
                leaf encryption-type {
                  type live_ncs_Keyring-encryption;
                  // NCS drop default statement
                  description
                    "encryption type used to store key";
                }
              }
              container both-key {
                description
                  "Both pre-shared key for the peer";
                leaf string {
                  type xr:live_ncs_Proprietary-password;
                  description
                    "Both pre-shared key";
                }
                leaf encryption-type {
                  type live_ncs_Keyring-encryption;
                  // NCS drop default statement
                  description
                    "encryption type used to store key";
                }
              }
            }
            leaf peer-sub {
              type empty;
              // NCS drop mandatory statement
              description
                "This indicates existence of keyring-peer";
            }
            leaf name {
              type xr:live_ncs_Cisco-ios-xr-string;
              description
                "Name of the keyring-peer";
            }
          }
        }
        leaf keyring-sub {
          type empty;
          // NCS drop mandatory statement
          description
            "This indicated existence of keyring";
        }
        leaf name {
          type xr:live_ncs_Cisco-ios-xr-string;
          description
            "Name of the keyring";
        }
      }
    }
  }
  augment "/ncs:devices/ncs:template/ncs:ned-id/ncs:config" {
    container keyring {
      description
        "Keyring config commands";
      list keyring-name {
        // NCS patched for predictable order
        ordered-by user;
        key "name";
        description
          "Keyring name";
        container peer-names {
          description
            "Keyring peer config commands";
          list peer-name {
            // NCS patched for predictable order
            ordered-by user;
            key "name";
            description
              "Keyring peer name";
            container address {
              presence "enable address";
              description
                "IP Address to identify the peer";
              leaf ip {
                type string;
                description
                  "IP Address";
              }
              leaf subnet {
                type string;
                description
                  "Subnet";
              }
            }
            container psk {
              description
                "Pre-shared key for peer";
              container local-remote-key {
                description
                  "Local/Remote pre-shared key for the peer";
                leaf local {
                  type xr:ncs_template_Proprietary-password;
                  description
                    "Local pre-shared key";
                }
                leaf remote {
                  type xr:ncs_template_Proprietary-password;
                  description
                    "Remote pre-shared key";
                }
                leaf encryption-type {
                  type ncs_template_Keyring-encryption;
                  // NCS drop default statement
                  description
                    "encryption type used to store key";
                }
              }
              container both-key {
                description
                  "Both pre-shared key for the peer";
                leaf string {
                  type xr:ncs_template_Proprietary-password;
                  description
                    "Both pre-shared key";
                }
                leaf encryption-type {
                  type ncs_template_Keyring-encryption;
                  // NCS drop default statement
                  description
                    "encryption type used to store key";
                }
              }
            }
            leaf peer-sub {
              type empty;
              // NCS drop mandatory statement
              description
                "This indicates existence of keyring-peer";
            }
            leaf name {
              type xr:ncs_template_Cisco-ios-xr-string;
              description
                "Name of the keyring-peer";
            }
          }
        }
        leaf keyring-sub {
          type empty;
          // NCS drop mandatory statement
          description
            "This indicated existence of keyring";
        }
        leaf name {
          type xr:ncs_template_Cisco-ios-xr-string;
          description
            "Name of the keyring";
        }
      }
    }
  }
}

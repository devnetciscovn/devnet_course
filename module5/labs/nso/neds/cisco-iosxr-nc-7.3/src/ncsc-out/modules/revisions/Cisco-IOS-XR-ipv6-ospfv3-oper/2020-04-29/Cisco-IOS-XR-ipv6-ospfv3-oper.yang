module Cisco-IOS-XR-ipv6-ospfv3-oper {
  // Generated by yanger -t ncs
  tailf:mount-id "cisco-iosxr-nc-7.3:cisco-iosxr-nc-7.3";
  tailf:ncs-device-type "netconf";

  namespace "http://cisco.com/ns/yang/Cisco-IOS-XR-ipv6-ospfv3-oper";
  prefix ipv6-ospfv3-oper;

  import ietf-inet-types {
    prefix inet;
  }
  import Cisco-IOS-XR-types {
    prefix xr;
  }
  import cisco-semver {
    prefix semver;
  }
  include Cisco-IOS-XR-ipv6-ospfv3-oper-sub1 {
    revision-date 2020-04-29;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv6-ospfv3 package operational data.

     This module contains definitions
     for the following management objects:
       ospfv3: OSPFv3 operational information

     Copyright (c) 2013-2020 by Cisco Systems, Inc.
     All rights reserved.";

  revision 2020-04-29 {
    description
      "Added mtu and Bandwidth to show command";
    semver:module-version "2.1.0";
  }
  revision 2020-02-04 {
    description
      "Modified for Conditional Advertising";
    semver:module-version "2.0.0";
  }
  revision 2019-07-28 {
    description
      "Added datalist operation for container fast-reroute topology";
    semver:module-version "1.1.0";
  }
  revision 2019-04-05 {
    description
      "Establish semantic version baseline.";
    semver:module-version "1.0.0";
  }
  revision 2019-01-08 {
    description
      "Modified for Programmability 2.0";
  }
  revision 2018-06-15 {
    description
      "Added Aggregate statistics under summary container";
  }
  revision 2017-10-30 {
    description
      "Added link information in grace LSA.";
  }
  revision 2017-09-07 {
    description
      "Fixed type translation error.";
  }
  revision 2015-11-09 {
    description
      "IOS XR 6.0 revision.";
  }

  typedef ncs_template_Ospfv3-lsa {
    type string;
    description
      "Ospfv3 lsa";
  }

  typedef ncs_rpc_notif_Ospfv3-lsa {
    type enumeration {
      enum "link-lsa" {
        value 8;
        description
          "Link LSA";
      }
      enum "grace-lsa" {
        value 11;
        description
          "Grace LSA";
      }
      enum "router" {
        value 8193;
        description
          "Router LSA";
      }
      enum "network" {
        value 8194;
        description
          "Network LSA";
      }
      enum "inter-area-prefix" {
        value 8195;
        description
          "Inter-Area Prefix LSA";
      }
      enum "inter-area-router" {
        value 8196;
        description
          "Inter-Area Router LSA";
      }
      enum "nssa-external" {
        value 8199;
        description
          "NSSA External LSA";
      }
      enum "intra-area-prefix" {
        value 8201;
        description
          "Intra-Area Prefix LSA";
      }
      enum "external" {
        value 16389;
        description
          "External LSA";
      }
      enum "opaque-link" {
        value 32768;
        description
          "Opaque LSALink Scope";
      }
      enum "opaque-area" {
        value 40960;
        description
          "Opaque LSA Area Scope";
      }
      enum "opaque-as" {
        value 49152;
        description
          "Opaque LSA AS Scope";
      }
      enum "unknown" {
        value 57344;
        description
          "Unknown Reserved Scope LSAs";
      }
    }
    description
      "Ospfv3 lsa";
  }

  typedef live_ncs_Ospfv3-lsa {
    type enumeration {
      enum "link-lsa" {
        value 8;
        description
          "Link LSA";
      }
      enum "grace-lsa" {
        value 11;
        description
          "Grace LSA";
      }
      enum "router" {
        value 8193;
        description
          "Router LSA";
      }
      enum "network" {
        value 8194;
        description
          "Network LSA";
      }
      enum "inter-area-prefix" {
        value 8195;
        description
          "Inter-Area Prefix LSA";
      }
      enum "inter-area-router" {
        value 8196;
        description
          "Inter-Area Router LSA";
      }
      enum "nssa-external" {
        value 8199;
        description
          "NSSA External LSA";
      }
      enum "intra-area-prefix" {
        value 8201;
        description
          "Intra-Area Prefix LSA";
      }
      enum "external" {
        value 16389;
        description
          "External LSA";
      }
      enum "opaque-link" {
        value 32768;
        description
          "Opaque LSALink Scope";
      }
      enum "opaque-area" {
        value 40960;
        description
          "Opaque LSA Area Scope";
      }
      enum "opaque-as" {
        value 49152;
        description
          "Opaque LSA AS Scope";
      }
      enum "unknown" {
        value 57344;
        description
          "Unknown Reserved Scope LSAs";
      }
    }
    description
      "Ospfv3 lsa";
  }

  typedef Ospfv3-lsa {
    type enumeration {
      enum "link-lsa" {
        value 8;
        description
          "Link LSA";
      }
      enum "grace-lsa" {
        value 11;
        description
          "Grace LSA";
      }
      enum "router" {
        value 8193;
        description
          "Router LSA";
      }
      enum "network" {
        value 8194;
        description
          "Network LSA";
      }
      enum "inter-area-prefix" {
        value 8195;
        description
          "Inter-Area Prefix LSA";
      }
      enum "inter-area-router" {
        value 8196;
        description
          "Inter-Area Router LSA";
      }
      enum "nssa-external" {
        value 8199;
        description
          "NSSA External LSA";
      }
      enum "intra-area-prefix" {
        value 8201;
        description
          "Intra-Area Prefix LSA";
      }
      enum "external" {
        value 16389;
        description
          "External LSA";
      }
      enum "opaque-link" {
        value 32768;
        description
          "Opaque LSALink Scope";
      }
      enum "opaque-area" {
        value 40960;
        description
          "Opaque LSA Area Scope";
      }
      enum "opaque-as" {
        value 49152;
        description
          "Opaque LSA AS Scope";
      }
      enum "unknown" {
        value 57344;
        description
          "Unknown Reserved Scope LSAs";
      }
    }
    description
      "Ospfv3 lsa";
  }

  grouping ncs_template_FLOOD-LIST-PROCESS-TABLE {
    description
      "Common node of default-vrf, vrf";
    container flood-list-process-table {
      description
        "OSPFv3 flood list information table for all
         areas";
      uses ncs_template_FLOOD-LIST;
    }
  }

  grouping ncs_template_FLOOD-LIST {
    description
      "Common node of flood-list-table,
       flood-list-process-table";
    list flood {
      // NCS patched for predictable order
      ordered-by user;
      key "interface-name";
      description
        "OSPFv3 flood list information";
      leaf interface-name {
        type xr:ncs_template_Interface-name;
        description
          "Name of the Interface";
      }
      uses ncs_template_OSPFV3-EDM-FLOOD-LIST;
    }
  }

  grouping ncs_template_BORDER-ROUTER-TABLE {
    description
      "Common node of default-vrf, vrf";
    container border-routers {
      description
        "OSPFv3 border router information table";
      list border-router {
        // NCS patched for predictable order
        ordered-by user;
        key "border-router-id";
        description
          "OSPFv3 border router information";
        leaf border-router-id {
          type string;
          description
            "Router address";
        }
        uses ncs_template_OSPFV3-EDM-BORDER-ROUTER;
      }
    }
  }

  grouping ncs_template_FAST-REROUTE-TABLE {
    description
      "Common node of default-vrf, vrf";
    container fast-reroutes {
      description
        "OSPFv3 fast reroute topology information table";
      list fast-reroute {
        // NCS patched for predictable order
        ordered-by user;
        key "remote-router-id area-id";
        description
          "OSPFv3 fast reroute topology information";
        leaf remote-router-id {
          type string;
          description
            "Remote Node Router ID";
        }
        leaf area-id {
          type string;
          description
            "AreaID";
        }
        uses ncs_template_OSPFV3-SH-IPFRR-TOPO;
      }
    }
  }

  grouping ncs_template_AREA-TABLE {
    description
      "Common node of default-vrf, vrf";
    container areas {
      description
        "OSPFv3 area table";
      list area {
        // NCS patched for predictable order
        ordered-by user;
        key "area-id";
        description
          "Per-area information";
        container neighbor-detail-table {
          description
            "OSPFv3 area neighbor information table";
          uses ncs_template_NEIGHBOR-DETAIL;
        }
        container interface-brief-table {
          description
            "OSPFv3 interface brief information table for
             an area";
          uses ncs_template_INTERFACE-BRIEF;
        }
        container request-list-table {
          description
            "OSPFv3 request list information in an area";
          uses ncs_template_REQUEST-LIST;
        }
        container neighbor-table {
          description
            "OSPFv3 neighbor information table";
          uses ncs_template_NEIGHBOR;
        }
        container interface-table {
          description
            "OSPFv3 interface information table for an area";
          uses ncs_template_INTERFACE;
        }
        container flood-list-table {
          description
            "OSPFv3 flood list information table for an
             area";
          uses ncs_template_FLOOD-LIST;
        }
        container retransmission-list-table {
          description
            "OSPFv3 retransmission list information table
             in an area";
          uses ncs_template_RETRANSMISSION-LIST;
        }
        leaf area-id {
          type string;
          description
            "Area ID";
        }
        uses ncs_template_DATABASE-TABLE;
        uses ncs_template_DATABASE-SUMMARY-TABLE;
      }
    }
  }

  grouping ncs_template_EXTERNAL-ROUTE-TABLE {
    description
      "Common node of default-vrf, vrf";
    container external-routes {
      description
        "OSPFv3 external route information table";
      list external-route {
        // NCS patched for predictable order
        ordered-by user;
        description
          "OSPFv3 external route information";
        leaf prefix {
          type string;
          description
            "Route prefix";
        }
        leaf prefix-length {
          type xr:ncs_template_Ipv6-prefix-length;
          description
            "Length of IPv6 Prefix";
        }
        uses ncs_template_OSPFV3-EDM-TOPOLOGY-EXTERNAL;
      }
    }
  }

  grouping ncs_template_NEIGHBOR-DETAIL-PROCESS-TABLE {
    description
      "Common node of default-vrf, vrf";
    container neighbor-detail-process-table {
      description
        "OSPFv3 neighbor information table for all areas";
      uses ncs_template_NEIGHBOR-DETAIL;
    }
  }

  grouping ncs_template_VRF-STATISTICS {
    description
      "Common node of default-vrf, vrf";
    container vrf-statistics {
      description
        "Container for Statistics";
      container protocol-stats {
        description
          "Protocol table";
        list protocol-stat {
          // NCS patched for predictable order
          ordered-by user;
          key "interface-name";
          description
            "Protocol statistics for an interface";
          leaf interface-name {
            type xr:ncs_template_Interface-name;
            description
              "Name of the Interface";
          }
          uses ncs_template_OSPFV3-EDM-PROTO-STATS;
        }
      }
      container spf-stats {
        description
          "OSPFv3 RIB batch statistics";
        uses ncs_template_OSPFV3-EDM-SPF-STATS;
      }
      container rawio-stats {
        description
          "OSPF Prefix SPF Prioritization statistics";
        uses ncs_template_OSPFV3-EDM-RAW-STATS;
      }
      container prefix-priority-stats {
        description
          "OSPF Prefix SPF Prioritization statistics";
        uses ncs_template_OSPFV3-EDM-PRIO-STATS;
      }
      container vrf-rib-batch-stats {
        description
          "OSPFv3 RIB batch statistics";
        uses ncs_template_OSPFV3-EDM-BATCH-STATS;
      }
    }
  }

  grouping ncs_template_INTERFACE {
    description
      "Common node of interface-table,
       interface-process-table";
    list interface {
      // NCS patched for predictable order
      ordered-by user;
      key "interface-name";
      description
        "OSPFv3 interface information";
      leaf interface-name {
        type xr:ncs_template_Interface-name;
        description
          "Name of the Interface";
      }
      uses ncs_template_OSPFV3-EDM-INTERFACE;
    }
  }

  grouping ncs_template_INTERFACE-BRIEF {
    description
      "Common node of interface-brief-table,
       interface-brief-process-table";
    list interface-brief {
      // NCS patched for predictable order
      ordered-by user;
      key "interface-name";
      description
        "Interface brief information";
      leaf interface-name {
        type xr:ncs_template_Interface-name;
        description
          "Name of the Interface";
      }
      uses ncs_template_OSPFV3-EDM-INTF-BRIEF;
    }
  }

  grouping ncs_template_ROUTE-SUMMARY {
    description
      "Common node of default-vrf, vrf";
    container route-summary {
      description
        "Summarize OSPFv3 local RIB tables";
      uses ncs_template_OSPFV3-EDM-ROUTE-SUM;
    }
  }

  grouping ncs_template_NEIGHBOR-DETAIL {
    description
      "Common node of neighbor-detail-process-table,
       neighbor-detail-table";
    list neighbor-detail {
      // NCS patched for predictable order
      ordered-by user;
      description
        "OSPFv3 neighbor detail information";
      leaf interface-name {
        type xr:ncs_template_Interface-name;
        description
          "Name of the Interface";
      }
      leaf neighbor-address {
        type string;
        description
          "Neighbor ID";
      }
      uses ncs_template_OSPFV3-EDM-NEIGHBOR;
    }
  }

  grouping ncs_template_LSA {
    description
      "Common node of lsa-table, lsa-internal-table";
    list lsa {
      // NCS patched for predictable order
      ordered-by user;
      description
        "Database LSA information";
      leaf area-id {
        type string;
        description
          "Area ID";
      }
      leaf ls-type {
        type ncs_template_Ospfv3-lsa;
        description
          "LSA type";
      }
      leaf advertising-router {
        type string;
        description
          "ID of the Advertising Router";
      }
      leaf ls-id {
        type string;
        description
          "Link state ID";
      }
      leaf interface-name {
        type xr:ncs_template_Interface-name;
        description
          "Name of the interface";
      }
      uses ncs_template_OSPFV3-EDM-DATABASE-LSAINFO;
    }
  }

  grouping ncs_template_RETRANSMISSION-LIST {
    description
      "Common node of retransmission-list-process-table,
       retransmission-list-table";
    list retransmission {
      // NCS patched for predictable order
      ordered-by user;
      description
        "OSPFv3 retransmission list information";
      leaf interface-name {
        type xr:ncs_template_Interface-name;
        description
          "Name of the Interface";
      }
      leaf neighbor-address {
        type string;
        description
          "Neighbor Router ID";
      }
      uses ncs_template_OSPFV3-EDM-RETRANS;
    }
  }

  grouping ncs_template_VIRTUAL-LINK-TABLE {
    description
      "Common node of default-vrf, vrf";
    container virtual-links {
      description
        "Virtual link information table";
      list virtual-link {
        // NCS patched for predictable order
        ordered-by user;
        key "vir-link-name";
        description
          "Virtual link information";
        leaf vir-link-name {
          type xr:ncs_template_Cisco-ios-xr-string;
          description
            "Virtual link name";
        }
        uses ncs_template_OSPFV3-EDM-VIRTUAL-LINKS;
      }
    }
  }

  grouping ncs_template_RETRANSMISSION-LIST-PROCESS-TABLE {
    description
      "Common node of default-vrf, vrf";
    container retransmission-list-process-table {
      description
        "OSPFv3 retransmission list information table for
         all areas";
      uses ncs_template_RETRANSMISSION-LIST;
    }
  }

  grouping ncs_template_SUMMARY-PREFIX-TABLE {
    description
      "Common node of default-vrf, vrf";
    container summary-prefixes {
      description
        "Summary prefix information table";
      list summary-prefix {
        // NCS patched for predictable order
        ordered-by user;
        description
          "Summary prefix information";
        leaf prefix {
          type string;
          description
            "Summary prefix";
        }
        leaf prefix-length {
          type xr:ncs_template_Ipv6-prefix-length;
          description
            "Length of IPv6 Prefix";
        }
        uses ncs_template_OSPFV3-EDM-SUMMARY-PREFIX;
      }
    }
  }

  grouping ncs_template_AREA-INFORMATION-TABLE {
    description
      "Common node of default-vrf, vrf";
    container area-informations {
      description
        "OSPFv3 area information table";
      list area-information {
        // NCS patched for predictable order
        ordered-by user;
        key "area-id";
        description
          "OSPFv3 area information details";
        leaf area-id {
          type string;
          description
            "Area ID";
        }
        uses ncs_template_OSPFV3-EDM-AREA;
      }
    }
  }

  grouping ncs_template_SHAM-LINK-TABLE {
    description
      "Common node of default-vrf, vrf";
    container sham-links {
      description
        "Sham link information table";
      list sham-link {
        // NCS patched for predictable order
        ordered-by user;
        key "sham-link-name";
        description
          "Sham link information";
        leaf sham-link-name {
          type xr:ncs_template_Cisco-ios-xr-string;
          description
            "Sham link name";
        }
        uses ncs_template_OSPFV3-SH-SHAM-LINKS;
      }
    }
  }

  grouping ncs_template_NEIGHBOR {
    description
      "Common node of neighbor-process-table,
       neighbor-table";
    list neighbor {
      // NCS patched for predictable order
      ordered-by user;
      description
        "OSPFv3 neighbor detail information";
      leaf interface-name {
        type xr:ncs_template_Interface-name;
        description
          "Name of the Interface";
      }
      leaf neighbor-address {
        type string;
        description
          "Neighbor ID";
      }
      uses ncs_template_OSPFV3-EDM-NEIGHBOR;
    }
  }

  grouping ncs_template_SUMMARY {
    description
      "Common node of default-vrf, vrf";
    container summary {
      description
        "OSPFv3 summary";
      container protocol {
        description
          "OSPFv3 protocol summary";
        uses ncs_template_OSPFV3-EDM-PROTOCOL;
      }
      container ospfv3 {
        description
          "OSPFv3 summary";
        uses ncs_template_OSPFV3-EDM-SUMMARY;
      }
      container aggregate-statistics {
        description
          "OSPFv3 aggregate statistics information";
        uses ncs_template_OSPFV3-SH-STATS-AGGT;
      }
      container route {
        description
          "OSPFv3 route summary";
        uses ncs_template_OSPFV3-EDM-ROUTE-SUM;
      }
    }
  }

  grouping ncs_template_REQUEST-LIST-PROCESS-TABLE {
    description
      "Common node of default-vrf, vrf";
    container request-list-process-table {
      description
        "OSPFv3 request list information for all areas";
      uses ncs_template_REQUEST-LIST;
    }
  }

  grouping ncs_template_DATABASE-TABLE {
    description
      "Common node of area, default-vrf, vrf";
    container database-table {
      description
        "OSPF Link State Database";
      container lsa-table {
        description
          "Database LSA information";
        uses ncs_template_LSA;
      }
      container lsa-internal-table {
        description
          "Database LSA information";
        uses ncs_template_LSA;
      }
    }
  }

  grouping ncs_template_CONNECTED-ROUTE-TABLE {
    description
      "Common node of default-vrf, vrf";
    container connected-routes {
      description
        "OSPFv3 connected route information table";
      list connected-route {
        // NCS patched for predictable order
        ordered-by user;
        description
          "OSPFv3 connected route information";
        leaf prefix {
          type string;
          description
            "Route prefix";
        }
        leaf prefix-length {
          type xr:ncs_template_Ipv6-prefix-length;
          description
            "Length of IPv6 Prefix";
        }
        uses ncs_template_OSPFV3-EDM-TOPOLOGY-CONNECTED;
      }
    }
  }

  grouping ncs_template_BAD-CHECKSUM-TABLE {
    description
      "Common node of default-vrf, vrf";
    container bad-checksums {
      description
        "Bad Checksum Packets information table";
      list bad-checksum {
        // NCS patched for predictable order
        ordered-by user;
        key "packet-number";
        description
          "Bad Checksum Packet information";
        leaf packet-number {
          type string;
          description
            "Bad Checksum Packets number";
        }
        uses ncs_template_OSPFV3-SH-BAD-CHECKSUM;
      }
    }
  }

  grouping ncs_template_DATABASE-SUMMARY-TABLE {
    description
      "Common node of default-vrf, vrf, area";
    container database-summary-table {
      description
        "Summary of the entire Database";
      container database-summary {
        description
          "Database Summary information";
        uses ncs_template_OSPFV3-EDM-DB-SUMMARY;
      }
    }
  }

  grouping ncs_template_REQUEST-LIST {
    description
      "Common node of request-list-process-table,
       request-list-table";
    list request {
      // NCS patched for predictable order
      ordered-by user;
      description
        "OSPFv3 request list information";
      leaf interface-name {
        type xr:ncs_template_Interface-name;
        description
          "Name of the Interface";
      }
      leaf neighbor-address {
        type string;
        description
          "Neighbor Router ID";
      }
      uses ncs_template_OSPFV3-EDM-REQUEST;
    }
  }

  grouping ncs_template_INTERFACE-BRIEF-PROCESS-TABLE {
    description
      "Common node of default-vrf, vrf";
    container interface-brief-process-table {
      description
        "OSPFv3 interface brief information table for all
         areas";
      uses ncs_template_INTERFACE-BRIEF;
    }
  }

  grouping ncs_template_NEIGHBOR-PROCESS-TABLE {
    description
      "Common node of default-vrf, vrf";
    container neighbor-process-table {
      description
        "OSPFv3 neighbor information table for all areas";
      uses ncs_template_NEIGHBOR;
    }
  }

  grouping ncs_template_INTERNAL-ROUTE-TABLE {
    description
      "Common node of default-vrf, vrf";
    container internal-routes {
      description
        "OSPFv3 internal route information table";
      list internal-route {
        // NCS patched for predictable order
        ordered-by user;
        description
          "OSPFv3 internal route information";
        leaf prefix {
          type string;
          description
            "Route prefix";
        }
        leaf prefix-length {
          type xr:ncs_template_Ipv6-prefix-length;
          description
            "Length of IPv6 Prefix";
        }
        uses ncs_template_OSPFV3-EDM-TOPOLOGY-INTERNAL;
      }
    }
  }

  grouping ncs_template_REDISTRIBUTION-TABLE {
    description
      "Common node of default-vrf, vrf";
    container redistributions {
      description
        "Redistribution information table";
      list redistribution {
        // NCS patched for predictable order
        ordered-by user;
        description
          "Redistribution information";
        leaf protocol-name {
          type xr:ncs_template_Cisco-ios-xr-string;
          description
            "Protocol name that is redistributed";
        }
        leaf process-name {
          type xr:ncs_template_Cisco-ios-xr-string;
          description
            "Process name of a protocolbeing redistributed ";
        }
        uses ncs_template_OSPFV3-EDM-REDIST;
      }
    }
  }

  grouping ncs_template_INTERFACE-PROCESS-TABLE {
    description
      "Common node of default-vrf, vrf";
    container interface-process-table {
      description
        "OSPFv3 interface information table for all areas";
      uses ncs_template_INTERFACE;
    }
  }

  grouping ncs_template_PROTOCOL-AREA-TABLE {
    description
      "Common node of default-vrf, vrf";
    container protocol-areas {
      description
        "Protocol area table ";
      list protocol-area {
        // NCS patched for predictable order
        ordered-by user;
        key "area-id";
        description
          "Area information ";
        leaf area-id {
          type string;
          description
            "Area ID";
        }
        uses ncs_template_OSPFV3-EDM-PROTO-AREA;
      }
    }
  }

  grouping ncs_rpc_notif_FLOOD-LIST-PROCESS-TABLE {
    description
      "Common node of default-vrf, vrf";
    container flood-list-process-table {
      description
        "OSPFv3 flood list information table for all
         areas";
      uses ncs_rpc_notif_FLOOD-LIST;
    }
  }

  grouping ncs_rpc_notif_FLOOD-LIST {
    description
      "Common node of flood-list-table,
       flood-list-process-table";
    list flood {
      key "interface-name";
      description
        "OSPFv3 flood list information";
      leaf interface-name {
        type xr:ncs_rpc_notif_Interface-name;
        description
          "Name of the Interface";
      }
      uses ncs_rpc_notif_OSPFV3-EDM-FLOOD-LIST;
    }
  }

  grouping ncs_rpc_notif_BORDER-ROUTER-TABLE {
    description
      "Common node of default-vrf, vrf";
    container border-routers {
      description
        "OSPFv3 border router information table";
      list border-router {
        key "border-router-id";
        description
          "OSPFv3 border router information";
        leaf border-router-id {
          type inet:ipv4-address-no-zone;
          description
            "Router address";
        }
        uses ncs_rpc_notif_OSPFV3-EDM-BORDER-ROUTER;
      }
    }
  }

  grouping ncs_rpc_notif_FAST-REROUTE-TABLE {
    description
      "Common node of default-vrf, vrf";
    container fast-reroutes {
      description
        "OSPFv3 fast reroute topology information table";
      list fast-reroute {
        key "remote-router-id area-id";
        description
          "OSPFv3 fast reroute topology information";
        leaf remote-router-id {
          type inet:ipv4-address-no-zone;
          description
            "Remote Node Router ID";
        }
        leaf area-id {
          type uint32 {
            range "0..4294967295";
          }
          description
            "AreaID";
        }
        uses ncs_rpc_notif_OSPFV3-SH-IPFRR-TOPO;
      }
    }
  }

  grouping ncs_rpc_notif_AREA-TABLE {
    description
      "Common node of default-vrf, vrf";
    container areas {
      description
        "OSPFv3 area table";
      list area {
        key "area-id";
        description
          "Per-area information";
        container neighbor-detail-table {
          description
            "OSPFv3 area neighbor information table";
          uses ncs_rpc_notif_NEIGHBOR-DETAIL;
        }
        container interface-brief-table {
          description
            "OSPFv3 interface brief information table for
             an area";
          uses ncs_rpc_notif_INTERFACE-BRIEF;
        }
        container request-list-table {
          description
            "OSPFv3 request list information in an area";
          uses ncs_rpc_notif_REQUEST-LIST;
        }
        container neighbor-table {
          description
            "OSPFv3 neighbor information table";
          uses ncs_rpc_notif_NEIGHBOR;
        }
        container interface-table {
          description
            "OSPFv3 interface information table for an area";
          uses ncs_rpc_notif_INTERFACE;
        }
        container flood-list-table {
          description
            "OSPFv3 flood list information table for an
             area";
          uses ncs_rpc_notif_FLOOD-LIST;
        }
        container retransmission-list-table {
          description
            "OSPFv3 retransmission list information table
             in an area";
          uses ncs_rpc_notif_RETRANSMISSION-LIST;
        }
        leaf area-id {
          type uint32 {
            range "0..4294967295";
          }
          description
            "Area ID";
        }
        uses ncs_rpc_notif_DATABASE-TABLE;
        uses ncs_rpc_notif_DATABASE-SUMMARY-TABLE;
      }
    }
  }

  grouping ncs_rpc_notif_EXTERNAL-ROUTE-TABLE {
    description
      "Common node of default-vrf, vrf";
    container external-routes {
      description
        "OSPFv3 external route information table";
      list external-route {
        description
          "OSPFv3 external route information";
        leaf prefix {
          type inet:ipv6-address-no-zone;
          description
            "Route prefix";
        }
        leaf prefix-length {
          type xr:ncs_rpc_notif_Ipv6-prefix-length;
          description
            "Length of IPv6 Prefix";
        }
        uses ncs_rpc_notif_OSPFV3-EDM-TOPOLOGY-EXTERNAL;
      }
    }
  }

  grouping ncs_rpc_notif_NEIGHBOR-DETAIL-PROCESS-TABLE {
    description
      "Common node of default-vrf, vrf";
    container neighbor-detail-process-table {
      description
        "OSPFv3 neighbor information table for all areas";
      uses ncs_rpc_notif_NEIGHBOR-DETAIL;
    }
  }

  grouping ncs_rpc_notif_VRF-STATISTICS {
    description
      "Common node of default-vrf, vrf";
    container vrf-statistics {
      description
        "Container for Statistics";
      container protocol-stats {
        description
          "Protocol table";
        list protocol-stat {
          key "interface-name";
          description
            "Protocol statistics for an interface";
          leaf interface-name {
            type xr:ncs_rpc_notif_Interface-name;
            description
              "Name of the Interface";
          }
          uses ncs_rpc_notif_OSPFV3-EDM-PROTO-STATS;
        }
      }
      container spf-stats {
        description
          "OSPFv3 RIB batch statistics";
        uses ncs_rpc_notif_OSPFV3-EDM-SPF-STATS;
      }
      container rawio-stats {
        description
          "OSPF Prefix SPF Prioritization statistics";
        uses ncs_rpc_notif_OSPFV3-EDM-RAW-STATS;
      }
      container prefix-priority-stats {
        description
          "OSPF Prefix SPF Prioritization statistics";
        uses ncs_rpc_notif_OSPFV3-EDM-PRIO-STATS;
      }
      container vrf-rib-batch-stats {
        description
          "OSPFv3 RIB batch statistics";
        uses ncs_rpc_notif_OSPFV3-EDM-BATCH-STATS;
      }
    }
  }

  grouping ncs_rpc_notif_INTERFACE {
    description
      "Common node of interface-table,
       interface-process-table";
    list interface {
      key "interface-name";
      description
        "OSPFv3 interface information";
      leaf interface-name {
        type xr:ncs_rpc_notif_Interface-name;
        description
          "Name of the Interface";
      }
      uses ncs_rpc_notif_OSPFV3-EDM-INTERFACE;
    }
  }

  grouping ncs_rpc_notif_INTERFACE-BRIEF {
    description
      "Common node of interface-brief-table,
       interface-brief-process-table";
    list interface-brief {
      key "interface-name";
      description
        "Interface brief information";
      leaf interface-name {
        type xr:ncs_rpc_notif_Interface-name;
        description
          "Name of the Interface";
      }
      uses ncs_rpc_notif_OSPFV3-EDM-INTF-BRIEF;
    }
  }

  grouping ncs_rpc_notif_ROUTE-SUMMARY {
    description
      "Common node of default-vrf, vrf";
    container route-summary {
      description
        "Summarize OSPFv3 local RIB tables";
      uses ncs_rpc_notif_OSPFV3-EDM-ROUTE-SUM;
    }
  }

  grouping ncs_rpc_notif_NEIGHBOR-DETAIL {
    description
      "Common node of neighbor-detail-process-table,
       neighbor-detail-table";
    list neighbor-detail {
      description
        "OSPFv3 neighbor detail information";
      leaf interface-name {
        type xr:ncs_rpc_notif_Interface-name;
        description
          "Name of the Interface";
      }
      leaf neighbor-address {
        type inet:ipv4-address-no-zone;
        description
          "Neighbor ID";
      }
      uses ncs_rpc_notif_OSPFV3-EDM-NEIGHBOR;
    }
  }

  grouping ncs_rpc_notif_LSA {
    description
      "Common node of lsa-table, lsa-internal-table";
    list lsa {
      description
        "Database LSA information";
      leaf area-id {
        type uint32 {
          range "0..4294967295";
        }
        description
          "Area ID";
      }
      leaf ls-type {
        type ncs_rpc_notif_Ospfv3-lsa;
        description
          "LSA type";
      }
      leaf advertising-router {
        type inet:ipv4-address-no-zone;
        description
          "ID of the Advertising Router";
      }
      leaf ls-id {
        type uint32 {
          range "0..4294967295";
        }
        description
          "Link state ID";
      }
      leaf interface-name {
        type xr:ncs_rpc_notif_Interface-name;
        description
          "Name of the interface";
      }
      uses ncs_rpc_notif_OSPFV3-EDM-DATABASE-LSAINFO;
    }
  }

  grouping ncs_rpc_notif_RETRANSMISSION-LIST {
    description
      "Common node of retransmission-list-process-table,
       retransmission-list-table";
    list retransmission {
      description
        "OSPFv3 retransmission list information";
      leaf interface-name {
        type xr:ncs_rpc_notif_Interface-name;
        description
          "Name of the Interface";
      }
      leaf neighbor-address {
        type inet:ipv4-address-no-zone;
        description
          "Neighbor Router ID";
      }
      uses ncs_rpc_notif_OSPFV3-EDM-RETRANS;
    }
  }

  grouping ncs_rpc_notif_VIRTUAL-LINK-TABLE {
    description
      "Common node of default-vrf, vrf";
    container virtual-links {
      description
        "Virtual link information table";
      list virtual-link {
        key "vir-link-name";
        description
          "Virtual link information";
        leaf vir-link-name {
          type xr:ncs_rpc_notif_Cisco-ios-xr-string;
          description
            "Virtual link name";
        }
        uses ncs_rpc_notif_OSPFV3-EDM-VIRTUAL-LINKS;
      }
    }
  }

  grouping ncs_rpc_notif_RETRANSMISSION-LIST-PROCESS-TABLE {
    description
      "Common node of default-vrf, vrf";
    container retransmission-list-process-table {
      description
        "OSPFv3 retransmission list information table for
         all areas";
      uses ncs_rpc_notif_RETRANSMISSION-LIST;
    }
  }

  grouping ncs_rpc_notif_SUMMARY-PREFIX-TABLE {
    description
      "Common node of default-vrf, vrf";
    container summary-prefixes {
      description
        "Summary prefix information table";
      list summary-prefix {
        description
          "Summary prefix information";
        leaf prefix {
          type inet:ipv6-address-no-zone;
          description
            "Summary prefix";
        }
        leaf prefix-length {
          type xr:ncs_rpc_notif_Ipv6-prefix-length;
          description
            "Length of IPv6 Prefix";
        }
        uses ncs_rpc_notif_OSPFV3-EDM-SUMMARY-PREFIX;
      }
    }
  }

  grouping ncs_rpc_notif_AREA-INFORMATION-TABLE {
    description
      "Common node of default-vrf, vrf";
    container area-informations {
      description
        "OSPFv3 area information table";
      list area-information {
        key "area-id";
        description
          "OSPFv3 area information details";
        leaf area-id {
          type uint32 {
            range "0..4294967295";
          }
          description
            "Area ID";
        }
        uses ncs_rpc_notif_OSPFV3-EDM-AREA;
      }
    }
  }

  grouping ncs_rpc_notif_SHAM-LINK-TABLE {
    description
      "Common node of default-vrf, vrf";
    container sham-links {
      description
        "Sham link information table";
      list sham-link {
        key "sham-link-name";
        description
          "Sham link information";
        leaf sham-link-name {
          type xr:ncs_rpc_notif_Cisco-ios-xr-string;
          description
            "Sham link name";
        }
        uses ncs_rpc_notif_OSPFV3-SH-SHAM-LINKS;
      }
    }
  }

  grouping ncs_rpc_notif_NEIGHBOR {
    description
      "Common node of neighbor-process-table,
       neighbor-table";
    list neighbor {
      description
        "OSPFv3 neighbor detail information";
      leaf interface-name {
        type xr:ncs_rpc_notif_Interface-name;
        description
          "Name of the Interface";
      }
      leaf neighbor-address {
        type inet:ipv4-address-no-zone;
        description
          "Neighbor ID";
      }
      uses ncs_rpc_notif_OSPFV3-EDM-NEIGHBOR;
    }
  }

  grouping ncs_rpc_notif_SUMMARY {
    description
      "Common node of default-vrf, vrf";
    container summary {
      description
        "OSPFv3 summary";
      container protocol {
        description
          "OSPFv3 protocol summary";
        uses ncs_rpc_notif_OSPFV3-EDM-PROTOCOL;
      }
      container ospfv3 {
        description
          "OSPFv3 summary";
        uses ncs_rpc_notif_OSPFV3-EDM-SUMMARY;
      }
      container aggregate-statistics {
        description
          "OSPFv3 aggregate statistics information";
        uses ncs_rpc_notif_OSPFV3-SH-STATS-AGGT;
      }
      container route {
        description
          "OSPFv3 route summary";
        uses ncs_rpc_notif_OSPFV3-EDM-ROUTE-SUM;
      }
    }
  }

  grouping ncs_rpc_notif_REQUEST-LIST-PROCESS-TABLE {
    description
      "Common node of default-vrf, vrf";
    container request-list-process-table {
      description
        "OSPFv3 request list information for all areas";
      uses ncs_rpc_notif_REQUEST-LIST;
    }
  }

  grouping ncs_rpc_notif_DATABASE-TABLE {
    description
      "Common node of area, default-vrf, vrf";
    container database-table {
      description
        "OSPF Link State Database";
      container lsa-table {
        description
          "Database LSA information";
        uses ncs_rpc_notif_LSA;
      }
      container lsa-internal-table {
        description
          "Database LSA information";
        uses ncs_rpc_notif_LSA;
      }
    }
  }

  grouping ncs_rpc_notif_CONNECTED-ROUTE-TABLE {
    description
      "Common node of default-vrf, vrf";
    container connected-routes {
      description
        "OSPFv3 connected route information table";
      list connected-route {
        description
          "OSPFv3 connected route information";
        leaf prefix {
          type inet:ipv6-address-no-zone;
          description
            "Route prefix";
        }
        leaf prefix-length {
          type xr:ncs_rpc_notif_Ipv6-prefix-length;
          description
            "Length of IPv6 Prefix";
        }
        uses ncs_rpc_notif_OSPFV3-EDM-TOPOLOGY-CONNECTED;
      }
    }
  }

  grouping ncs_rpc_notif_BAD-CHECKSUM-TABLE {
    description
      "Common node of default-vrf, vrf";
    container bad-checksums {
      description
        "Bad Checksum Packets information table";
      list bad-checksum {
        key "packet-number";
        description
          "Bad Checksum Packet information";
        leaf packet-number {
          type uint32 {
            range "0..9";
          }
          description
            "Bad Checksum Packets number";
        }
        uses ncs_rpc_notif_OSPFV3-SH-BAD-CHECKSUM;
      }
    }
  }

  grouping ncs_rpc_notif_DATABASE-SUMMARY-TABLE {
    description
      "Common node of default-vrf, vrf, area";
    container database-summary-table {
      description
        "Summary of the entire Database";
      container database-summary {
        description
          "Database Summary information";
        uses ncs_rpc_notif_OSPFV3-EDM-DB-SUMMARY;
      }
    }
  }

  grouping ncs_rpc_notif_REQUEST-LIST {
    description
      "Common node of request-list-process-table,
       request-list-table";
    list request {
      description
        "OSPFv3 request list information";
      leaf interface-name {
        type xr:ncs_rpc_notif_Interface-name;
        description
          "Name of the Interface";
      }
      leaf neighbor-address {
        type inet:ipv4-address-no-zone;
        description
          "Neighbor Router ID";
      }
      uses ncs_rpc_notif_OSPFV3-EDM-REQUEST;
    }
  }

  grouping ncs_rpc_notif_INTERFACE-BRIEF-PROCESS-TABLE {
    description
      "Common node of default-vrf, vrf";
    container interface-brief-process-table {
      description
        "OSPFv3 interface brief information table for all
         areas";
      uses ncs_rpc_notif_INTERFACE-BRIEF;
    }
  }

  grouping ncs_rpc_notif_NEIGHBOR-PROCESS-TABLE {
    description
      "Common node of default-vrf, vrf";
    container neighbor-process-table {
      description
        "OSPFv3 neighbor information table for all areas";
      uses ncs_rpc_notif_NEIGHBOR;
    }
  }

  grouping ncs_rpc_notif_INTERNAL-ROUTE-TABLE {
    description
      "Common node of default-vrf, vrf";
    container internal-routes {
      description
        "OSPFv3 internal route information table";
      list internal-route {
        description
          "OSPFv3 internal route information";
        leaf prefix {
          type inet:ipv6-address-no-zone;
          description
            "Route prefix";
        }
        leaf prefix-length {
          type xr:ncs_rpc_notif_Ipv6-prefix-length;
          description
            "Length of IPv6 Prefix";
        }
        uses ncs_rpc_notif_OSPFV3-EDM-TOPOLOGY-INTERNAL;
      }
    }
  }

  grouping ncs_rpc_notif_REDISTRIBUTION-TABLE {
    description
      "Common node of default-vrf, vrf";
    container redistributions {
      description
        "Redistribution information table";
      list redistribution {
        description
          "Redistribution information";
        leaf protocol-name {
          type xr:ncs_rpc_notif_Cisco-ios-xr-string;
          description
            "Protocol name that is redistributed";
        }
        leaf process-name {
          type xr:ncs_rpc_notif_Cisco-ios-xr-string;
          description
            "Process name of a protocolbeing redistributed ";
        }
        uses ncs_rpc_notif_OSPFV3-EDM-REDIST;
      }
    }
  }

  grouping ncs_rpc_notif_INTERFACE-PROCESS-TABLE {
    description
      "Common node of default-vrf, vrf";
    container interface-process-table {
      description
        "OSPFv3 interface information table for all areas";
      uses ncs_rpc_notif_INTERFACE;
    }
  }

  grouping ncs_rpc_notif_PROTOCOL-AREA-TABLE {
    description
      "Common node of default-vrf, vrf";
    container protocol-areas {
      description
        "Protocol area table ";
      list protocol-area {
        key "area-id";
        description
          "Area information ";
        leaf area-id {
          type uint32 {
            range "0..4294967295";
          }
          description
            "Area ID";
        }
        uses ncs_rpc_notif_OSPFV3-EDM-PROTO-AREA;
      }
    }
  }

  grouping live_ncs_FLOOD-LIST-PROCESS-TABLE {
    description
      "Common node of default-vrf, vrf";
    container flood-list-process-table {
      description
        "OSPFv3 flood list information table for all
         areas";
      uses live_ncs_FLOOD-LIST;
    }
  }

  grouping live_ncs_FLOOD-LIST {
    description
      "Common node of flood-list-table,
       flood-list-process-table";
    list flood {
      key "interface-name";
      description
        "OSPFv3 flood list information";
      leaf interface-name {
        type xr:live_ncs_Interface-name;
        description
          "Name of the Interface";
      }
      uses live_ncs_OSPFV3-EDM-FLOOD-LIST;
    }
  }

  grouping live_ncs_BORDER-ROUTER-TABLE {
    description
      "Common node of default-vrf, vrf";
    container border-routers {
      description
        "OSPFv3 border router information table";
      list border-router {
        key "border-router-id";
        description
          "OSPFv3 border router information";
        leaf border-router-id {
          type inet:ipv4-address-no-zone;
          description
            "Router address";
        }
        uses live_ncs_OSPFV3-EDM-BORDER-ROUTER;
      }
    }
  }

  grouping live_ncs_FAST-REROUTE-TABLE {
    description
      "Common node of default-vrf, vrf";
    container fast-reroutes {
      description
        "OSPFv3 fast reroute topology information table";
      list fast-reroute {
        key "remote-router-id area-id";
        description
          "OSPFv3 fast reroute topology information";
        leaf remote-router-id {
          type inet:ipv4-address-no-zone;
          description
            "Remote Node Router ID";
        }
        leaf area-id {
          type uint32 {
            range "0..4294967295";
          }
          description
            "AreaID";
        }
        uses live_ncs_OSPFV3-SH-IPFRR-TOPO;
      }
    }
  }

  grouping live_ncs_AREA-TABLE {
    description
      "Common node of default-vrf, vrf";
    container areas {
      description
        "OSPFv3 area table";
      list area {
        key "area-id";
        description
          "Per-area information";
        container neighbor-detail-table {
          description
            "OSPFv3 area neighbor information table";
          uses live_ncs_NEIGHBOR-DETAIL;
        }
        container interface-brief-table {
          description
            "OSPFv3 interface brief information table for
             an area";
          uses live_ncs_INTERFACE-BRIEF;
        }
        container request-list-table {
          description
            "OSPFv3 request list information in an area";
          uses live_ncs_REQUEST-LIST;
        }
        container neighbor-table {
          description
            "OSPFv3 neighbor information table";
          uses live_ncs_NEIGHBOR;
        }
        container interface-table {
          description
            "OSPFv3 interface information table for an area";
          uses live_ncs_INTERFACE;
        }
        container flood-list-table {
          description
            "OSPFv3 flood list information table for an
             area";
          uses live_ncs_FLOOD-LIST;
        }
        container retransmission-list-table {
          description
            "OSPFv3 retransmission list information table
             in an area";
          uses live_ncs_RETRANSMISSION-LIST;
        }
        leaf area-id {
          type uint32 {
            range "0..4294967295";
          }
          description
            "Area ID";
        }
        uses live_ncs_DATABASE-TABLE;
        uses live_ncs_DATABASE-SUMMARY-TABLE;
      }
    }
  }

  grouping live_ncs_EXTERNAL-ROUTE-TABLE {
    description
      "Common node of default-vrf, vrf";
    container external-routes {
      description
        "OSPFv3 external route information table";
      list external-route {
        description
          "OSPFv3 external route information";
        leaf prefix {
          type inet:ipv6-address-no-zone;
          description
            "Route prefix";
        }
        leaf prefix-length {
          type xr:live_ncs_Ipv6-prefix-length;
          description
            "Length of IPv6 Prefix";
        }
        uses live_ncs_OSPFV3-EDM-TOPOLOGY-EXTERNAL;
      }
    }
  }

  grouping live_ncs_NEIGHBOR-DETAIL-PROCESS-TABLE {
    description
      "Common node of default-vrf, vrf";
    container neighbor-detail-process-table {
      description
        "OSPFv3 neighbor information table for all areas";
      uses live_ncs_NEIGHBOR-DETAIL;
    }
  }

  grouping live_ncs_VRF-STATISTICS {
    description
      "Common node of default-vrf, vrf";
    container vrf-statistics {
      description
        "Container for Statistics";
      container protocol-stats {
        description
          "Protocol table";
        list protocol-stat {
          key "interface-name";
          description
            "Protocol statistics for an interface";
          leaf interface-name {
            type xr:live_ncs_Interface-name;
            description
              "Name of the Interface";
          }
          uses live_ncs_OSPFV3-EDM-PROTO-STATS;
        }
      }
      container spf-stats {
        description
          "OSPFv3 RIB batch statistics";
        uses live_ncs_OSPFV3-EDM-SPF-STATS;
      }
      container rawio-stats {
        description
          "OSPF Prefix SPF Prioritization statistics";
        uses live_ncs_OSPFV3-EDM-RAW-STATS;
      }
      container prefix-priority-stats {
        description
          "OSPF Prefix SPF Prioritization statistics";
        uses live_ncs_OSPFV3-EDM-PRIO-STATS;
      }
      container vrf-rib-batch-stats {
        description
          "OSPFv3 RIB batch statistics";
        uses live_ncs_OSPFV3-EDM-BATCH-STATS;
      }
    }
  }

  grouping live_ncs_INTERFACE {
    description
      "Common node of interface-table,
       interface-process-table";
    list interface {
      key "interface-name";
      description
        "OSPFv3 interface information";
      leaf interface-name {
        type xr:live_ncs_Interface-name;
        description
          "Name of the Interface";
      }
      uses live_ncs_OSPFV3-EDM-INTERFACE;
    }
  }

  grouping live_ncs_INTERFACE-BRIEF {
    description
      "Common node of interface-brief-table,
       interface-brief-process-table";
    list interface-brief {
      key "interface-name";
      description
        "Interface brief information";
      leaf interface-name {
        type xr:live_ncs_Interface-name;
        description
          "Name of the Interface";
      }
      uses live_ncs_OSPFV3-EDM-INTF-BRIEF;
    }
  }

  grouping live_ncs_ROUTE-SUMMARY {
    description
      "Common node of default-vrf, vrf";
    container route-summary {
      description
        "Summarize OSPFv3 local RIB tables";
      uses live_ncs_OSPFV3-EDM-ROUTE-SUM;
    }
  }

  grouping live_ncs_NEIGHBOR-DETAIL {
    description
      "Common node of neighbor-detail-process-table,
       neighbor-detail-table";
    list neighbor-detail {
      description
        "OSPFv3 neighbor detail information";
      leaf interface-name {
        type xr:live_ncs_Interface-name;
        description
          "Name of the Interface";
      }
      leaf neighbor-address {
        type inet:ipv4-address-no-zone;
        description
          "Neighbor ID";
      }
      uses live_ncs_OSPFV3-EDM-NEIGHBOR;
    }
  }

  grouping live_ncs_LSA {
    description
      "Common node of lsa-table, lsa-internal-table";
    list lsa {
      description
        "Database LSA information";
      leaf area-id {
        type uint32 {
          range "0..4294967295";
        }
        description
          "Area ID";
      }
      leaf ls-type {
        type live_ncs_Ospfv3-lsa;
        description
          "LSA type";
      }
      leaf advertising-router {
        type inet:ipv4-address-no-zone;
        description
          "ID of the Advertising Router";
      }
      leaf ls-id {
        type uint32 {
          range "0..4294967295";
        }
        description
          "Link state ID";
      }
      leaf interface-name {
        type xr:live_ncs_Interface-name;
        description
          "Name of the interface";
      }
      uses live_ncs_OSPFV3-EDM-DATABASE-LSAINFO;
    }
  }

  grouping live_ncs_RETRANSMISSION-LIST {
    description
      "Common node of retransmission-list-process-table,
       retransmission-list-table";
    list retransmission {
      description
        "OSPFv3 retransmission list information";
      leaf interface-name {
        type xr:live_ncs_Interface-name;
        description
          "Name of the Interface";
      }
      leaf neighbor-address {
        type inet:ipv4-address-no-zone;
        description
          "Neighbor Router ID";
      }
      uses live_ncs_OSPFV3-EDM-RETRANS;
    }
  }

  grouping live_ncs_VIRTUAL-LINK-TABLE {
    description
      "Common node of default-vrf, vrf";
    container virtual-links {
      description
        "Virtual link information table";
      list virtual-link {
        key "vir-link-name";
        description
          "Virtual link information";
        leaf vir-link-name {
          type xr:live_ncs_Cisco-ios-xr-string;
          description
            "Virtual link name";
        }
        uses live_ncs_OSPFV3-EDM-VIRTUAL-LINKS;
      }
    }
  }

  grouping live_ncs_RETRANSMISSION-LIST-PROCESS-TABLE {
    description
      "Common node of default-vrf, vrf";
    container retransmission-list-process-table {
      description
        "OSPFv3 retransmission list information table for
         all areas";
      uses live_ncs_RETRANSMISSION-LIST;
    }
  }

  grouping live_ncs_SUMMARY-PREFIX-TABLE {
    description
      "Common node of default-vrf, vrf";
    container summary-prefixes {
      description
        "Summary prefix information table";
      list summary-prefix {
        description
          "Summary prefix information";
        leaf prefix {
          type inet:ipv6-address-no-zone;
          description
            "Summary prefix";
        }
        leaf prefix-length {
          type xr:live_ncs_Ipv6-prefix-length;
          description
            "Length of IPv6 Prefix";
        }
        uses live_ncs_OSPFV3-EDM-SUMMARY-PREFIX;
      }
    }
  }

  grouping live_ncs_AREA-INFORMATION-TABLE {
    description
      "Common node of default-vrf, vrf";
    container area-informations {
      description
        "OSPFv3 area information table";
      list area-information {
        key "area-id";
        description
          "OSPFv3 area information details";
        leaf area-id {
          type uint32 {
            range "0..4294967295";
          }
          description
            "Area ID";
        }
        uses live_ncs_OSPFV3-EDM-AREA;
      }
    }
  }

  grouping live_ncs_SHAM-LINK-TABLE {
    description
      "Common node of default-vrf, vrf";
    container sham-links {
      description
        "Sham link information table";
      list sham-link {
        key "sham-link-name";
        description
          "Sham link information";
        leaf sham-link-name {
          type xr:live_ncs_Cisco-ios-xr-string;
          description
            "Sham link name";
        }
        uses live_ncs_OSPFV3-SH-SHAM-LINKS;
      }
    }
  }

  grouping live_ncs_NEIGHBOR {
    description
      "Common node of neighbor-process-table,
       neighbor-table";
    list neighbor {
      description
        "OSPFv3 neighbor detail information";
      leaf interface-name {
        type xr:live_ncs_Interface-name;
        description
          "Name of the Interface";
      }
      leaf neighbor-address {
        type inet:ipv4-address-no-zone;
        description
          "Neighbor ID";
      }
      uses live_ncs_OSPFV3-EDM-NEIGHBOR;
    }
  }

  grouping live_ncs_SUMMARY {
    description
      "Common node of default-vrf, vrf";
    container summary {
      description
        "OSPFv3 summary";
      container protocol {
        description
          "OSPFv3 protocol summary";
        uses live_ncs_OSPFV3-EDM-PROTOCOL;
      }
      container ospfv3 {
        description
          "OSPFv3 summary";
        uses live_ncs_OSPFV3-EDM-SUMMARY;
      }
      container aggregate-statistics {
        description
          "OSPFv3 aggregate statistics information";
        uses live_ncs_OSPFV3-SH-STATS-AGGT;
      }
      container route {
        description
          "OSPFv3 route summary";
        uses live_ncs_OSPFV3-EDM-ROUTE-SUM;
      }
    }
  }

  grouping live_ncs_REQUEST-LIST-PROCESS-TABLE {
    description
      "Common node of default-vrf, vrf";
    container request-list-process-table {
      description
        "OSPFv3 request list information for all areas";
      uses live_ncs_REQUEST-LIST;
    }
  }

  grouping live_ncs_DATABASE-TABLE {
    description
      "Common node of area, default-vrf, vrf";
    container database-table {
      description
        "OSPF Link State Database";
      container lsa-table {
        description
          "Database LSA information";
        uses live_ncs_LSA;
      }
      container lsa-internal-table {
        description
          "Database LSA information";
        uses live_ncs_LSA;
      }
    }
  }

  grouping live_ncs_CONNECTED-ROUTE-TABLE {
    description
      "Common node of default-vrf, vrf";
    container connected-routes {
      description
        "OSPFv3 connected route information table";
      list connected-route {
        description
          "OSPFv3 connected route information";
        leaf prefix {
          type inet:ipv6-address-no-zone;
          description
            "Route prefix";
        }
        leaf prefix-length {
          type xr:live_ncs_Ipv6-prefix-length;
          description
            "Length of IPv6 Prefix";
        }
        uses live_ncs_OSPFV3-EDM-TOPOLOGY-CONNECTED;
      }
    }
  }

  grouping live_ncs_BAD-CHECKSUM-TABLE {
    description
      "Common node of default-vrf, vrf";
    container bad-checksums {
      description
        "Bad Checksum Packets information table";
      list bad-checksum {
        key "packet-number";
        description
          "Bad Checksum Packet information";
        leaf packet-number {
          type uint32 {
            range "0..9";
          }
          description
            "Bad Checksum Packets number";
        }
        uses live_ncs_OSPFV3-SH-BAD-CHECKSUM;
      }
    }
  }

  grouping live_ncs_DATABASE-SUMMARY-TABLE {
    description
      "Common node of default-vrf, vrf, area";
    container database-summary-table {
      description
        "Summary of the entire Database";
      container database-summary {
        description
          "Database Summary information";
        uses live_ncs_OSPFV3-EDM-DB-SUMMARY;
      }
    }
  }

  grouping live_ncs_REQUEST-LIST {
    description
      "Common node of request-list-process-table,
       request-list-table";
    list request {
      description
        "OSPFv3 request list information";
      leaf interface-name {
        type xr:live_ncs_Interface-name;
        description
          "Name of the Interface";
      }
      leaf neighbor-address {
        type inet:ipv4-address-no-zone;
        description
          "Neighbor Router ID";
      }
      uses live_ncs_OSPFV3-EDM-REQUEST;
    }
  }

  grouping live_ncs_INTERFACE-BRIEF-PROCESS-TABLE {
    description
      "Common node of default-vrf, vrf";
    container interface-brief-process-table {
      description
        "OSPFv3 interface brief information table for all
         areas";
      uses live_ncs_INTERFACE-BRIEF;
    }
  }

  grouping live_ncs_NEIGHBOR-PROCESS-TABLE {
    description
      "Common node of default-vrf, vrf";
    container neighbor-process-table {
      description
        "OSPFv3 neighbor information table for all areas";
      uses live_ncs_NEIGHBOR;
    }
  }

  grouping live_ncs_INTERNAL-ROUTE-TABLE {
    description
      "Common node of default-vrf, vrf";
    container internal-routes {
      description
        "OSPFv3 internal route information table";
      list internal-route {
        description
          "OSPFv3 internal route information";
        leaf prefix {
          type inet:ipv6-address-no-zone;
          description
            "Route prefix";
        }
        leaf prefix-length {
          type xr:live_ncs_Ipv6-prefix-length;
          description
            "Length of IPv6 Prefix";
        }
        uses live_ncs_OSPFV3-EDM-TOPOLOGY-INTERNAL;
      }
    }
  }

  grouping live_ncs_REDISTRIBUTION-TABLE {
    description
      "Common node of default-vrf, vrf";
    container redistributions {
      description
        "Redistribution information table";
      list redistribution {
        description
          "Redistribution information";
        leaf protocol-name {
          type xr:live_ncs_Cisco-ios-xr-string;
          description
            "Protocol name that is redistributed";
        }
        leaf process-name {
          type xr:live_ncs_Cisco-ios-xr-string;
          description
            "Process name of a protocolbeing redistributed ";
        }
        uses live_ncs_OSPFV3-EDM-REDIST;
      }
    }
  }

  grouping live_ncs_INTERFACE-PROCESS-TABLE {
    description
      "Common node of default-vrf, vrf";
    container interface-process-table {
      description
        "OSPFv3 interface information table for all areas";
      uses live_ncs_INTERFACE;
    }
  }

  grouping live_ncs_PROTOCOL-AREA-TABLE {
    description
      "Common node of default-vrf, vrf";
    container protocol-areas {
      description
        "Protocol area table ";
      list protocol-area {
        key "area-id";
        description
          "Area information ";
        leaf area-id {
          type uint32 {
            range "0..4294967295";
          }
          description
            "Area ID";
        }
        uses live_ncs_OSPFV3-EDM-PROTO-AREA;
      }
    }
  }

  grouping FLOOD-LIST-PROCESS-TABLE {
    description
      "Common node of default-vrf, vrf";
    container flood-list-process-table {
      description
        "OSPFv3 flood list information table for all
         areas";
      uses FLOOD-LIST;
    }
  }

  grouping FLOOD-LIST {
    description
      "Common node of flood-list-table,
       flood-list-process-table";
    list flood {
      key "interface-name";
      description
        "OSPFv3 flood list information";
      leaf interface-name {
        type xr:Interface-name;
        description
          "Name of the Interface";
      }
      uses OSPFV3-EDM-FLOOD-LIST;
    }
  }

  grouping BORDER-ROUTER-TABLE {
    description
      "Common node of default-vrf, vrf";
    container border-routers {
      description
        "OSPFv3 border router information table";
      list border-router {
        key "border-router-id";
        description
          "OSPFv3 border router information";
        leaf border-router-id {
          type inet:ipv4-address-no-zone;
          description
            "Router address";
        }
        uses OSPFV3-EDM-BORDER-ROUTER;
      }
    }
  }

  grouping FAST-REROUTE-TABLE {
    description
      "Common node of default-vrf, vrf";
    container fast-reroutes {
      description
        "OSPFv3 fast reroute topology information table";
      list fast-reroute {
        key "remote-router-id area-id";
        description
          "OSPFv3 fast reroute topology information";
        leaf remote-router-id {
          type inet:ipv4-address-no-zone;
          description
            "Remote Node Router ID";
        }
        leaf area-id {
          type uint32 {
            range "0..4294967295";
          }
          description
            "AreaID";
        }
        uses OSPFV3-SH-IPFRR-TOPO;
      }
    }
  }

  grouping AREA-TABLE {
    description
      "Common node of default-vrf, vrf";
    container areas {
      description
        "OSPFv3 area table";
      list area {
        key "area-id";
        description
          "Per-area information";
        container neighbor-detail-table {
          description
            "OSPFv3 area neighbor information table";
          uses NEIGHBOR-DETAIL;
        }
        container interface-brief-table {
          description
            "OSPFv3 interface brief information table for
             an area";
          uses INTERFACE-BRIEF;
        }
        container request-list-table {
          description
            "OSPFv3 request list information in an area";
          uses REQUEST-LIST;
        }
        container neighbor-table {
          description
            "OSPFv3 neighbor information table";
          uses NEIGHBOR;
        }
        container interface-table {
          description
            "OSPFv3 interface information table for an area";
          uses INTERFACE;
        }
        container flood-list-table {
          description
            "OSPFv3 flood list information table for an
             area";
          uses FLOOD-LIST;
        }
        container retransmission-list-table {
          description
            "OSPFv3 retransmission list information table
             in an area";
          uses RETRANSMISSION-LIST;
        }
        leaf area-id {
          type uint32 {
            range "0..4294967295";
          }
          description
            "Area ID";
        }
        uses DATABASE-TABLE;
        uses DATABASE-SUMMARY-TABLE;
      }
    }
  }

  grouping EXTERNAL-ROUTE-TABLE {
    description
      "Common node of default-vrf, vrf";
    container external-routes {
      description
        "OSPFv3 external route information table";
      list external-route {
        description
          "OSPFv3 external route information";
        leaf prefix {
          type inet:ipv6-address-no-zone;
          description
            "Route prefix";
        }
        leaf prefix-length {
          type xr:Ipv6-prefix-length;
          description
            "Length of IPv6 Prefix";
        }
        uses OSPFV3-EDM-TOPOLOGY-EXTERNAL;
      }
    }
  }

  grouping NEIGHBOR-DETAIL-PROCESS-TABLE {
    description
      "Common node of default-vrf, vrf";
    container neighbor-detail-process-table {
      description
        "OSPFv3 neighbor information table for all areas";
      uses NEIGHBOR-DETAIL;
    }
  }

  grouping VRF-STATISTICS {
    description
      "Common node of default-vrf, vrf";
    container vrf-statistics {
      description
        "Container for Statistics";
      container protocol-stats {
        description
          "Protocol table";
        list protocol-stat {
          key "interface-name";
          description
            "Protocol statistics for an interface";
          leaf interface-name {
            type xr:Interface-name;
            description
              "Name of the Interface";
          }
          uses OSPFV3-EDM-PROTO-STATS;
        }
      }
      container spf-stats {
        description
          "OSPFv3 RIB batch statistics";
        uses OSPFV3-EDM-SPF-STATS;
      }
      container rawio-stats {
        description
          "OSPF Prefix SPF Prioritization statistics";
        uses OSPFV3-EDM-RAW-STATS;
      }
      container prefix-priority-stats {
        description
          "OSPF Prefix SPF Prioritization statistics";
        uses OSPFV3-EDM-PRIO-STATS;
      }
      container vrf-rib-batch-stats {
        description
          "OSPFv3 RIB batch statistics";
        uses OSPFV3-EDM-BATCH-STATS;
      }
    }
  }

  grouping INTERFACE {
    description
      "Common node of interface-table,
       interface-process-table";
    list interface {
      key "interface-name";
      description
        "OSPFv3 interface information";
      leaf interface-name {
        type xr:Interface-name;
        description
          "Name of the Interface";
      }
      uses OSPFV3-EDM-INTERFACE;
    }
  }

  grouping INTERFACE-BRIEF {
    description
      "Common node of interface-brief-table,
       interface-brief-process-table";
    list interface-brief {
      key "interface-name";
      description
        "Interface brief information";
      leaf interface-name {
        type xr:Interface-name;
        description
          "Name of the Interface";
      }
      uses OSPFV3-EDM-INTF-BRIEF;
    }
  }

  grouping ROUTE-SUMMARY {
    description
      "Common node of default-vrf, vrf";
    container route-summary {
      description
        "Summarize OSPFv3 local RIB tables";
      uses OSPFV3-EDM-ROUTE-SUM;
    }
  }

  grouping NEIGHBOR-DETAIL {
    description
      "Common node of neighbor-detail-process-table,
       neighbor-detail-table";
    list neighbor-detail {
      description
        "OSPFv3 neighbor detail information";
      leaf interface-name {
        type xr:Interface-name;
        description
          "Name of the Interface";
      }
      leaf neighbor-address {
        type inet:ipv4-address-no-zone;
        description
          "Neighbor ID";
      }
      uses OSPFV3-EDM-NEIGHBOR;
    }
  }

  grouping LSA {
    description
      "Common node of lsa-table, lsa-internal-table";
    list lsa {
      description
        "Database LSA information";
      leaf area-id {
        type uint32 {
          range "0..4294967295";
        }
        description
          "Area ID";
      }
      leaf ls-type {
        type Ospfv3-lsa;
        description
          "LSA type";
      }
      leaf advertising-router {
        type inet:ipv4-address-no-zone;
        description
          "ID of the Advertising Router";
      }
      leaf ls-id {
        type uint32 {
          range "0..4294967295";
        }
        description
          "Link state ID";
      }
      leaf interface-name {
        type xr:Interface-name;
        description
          "Name of the interface";
      }
      uses OSPFV3-EDM-DATABASE-LSAINFO;
    }
  }

  grouping RETRANSMISSION-LIST {
    description
      "Common node of retransmission-list-process-table,
       retransmission-list-table";
    list retransmission {
      description
        "OSPFv3 retransmission list information";
      leaf interface-name {
        type xr:Interface-name;
        description
          "Name of the Interface";
      }
      leaf neighbor-address {
        type inet:ipv4-address-no-zone;
        description
          "Neighbor Router ID";
      }
      uses OSPFV3-EDM-RETRANS;
    }
  }

  grouping VIRTUAL-LINK-TABLE {
    description
      "Common node of default-vrf, vrf";
    container virtual-links {
      description
        "Virtual link information table";
      list virtual-link {
        key "vir-link-name";
        description
          "Virtual link information";
        leaf vir-link-name {
          type xr:Cisco-ios-xr-string;
          description
            "Virtual link name";
        }
        uses OSPFV3-EDM-VIRTUAL-LINKS;
      }
    }
  }

  grouping RETRANSMISSION-LIST-PROCESS-TABLE {
    description
      "Common node of default-vrf, vrf";
    container retransmission-list-process-table {
      description
        "OSPFv3 retransmission list information table for
         all areas";
      uses RETRANSMISSION-LIST;
    }
  }

  grouping SUMMARY-PREFIX-TABLE {
    description
      "Common node of default-vrf, vrf";
    container summary-prefixes {
      description
        "Summary prefix information table";
      list summary-prefix {
        description
          "Summary prefix information";
        leaf prefix {
          type inet:ipv6-address-no-zone;
          description
            "Summary prefix";
        }
        leaf prefix-length {
          type xr:Ipv6-prefix-length;
          description
            "Length of IPv6 Prefix";
        }
        uses OSPFV3-EDM-SUMMARY-PREFIX;
      }
    }
  }

  grouping AREA-INFORMATION-TABLE {
    description
      "Common node of default-vrf, vrf";
    container area-informations {
      description
        "OSPFv3 area information table";
      list area-information {
        key "area-id";
        description
          "OSPFv3 area information details";
        leaf area-id {
          type uint32 {
            range "0..4294967295";
          }
          description
            "Area ID";
        }
        uses OSPFV3-EDM-AREA;
      }
    }
  }

  grouping SHAM-LINK-TABLE {
    description
      "Common node of default-vrf, vrf";
    container sham-links {
      description
        "Sham link information table";
      list sham-link {
        key "sham-link-name";
        description
          "Sham link information";
        leaf sham-link-name {
          type xr:Cisco-ios-xr-string;
          description
            "Sham link name";
        }
        uses OSPFV3-SH-SHAM-LINKS;
      }
    }
  }

  grouping NEIGHBOR {
    description
      "Common node of neighbor-process-table,
       neighbor-table";
    list neighbor {
      description
        "OSPFv3 neighbor detail information";
      leaf interface-name {
        type xr:Interface-name;
        description
          "Name of the Interface";
      }
      leaf neighbor-address {
        type inet:ipv4-address-no-zone;
        description
          "Neighbor ID";
      }
      uses OSPFV3-EDM-NEIGHBOR;
    }
  }

  grouping SUMMARY {
    description
      "Common node of default-vrf, vrf";
    container summary {
      description
        "OSPFv3 summary";
      container protocol {
        description
          "OSPFv3 protocol summary";
        uses OSPFV3-EDM-PROTOCOL;
      }
      container ospfv3 {
        description
          "OSPFv3 summary";
        uses OSPFV3-EDM-SUMMARY;
      }
      container aggregate-statistics {
        description
          "OSPFv3 aggregate statistics information";
        uses OSPFV3-SH-STATS-AGGT;
      }
      container route {
        description
          "OSPFv3 route summary";
        uses OSPFV3-EDM-ROUTE-SUM;
      }
    }
  }

  grouping REQUEST-LIST-PROCESS-TABLE {
    description
      "Common node of default-vrf, vrf";
    container request-list-process-table {
      description
        "OSPFv3 request list information for all areas";
      uses REQUEST-LIST;
    }
  }

  grouping DATABASE-TABLE {
    description
      "Common node of area, default-vrf, vrf";
    container database-table {
      description
        "OSPF Link State Database";
      container lsa-table {
        description
          "Database LSA information";
        uses LSA;
      }
      container lsa-internal-table {
        description
          "Database LSA information";
        uses LSA;
      }
    }
  }

  grouping CONNECTED-ROUTE-TABLE {
    description
      "Common node of default-vrf, vrf";
    container connected-routes {
      description
        "OSPFv3 connected route information table";
      list connected-route {
        description
          "OSPFv3 connected route information";
        leaf prefix {
          type inet:ipv6-address-no-zone;
          description
            "Route prefix";
        }
        leaf prefix-length {
          type xr:Ipv6-prefix-length;
          description
            "Length of IPv6 Prefix";
        }
        uses OSPFV3-EDM-TOPOLOGY-CONNECTED;
      }
    }
  }

  grouping BAD-CHECKSUM-TABLE {
    description
      "Common node of default-vrf, vrf";
    container bad-checksums {
      description
        "Bad Checksum Packets information table";
      list bad-checksum {
        key "packet-number";
        description
          "Bad Checksum Packet information";
        leaf packet-number {
          type uint32 {
            range "0..9";
          }
          description
            "Bad Checksum Packets number";
        }
        uses OSPFV3-SH-BAD-CHECKSUM;
      }
    }
  }

  grouping DATABASE-SUMMARY-TABLE {
    description
      "Common node of default-vrf, vrf, area";
    container database-summary-table {
      description
        "Summary of the entire Database";
      container database-summary {
        description
          "Database Summary information";
        uses OSPFV3-EDM-DB-SUMMARY;
      }
    }
  }

  grouping REQUEST-LIST {
    description
      "Common node of request-list-process-table,
       request-list-table";
    list request {
      description
        "OSPFv3 request list information";
      leaf interface-name {
        type xr:Interface-name;
        description
          "Name of the Interface";
      }
      leaf neighbor-address {
        type inet:ipv4-address-no-zone;
        description
          "Neighbor Router ID";
      }
      uses OSPFV3-EDM-REQUEST;
    }
  }

  grouping INTERFACE-BRIEF-PROCESS-TABLE {
    description
      "Common node of default-vrf, vrf";
    container interface-brief-process-table {
      description
        "OSPFv3 interface brief information table for all
         areas";
      uses INTERFACE-BRIEF;
    }
  }

  grouping NEIGHBOR-PROCESS-TABLE {
    description
      "Common node of default-vrf, vrf";
    container neighbor-process-table {
      description
        "OSPFv3 neighbor information table for all areas";
      uses NEIGHBOR;
    }
  }

  grouping INTERNAL-ROUTE-TABLE {
    description
      "Common node of default-vrf, vrf";
    container internal-routes {
      description
        "OSPFv3 internal route information table";
      list internal-route {
        description
          "OSPFv3 internal route information";
        leaf prefix {
          type inet:ipv6-address-no-zone;
          description
            "Route prefix";
        }
        leaf prefix-length {
          type xr:Ipv6-prefix-length;
          description
            "Length of IPv6 Prefix";
        }
        uses OSPFV3-EDM-TOPOLOGY-INTERNAL;
      }
    }
  }

  grouping REDISTRIBUTION-TABLE {
    description
      "Common node of default-vrf, vrf";
    container redistributions {
      description
        "Redistribution information table";
      list redistribution {
        description
          "Redistribution information";
        leaf protocol-name {
          type xr:Cisco-ios-xr-string;
          description
            "Protocol name that is redistributed";
        }
        leaf process-name {
          type xr:Cisco-ios-xr-string;
          description
            "Process name of a protocolbeing redistributed ";
        }
        uses OSPFV3-EDM-REDIST;
      }
    }
  }

  grouping INTERFACE-PROCESS-TABLE {
    description
      "Common node of default-vrf, vrf";
    container interface-process-table {
      description
        "OSPFv3 interface information table for all areas";
      uses INTERFACE;
    }
  }

  grouping PROTOCOL-AREA-TABLE {
    description
      "Common node of default-vrf, vrf";
    container protocol-areas {
      description
        "Protocol area table ";
      list protocol-area {
        key "area-id";
        description
          "Area information ";
        leaf area-id {
          type uint32 {
            range "0..4294967295";
          }
          description
            "Area ID";
        }
        uses OSPFV3-EDM-PROTO-AREA;
      }
    }
  }

  augment "/ncs:devices/ncs:device/ncs:config" {
    // NCS drop config false container ospfv3
  }
  augment "/ncs:devices/ncs:device/ncs:live-status" {
    container ospfv3 {
      tailf:ncs-device-type "netconf";
      tailf:display-when "not(../../ncs:module) or ../../ncs:module[ncs:name='Cisco-IOS-XR-ipv6-ospfv3-oper'] or (../../ncs:live-status-protocol[not(ncs:capability)]) or (../../ncs:live-status-protocol/ncs:capability/ncs:module[.='Cisco-IOS-XR-ipv6-ospfv3-oper'])";
      description
        "OSPFv3 operational information ";
      container processes {
        description
          "OSPFv3 Process Table";
        list process {
          key "process-name";
          description
            "OSPFv3 Operational data for a particular OSPFv3
             process ";
          container vrfs {
            description
              "Table for each VRF";
            list vrf {
              key "vrf-name";
              description
                "Operational data for a particular VRF
                 (instance) in the OSPFv3 process";
              leaf vrf-name {
                type xr:live_ncs_Cisco-ios-xr-string;
                description
                  "VRF Name";
              }
              uses live_ncs_SUMMARY-PREFIX-TABLE;
              uses live_ncs_BORDER-ROUTER-TABLE;
              uses live_ncs_AREA-INFORMATION-TABLE;
              uses live_ncs_DATABASE-TABLE;
              uses live_ncs_VIRTUAL-LINK-TABLE;
              uses live_ncs_INTERFACE-PROCESS-TABLE;
              uses live_ncs_REDISTRIBUTION-TABLE;
              uses live_ncs_EXTERNAL-ROUTE-TABLE;
              uses live_ncs_REQUEST-LIST-PROCESS-TABLE;
              uses live_ncs_FLOOD-LIST-PROCESS-TABLE;
              uses live_ncs_ROUTE-SUMMARY;
              uses live_ncs_AREA-TABLE;
              uses live_ncs_INTERNAL-ROUTE-TABLE;
              uses live_ncs_SHAM-LINK-TABLE;
              uses live_ncs_PROTOCOL-AREA-TABLE;
              uses live_ncs_CONNECTED-ROUTE-TABLE;
              uses live_ncs_VRF-STATISTICS;
              uses live_ncs_SUMMARY;
              uses live_ncs_RETRANSMISSION-LIST-PROCESS-TABLE;
              uses live_ncs_BAD-CHECKSUM-TABLE;
              uses live_ncs_DATABASE-SUMMARY-TABLE;
              uses live_ncs_NEIGHBOR-PROCESS-TABLE;
              uses live_ncs_FAST-REROUTE-TABLE;
              uses live_ncs_INTERFACE-BRIEF-PROCESS-TABLE;
              uses live_ncs_NEIGHBOR-DETAIL-PROCESS-TABLE;
            }
          }
          container statistics {
            description
              "Container for Statistics";
            container nsr-stats {
              description
                "OSPF NSR statistics";
              uses live_ncs_OSPFV3-EDM-NSR-STATS;
            }
            container rib-thread-stats {
              description
                "OSPFv3 RIB thread statistics";
              uses live_ncs_OSPFV3-EDM-RTHREAD-STATS;
            }
            container issu-stats {
              description
                "OSPF ISSU statistics";
              uses live_ncs_OSPFV3-EDM-NSR-STATS;
            }
            container nsr-pl-stats {
              description
                "OSPF NSR packet library statistics";
              uses live_ncs_OSPF-SH-NCD-STATS;
            }
          }
          container default-vrf {
            description
              "Operational data for the default VRF
               (instance) in the OSPFv3 process";
            uses live_ncs_SUMMARY-PREFIX-TABLE;
            uses live_ncs_BORDER-ROUTER-TABLE;
            uses live_ncs_AREA-INFORMATION-TABLE;
            uses live_ncs_DATABASE-TABLE;
            uses live_ncs_VIRTUAL-LINK-TABLE;
            uses live_ncs_INTERFACE-PROCESS-TABLE;
            uses live_ncs_REDISTRIBUTION-TABLE;
            uses live_ncs_EXTERNAL-ROUTE-TABLE;
            uses live_ncs_REQUEST-LIST-PROCESS-TABLE;
            uses live_ncs_FLOOD-LIST-PROCESS-TABLE;
            uses live_ncs_ROUTE-SUMMARY;
            uses live_ncs_AREA-TABLE;
            uses live_ncs_INTERNAL-ROUTE-TABLE;
            uses live_ncs_SHAM-LINK-TABLE;
            uses live_ncs_PROTOCOL-AREA-TABLE;
            uses live_ncs_CONNECTED-ROUTE-TABLE;
            uses live_ncs_VRF-STATISTICS;
            uses live_ncs_SUMMARY;
            uses live_ncs_RETRANSMISSION-LIST-PROCESS-TABLE;
            uses live_ncs_BAD-CHECKSUM-TABLE;
            uses live_ncs_DATABASE-SUMMARY-TABLE;
            uses live_ncs_NEIGHBOR-PROCESS-TABLE;
            uses live_ncs_FAST-REROUTE-TABLE;
            uses live_ncs_INTERFACE-BRIEF-PROCESS-TABLE;
            uses live_ncs_NEIGHBOR-DETAIL-PROCESS-TABLE;
          }
          leaf process-name {
            type xr:live_ncs_Cisco-ios-xr-string;
            description
              "Particular OSPFv3 process";
          }
        }
      }
    }
  }
  augment "/ncs:devices/ncs:template/ncs:ned-id/ncs:config" {
    // NCS drop config false container ospfv3
  }
}

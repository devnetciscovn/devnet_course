module Cisco-IOS-XR-install-cfg {
  // Generated by yanger -t ncs
  tailf:mount-id "cisco-iosxr-nc-7.3:cisco-iosxr-nc-7.3";
  tailf:ncs-device-type "netconf";

  namespace "http://cisco.com/ns/yang/Cisco-IOS-XR-install-cfg";
  prefix install-cfg;

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR install package configuration.

     This module contains definitions
     for the following management objects:
       install: Install configuration data

     Copyright (c) 2013-2019 by Cisco Systems, Inc.
     All rights reserved.";

  revision 2019-12-11 {
    description
      "Repository URL description updated.";
    semver:module-version "1.0.1";
  }
  revision 2019-04-05 {
    description
      "Establish semantic version baseline.";
    semver:module-version "1.0.0";
  }
  revision 2015-11-09 {
    description
      "IOS XR 6.0 revision.";
  }

  augment "/ncs:devices/ncs:device/ncs:config" {
    container install {
      tailf:ncs-device-type "netconf";
      tailf:display-when "not(../../ncs:module) or ../../ncs:module[ncs:name='Cisco-IOS-XR-install-cfg']";
      description
        "Install configuration data";
      container repositories {
        description
          "Table of repositories";
        list repository {
          key "id";
          description
            "Repository configuration";
          leaf url {
            type string {
              length "1..900";
            }
            description
              "Repository URL - path to local repository or
               directory or ftp, http, or https path to
               remote repository, optionally containing the
               name of a VRF for the repository. Format one
               of:
                 ftp://<server>[;<vrf>]/<path_to_repo>

                 http://<server>[;<vrf>]/<path_to_repo>

               https://<server>[;<vrf>]/<path_to_repo>

               file:///<path_to_repo>";
          }
          leaf description {
            type string {
              length "1..900";
            }
            description
              "Repository name or description";
          }
          leaf id {
            type string {
              length "1..80";
            }
            description
              "Repository identifier";
          }
        }
      }
    }
  }
  augment "/ncs:devices/ncs:device/ncs:live-status" {
    container install {
      tailf:ncs-device-type "netconf";
      tailf:display-when "not(../../ncs:module) or ../../ncs:module[ncs:name='Cisco-IOS-XR-install-cfg'] or (../../ncs:live-status-protocol[not(ncs:capability)]) or (../../ncs:live-status-protocol/ncs:capability/ncs:module[.='Cisco-IOS-XR-install-cfg'])";
      description
        "Install configuration data";
      container repositories {
        description
          "Table of repositories";
        list repository {
          key "id";
          description
            "Repository configuration";
          leaf url {
            type string {
              length "1..900";
            }
            description
              "Repository URL - path to local repository or
               directory or ftp, http, or https path to
               remote repository, optionally containing the
               name of a VRF for the repository. Format one
               of:
                 ftp://<server>[;<vrf>]/<path_to_repo>

                 http://<server>[;<vrf>]/<path_to_repo>

               https://<server>[;<vrf>]/<path_to_repo>

               file:///<path_to_repo>";
          }
          leaf description {
            type string {
              length "1..900";
            }
            description
              "Repository name or description";
          }
          leaf id {
            type string {
              length "1..80";
            }
            description
              "Repository identifier";
          }
        }
      }
    }
  }
  augment "/ncs:devices/ncs:template/ncs:ned-id/ncs:config" {
    container install {
      description
        "Install configuration data";
      container repositories {
        description
          "Table of repositories";
        list repository {
          // NCS patched for predictable order
          ordered-by user;
          key "id";
          description
            "Repository configuration";
          leaf url {
            type string;
            description
              "Repository URL - path to local repository or
               directory or ftp, http, or https path to
               remote repository, optionally containing the
               name of a VRF for the repository. Format one
               of:
                 ftp://<server>[;<vrf>]/<path_to_repo>

                 http://<server>[;<vrf>]/<path_to_repo>

               https://<server>[;<vrf>]/<path_to_repo>

               file:///<path_to_repo>";
          }
          leaf description {
            type string;
            description
              "Repository name or description";
          }
          leaf id {
            type string;
            description
              "Repository identifier";
          }
        }
      }
    }
  }
}

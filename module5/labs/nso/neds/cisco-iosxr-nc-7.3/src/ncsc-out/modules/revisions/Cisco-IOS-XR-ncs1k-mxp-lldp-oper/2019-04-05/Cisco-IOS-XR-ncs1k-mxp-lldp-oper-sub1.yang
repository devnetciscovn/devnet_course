submodule Cisco-IOS-XR-ncs1k-mxp-lldp-oper-sub1 {
  // Generated by yanger -t ncs
  tailf:mount-id "cisco-iosxr-nc-7.3:cisco-iosxr-nc-7.3";

  belongs-to Cisco-IOS-XR-ncs1k-mxp-lldp-oper {
    prefix Cisco-IOS-XR-ncs1k-mxp-lldp-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1k-mxp-lldp package operational data.

     Copyright (c) 2013-2019 by Cisco Systems, Inc.
     All rights reserved.";

  revision 2019-04-05 {
    description
      "Establish semantic version baseline.";
    semver:module-version "1.0.0";
  }
  revision 2016-10-13 {
    description
      "Added Additional bag for show lldp neighbor command.";
  }
  revision 2015-11-09 {
    description
      "IOS XR 6.0 revision.";
  }

  typedef ncs_template_In6-addr {
    type string;
    description
      "In6 addr";
  }

  typedef ncs_template_Lldp-l3-addr-protocol {
    type string;
    description
      "Lldp l3 addr protocol";
  }

  typedef ncs_rpc_notif_In6-addr {
    type inet:ipv6-address;
    description
      "In6 addr";
  }

  typedef ncs_rpc_notif_Lldp-l3-addr-protocol {
    type enumeration {
      enum "ipv4" {
        description
          "IPv4";
      }
      enum "ipv6" {
        description
          "IPv6";
      }
    }
    description
      "Lldp l3 addr protocol";
  }

  typedef live_ncs_In6-addr {
    type inet:ipv6-address;
    description
      "In6 addr";
  }

  typedef live_ncs_Lldp-l3-addr-protocol {
    type enumeration {
      enum "ipv4" {
        description
          "IPv4";
      }
      enum "ipv6" {
        description
          "IPv6";
      }
    }
    description
      "Lldp l3 addr protocol";
  }

  typedef In6-addr {
    type inet:ipv6-address;
    description
      "In6 addr";
  }

  typedef Lldp-l3-addr-protocol {
    type enumeration {
      enum "ipv4" {
        description
          "IPv4";
      }
      enum "ipv6" {
        description
          "IPv6";
      }
    }
    description
      "Lldp l3 addr protocol";
  }

  grouping ncs_template_LLDP-L3-ADDR {
    description
      "LLDP L3 ADDR";
    leaf address-type {
      type ncs_template_Lldp-l3-addr-protocol;
      description
        "AddressType";
    }
    leaf ipv4-address {
      // NCS drop when statement
      type string;
      description
        "IPv4 address";
    }
    leaf ipv6-address {
      // NCS drop when statement
      type ncs_template_In6-addr;
      description
        "IPv6 address";
    }
  }

  grouping ncs_template_LLDP-ADDRESS-ENTRY {
    description
      "LLDP Address entry";
    list lldp-addr-entry {
      // NCS patched for predictable order
      ordered-by user;
      description
        "Next address entry in list";
      container address {
        description
          "Network layer address";
        uses ncs_template_LLDP-L3-ADDR;
      }
      leaf ma-subtype {
        type string;
        description
          "MA sub type";
      }
      leaf if-num {
        type string;
        description
          "Interface num";
      }
    }
  }

  grouping ncs_template_MXP-LLDP-NEIGHBOR {
    description
      "LLDP neighbor info";
    container network-addresses {
      description
        "Management Addresses";
      uses ncs_template_LLDP-ADDRESS-ENTRY;
    }
    leaf source-mac {
      type string;
      description
        "Mac address of the neighbor";
    }
    leaf chassis-id {
      type string;
      description
        "Chassis id";
    }
    leaf port-id-detail {
      type string;
      description
        "Outgoing port identifier";
    }
    leaf hold-time {
      type string;
      description
        "Remaining hold time";
    }
    leaf port-description {
      type string;
      description
        "Port Description";
    }
    leaf system-name {
      type string;
      description
        "System Name";
    }
    leaf system-description {
      type string;
      description
        "System Description";
    }
    leaf system-capabilities {
      type string;
      description
        "System Capabilities";
    }
    leaf enabled-capabilities {
      type string;
      description
        "Enabled Capabilities";
    }
    leaf lldp-neighbor {
      type string;
      description
        "LldpNeighbor";
    }
    leaf drop-enabled {
      type string;
      description
        "LLDP Packet Drop Enabled";
    }
    leaf rx-lldp-pkts {
      type string;
      description
        "Received LLDP Packets count";
    }
  }

  grouping ncs_rpc_notif_LLDP-L3-ADDR {
    description
      "LLDP L3 ADDR";
    leaf address-type {
      type ncs_rpc_notif_Lldp-l3-addr-protocol;
      description
        "AddressType";
    }
    leaf ipv4-address {
      when "../address-type = 'ipv4'" {
        tailf:xpath-root 3;
        description
          "../AddressType = 'IPv4'";
      }
      type inet:ipv4-address;
      description
        "IPv4 address";
    }
    leaf ipv6-address {
      when "../address-type = 'ipv6'" {
        tailf:xpath-root 3;
        description
          "../AddressType = 'IPv6'";
      }
      type ncs_rpc_notif_In6-addr;
      description
        "IPv6 address";
    }
  }

  grouping ncs_rpc_notif_LLDP-ADDRESS-ENTRY {
    description
      "LLDP Address entry";
    list lldp-addr-entry {
      description
        "Next address entry in list";
      container address {
        description
          "Network layer address";
        uses ncs_rpc_notif_LLDP-L3-ADDR;
      }
      leaf ma-subtype {
        type uint8;
        description
          "MA sub type";
      }
      leaf if-num {
        type uint32;
        description
          "Interface num";
      }
    }
  }

  grouping ncs_rpc_notif_MXP-LLDP-NEIGHBOR {
    description
      "LLDP neighbor info";
    container network-addresses {
      description
        "Management Addresses";
      uses ncs_rpc_notif_LLDP-ADDRESS-ENTRY;
    }
    leaf source-mac {
      type string;
      description
        "Mac address of the neighbor";
    }
    leaf chassis-id {
      type string;
      description
        "Chassis id";
    }
    leaf port-id-detail {
      type string;
      description
        "Outgoing port identifier";
    }
    leaf hold-time {
      type uint16;
      description
        "Remaining hold time";
    }
    leaf port-description {
      type string;
      description
        "Port Description";
    }
    leaf system-name {
      type string;
      description
        "System Name";
    }
    leaf system-description {
      type string;
      description
        "System Description";
    }
    leaf system-capabilities {
      type string;
      description
        "System Capabilities";
    }
    leaf enabled-capabilities {
      type string;
      description
        "Enabled Capabilities";
    }
    leaf lldp-neighbor {
      type string {
        length "0..40";
      }
      description
        "LldpNeighbor";
    }
    leaf drop-enabled {
      type boolean;
      description
        "LLDP Packet Drop Enabled";
    }
    leaf rx-lldp-pkts {
      type uint64;
      description
        "Received LLDP Packets count";
    }
  }

  grouping live_ncs_LLDP-L3-ADDR {
    description
      "LLDP L3 ADDR";
    leaf address-type {
      type live_ncs_Lldp-l3-addr-protocol;
      description
        "AddressType";
    }
    leaf ipv4-address {
      // NCS drop when statement
      type inet:ipv4-address;
      description
        "IPv4 address";
    }
    leaf ipv6-address {
      // NCS drop when statement
      type live_ncs_In6-addr;
      description
        "IPv6 address";
    }
  }

  grouping live_ncs_LLDP-ADDRESS-ENTRY {
    description
      "LLDP Address entry";
    list lldp-addr-entry {
      description
        "Next address entry in list";
      container address {
        description
          "Network layer address";
        uses live_ncs_LLDP-L3-ADDR;
      }
      leaf ma-subtype {
        type uint8;
        description
          "MA sub type";
      }
      leaf if-num {
        type uint32;
        description
          "Interface num";
      }
    }
  }

  grouping live_ncs_MXP-LLDP-NEIGHBOR {
    description
      "LLDP neighbor info";
    container network-addresses {
      description
        "Management Addresses";
      uses live_ncs_LLDP-ADDRESS-ENTRY;
    }
    leaf source-mac {
      type string;
      description
        "Mac address of the neighbor";
    }
    leaf chassis-id {
      type string;
      description
        "Chassis id";
    }
    leaf port-id-detail {
      type string;
      description
        "Outgoing port identifier";
    }
    leaf hold-time {
      type uint16;
      description
        "Remaining hold time";
    }
    leaf port-description {
      type string;
      description
        "Port Description";
    }
    leaf system-name {
      type string;
      description
        "System Name";
    }
    leaf system-description {
      type string;
      description
        "System Description";
    }
    leaf system-capabilities {
      type string;
      description
        "System Capabilities";
    }
    leaf enabled-capabilities {
      type string;
      description
        "Enabled Capabilities";
    }
    leaf lldp-neighbor {
      type string {
        length "0..40";
      }
      description
        "LldpNeighbor";
    }
    leaf drop-enabled {
      type boolean;
      description
        "LLDP Packet Drop Enabled";
    }
    leaf rx-lldp-pkts {
      type uint64;
      description
        "Received LLDP Packets count";
    }
  }

  grouping LLDP-L3-ADDR {
    description
      "LLDP L3 ADDR";
    leaf address-type {
      type Lldp-l3-addr-protocol;
      description
        "AddressType";
    }
    leaf ipv4-address {
      when "../address-type = 'ipv4'" {
        tailf:xpath-root 3;
        description
          "../AddressType = 'IPv4'";
      }
      type inet:ipv4-address;
      description
        "IPv4 address";
    }
    leaf ipv6-address {
      when "../address-type = 'ipv6'" {
        tailf:xpath-root 3;
        description
          "../AddressType = 'IPv6'";
      }
      type In6-addr;
      description
        "IPv6 address";
    }
  }

  grouping LLDP-ADDRESS-ENTRY {
    description
      "LLDP Address entry";
    list lldp-addr-entry {
      description
        "Next address entry in list";
      container address {
        description
          "Network layer address";
        uses LLDP-L3-ADDR;
      }
      leaf ma-subtype {
        type uint8;
        description
          "MA sub type";
      }
      leaf if-num {
        type uint32;
        description
          "Interface num";
      }
    }
  }

  grouping MXP-LLDP-NEIGHBOR {
    description
      "LLDP neighbor info";
    container network-addresses {
      description
        "Management Addresses";
      uses LLDP-ADDRESS-ENTRY;
    }
    leaf source-mac {
      type string;
      description
        "Mac address of the neighbor";
    }
    leaf chassis-id {
      type string;
      description
        "Chassis id";
    }
    leaf port-id-detail {
      type string;
      description
        "Outgoing port identifier";
    }
    leaf hold-time {
      type uint16;
      description
        "Remaining hold time";
    }
    leaf port-description {
      type string;
      description
        "Port Description";
    }
    leaf system-name {
      type string;
      description
        "System Name";
    }
    leaf system-description {
      type string;
      description
        "System Description";
    }
    leaf system-capabilities {
      type string;
      description
        "System Capabilities";
    }
    leaf enabled-capabilities {
      type string;
      description
        "Enabled Capabilities";
    }
    leaf lldp-neighbor {
      type string {
        length "0..40";
      }
      description
        "LldpNeighbor";
    }
    leaf drop-enabled {
      type boolean;
      description
        "LLDP Packet Drop Enabled";
    }
    leaf rx-lldp-pkts {
      type uint64;
      description
        "Received LLDP Packets count";
    }
  }
}

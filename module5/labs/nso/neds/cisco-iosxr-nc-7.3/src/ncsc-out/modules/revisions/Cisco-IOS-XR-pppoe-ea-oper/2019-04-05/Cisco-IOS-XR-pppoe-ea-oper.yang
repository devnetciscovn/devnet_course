module Cisco-IOS-XR-pppoe-ea-oper {
  // Generated by yanger -t ncs
  tailf:mount-id "cisco-iosxr-nc-7.3:cisco-iosxr-nc-7.3";
  tailf:ncs-device-type "netconf";

  namespace "http://cisco.com/ns/yang/Cisco-IOS-XR-pppoe-ea-oper";
  prefix pppoe-ea-oper;

  import Cisco-IOS-XR-types {
    prefix xr;
  }
  import cisco-semver {
    prefix semver;
  }
  include Cisco-IOS-XR-pppoe-ea-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pppoe-ea package operational data.

     This module contains definitions
     for the following management objects:
       pppoe-ea: PPPoE Ea data

     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/ncs:devices/ncs:device/ncs:config" {
    // NCS drop config false container 'pppoe-ea'
  }
  augment "/ncs:devices/ncs:device/ncs:live-status" {
    container pppoe-ea {
      tailf:ncs-device-type "netconf";
      tailf:display-when "not(../../ncs:module) or ../../ncs:module[ncs:name='Cisco-IOS-XR-pppoe-ea-oper'] or (../../ncs:live-status-protocol[not(ncs:capability)]) or (../../ncs:live-status-protocol/ncs:capability/ncs:module[.='Cisco-IOS-XR-pppoe-ea-oper'])";
      description
        "PPPoE Ea data";
      container nodes {
        description
          "PPPOE_EA list of nodes";
        list node {
          key "node-name";
          description
            "PPPOE-EA operational data for a particular node";
          container parent-interface-ids {
            description
              "PPPoE parent interface info";
            list parent-interface-id {
              key "parent-interface-name";
              description
                "PPPoE parent interface info";
              leaf parent-interface-name {
                type xr:live_ncs_Interface-name;
                description
                  "Interface Name";
              }
              uses live_ncs_PPPOE-EA-PARENT-INTERFACE-INFO;
            }
          }
          container interface-ids {
            description
              "PPPoE interface info";
            list interface-id {
              key "interface-name";
              description
                "PPPoE interface info";
              leaf interface-name {
                type xr:live_ncs_Interface-name;
                description
                  "Interface Name";
              }
              uses live_ncs_PPPOE-EA-INTERFACE-INFO;
            }
          }
          leaf node-name {
            type xr:live_ncs_Node-id;
            description
              "Node name";
          }
        }
      }
    }
  }
  augment "/ncs:devices/ncs:template/ncs:ned-id/ncs:config" {
    // NCS drop config false container 'pppoe-ea'
  }
}

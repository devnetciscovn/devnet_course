module Cisco-IOS-XR-npu-hw-profile-cfg {
  // Generated by yanger -t ncs
  tailf:mount-id "cisco-iosxr-nc-7.3:cisco-iosxr-nc-7.3";
  tailf:ncs-device-type "netconf";

  namespace "http://cisco.com/ns/yang/Cisco-IOS-XR-npu-hw-profile-cfg";
  prefix npu-hw-profile-cfg;

  import Cisco-IOS-XR-types {
    prefix xr;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR npu-hw-profile package configuration.

     This module contains definitions
     for the following management objects:
       macsec-hw-module: Macsec Related HW Module configs, Reload
         Card after config
       npu-hw-module-profile-config: none

     Copyright (c) 2013-2021 by Cisco Systems, Inc.
     All rights reserved.";

  revision 2021-06-28 {
    description
      "Yang Schema updated to accept a range of values for lpts entry counters
       2021-04-30
         Yang Schema added for bd flush convergence
       2021-03-04
         Yang Schema added for pifib entry counters
       2021-02-16
         Yang Schema added for cbf";
    semver:module-version "1.1.0";
  }
  revision 2021-01-26 {
    description
      "Added CEF profile for punting ip-redirect";
    semver:module-version "1.0.0";
  }
  revision 2021-01-11 {
    description
      "Added profile CEF IPv6 hop-limit punt";
  }
  revision 2020-11-13 {
    description
      "Yang Schema removed block for NPU power profile in hw-module config.";
  }
  revision 2020-11-09 {
    description
      "Yang Schema fixed for npu config hw module cli - power profile model.";
  }
  revision 2020-09-29 {
    description
      "Yang Schema added for l2-qos-mode";
  }
  revision 2020-09-01 {
    description
      "Yang Schema added new VoQ modes.";
  }
  revision 2020-07-30 {
    description
      "Yang Schema added for npu-power-optimize";
  }
  revision 2020-06-04 {
    description
      "Yang Schema added for ttl mode of ip tunnel";
  }
  revision 2020-05-27 {
    description
      "Yang Schema added Macsec Related Yang Config Model.";
  }
  revision 2020-04-03 {
    description
      "Yang Schema added for label stats";
  }
  revision 2020-02-05 {
    description
      "Yang Schema updated for reorganized cli knobs.";
  }
  revision 2020-01-22 {
    description
      "Yang Schema added for bw-threshold.";
  }
  revision 2019-12-23 {
    description
      "Yang Schema adde for VoQ and Counter Sharing modes.";
  }
  revision 2019-10-14 {
    description
      "Yang Schema fixed for npu config hw module cli.";
  }
  revision 2019-04-05 {
    description
      "Establish semantic version baseline.";
  }
  revision 2015-11-09 {
    description
      "IOS XR 6.0 revision.";
  }

  typedef ncs_template_Ipv6-hop-limit-action {
    type string;
    description
      "Ipv6 hop limit action";
  }

  typedef ncs_template_Qos-voq-mode {
    type string;
    description
      "Qos voq mode";
  }

  typedef ncs_rpc_notif_Ipv6-hop-limit-action {
    type enumeration {
      enum "punt" {
        value 1;
        description
          "IPv6 hop-limit punt";
      }
    }
    description
      "Ipv6 hop limit action";
  }

  typedef ncs_rpc_notif_Qos-voq-mode {
    type enumeration {
      enum "4" {
        value 4;
        description
          "4 VoQ Mode";
      }
      enum "8" {
        value 8;
        description
          "8 VoQ Mode";
      }
    }
    description
      "Qos voq mode";
  }

  typedef live_ncs_Ipv6-hop-limit-action {
    type enumeration {
      enum "punt" {
        value 1;
        description
          "IPv6 hop-limit punt";
      }
    }
    description
      "Ipv6 hop limit action";
  }

  typedef live_ncs_Qos-voq-mode {
    type enumeration {
      enum "4" {
        value 4;
        description
          "4 VoQ Mode";
      }
      enum "8" {
        value 8;
        description
          "8 VoQ Mode";
      }
    }
    description
      "Qos voq mode";
  }

  typedef Ipv6-hop-limit-action {
    type enumeration {
      enum "punt" {
        value 1;
        description
          "IPv6 hop-limit punt";
      }
    }
    description
      "Ipv6 hop limit action";
  }

  typedef Qos-voq-mode {
    type enumeration {
      enum "4" {
        value 4;
        description
          "4 VoQ Mode";
      }
      enum "8" {
        value 8;
        description
          "8 VoQ Mode";
      }
    }
    description
      "Qos voq mode";
  }

  augment "/ncs:devices/ncs:device/ncs:config" {
    container macsec-hw-module {
      tailf:ncs-device-type "netconf";
      tailf:display-when "not(../../ncs:module) or ../../ncs:module[ncs:name='Cisco-IOS-XR-npu-hw-profile-cfg']";
      description
        "Macsec Related HW Module configs, Reload Card
         after config";
      container fips-post-location-tables {
        description
          "Enable macsec-fips-post";
        list fips-post-location-table {
          key "location-string";
          description
            "none";
          leaf location-string {
            type xr:Cisco-ios-xr-string;
            description
              "Location of MacsecFipsPost config or all";
          }
          list fips-post-location {
            key "location-id";
            description
              "none";
            leaf location-id {
              type uint32;
              description
                "Location ID if all set to 65535";
            }
            leaf enable-val {
              type uint32;
              mandatory true;
              description
                "If Enabled set value to 65535";
            }
          }
        }
      }
      container macsec-mode-location-tables {
        description
          "Enable macsec-mode";
        list macsec-mode-location-table {
          key "location-string";
          description
            "none";
          leaf location-string {
            type xr:Cisco-ios-xr-string;
            description
              "Location of MacSecMode config or all";
          }
          list macsec-mode-location {
            key "location-id";
            description
              "none";
            leaf location-id {
              type uint32;
              description
                "Location ID if all set to 65535";
            }
            leaf enable-val {
              type uint32;
              mandatory true;
              description
                "If Enabled set value to 65535";
            }
          }
        }
      }
    }
    container npu-hw-module-profile-config {
      tailf:ncs-device-type "netconf";
      tailf:display-when "not(../../ncs:module) or ../../ncs:module[ncs:name='Cisco-IOS-XR-npu-hw-profile-cfg']";
      description
        "none";
      container profile {
        description
          "Configure profile.";
        container qos {
          description
            "Configure qos profile";
          leaf l2-mode {
            type uint32 {
              range "2..3";
            }
            description
              "value either 2 or 3 (for L2 or L3 mode)";
          }
          leaf voq-mode {
            type Qos-voq-mode;
            description
              "voq mode to configure";
          }
        }
        container tcam-table {
          description
            "Configure profile for TCAM LC cards";
          container fib-table {
            description
              "FIB table for TCAM LC cards";
            container ipv6-address {
              description
                "IPv6 table for TCAM LC cards";
              container ipv6-unicast {
                description
                  "Unicast table for TCAM LC cards";
                leaf ipv6-unicast-percent {
                  type uint32 {
                    range "0..100";
                  }
                  units "percentage";
                  description
                    "curve out percentage of TCAM table entries";
                }
              }
            }
            container ipv4-address {
              description
                "IPv4 table for TCAM LC cards";
              container ipv4-unicast {
                description
                  "Unicast table for TCAM LC cards";
                leaf ipv4-unicast-percent {
                  type uint32 {
                    range "0..100";
                  }
                  units "percentage";
                  description
                    "curve out percentage of TCAM table entries";
                }
              }
            }
          }
          container acl-table {
            description
              "ACL table for TCAM LC cards";
            leaf acl-percent {
              type uint32 {
                range "0..100";
              }
              units "percentage";
              description
                "curve out percentage of TCAM table entries";
            }
          }
        }
        container netflow {
          description
            "Configure Netflow profile.";
          container ipfix-netflow-locations {
            description
              "none";
            list ipfix-netflow-location {
              key "location-string";
              description
                "none";
              leaf location-string {
                type xr:Cisco-ios-xr-string;
                description
                  "Location of NETFLOW config";
              }
              list ipfix-netflow-location-leaf {
                key "location-id";
                description
                  "none";
                leaf location-id {
                  type uint32;
                  description
                    "Location ID";
                }
                leaf enable-val {
                  type uint32;
                  mandatory true;
                  description
                    "If Enabled set value to 65535";
                }
              }
            }
          }
          container ipfix-location-all {
            description
              "IPFIX315 Location All";
            leaf ipfix-location-all-leaf {
              type uint32;
              description
                "If Enabled set value to 65535";
            }
          }
        }
        container stats {
          description
            "Configure statistics profile";
          leaf voq-sharing-counters {
            type uint32 {
              range "1..4";
            }
            description
              "Configure number of voqs (1, 2, 4) sharing
               counters";
          }
        }
        container l2fib {
          description
            "Configure l2fib profiles";
          leaf pw-stats {
            type uint32;
            description
              "If enabled, set value to 1";
          }
          leaf bd-flush-conv {
            type boolean;
            description
              "TRUE if enabled, FALSE if disabled";
          }
        }
        container cef-forwarding {
          description
            "Configure cef profiles";
          container te-tunnel {
            description
              "Configure te-tunnel profile";
            leaf high-scale {
              type uint32;
              description
                "Configure te-tunnel highscale and disable ldp
                 over te feature";
            }
          }
          container cef-stats {
            description
              "Configure feature level stats";
            container label {
              description
                "Configure label stats";
              container app-default {
                description
                  "Applies to - LDP and SR";
                leaf dynamic {
                  type uint32;
                  description
                    "If enabled, set value to 1";
                }
              }
            }
          }
          container ttl {
            description
              "Configure ttl profile";
            container tunnel-ip {
              description
                "Configure tunnel-ip ttl mode";
              leaf decrement {
                type uint32;
                description
                  "Configure tunnel-ip ttl decrement attribute";
              }
            }
          }
          container ipv6 {
            description
              "IPv6";
            leaf hop-limit {
              type Ipv6-hop-limit-action;
              description
                "IPv6 hop-limit 0 packets";
            }
          }
          container lpts-xr {
            description
              "Enable lpts pifib per-entry counters";
            leaf pifib-entry-counters {
              type uint32 {
                range "256..512";
              }
              description
                "Configure number of counters";
            }
          }
          container lpts {
            description
              "LPTS";
            leaf acl {
              type empty;
              description
                "Enable profile CEF LPTS ACL";
            }
          }
          leaf cbf {
            type empty;
            description
              "Enable cbf feature";
          }
          leaf bgplu {
            type uint32;
            description
              "If Enabled set value to 1";
          }
          leaf dark-bandwidth {
            type uint32 {
              range "0..1";
            }
            description
              "Configure dark-bandwidth feature";
          }
          leaf ip-redirect {
            type uint32 {
              range "0..1";
            }
            description
              "value either 0 or 1";
          }
        }
        leaf bw-threshold {
          type string;
          units "percentage";
          description
            "Configure fabric BW";
        }
      }
    }
  }
  augment "/ncs:devices/ncs:device/ncs:live-status" {
    container macsec-hw-module {
      tailf:ncs-device-type "netconf";
      tailf:display-when "not(../../ncs:module) or ../../ncs:module[ncs:name='Cisco-IOS-XR-npu-hw-profile-cfg'] or (../../ncs:live-status-protocol[not(ncs:capability)]) or (../../ncs:live-status-protocol/ncs:capability/ncs:module[.='Cisco-IOS-XR-npu-hw-profile-cfg'])";
      description
        "Macsec Related HW Module configs, Reload Card
         after config";
      container fips-post-location-tables {
        description
          "Enable macsec-fips-post";
        list fips-post-location-table {
          key "location-string";
          description
            "none";
          leaf location-string {
            type xr:live_ncs_Cisco-ios-xr-string;
            description
              "Location of MacsecFipsPost config or all";
          }
          list fips-post-location {
            key "location-id";
            description
              "none";
            leaf location-id {
              type uint32;
              description
                "Location ID if all set to 65535";
            }
            leaf enable-val {
              type uint32;
              // NCS drop mandatory statement
              description
                "If Enabled set value to 65535";
            }
          }
        }
      }
      container macsec-mode-location-tables {
        description
          "Enable macsec-mode";
        list macsec-mode-location-table {
          key "location-string";
          description
            "none";
          leaf location-string {
            type xr:live_ncs_Cisco-ios-xr-string;
            description
              "Location of MacSecMode config or all";
          }
          list macsec-mode-location {
            key "location-id";
            description
              "none";
            leaf location-id {
              type uint32;
              description
                "Location ID if all set to 65535";
            }
            leaf enable-val {
              type uint32;
              // NCS drop mandatory statement
              description
                "If Enabled set value to 65535";
            }
          }
        }
      }
    }
    container npu-hw-module-profile-config {
      tailf:ncs-device-type "netconf";
      tailf:display-when "not(../../ncs:module) or ../../ncs:module[ncs:name='Cisco-IOS-XR-npu-hw-profile-cfg'] or (../../ncs:live-status-protocol[not(ncs:capability)]) or (../../ncs:live-status-protocol/ncs:capability/ncs:module[.='Cisco-IOS-XR-npu-hw-profile-cfg'])";
      description
        "none";
      container profile {
        description
          "Configure profile.";
        container qos {
          description
            "Configure qos profile";
          leaf l2-mode {
            type uint32 {
              range "2..3";
            }
            description
              "value either 2 or 3 (for L2 or L3 mode)";
          }
          leaf voq-mode {
            type live_ncs_Qos-voq-mode;
            description
              "voq mode to configure";
          }
        }
        container tcam-table {
          description
            "Configure profile for TCAM LC cards";
          container fib-table {
            description
              "FIB table for TCAM LC cards";
            container ipv6-address {
              description
                "IPv6 table for TCAM LC cards";
              container ipv6-unicast {
                description
                  "Unicast table for TCAM LC cards";
                leaf ipv6-unicast-percent {
                  type uint32 {
                    range "0..100";
                  }
                  units "percentage";
                  description
                    "curve out percentage of TCAM table entries";
                }
              }
            }
            container ipv4-address {
              description
                "IPv4 table for TCAM LC cards";
              container ipv4-unicast {
                description
                  "Unicast table for TCAM LC cards";
                leaf ipv4-unicast-percent {
                  type uint32 {
                    range "0..100";
                  }
                  units "percentage";
                  description
                    "curve out percentage of TCAM table entries";
                }
              }
            }
          }
          container acl-table {
            description
              "ACL table for TCAM LC cards";
            leaf acl-percent {
              type uint32 {
                range "0..100";
              }
              units "percentage";
              description
                "curve out percentage of TCAM table entries";
            }
          }
        }
        container netflow {
          description
            "Configure Netflow profile.";
          container ipfix-netflow-locations {
            description
              "none";
            list ipfix-netflow-location {
              key "location-string";
              description
                "none";
              leaf location-string {
                type xr:live_ncs_Cisco-ios-xr-string;
                description
                  "Location of NETFLOW config";
              }
              list ipfix-netflow-location-leaf {
                key "location-id";
                description
                  "none";
                leaf location-id {
                  type uint32;
                  description
                    "Location ID";
                }
                leaf enable-val {
                  type uint32;
                  // NCS drop mandatory statement
                  description
                    "If Enabled set value to 65535";
                }
              }
            }
          }
          container ipfix-location-all {
            description
              "IPFIX315 Location All";
            leaf ipfix-location-all-leaf {
              type uint32;
              description
                "If Enabled set value to 65535";
            }
          }
        }
        container stats {
          description
            "Configure statistics profile";
          leaf voq-sharing-counters {
            type uint32 {
              range "1..4";
            }
            description
              "Configure number of voqs (1, 2, 4) sharing
               counters";
          }
        }
        container l2fib {
          description
            "Configure l2fib profiles";
          leaf pw-stats {
            type uint32;
            description
              "If enabled, set value to 1";
          }
          leaf bd-flush-conv {
            type boolean;
            description
              "TRUE if enabled, FALSE if disabled";
          }
        }
        container cef-forwarding {
          description
            "Configure cef profiles";
          container te-tunnel {
            description
              "Configure te-tunnel profile";
            leaf high-scale {
              type uint32;
              description
                "Configure te-tunnel highscale and disable ldp
                 over te feature";
            }
          }
          container cef-stats {
            description
              "Configure feature level stats";
            container label {
              description
                "Configure label stats";
              container app-default {
                description
                  "Applies to - LDP and SR";
                leaf dynamic {
                  type uint32;
                  description
                    "If enabled, set value to 1";
                }
              }
            }
          }
          container ttl {
            description
              "Configure ttl profile";
            container tunnel-ip {
              description
                "Configure tunnel-ip ttl mode";
              leaf decrement {
                type uint32;
                description
                  "Configure tunnel-ip ttl decrement attribute";
              }
            }
          }
          container ipv6 {
            description
              "IPv6";
            leaf hop-limit {
              type live_ncs_Ipv6-hop-limit-action;
              description
                "IPv6 hop-limit 0 packets";
            }
          }
          container lpts-xr {
            description
              "Enable lpts pifib per-entry counters";
            leaf pifib-entry-counters {
              type uint32 {
                range "256..512";
              }
              description
                "Configure number of counters";
            }
          }
          container lpts {
            description
              "LPTS";
            leaf acl {
              type empty;
              description
                "Enable profile CEF LPTS ACL";
            }
          }
          leaf cbf {
            type empty;
            description
              "Enable cbf feature";
          }
          leaf bgplu {
            type uint32;
            description
              "If Enabled set value to 1";
          }
          leaf dark-bandwidth {
            type uint32 {
              range "0..1";
            }
            description
              "Configure dark-bandwidth feature";
          }
          leaf ip-redirect {
            type uint32 {
              range "0..1";
            }
            description
              "value either 0 or 1";
          }
        }
        leaf bw-threshold {
          type string;
          units "percentage";
          description
            "Configure fabric BW";
        }
      }
    }
  }
  augment "/ncs:devices/ncs:template/ncs:ned-id/ncs:config" {
    container macsec-hw-module {
      description
        "Macsec Related HW Module configs, Reload Card
         after config";
      container fips-post-location-tables {
        description
          "Enable macsec-fips-post";
        list fips-post-location-table {
          // NCS patched for predictable order
          ordered-by user;
          key "location-string";
          description
            "none";
          leaf location-string {
            type xr:ncs_template_Cisco-ios-xr-string;
            description
              "Location of MacsecFipsPost config or all";
          }
          list fips-post-location {
            // NCS patched for predictable order
            ordered-by user;
            key "location-id";
            description
              "none";
            leaf location-id {
              type string;
              description
                "Location ID if all set to 65535";
            }
            leaf enable-val {
              type string;
              // NCS drop mandatory statement
              description
                "If Enabled set value to 65535";
            }
          }
        }
      }
      container macsec-mode-location-tables {
        description
          "Enable macsec-mode";
        list macsec-mode-location-table {
          // NCS patched for predictable order
          ordered-by user;
          key "location-string";
          description
            "none";
          leaf location-string {
            type xr:ncs_template_Cisco-ios-xr-string;
            description
              "Location of MacSecMode config or all";
          }
          list macsec-mode-location {
            // NCS patched for predictable order
            ordered-by user;
            key "location-id";
            description
              "none";
            leaf location-id {
              type string;
              description
                "Location ID if all set to 65535";
            }
            leaf enable-val {
              type string;
              // NCS drop mandatory statement
              description
                "If Enabled set value to 65535";
            }
          }
        }
      }
    }
    container npu-hw-module-profile-config {
      description
        "none";
      container profile {
        description
          "Configure profile.";
        container qos {
          description
            "Configure qos profile";
          leaf l2-mode {
            type string;
            description
              "value either 2 or 3 (for L2 or L3 mode)";
          }
          leaf voq-mode {
            type ncs_template_Qos-voq-mode;
            description
              "voq mode to configure";
          }
        }
        container tcam-table {
          description
            "Configure profile for TCAM LC cards";
          container fib-table {
            description
              "FIB table for TCAM LC cards";
            container ipv6-address {
              description
                "IPv6 table for TCAM LC cards";
              container ipv6-unicast {
                description
                  "Unicast table for TCAM LC cards";
                leaf ipv6-unicast-percent {
                  type string;
                  units "percentage";
                  description
                    "curve out percentage of TCAM table entries";
                }
              }
            }
            container ipv4-address {
              description
                "IPv4 table for TCAM LC cards";
              container ipv4-unicast {
                description
                  "Unicast table for TCAM LC cards";
                leaf ipv4-unicast-percent {
                  type string;
                  units "percentage";
                  description
                    "curve out percentage of TCAM table entries";
                }
              }
            }
          }
          container acl-table {
            description
              "ACL table for TCAM LC cards";
            leaf acl-percent {
              type string;
              units "percentage";
              description
                "curve out percentage of TCAM table entries";
            }
          }
        }
        container netflow {
          description
            "Configure Netflow profile.";
          container ipfix-netflow-locations {
            description
              "none";
            list ipfix-netflow-location {
              // NCS patched for predictable order
              ordered-by user;
              key "location-string";
              description
                "none";
              leaf location-string {
                type xr:ncs_template_Cisco-ios-xr-string;
                description
                  "Location of NETFLOW config";
              }
              list ipfix-netflow-location-leaf {
                // NCS patched for predictable order
                ordered-by user;
                key "location-id";
                description
                  "none";
                leaf location-id {
                  type string;
                  description
                    "Location ID";
                }
                leaf enable-val {
                  type string;
                  // NCS drop mandatory statement
                  description
                    "If Enabled set value to 65535";
                }
              }
            }
          }
          container ipfix-location-all {
            description
              "IPFIX315 Location All";
            leaf ipfix-location-all-leaf {
              type string;
              description
                "If Enabled set value to 65535";
            }
          }
        }
        container stats {
          description
            "Configure statistics profile";
          leaf voq-sharing-counters {
            type string;
            description
              "Configure number of voqs (1, 2, 4) sharing
               counters";
          }
        }
        container l2fib {
          description
            "Configure l2fib profiles";
          leaf pw-stats {
            type string;
            description
              "If enabled, set value to 1";
          }
          leaf bd-flush-conv {
            type string;
            description
              "TRUE if enabled, FALSE if disabled";
          }
        }
        container cef-forwarding {
          description
            "Configure cef profiles";
          container te-tunnel {
            description
              "Configure te-tunnel profile";
            leaf high-scale {
              type string;
              description
                "Configure te-tunnel highscale and disable ldp
                 over te feature";
            }
          }
          container cef-stats {
            description
              "Configure feature level stats";
            container label {
              description
                "Configure label stats";
              container app-default {
                description
                  "Applies to - LDP and SR";
                leaf dynamic {
                  type string;
                  description
                    "If enabled, set value to 1";
                }
              }
            }
          }
          container ttl {
            description
              "Configure ttl profile";
            container tunnel-ip {
              description
                "Configure tunnel-ip ttl mode";
              leaf decrement {
                type string;
                description
                  "Configure tunnel-ip ttl decrement attribute";
              }
            }
          }
          container ipv6 {
            description
              "IPv6";
            leaf hop-limit {
              type ncs_template_Ipv6-hop-limit-action;
              description
                "IPv6 hop-limit 0 packets";
            }
          }
          container lpts-xr {
            description
              "Enable lpts pifib per-entry counters";
            leaf pifib-entry-counters {
              type string;
              description
                "Configure number of counters";
            }
          }
          container lpts {
            description
              "LPTS";
            leaf acl {
              type empty;
              description
                "Enable profile CEF LPTS ACL";
            }
          }
          leaf cbf {
            type empty;
            description
              "Enable cbf feature";
          }
          leaf bgplu {
            type string;
            description
              "If Enabled set value to 1";
          }
          leaf dark-bandwidth {
            type string;
            description
              "Configure dark-bandwidth feature";
          }
          leaf ip-redirect {
            type string;
            description
              "value either 0 or 1";
          }
        }
        leaf bw-threshold {
          type string;
          units "percentage";
          description
            "Configure fabric BW";
        }
      }
    }
  }
}

module Cisco-IOS-XR-infra-statsd-oper {
  // Generated by yanger -t ncs
  tailf:mount-id "cisco-iosxr-nc-7.3:cisco-iosxr-nc-7.3";
  tailf:ncs-device-type "netconf";

  namespace "http://cisco.com/ns/yang/Cisco-IOS-XR-infra-statsd-oper";
  prefix infra-statsd-oper;

  import Cisco-IOS-XR-types {
    prefix xr;
  }
  import cisco-semver {
    prefix semver;
  }
  include Cisco-IOS-XR-infra-statsd-oper-sub1 {
    revision-date 2020-12-17;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-statsd package operational data.

     This module contains definitions
     for the following management objects:
       infra-statistics: Statistics Infrastructure

     Copyright (c) 2013-2020 by Cisco Systems, Inc.
     All rights reserved.";

  revision 2020-12-17 {
    description
      "Unit of bandwidth in datarate container changed from 32-bit to 64-bit.";
    semver:module-version "1.2.0";
  }
  revision 2020-10-08 {
    description
      "Unit of last-data-time in milliseconds reverted to seconds for generic stats
       2020-05-05
       Added Hardware timestamp support for protocol stats.
       2020-04-14
       Unit of last-data-time changed from seconds to milliseconds for generic stats
       2020-04-14
       Data type of last-data-time changed from uint32 to uint64 for generic and proto stats
       2020-04-14
       Adding Hardware timestamp feature in generic structure.";
    semver:module-version "1.1.0";
  }
  revision 2019-04-05 {
    description
      "Establish semantic version baseline.";
    semver:module-version "1.0.1";
  }
  revision 2015-11-09 {
    description
      "IOS XR 6.0 revision.";
  }

  grouping ncs_template_DATA-RATE {
    description
      "Common node of latest, cache, total, interface";
    container data-rate {
      description
        "Datarate information";
      uses ncs_template_STATSDBAG-DATARATE;
    }
  }

  grouping ncs_template_PROTOCOL-TABLE {
    description
      "Common node of latest, cache, total, interface";
    container protocols {
      description
        "List of protocols";
      list protocol {
        // NCS patched for predictable order
        ordered-by user;
        key "protocol-name";
        description
          "Interface counters per protocol";
        leaf protocol-name {
          type xr:ncs_template_Cisco-ios-xr-string;
          description
            "Name of the protocol";
        }
        uses ncs_template_IFSTATSBAG-PROTO;
      }
    }
  }

  grouping ncs_template_INTERFACES-MIB-COUNTERS {
    description
      "Common node of latest, cache, total, interface";
    container interfaces-mib-counters {
      description
        "Set of interface counters as displayed by the
         InterfacesMIB";
      uses ncs_template_IFSTATSBAG-GENERIC;
    }
  }

  grouping ncs_template_GENERIC-COUNTERS {
    description
      "Common node of latest, cache, total, interface";
    container generic-counters {
      description
        "Generic set of interface counters";
      uses ncs_template_IFSTATSBAG-GENERIC;
    }
  }

  grouping ncs_rpc_notif_DATA-RATE {
    description
      "Common node of latest, cache, total, interface";
    container data-rate {
      description
        "Datarate information";
      uses ncs_rpc_notif_STATSDBAG-DATARATE;
    }
  }

  grouping ncs_rpc_notif_PROTOCOL-TABLE {
    description
      "Common node of latest, cache, total, interface";
    container protocols {
      description
        "List of protocols";
      list protocol {
        key "protocol-name";
        description
          "Interface counters per protocol";
        leaf protocol-name {
          type xr:ncs_rpc_notif_Cisco-ios-xr-string;
          description
            "Name of the protocol";
        }
        uses ncs_rpc_notif_IFSTATSBAG-PROTO;
      }
    }
  }

  grouping ncs_rpc_notif_INTERFACES-MIB-COUNTERS {
    description
      "Common node of latest, cache, total, interface";
    container interfaces-mib-counters {
      description
        "Set of interface counters as displayed by the
         InterfacesMIB";
      uses ncs_rpc_notif_IFSTATSBAG-GENERIC;
    }
  }

  grouping ncs_rpc_notif_GENERIC-COUNTERS {
    description
      "Common node of latest, cache, total, interface";
    container generic-counters {
      description
        "Generic set of interface counters";
      uses ncs_rpc_notif_IFSTATSBAG-GENERIC;
    }
  }

  grouping live_ncs_DATA-RATE {
    description
      "Common node of latest, cache, total, interface";
    container data-rate {
      description
        "Datarate information";
      uses live_ncs_STATSDBAG-DATARATE;
    }
  }

  grouping live_ncs_PROTOCOL-TABLE {
    description
      "Common node of latest, cache, total, interface";
    container protocols {
      description
        "List of protocols";
      list protocol {
        key "protocol-name";
        description
          "Interface counters per protocol";
        leaf protocol-name {
          type xr:live_ncs_Cisco-ios-xr-string;
          description
            "Name of the protocol";
        }
        uses live_ncs_IFSTATSBAG-PROTO;
      }
    }
  }

  grouping live_ncs_INTERFACES-MIB-COUNTERS {
    description
      "Common node of latest, cache, total, interface";
    container interfaces-mib-counters {
      description
        "Set of interface counters as displayed by the
         InterfacesMIB";
      uses live_ncs_IFSTATSBAG-GENERIC;
    }
  }

  grouping live_ncs_GENERIC-COUNTERS {
    description
      "Common node of latest, cache, total, interface";
    container generic-counters {
      description
        "Generic set of interface counters";
      uses live_ncs_IFSTATSBAG-GENERIC;
    }
  }

  grouping DATA-RATE {
    description
      "Common node of latest, cache, total, interface";
    container data-rate {
      description
        "Datarate information";
      uses STATSDBAG-DATARATE;
    }
  }

  grouping PROTOCOL-TABLE {
    description
      "Common node of latest, cache, total, interface";
    container protocols {
      description
        "List of protocols";
      list protocol {
        key "protocol-name";
        description
          "Interface counters per protocol";
        leaf protocol-name {
          type xr:Cisco-ios-xr-string;
          description
            "Name of the protocol";
        }
        uses IFSTATSBAG-PROTO;
      }
    }
  }

  grouping INTERFACES-MIB-COUNTERS {
    description
      "Common node of latest, cache, total, interface";
    container interfaces-mib-counters {
      description
        "Set of interface counters as displayed by the
         InterfacesMIB";
      uses IFSTATSBAG-GENERIC;
    }
  }

  grouping GENERIC-COUNTERS {
    description
      "Common node of latest, cache, total, interface";
    container generic-counters {
      description
        "Generic set of interface counters";
      uses IFSTATSBAG-GENERIC;
    }
  }

  augment "/ncs:devices/ncs:device/ncs:config" {
    // NCS drop config false container 'infra-statistics'
  }
  augment "/ncs:devices/ncs:device/ncs:live-status" {
    container infra-statistics {
      tailf:ncs-device-type "netconf";
      tailf:display-when "not(../../ncs:module) or ../../ncs:module[ncs:name='Cisco-IOS-XR-infra-statsd-oper'] or (../../ncs:live-status-protocol[not(ncs:capability)]) or (../../ncs:live-status-protocol/ncs:capability/ncs:module[.='Cisco-IOS-XR-infra-statsd-oper'])";
      description
        "Statistics Infrastructure";
      container interfaces {
        description
          "List of interfaces";
        list interface {
          key "interface-name";
          description
            "Statistics of an interface";
          container cache {
            description
              "Cached stats data of interfaces";
            uses live_ncs_PROTOCOL-TABLE;
            uses live_ncs_INTERFACES-MIB-COUNTERS;
            uses live_ncs_DATA-RATE;
            uses live_ncs_GENERIC-COUNTERS;
          }
          container latest {
            description
              "Latest stats data of interfaces";
            uses live_ncs_PROTOCOL-TABLE;
            uses live_ncs_INTERFACES-MIB-COUNTERS;
            uses live_ncs_DATA-RATE;
            uses live_ncs_GENERIC-COUNTERS;
          }
          container total {
            description
              "Total stats data of interfaces";
            uses live_ncs_PROTOCOL-TABLE;
            uses live_ncs_INTERFACES-MIB-COUNTERS;
            uses live_ncs_DATA-RATE;
            uses live_ncs_GENERIC-COUNTERS;
          }
          leaf interface-name {
            type xr:live_ncs_Interface-name;
            description
              "Name of the interface";
          }
          uses live_ncs_PROTOCOL-TABLE;
          uses live_ncs_INTERFACES-MIB-COUNTERS;
          uses live_ncs_DATA-RATE;
          uses live_ncs_GENERIC-COUNTERS;
        }
      }
    }
  }
  augment "/ncs:devices/ncs:template/ncs:ned-id/ncs:config" {
    // NCS drop config false container 'infra-statistics'
  }
}

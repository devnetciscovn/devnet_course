submodule Cisco-IOS-XR-shellutil-filesystem-oper-sub1 {
  // Generated by yanger -t ncs
  tailf:mount-id "cisco-iosxr-nc-7.3:cisco-iosxr-nc-7.3";

  belongs-to Cisco-IOS-XR-shellutil-filesystem-oper {
    prefix Cisco-IOS-XR-shellutil-filesystem-oper;
  }

  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR shellutil-filesystem package operational data.

     Copyright (c) 2013-2021 by Cisco Systems, Inc.
     All rights reserved.";

  revision 2021-03-22 {
    description
      "Changing type of size and free from string to uint64_t.";
    semver:module-version "2.0.0";
  }
  revision 2019-04-05 {
    description
      "Establish semantic version baseline.";
    semver:module-version "1.0.1";
  }
  revision 2015-11-09 {
    description
      "IOS XR 6.0 revision.";
  }

  grouping ncs_template_FILESYSTEM-UTIL {
    description
      "File System Description";
    leaf size {
      type string;
      units "byte";
      description
        "Size of the file system in bytes";
    }
    leaf free {
      type string;
      units "byte";
      description
        "Free space in the file system in bytes";
    }
    leaf type {
      type string;
      description
        "Type of file system";
    }
    leaf flags {
      type string;
      description
        "Flags of file system";
    }
    leaf prefixes {
      type string;
      description
        "Prefixes of file system";
    }
  }

  grouping ncs_template_FILESYSTEM {
    description
      "File Systems";
    list file-system {
      // NCS patched for predictable order
      ordered-by user;
      description
        "Available file systems";
      uses ncs_template_FILESYSTEM-UTIL;
    }
  }

  grouping ncs_rpc_notif_FILESYSTEM-UTIL {
    description
      "File System Description";
    leaf size {
      type uint64;
      units "byte";
      description
        "Size of the file system in bytes";
    }
    leaf free {
      type uint64;
      units "byte";
      description
        "Free space in the file system in bytes";
    }
    leaf type {
      type string;
      description
        "Type of file system";
    }
    leaf flags {
      type string;
      description
        "Flags of file system";
    }
    leaf prefixes {
      type string;
      description
        "Prefixes of file system";
    }
  }

  grouping ncs_rpc_notif_FILESYSTEM {
    description
      "File Systems";
    list file-system {
      description
        "Available file systems";
      uses ncs_rpc_notif_FILESYSTEM-UTIL;
    }
  }

  grouping live_ncs_FILESYSTEM-UTIL {
    description
      "File System Description";
    leaf size {
      type uint64;
      units "byte";
      description
        "Size of the file system in bytes";
    }
    leaf free {
      type uint64;
      units "byte";
      description
        "Free space in the file system in bytes";
    }
    leaf type {
      type string;
      description
        "Type of file system";
    }
    leaf flags {
      type string;
      description
        "Flags of file system";
    }
    leaf prefixes {
      type string;
      description
        "Prefixes of file system";
    }
  }

  grouping live_ncs_FILESYSTEM {
    description
      "File Systems";
    list file-system {
      description
        "Available file systems";
      uses live_ncs_FILESYSTEM-UTIL;
    }
  }

  grouping FILESYSTEM-UTIL {
    description
      "File System Description";
    leaf size {
      type uint64;
      units "byte";
      description
        "Size of the file system in bytes";
    }
    leaf free {
      type uint64;
      units "byte";
      description
        "Free space in the file system in bytes";
    }
    leaf type {
      type string;
      description
        "Type of file system";
    }
    leaf flags {
      type string;
      description
        "Flags of file system";
    }
    leaf prefixes {
      type string;
      description
        "Prefixes of file system";
    }
  }

  grouping FILESYSTEM {
    description
      "File Systems";
    list file-system {
      description
        "Available file systems";
      uses FILESYSTEM-UTIL;
    }
  }
}

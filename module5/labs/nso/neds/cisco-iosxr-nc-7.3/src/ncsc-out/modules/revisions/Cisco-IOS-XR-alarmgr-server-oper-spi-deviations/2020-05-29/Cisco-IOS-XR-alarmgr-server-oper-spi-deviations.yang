module Cisco-IOS-XR-alarmgr-server-oper-spi-deviations {
  // Generated by yanger -t ncs
  tailf:mount-id "cisco-iosxr-nc-7.3:cisco-iosxr-nc-7.3";
  tailf:ncs-device-type "netconf";

  namespace "http://cisco.com/ns/yang/Cisco-IOS-XR-alarmgr-server-oper-spi-deviations";
  prefix alarmgr-server-oper-spi-dev;

  import Cisco-IOS-XR-alarmgr-server-oper {
    prefix am-server-oper;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations of container conditions
     for SPI platform on Ciso-IOS-XR device.

     Copyright (c) 2017, 2019-2020 by Cisco Systems, Inc.
     All rights reserved.";

  revision 2020-05-29 {
    description
      "Initial revision applicable to IOS-XR 6.0 and older releases";
    reference "RFC RFC 8407: 4.8";
  }

  deviation "/ncs:devices/ncs:device/ncs:live-status/am-server-oper:alarms/am-server-oper:detail/am-server-oper:detail-system/am-server-oper:conditions" {
    deviate not-supported;
  }
  deviation "/ncs:devices/ncs:device/ncs:live-status/am-server-oper:alarms/am-server-oper:detail/am-server-oper:detail-card/am-server-oper:detail-locations/am-server-oper:detail-location/am-server-oper:conditions" {
    deviate not-supported;
  }
  deviation "/ncs:devices/ncs:device/ncs:live-status/am-server-oper:alarms/am-server-oper:brief/am-server-oper:brief-system/am-server-oper:conditions" {
    deviate not-supported;
  }
  deviation "/ncs:devices/ncs:device/ncs:live-status/am-server-oper:alarms/am-server-oper:brief/am-server-oper:brief-card/am-server-oper:brief-locations/am-server-oper:brief-location/am-server-oper:conditions" {
    deviate not-supported;
  }
}

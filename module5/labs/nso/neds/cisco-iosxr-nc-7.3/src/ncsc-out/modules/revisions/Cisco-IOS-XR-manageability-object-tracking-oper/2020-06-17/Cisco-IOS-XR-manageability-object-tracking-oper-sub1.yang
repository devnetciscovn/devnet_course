submodule Cisco-IOS-XR-manageability-object-tracking-oper-sub1 {
  // Generated by yanger -t ncs
  tailf:mount-id "cisco-iosxr-nc-7.3:cisco-iosxr-nc-7.3";

  belongs-to Cisco-IOS-XR-manageability-object-tracking-oper {
    prefix Cisco-IOS-XR-manageability-object-tracking-oper;
  }

  import ietf-inet-types {
    prefix inet;
  }
  import cisco-semver {
    prefix semver;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR manageability-object-tracking package operational data.

     Copyright (c) 2013-2020 by Cisco Systems, Inc.
     All rights reserved.";

  revision 2020-06-17 {
    description
      "Added support to display delay up/down values in show track.";
    semver:module-version "2.2.0";
  }
  revision 2019-10-07 {
    description
      "Added support for track type bgp nbr af.";
    semver:module-version "2.1.0";
  }
  revision 2019-09-07 {
    description
      "Removed IPv4 Route type nodes and added generic node for both IPv4 and IPv6.";
    semver:module-version "2.0.0";
  }
  revision 2019-04-05 {
    description
      "Establish semantic version baseline.";
    semver:module-version "1.0.0";
  }
  revision 2015-11-09 {
    description
      "IOS XR 6.0 revision.";
  }

  typedef ncs_template_Track {
    type string;
    description
      "Track";
  }

  typedef ncs_rpc_notif_Track {
    type enumeration {
      enum "interface-type" {
        value 1;
        description
          "Line protocol type";
      }
      enum "route-type" {
        value 2;
        description
          "Route type";
      }
      enum "bool-and-type" {
        value 3;
        description
          "Boolean and type";
      }
      enum "bool-or-type" {
        value 4;
        description
          "Boolean or type";
      }
      enum "ipsla-type" {
        value 5;
        description
          "Ipsla track type";
      }
      enum "undefined-type" {
        value 6;
        description
          "type undefined";
      }
      enum "threshold-weight" {
        value 7;
        description
          "type threshold weight";
      }
      enum "threshold-percentage" {
        value 8;
        description
          "type threshold percentage";
      }
      enum "bfd-type" {
        value 9;
        description
          "type bfd rtr";
      }
      enum "iflist-bool-and-type" {
        value 10;
        description
          "Interface list boolean and type";
      }
      enum "iflist-bool-or-type" {
        value 11;
        description
          "Interface list boolean or type";
      }
      enum "iflist-thld-weight" {
        value 12;
        description
          "Interface list threshold weight type";
      }
      enum "iflist-thld-percent" {
        value 13;
        description
          "Interface list threshold percent type";
      }
      enum "bgp-nbr-af-type" {
        value 14;
        description
          "type bgp nbr af";
      }
    }
    description
      "Track";
  }

  typedef live_ncs_Track {
    type enumeration {
      enum "interface-type" {
        value 1;
        description
          "Line protocol type";
      }
      enum "route-type" {
        value 2;
        description
          "Route type";
      }
      enum "bool-and-type" {
        value 3;
        description
          "Boolean and type";
      }
      enum "bool-or-type" {
        value 4;
        description
          "Boolean or type";
      }
      enum "ipsla-type" {
        value 5;
        description
          "Ipsla track type";
      }
      enum "undefined-type" {
        value 6;
        description
          "type undefined";
      }
      enum "threshold-weight" {
        value 7;
        description
          "type threshold weight";
      }
      enum "threshold-percentage" {
        value 8;
        description
          "type threshold percentage";
      }
      enum "bfd-type" {
        value 9;
        description
          "type bfd rtr";
      }
      enum "iflist-bool-and-type" {
        value 10;
        description
          "Interface list boolean and type";
      }
      enum "iflist-bool-or-type" {
        value 11;
        description
          "Interface list boolean or type";
      }
      enum "iflist-thld-weight" {
        value 12;
        description
          "Interface list threshold weight type";
      }
      enum "iflist-thld-percent" {
        value 13;
        description
          "Interface list threshold percent type";
      }
      enum "bgp-nbr-af-type" {
        value 14;
        description
          "type bgp nbr af";
      }
    }
    description
      "Track";
  }

  typedef Track {
    type enumeration {
      enum "interface-type" {
        value 1;
        description
          "Line protocol type";
      }
      enum "route-type" {
        value 2;
        description
          "Route type";
      }
      enum "bool-and-type" {
        value 3;
        description
          "Boolean and type";
      }
      enum "bool-or-type" {
        value 4;
        description
          "Boolean or type";
      }
      enum "ipsla-type" {
        value 5;
        description
          "Ipsla track type";
      }
      enum "undefined-type" {
        value 6;
        description
          "type undefined";
      }
      enum "threshold-weight" {
        value 7;
        description
          "type threshold weight";
      }
      enum "threshold-percentage" {
        value 8;
        description
          "type threshold percentage";
      }
      enum "bfd-type" {
        value 9;
        description
          "type bfd rtr";
      }
      enum "iflist-bool-and-type" {
        value 10;
        description
          "Interface list boolean and type";
      }
      enum "iflist-bool-or-type" {
        value 11;
        description
          "Interface list boolean or type";
      }
      enum "iflist-thld-weight" {
        value 12;
        description
          "Interface list threshold weight type";
      }
      enum "iflist-thld-percent" {
        value 13;
        description
          "Interface list threshold percent type";
      }
      enum "bgp-nbr-af-type" {
        value 14;
        description
          "type bgp nbr af";
      }
    }
    description
      "Track";
  }

  grouping ncs_template_TRACK-INFO-BRIEF {
    description
      "TRACK INFO BRIEF";
    list track-info-brief {
      // NCS patched for predictable order
      ordered-by user;
      description
        "track info brief";
      container track-type-info {
        description
          "Track type information";
        uses ncs_template_TRACK-TYPE-INFO-UNION;
      }
      leaf tracke-name {
        type string;
        description
          "Track Name";
      }
      leaf type {
        type ncs_template_Track;
        description
          "Track type";
      }
      leaf track-state {
        type string;
        description
          "Track state";
      }
    }
  }

  grouping ncs_template_DELAYED-STATE-STATUS {
    description
      "DELAYED STATE STATUS";
    leaf time-remaining {
      type string;
      units "second";
      description
        "The time remaining in seconds for the counter to
         trigger state change";
    }
    leaf track-state {
      type string;
      description
        "State the track will transition to. Track state.
         True means track is up; False means track is
         down.";
    }
  }

  grouping ncs_template_INTERFACE-TRACKING-INFO {
    description
      "INTERFACE TRACKING INFO";
    list interface-tracking-info {
      // NCS patched for predictable order
      ordered-by user;
      description
        "interface tracking info";
      leaf interface-name {
        type string;
        description
          "Interface Name";
      }
    }
  }

  grouping ncs_template_THRESHOLD-TRACK-INFO {
    description
      "THRESHOLD TRACK INFO";
    list threshold-track-info {
      // NCS patched for predictable order
      ordered-by user;
      description
        "threshold track info";
      leaf object-name {
        type string;
        description
          "Object name";
      }
      leaf track-state {
        type string;
        description
          "Track state. True means track is up; False
           means track is down.";
      }
      leaf weight {
        type string;
        units "percentage";
        description
          "Weight is the number assigned to a track object
           . In case of a type threshold weight( i.e.
           weighted sum list), weight is asigned by User
           at the time of configuration. In case of a type
           threshold percentage (i.e. percentage based
           list), weight is internally computed by
           (1/N)x100, where N is the number of objects in
           the list.";
      }
    }
  }

  grouping ncs_template_BOOL-TRACK-INFO {
    description
      "BOOL TRACK INFO";
    list bool-track-info {
      // NCS patched for predictable order
      ordered-by user;
      description
        "bool track info";
      leaf object-name {
        type string;
        description
          "Object Name";
      }
      leaf track-state {
        type string;
        description
          "Track state";
      }
      leaf with-not {
        type string;
        description
          "Track object with Not";
      }
    }
  }

  grouping ncs_template_BFDRTR-TRACK-INFO {
    description
      "BFDRTR TRACK INFO";
    leaf interface-name {
      type string;
      description
        "Interface Name";
    }
    leaf destination-address {
      type string;
      description
        "Destination Address";
    }
    leaf rate {
      type string;
      description
        "Rate";
    }
    leaf debounce-count {
      type string;
      description
        "Debounce Count";
    }
  }

  grouping ncs_template_RTR-TRACK-INFO {
    description
      "RTR TRACK INFO";
    leaf ipsla-op-id {
      type string;
      description
        "Op Id";
    }
    leaf rtt {
      type string;
      description
        "Latest RTT";
    }
    leaf return-code {
      type string;
      description
        "Latest Return Code";
    }
    leaf return-code-string {
      type string;
      description
        "Latest Ret Code String";
    }
  }

  grouping ncs_template_BGP-NBR-AF-TRACK-INFO {
    description
      "BGP NBR AF TRACK INFO";
    leaf is-neighbor-ipv4 {
      type string;
      description
        "Is BGP neighbor addr IPv4";
    }
    leaf ipv4-address {
      type string;
      description
        "IPv4 address";
    }
    leaf ipv6-address {
      type string;
      description
        "IPv6 address";
    }
    leaf afi {
      type string;
      description
        "AFI";
    }
    leaf safi {
      type string;
      description
        "SAFI";
    }
    leaf neighbor-object-state {
      type string;
      description
        "BGP neighborship state";
    }
    leaf disable-fib-check {
      type string;
      description
        "Disable Neighbor's route reachablity state";
    }
    leaf neighbor-route-reach-state {
      type string;
      description
        "BGP Neighbor's route reachablity state";
    }
    leaf vrf {
      type string;
      description
        "VRF Name";
    }
    leaf ins {
      type string;
      description
        "VRF Name";
    }
  }

  grouping ncs_template_ROUTE-TRACK-INFO {
    description
      "ROUTE TRACK INFO";
    leaf prefix {
      type string;
      description
        "IPv4 or IPv6 Prefix";
    }
    leaf prefix-length {
      type string;
      description
        "Prefix Length";
    }
    leaf vrf {
      type string;
      description
        "VRF Name";
    }
    leaf next-hop {
      type string;
      description
        "Next Hop";
    }
  }

  grouping ncs_template_INTF-TRACK-INFO {
    description
      "INTF TRACK INFO";
    leaf interface-name {
      type string;
      description
        "Interface Name";
    }
  }

  grouping ncs_template_TRACK-TYPE-INFO-UNION {
    description
      "TRACK TYPE INFO UNION";
    container interface-tracks {
      // NCS drop when statement
      description
        "track type interface info";
      uses ncs_template_INTF-TRACK-INFO;
    }
    container route-tracks {
      // NCS drop when statement
      description
        "track type route info";
      uses ncs_template_ROUTE-TRACK-INFO;
    }
    container bgp-nbr-af-tracks {
      // NCS drop when statement
      description
        "track type bgp nbr af info";
      uses ncs_template_BGP-NBR-AF-TRACK-INFO;
    }
    container ipsla-tracks {
      // NCS drop when statement
      description
        "track type rtr info";
      uses ncs_template_RTR-TRACK-INFO;
    }
    container bfd-tracks {
      // NCS drop when statement
      description
        "track type bfdrtr info";
      uses ncs_template_BFDRTR-TRACK-INFO;
    }
    leaf discriminant {
      type ncs_template_Track;
      description
        "discriminant";
    }
  }

  grouping ncs_template_TRACK-INFO {
    description
      "TRACK INFO";
    list track-info {
      // NCS patched for predictable order
      ordered-by user;
      description
        "track info";
      container track-type-info {
        description
          "Track type information";
        uses ncs_template_TRACK-TYPE-INFO-UNION;
      }
      container bool-tracks {
        description
          "boolean objects";
        uses ncs_template_BOOL-TRACK-INFO;
      }
      container threshold-tracks {
        description
          "Threshold objects";
        uses ncs_template_THRESHOLD-TRACK-INFO;
      }
      container tracking-interaces {
        description
          "Tracking Interfaces";
        uses ncs_template_INTERFACE-TRACKING-INFO;
      }
      container delayed {
        description
          "Is the state change delay counter in progress";
        uses ncs_template_DELAYED-STATE-STATUS;
      }
      leaf tracke-name {
        type string;
        description
          "Track Name";
      }
      leaf type {
        type ncs_template_Track;
        description
          "Track type";
      }
      leaf track-state {
        type string;
        description
          "Track state";
      }
      leaf state-change-counter {
        type string;
        description
          "State Change Counter";
      }
      leaf seconds-last-change {
        type string;
        units "second";
        description
          "Seconds Last Change";
      }
      leaf mili-seconds-last-change {
        type string;
        units "second";
        description
          "Mili Seconds Last Change";
      }
      leaf threshold-up {
        type string;
        description
          "User specified threshold upper limit";
      }
      leaf threshold-down {
        type string;
        description
          "User specified threshold lower limit";
      }
      leaf delay-up-time {
        type string;
        units "second";
        description
          "Delay up time in Seconds";
      }
      leaf delay-up-config {
        type string;
        description
          "True, if Delay up is set in config";
      }
      leaf delay-down-time {
        type string;
        units "second";
        description
          "Delay down time in Seconds";
      }
      leaf delay-down-config {
        type string;
        description
          "True, if Delay down is set in Config";
      }
    }
  }

  grouping ncs_rpc_notif_TRACK-INFO-BRIEF {
    description
      "TRACK INFO BRIEF";
    list track-info-brief {
      description
        "track info brief";
      container track-type-info {
        description
          "Track type information";
        uses ncs_rpc_notif_TRACK-TYPE-INFO-UNION;
      }
      leaf tracke-name {
        type string {
          length "0..33";
        }
        description
          "Track Name";
      }
      leaf type {
        type ncs_rpc_notif_Track;
        description
          "Track type";
      }
      leaf track-state {
        type boolean;
        description
          "Track state";
      }
    }
  }

  grouping ncs_rpc_notif_DELAYED-STATE-STATUS {
    description
      "DELAYED STATE STATUS";
    leaf time-remaining {
      type uint32;
      units "second";
      description
        "The time remaining in seconds for the counter to
         trigger state change";
    }
    leaf track-state {
      type boolean;
      description
        "State the track will transition to. Track state.
         True means track is up; False means track is
         down.";
    }
  }

  grouping ncs_rpc_notif_INTERFACE-TRACKING-INFO {
    description
      "INTERFACE TRACKING INFO";
    list interface-tracking-info {
      description
        "interface tracking info";
      leaf interface-name {
        type string {
          length "0..120";
        }
        description
          "Interface Name";
      }
    }
  }

  grouping ncs_rpc_notif_THRESHOLD-TRACK-INFO {
    description
      "THRESHOLD TRACK INFO";
    list threshold-track-info {
      description
        "threshold track info";
      leaf object-name {
        type string {
          length "0..33";
        }
        description
          "Object name";
      }
      leaf track-state {
        type boolean;
        description
          "Track state. True means track is up; False
           means track is down.";
      }
      leaf weight {
        type uint32;
        units "percentage";
        description
          "Weight is the number assigned to a track object
           . In case of a type threshold weight( i.e.
           weighted sum list), weight is asigned by User
           at the time of configuration. In case of a type
           threshold percentage (i.e. percentage based
           list), weight is internally computed by
           (1/N)x100, where N is the number of objects in
           the list.";
      }
    }
  }

  grouping ncs_rpc_notif_BOOL-TRACK-INFO {
    description
      "BOOL TRACK INFO";
    list bool-track-info {
      description
        "bool track info";
      leaf object-name {
        type string {
          length "0..33";
        }
        description
          "Object Name";
      }
      leaf track-state {
        type boolean;
        description
          "Track state";
      }
      leaf with-not {
        type boolean;
        description
          "Track object with Not";
      }
    }
  }

  grouping ncs_rpc_notif_BFDRTR-TRACK-INFO {
    description
      "BFDRTR TRACK INFO";
    leaf interface-name {
      type string {
        length "0..120";
      }
      description
        "Interface Name";
    }
    leaf destination-address {
      type uint32;
      description
        "Destination Address";
    }
    leaf rate {
      type uint32;
      description
        "Rate";
    }
    leaf debounce-count {
      type uint32;
      description
        "Debounce Count";
    }
  }

  grouping ncs_rpc_notif_RTR-TRACK-INFO {
    description
      "RTR TRACK INFO";
    leaf ipsla-op-id {
      type uint32;
      description
        "Op Id";
    }
    leaf rtt {
      type uint32;
      description
        "Latest RTT";
    }
    leaf return-code {
      type uint32;
      description
        "Latest Return Code";
    }
    leaf return-code-string {
      type string {
        length "0..120";
      }
      description
        "Latest Ret Code String";
    }
  }

  grouping ncs_rpc_notif_BGP-NBR-AF-TRACK-INFO {
    description
      "BGP NBR AF TRACK INFO";
    leaf is-neighbor-ipv4 {
      type boolean;
      description
        "Is BGP neighbor addr IPv4";
    }
    leaf ipv4-address {
      type inet:ipv4-address;
      description
        "IPv4 address";
    }
    leaf ipv6-address {
      type inet:ipv6-address;
      description
        "IPv6 address";
    }
    leaf afi {
      type uint16;
      description
        "AFI";
    }
    leaf safi {
      type uint8;
      description
        "SAFI";
    }
    leaf neighbor-object-state {
      type uint32;
      description
        "BGP neighborship state";
    }
    leaf disable-fib-check {
      type boolean;
      description
        "Disable Neighbor's route reachablity state";
    }
    leaf neighbor-route-reach-state {
      type boolean;
      description
        "BGP Neighbor's route reachablity state";
    }
    leaf vrf {
      type string {
        length "0..120";
      }
      description
        "VRF Name";
    }
    leaf ins {
      type string {
        length "0..120";
      }
      description
        "VRF Name";
    }
  }

  grouping ncs_rpc_notif_ROUTE-TRACK-INFO {
    description
      "ROUTE TRACK INFO";
    leaf prefix {
      type string {
        length "0..46";
      }
      description
        "IPv4 or IPv6 Prefix";
    }
    leaf prefix-length {
      type uint32;
      description
        "Prefix Length";
    }
    leaf vrf {
      type string {
        length "0..120";
      }
      description
        "VRF Name";
    }
    leaf next-hop {
      type string {
        length "0..120";
      }
      description
        "Next Hop";
    }
  }

  grouping ncs_rpc_notif_INTF-TRACK-INFO {
    description
      "INTF TRACK INFO";
    leaf interface-name {
      type string {
        length "0..120";
      }
      description
        "Interface Name";
    }
  }

  grouping ncs_rpc_notif_TRACK-TYPE-INFO-UNION {
    description
      "TRACK TYPE INFO UNION";
    container interface-tracks {
      when "../discriminant = 'interface-type'" {
        tailf:xpath-root 3;
        description
          "../discriminant = 'InterfaceType'";
      }
      description
        "track type interface info";
      uses ncs_rpc_notif_INTF-TRACK-INFO;
    }
    container route-tracks {
      when "../discriminant = 'route-type'" {
        tailf:xpath-root 3;
        description
          "../discriminant = 'RouteType'";
      }
      description
        "track type route info";
      uses ncs_rpc_notif_ROUTE-TRACK-INFO;
    }
    container bgp-nbr-af-tracks {
      when "../discriminant = 'bgp-nbr-af-type'" {
        tailf:xpath-root 3;
        description
          "../discriminant = 'BgpNbrAfType'";
      }
      description
        "track type bgp nbr af info";
      uses ncs_rpc_notif_BGP-NBR-AF-TRACK-INFO;
    }
    container ipsla-tracks {
      when "../discriminant = 'ipsla-type'" {
        tailf:xpath-root 3;
        description
          "../discriminant = 'IpslaType'";
      }
      description
        "track type rtr info";
      uses ncs_rpc_notif_RTR-TRACK-INFO;
    }
    container bfd-tracks {
      when "../discriminant = 'bfd-type'" {
        tailf:xpath-root 3;
        description
          "../discriminant = 'BfdType'";
      }
      description
        "track type bfdrtr info";
      uses ncs_rpc_notif_BFDRTR-TRACK-INFO;
    }
    leaf discriminant {
      type ncs_rpc_notif_Track;
      description
        "discriminant";
    }
  }

  grouping ncs_rpc_notif_TRACK-INFO {
    description
      "TRACK INFO";
    list track-info {
      description
        "track info";
      container track-type-info {
        description
          "Track type information";
        uses ncs_rpc_notif_TRACK-TYPE-INFO-UNION;
      }
      container bool-tracks {
        description
          "boolean objects";
        uses ncs_rpc_notif_BOOL-TRACK-INFO;
      }
      container threshold-tracks {
        description
          "Threshold objects";
        uses ncs_rpc_notif_THRESHOLD-TRACK-INFO;
      }
      container tracking-interaces {
        description
          "Tracking Interfaces";
        uses ncs_rpc_notif_INTERFACE-TRACKING-INFO;
      }
      container delayed {
        description
          "Is the state change delay counter in progress";
        uses ncs_rpc_notif_DELAYED-STATE-STATUS;
      }
      leaf tracke-name {
        type string {
          length "0..33";
        }
        description
          "Track Name";
      }
      leaf type {
        type ncs_rpc_notif_Track;
        description
          "Track type";
      }
      leaf track-state {
        type boolean;
        description
          "Track state";
      }
      leaf state-change-counter {
        type uint32;
        description
          "State Change Counter";
      }
      leaf seconds-last-change {
        type uint64;
        units "second";
        description
          "Seconds Last Change";
      }
      leaf mili-seconds-last-change {
        type uint64;
        units "second";
        description
          "Mili Seconds Last Change";
      }
      leaf threshold-up {
        type uint32;
        description
          "User specified threshold upper limit";
      }
      leaf threshold-down {
        type uint32;
        description
          "User specified threshold lower limit";
      }
      leaf delay-up-time {
        type uint16;
        units "second";
        description
          "Delay up time in Seconds";
      }
      leaf delay-up-config {
        type boolean;
        description
          "True, if Delay up is set in config";
      }
      leaf delay-down-time {
        type uint16;
        units "second";
        description
          "Delay down time in Seconds";
      }
      leaf delay-down-config {
        type boolean;
        description
          "True, if Delay down is set in Config";
      }
    }
  }

  grouping live_ncs_TRACK-INFO-BRIEF {
    description
      "TRACK INFO BRIEF";
    list track-info-brief {
      description
        "track info brief";
      container track-type-info {
        description
          "Track type information";
        uses live_ncs_TRACK-TYPE-INFO-UNION;
      }
      leaf tracke-name {
        type string {
          length "0..33";
        }
        description
          "Track Name";
      }
      leaf type {
        type live_ncs_Track;
        description
          "Track type";
      }
      leaf track-state {
        type boolean;
        description
          "Track state";
      }
    }
  }

  grouping live_ncs_DELAYED-STATE-STATUS {
    description
      "DELAYED STATE STATUS";
    leaf time-remaining {
      type uint32;
      units "second";
      description
        "The time remaining in seconds for the counter to
         trigger state change";
    }
    leaf track-state {
      type boolean;
      description
        "State the track will transition to. Track state.
         True means track is up; False means track is
         down.";
    }
  }

  grouping live_ncs_INTERFACE-TRACKING-INFO {
    description
      "INTERFACE TRACKING INFO";
    list interface-tracking-info {
      description
        "interface tracking info";
      leaf interface-name {
        type string {
          length "0..120";
        }
        description
          "Interface Name";
      }
    }
  }

  grouping live_ncs_THRESHOLD-TRACK-INFO {
    description
      "THRESHOLD TRACK INFO";
    list threshold-track-info {
      description
        "threshold track info";
      leaf object-name {
        type string {
          length "0..33";
        }
        description
          "Object name";
      }
      leaf track-state {
        type boolean;
        description
          "Track state. True means track is up; False
           means track is down.";
      }
      leaf weight {
        type uint32;
        units "percentage";
        description
          "Weight is the number assigned to a track object
           . In case of a type threshold weight( i.e.
           weighted sum list), weight is asigned by User
           at the time of configuration. In case of a type
           threshold percentage (i.e. percentage based
           list), weight is internally computed by
           (1/N)x100, where N is the number of objects in
           the list.";
      }
    }
  }

  grouping live_ncs_BOOL-TRACK-INFO {
    description
      "BOOL TRACK INFO";
    list bool-track-info {
      description
        "bool track info";
      leaf object-name {
        type string {
          length "0..33";
        }
        description
          "Object Name";
      }
      leaf track-state {
        type boolean;
        description
          "Track state";
      }
      leaf with-not {
        type boolean;
        description
          "Track object with Not";
      }
    }
  }

  grouping live_ncs_BFDRTR-TRACK-INFO {
    description
      "BFDRTR TRACK INFO";
    leaf interface-name {
      type string {
        length "0..120";
      }
      description
        "Interface Name";
    }
    leaf destination-address {
      type uint32;
      description
        "Destination Address";
    }
    leaf rate {
      type uint32;
      description
        "Rate";
    }
    leaf debounce-count {
      type uint32;
      description
        "Debounce Count";
    }
  }

  grouping live_ncs_RTR-TRACK-INFO {
    description
      "RTR TRACK INFO";
    leaf ipsla-op-id {
      type uint32;
      description
        "Op Id";
    }
    leaf rtt {
      type uint32;
      description
        "Latest RTT";
    }
    leaf return-code {
      type uint32;
      description
        "Latest Return Code";
    }
    leaf return-code-string {
      type string {
        length "0..120";
      }
      description
        "Latest Ret Code String";
    }
  }

  grouping live_ncs_BGP-NBR-AF-TRACK-INFO {
    description
      "BGP NBR AF TRACK INFO";
    leaf is-neighbor-ipv4 {
      type boolean;
      description
        "Is BGP neighbor addr IPv4";
    }
    leaf ipv4-address {
      type inet:ipv4-address;
      description
        "IPv4 address";
    }
    leaf ipv6-address {
      type inet:ipv6-address;
      description
        "IPv6 address";
    }
    leaf afi {
      type uint16;
      description
        "AFI";
    }
    leaf safi {
      type uint8;
      description
        "SAFI";
    }
    leaf neighbor-object-state {
      type uint32;
      description
        "BGP neighborship state";
    }
    leaf disable-fib-check {
      type boolean;
      description
        "Disable Neighbor's route reachablity state";
    }
    leaf neighbor-route-reach-state {
      type boolean;
      description
        "BGP Neighbor's route reachablity state";
    }
    leaf vrf {
      type string {
        length "0..120";
      }
      description
        "VRF Name";
    }
    leaf ins {
      type string {
        length "0..120";
      }
      description
        "VRF Name";
    }
  }

  grouping live_ncs_ROUTE-TRACK-INFO {
    description
      "ROUTE TRACK INFO";
    leaf prefix {
      type string {
        length "0..46";
      }
      description
        "IPv4 or IPv6 Prefix";
    }
    leaf prefix-length {
      type uint32;
      description
        "Prefix Length";
    }
    leaf vrf {
      type string {
        length "0..120";
      }
      description
        "VRF Name";
    }
    leaf next-hop {
      type string {
        length "0..120";
      }
      description
        "Next Hop";
    }
  }

  grouping live_ncs_INTF-TRACK-INFO {
    description
      "INTF TRACK INFO";
    leaf interface-name {
      type string {
        length "0..120";
      }
      description
        "Interface Name";
    }
  }

  grouping live_ncs_TRACK-TYPE-INFO-UNION {
    description
      "TRACK TYPE INFO UNION";
    container interface-tracks {
      // NCS drop when statement
      description
        "track type interface info";
      uses live_ncs_INTF-TRACK-INFO;
    }
    container route-tracks {
      // NCS drop when statement
      description
        "track type route info";
      uses live_ncs_ROUTE-TRACK-INFO;
    }
    container bgp-nbr-af-tracks {
      // NCS drop when statement
      description
        "track type bgp nbr af info";
      uses live_ncs_BGP-NBR-AF-TRACK-INFO;
    }
    container ipsla-tracks {
      // NCS drop when statement
      description
        "track type rtr info";
      uses live_ncs_RTR-TRACK-INFO;
    }
    container bfd-tracks {
      // NCS drop when statement
      description
        "track type bfdrtr info";
      uses live_ncs_BFDRTR-TRACK-INFO;
    }
    leaf discriminant {
      type live_ncs_Track;
      description
        "discriminant";
    }
  }

  grouping live_ncs_TRACK-INFO {
    description
      "TRACK INFO";
    list track-info {
      description
        "track info";
      container track-type-info {
        description
          "Track type information";
        uses live_ncs_TRACK-TYPE-INFO-UNION;
      }
      container bool-tracks {
        description
          "boolean objects";
        uses live_ncs_BOOL-TRACK-INFO;
      }
      container threshold-tracks {
        description
          "Threshold objects";
        uses live_ncs_THRESHOLD-TRACK-INFO;
      }
      container tracking-interaces {
        description
          "Tracking Interfaces";
        uses live_ncs_INTERFACE-TRACKING-INFO;
      }
      container delayed {
        description
          "Is the state change delay counter in progress";
        uses live_ncs_DELAYED-STATE-STATUS;
      }
      leaf tracke-name {
        type string {
          length "0..33";
        }
        description
          "Track Name";
      }
      leaf type {
        type live_ncs_Track;
        description
          "Track type";
      }
      leaf track-state {
        type boolean;
        description
          "Track state";
      }
      leaf state-change-counter {
        type uint32;
        description
          "State Change Counter";
      }
      leaf seconds-last-change {
        type uint64;
        units "second";
        description
          "Seconds Last Change";
      }
      leaf mili-seconds-last-change {
        type uint64;
        units "second";
        description
          "Mili Seconds Last Change";
      }
      leaf threshold-up {
        type uint32;
        description
          "User specified threshold upper limit";
      }
      leaf threshold-down {
        type uint32;
        description
          "User specified threshold lower limit";
      }
      leaf delay-up-time {
        type uint16;
        units "second";
        description
          "Delay up time in Seconds";
      }
      leaf delay-up-config {
        type boolean;
        description
          "True, if Delay up is set in config";
      }
      leaf delay-down-time {
        type uint16;
        units "second";
        description
          "Delay down time in Seconds";
      }
      leaf delay-down-config {
        type boolean;
        description
          "True, if Delay down is set in Config";
      }
    }
  }

  grouping TRACK-INFO-BRIEF {
    description
      "TRACK INFO BRIEF";
    list track-info-brief {
      description
        "track info brief";
      container track-type-info {
        description
          "Track type information";
        uses TRACK-TYPE-INFO-UNION;
      }
      leaf tracke-name {
        type string {
          length "0..33";
        }
        description
          "Track Name";
      }
      leaf type {
        type Track;
        description
          "Track type";
      }
      leaf track-state {
        type boolean;
        description
          "Track state";
      }
    }
  }

  grouping DELAYED-STATE-STATUS {
    description
      "DELAYED STATE STATUS";
    leaf time-remaining {
      type uint32;
      units "second";
      description
        "The time remaining in seconds for the counter to
         trigger state change";
    }
    leaf track-state {
      type boolean;
      description
        "State the track will transition to. Track state.
         True means track is up; False means track is
         down.";
    }
  }

  grouping INTERFACE-TRACKING-INFO {
    description
      "INTERFACE TRACKING INFO";
    list interface-tracking-info {
      description
        "interface tracking info";
      leaf interface-name {
        type string {
          length "0..120";
        }
        description
          "Interface Name";
      }
    }
  }

  grouping THRESHOLD-TRACK-INFO {
    description
      "THRESHOLD TRACK INFO";
    list threshold-track-info {
      description
        "threshold track info";
      leaf object-name {
        type string {
          length "0..33";
        }
        description
          "Object name";
      }
      leaf track-state {
        type boolean;
        description
          "Track state. True means track is up; False
           means track is down.";
      }
      leaf weight {
        type uint32;
        units "percentage";
        description
          "Weight is the number assigned to a track object
           . In case of a type threshold weight( i.e.
           weighted sum list), weight is asigned by User
           at the time of configuration. In case of a type
           threshold percentage (i.e. percentage based
           list), weight is internally computed by
           (1/N)x100, where N is the number of objects in
           the list.";
      }
    }
  }

  grouping BOOL-TRACK-INFO {
    description
      "BOOL TRACK INFO";
    list bool-track-info {
      description
        "bool track info";
      leaf object-name {
        type string {
          length "0..33";
        }
        description
          "Object Name";
      }
      leaf track-state {
        type boolean;
        description
          "Track state";
      }
      leaf with-not {
        type boolean;
        description
          "Track object with Not";
      }
    }
  }

  grouping BFDRTR-TRACK-INFO {
    description
      "BFDRTR TRACK INFO";
    leaf interface-name {
      type string {
        length "0..120";
      }
      description
        "Interface Name";
    }
    leaf destination-address {
      type uint32;
      description
        "Destination Address";
    }
    leaf rate {
      type uint32;
      description
        "Rate";
    }
    leaf debounce-count {
      type uint32;
      description
        "Debounce Count";
    }
  }

  grouping RTR-TRACK-INFO {
    description
      "RTR TRACK INFO";
    leaf ipsla-op-id {
      type uint32;
      description
        "Op Id";
    }
    leaf rtt {
      type uint32;
      description
        "Latest RTT";
    }
    leaf return-code {
      type uint32;
      description
        "Latest Return Code";
    }
    leaf return-code-string {
      type string {
        length "0..120";
      }
      description
        "Latest Ret Code String";
    }
  }

  grouping BGP-NBR-AF-TRACK-INFO {
    description
      "BGP NBR AF TRACK INFO";
    leaf is-neighbor-ipv4 {
      type boolean;
      description
        "Is BGP neighbor addr IPv4";
    }
    leaf ipv4-address {
      type inet:ipv4-address;
      description
        "IPv4 address";
    }
    leaf ipv6-address {
      type inet:ipv6-address;
      description
        "IPv6 address";
    }
    leaf afi {
      type uint16;
      description
        "AFI";
    }
    leaf safi {
      type uint8;
      description
        "SAFI";
    }
    leaf neighbor-object-state {
      type uint32;
      description
        "BGP neighborship state";
    }
    leaf disable-fib-check {
      type boolean;
      description
        "Disable Neighbor's route reachablity state";
    }
    leaf neighbor-route-reach-state {
      type boolean;
      description
        "BGP Neighbor's route reachablity state";
    }
    leaf vrf {
      type string {
        length "0..120";
      }
      description
        "VRF Name";
    }
    leaf ins {
      type string {
        length "0..120";
      }
      description
        "VRF Name";
    }
  }

  grouping ROUTE-TRACK-INFO {
    description
      "ROUTE TRACK INFO";
    leaf prefix {
      type string {
        length "0..46";
      }
      description
        "IPv4 or IPv6 Prefix";
    }
    leaf prefix-length {
      type uint32;
      description
        "Prefix Length";
    }
    leaf vrf {
      type string {
        length "0..120";
      }
      description
        "VRF Name";
    }
    leaf next-hop {
      type string {
        length "0..120";
      }
      description
        "Next Hop";
    }
  }

  grouping INTF-TRACK-INFO {
    description
      "INTF TRACK INFO";
    leaf interface-name {
      type string {
        length "0..120";
      }
      description
        "Interface Name";
    }
  }

  grouping TRACK-TYPE-INFO-UNION {
    description
      "TRACK TYPE INFO UNION";
    container interface-tracks {
      when "../discriminant = 'interface-type'" {
        tailf:xpath-root 3;
        description
          "../discriminant = 'InterfaceType'";
      }
      description
        "track type interface info";
      uses INTF-TRACK-INFO;
    }
    container route-tracks {
      when "../discriminant = 'route-type'" {
        tailf:xpath-root 3;
        description
          "../discriminant = 'RouteType'";
      }
      description
        "track type route info";
      uses ROUTE-TRACK-INFO;
    }
    container bgp-nbr-af-tracks {
      when "../discriminant = 'bgp-nbr-af-type'" {
        tailf:xpath-root 3;
        description
          "../discriminant = 'BgpNbrAfType'";
      }
      description
        "track type bgp nbr af info";
      uses BGP-NBR-AF-TRACK-INFO;
    }
    container ipsla-tracks {
      when "../discriminant = 'ipsla-type'" {
        tailf:xpath-root 3;
        description
          "../discriminant = 'IpslaType'";
      }
      description
        "track type rtr info";
      uses RTR-TRACK-INFO;
    }
    container bfd-tracks {
      when "../discriminant = 'bfd-type'" {
        tailf:xpath-root 3;
        description
          "../discriminant = 'BfdType'";
      }
      description
        "track type bfdrtr info";
      uses BFDRTR-TRACK-INFO;
    }
    leaf discriminant {
      type Track;
      description
        "discriminant";
    }
  }

  grouping TRACK-INFO {
    description
      "TRACK INFO";
    list track-info {
      description
        "track info";
      container track-type-info {
        description
          "Track type information";
        uses TRACK-TYPE-INFO-UNION;
      }
      container bool-tracks {
        description
          "boolean objects";
        uses BOOL-TRACK-INFO;
      }
      container threshold-tracks {
        description
          "Threshold objects";
        uses THRESHOLD-TRACK-INFO;
      }
      container tracking-interaces {
        description
          "Tracking Interfaces";
        uses INTERFACE-TRACKING-INFO;
      }
      container delayed {
        description
          "Is the state change delay counter in progress";
        uses DELAYED-STATE-STATUS;
      }
      leaf tracke-name {
        type string {
          length "0..33";
        }
        description
          "Track Name";
      }
      leaf type {
        type Track;
        description
          "Track type";
      }
      leaf track-state {
        type boolean;
        description
          "Track state";
      }
      leaf state-change-counter {
        type uint32;
        description
          "State Change Counter";
      }
      leaf seconds-last-change {
        type uint64;
        units "second";
        description
          "Seconds Last Change";
      }
      leaf mili-seconds-last-change {
        type uint64;
        units "second";
        description
          "Mili Seconds Last Change";
      }
      leaf threshold-up {
        type uint32;
        description
          "User specified threshold upper limit";
      }
      leaf threshold-down {
        type uint32;
        description
          "User specified threshold lower limit";
      }
      leaf delay-up-time {
        type uint16;
        units "second";
        description
          "Delay up time in Seconds";
      }
      leaf delay-up-config {
        type boolean;
        description
          "True, if Delay up is set in config";
      }
      leaf delay-down-time {
        type uint16;
        units "second";
        description
          "Delay down time in Seconds";
      }
      leaf delay-down-config {
        type boolean;
        description
          "True, if Delay down is set in Config";
      }
    }
  }
}

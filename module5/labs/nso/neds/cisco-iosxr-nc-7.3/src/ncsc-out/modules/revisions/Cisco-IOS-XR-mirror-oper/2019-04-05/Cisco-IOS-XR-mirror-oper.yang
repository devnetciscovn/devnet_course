module Cisco-IOS-XR-mirror-oper {
  // Generated by yanger -t ncs
  tailf:mount-id "cisco-iosxr-nc-7.3:cisco-iosxr-nc-7.3";
  tailf:ncs-device-type "netconf";

  namespace "http://cisco.com/ns/yang/Cisco-IOS-XR-mirror-oper";
  prefix mirror-oper;

  import cisco-semver {
    prefix semver;
  }
  include Cisco-IOS-XR-mirror-oper-sub1 {
    revision-date 2019-04-05;
  }
  import tailf-common {
    prefix tailf;
  }
  import tailf-ncs {
    prefix ncs;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mirror package operational data.

     This module contains definitions
     for the following management objects:
       mirror-oper: Mirror operational data

     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/ncs:devices/ncs:device/ncs:config" {
    // NCS drop config false container 'mirror-oper'
  }
  augment "/ncs:devices/ncs:device/ncs:live-status" {
    container mirror-oper {
      tailf:ncs-device-type "netconf";
      tailf:display-when "not(../../ncs:module) or ../../ncs:module[ncs:name='Cisco-IOS-XR-mirror-oper'] or (../../ncs:live-status-protocol[not(ncs:capability)]) or (../../ncs:live-status-protocol/ncs:capability/ncs:module[.='Cisco-IOS-XR-mirror-oper'])";
      description
        "Mirror operational data";
      container show-mirror-sync-entries {
        description
          "The list of dirs which are being synced";
        list show-mirror-sync-entry {
          key "directory";
          description
            "The dirs subject to syncing and if they are
             currently syncing";
          leaf directory {
            type string;
            description
              "Directory";
          }
          uses live_ncs_MIRROR-SYNC-ENTRY;
        }
      }
      container show-mirror-entries {
        description
          "Entries from show mirror";
        container show-mirror-mismatch-entries {
          description
            "Only entries which are not mirrored";
          list show-mirror-mismatch-entry {
            key "path";
            description
              "The individual path entries from show mirror";
            leaf path {
              type string;
              description
                "Path";
            }
            uses live_ncs_MIRROR-FILE-ENTRY;
          }
        }
        container show-mirror-entries {
          description
            "All file entries from show mirror";
          list show-mirror-entry {
            key "path";
            description
              "The individual path entries from show mirror";
            leaf path {
              type string;
              description
                "Path";
            }
            uses live_ncs_MIRROR-FILE-ENTRY;
          }
        }
      }
    }
  }
  augment "/ncs:devices/ncs:template/ncs:ned-id/ncs:config" {
    // NCS drop config false container 'mirror-oper'
  }
}

module Cisco-IOS-XR-sysadmin-entity-mib {
  namespace "http://www.cisco.com/ns/yang/Cisco-IOS-XR-sysadmin-entity-mib";
  prefix ENTITY_MIB;

  import ietf-yang-types {
    prefix yang;
  }
  import tailf-common {
    prefix tailf;
  }
  import SNMPv2-TC {
    prefix SNMPv2-TC;
  }
  import SNMP-FRAMEWORK-MIB {
    prefix SNMP-FRAMEWORK-MIB;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2015-2020 by Cisco Systems, Inc.
     All rights reserved.";

  revision 2019-04-15 {
    description
      "Establish semantic version baseline.";
    semver:module-version "1.0.0";
  }
  revision 2017-04-12 {
    description
      "Changed namespace and module name";
  }
  revision 1999-12-07 {
    description
      "";
  }

  typedef PhysicalIndex {
    type int32 {
      range "1 .. 2147483647";
    }
  }

  typedef PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef SnmpEngineIdOrNone {
    type tailf:hex-list;
  }

  typedef entPhysicalContainedInType {
    type int32 {
      range "0 .. 2147483647";
    }
  }

  typedef entPhysicalParentRelPosType {
    type int32 {
      range "-1 .. 2147483647";
    }
  }

  typedef entPhysicalSerialNumType {
    type string {
      length "min .. 32";
    }
  }

  typedef entPhysicalAliasType {
    type string {
      length "min .. 32";
    }
  }

  typedef entPhysicalAssetIDType {
    type string {
      length "min .. 32";
    }
  }

  typedef entLogicalIndexType {
    type int32 {
      range "1 .. 2147483647";
    }
  }

  typedef entLogicalCommunityType {
    type tailf:hex-list;
  }

  typedef entAliasLogicalIndexOrZeroType {
    type int32 {
      range "0 .. 2147483647";
    }
  }



  container ENTITY-MIB {
    container entityGeneral {
      config false;

      leaf entLastChangeTime {
        type yang:timestamp;
        config false;

      }
    }
    container entPhysicalTable {
      config false;
      list entPhysicalEntry {
        key "entPhysicalIndex";
        config false;


        leaf entPhysicalIndex {
          type PhysicalIndex;

        }
        leaf entPhysicalDescr {
          type SNMP-FRAMEWORK-MIB:SnmpAdminString;
          config false;

        }
        leaf entPhysicalVendorType {
          type SNMPv2-TC:AutonomousType;
          config false;

        }
        leaf entPhysicalContainedIn {
          type entPhysicalContainedInType;
          config false;

        }
        leaf entPhysicalClass {
          type PhysicalClass;
          config false;

        }
        leaf entPhysicalParentRelPos {
          type entPhysicalParentRelPosType;
          config false;

        }
        leaf entPhysicalName {
          type SNMP-FRAMEWORK-MIB:SnmpAdminString;
          config false;

        }
        leaf entPhysicalHardwareRev {
          type SNMP-FRAMEWORK-MIB:SnmpAdminString;
          config false;

        }
        leaf entPhysicalFirmwareRev {
          type SNMP-FRAMEWORK-MIB:SnmpAdminString;
          config false;

        }
        leaf entPhysicalSoftwareRev {
          type SNMP-FRAMEWORK-MIB:SnmpAdminString;
          config false;

        }
        leaf entPhysicalSerialNum {
          type entPhysicalSerialNumType;
          config false;

        }
        leaf entPhysicalMfgName {
          type SNMP-FRAMEWORK-MIB:SnmpAdminString;
          config false;

        }
        leaf entPhysicalModelName {
          type SNMP-FRAMEWORK-MIB:SnmpAdminString;
          config false;

        }
        leaf entPhysicalAlias {
          type entPhysicalAliasType;
          config false;

        }
        leaf entPhysicalAssetID {
          type entPhysicalAssetIDType;
          config false;

        }
        leaf entPhysicalIsFRU {
          type SNMPv2-TC:TruthValue;
          config false;

        }
      }
    }
    container entLogicalTable {
      config false;
      list entLogicalEntry {
        key "entLogicalIndex";
        config false;


        leaf entLogicalIndex {
          type entLogicalIndexType;

        }
        leaf entLogicalDescr {
          type SNMP-FRAMEWORK-MIB:SnmpAdminString;
          config false;

        }
        leaf entLogicalType {
          type SNMPv2-TC:AutonomousType;
          config false;

        }
        leaf entLogicalCommunity {
          type entLogicalCommunityType;
          config false;

        }
        leaf entLogicalTAddress {
          type SNMPv2-TC:TAddress;
          config false;

        }
        leaf entLogicalTDomain {
          type SNMPv2-TC:TDomain;
          config false;

        }
        leaf entLogicalContextEngineID {
          type SnmpEngineIdOrNone;
          config false;

        }
        leaf entLogicalContextName {
          type SNMP-FRAMEWORK-MIB:SnmpAdminString;
          config false;

        }
      }
    }
    container entLPMappingTable {
      config false;
      list entLPMappingEntry {
        key "entLogicalIndex entLPPhysicalIndex";
        config false;


        leaf entLogicalIndex {
          type entLogicalIndexType;

        }
        leaf entLPPhysicalIndex {
          type PhysicalIndex;

        }
      }
    }
    container entAliasMappingTable {
      config false;
      list entAliasMappingEntry {
        key "entPhysicalIndex entAliasLogicalIndexOrZero";
        config false;


        leaf entPhysicalIndex {
          type PhysicalIndex;

        }
        leaf entAliasLogicalIndexOrZero {
          type entAliasLogicalIndexOrZeroType;

        }
        leaf entAliasMappingIdentifier {
          type SNMPv2-TC:RowPointer;
          config false;

        }
      }
    }
    container entPhysicalContainsTable {
      config false;
      list entPhysicalContainsEntry {
        key "entPhysicalIndex entPhysicalChildIndex";
        config false;


        leaf entPhysicalIndex {
          type PhysicalIndex;

        }
        leaf entPhysicalChildIndex {
          type PhysicalIndex;

        }
      }
    }
  }
}

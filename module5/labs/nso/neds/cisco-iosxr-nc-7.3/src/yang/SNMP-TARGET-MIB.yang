module SNMP-TARGET-MIB {
  namespace "http://tail-f.com/ns/mibs/SNMP-TARGET-MIB/200210140000Z";
  prefix SNMP_TARGET_MIB;



  import ietf-yang-types {
    prefix yang;
  }
  import tailf-common {
    prefix tailf;
  }
  import SNMPv2-TC {
    prefix SNMPv2_TC;
  }
  import SNMP-FRAMEWORK-MIB {
    prefix SNMP_FRAMEWORK_MIB;
  }

  revision 2002-10-14 {
    description
      "";
  }

  typedef UDPIPv4TAddress {
    tailf:info "ipv4+port (6 dot-separated octets)";
    type tailf:octet-list {

    }
  }

  typedef UDPIPv6TAddress {
    tailf:info "ipv6+port (18 dot-separated octets)";
    type tailf:octet-list {

    }
  }

  typedef UDPTAddress {
    type union {
      type UDPIPv4TAddress;
      type UDPIPv6TAddress;
    }
  }

  typedef EmptyOctetList {
    type tailf:octet-list {

    }
  }

  typedef UDPTMask {
    tailf:info "octectList, 0, 6 or 18 octets long";
    type union {
      type UDPTAddress;
      type EmptyOctetList;
    }
  }

  container SNMP-TARGET-MIB {
    container snmpTargetObjects {

      config false;
      leaf snmpUnavailableContexts {
        type yang:counter32;

        config false;
      }
      leaf snmpUnknownContexts {
        type yang:counter32;

        config false;
      }
    }
    container snmpTargetAddrTable {
      list snmpTargetAddrEntry {
        key "snmpTargetAddrName";





        leaf snmpTargetAddrName {
          type snmpTargetAddrNameType;

        }
        leaf snmpTargetAddrTDomain {
          type SNMPv2_TC:TDomain;
          mandatory true;

        }
        leaf snmpTargetAddrTAddress {
          type UDPTAddress;
          mandatory true;

        }
        leaf snmpTargetAddrTimeout {
          type SNMPv2_TC:TimeInterval;

          default "1500";
        }
        leaf snmpTargetAddrRetryCount {
          type snmpTargetAddrRetryCountType;

          default "3";
        }
        leaf snmpTargetAddrTagList {
          type SnmpTagList;

          default "";
        }
        leaf snmpTargetAddrParams {
          type snmpTargetAddrParamsType;
          mandatory true;

        }
        leaf snmpTargetAddrStorageType {
          type SNMPv2_TC:StorageType;

          default "nonVolatile";
        }
        leaf snmpTargetAddrEngineID {
          type snmpTargetAddrEngineIDType;
          default "";
        }
        leaf snmpTargetAddrTMask {
          type UDPTMask;
//          tailf:snmp-oid "1.3.6.1.6.3.18.1.2.1.1";

          default "";
        }
        leaf snmpTargetAddrMMS {
          type snmpTargetAddrMMSType;
//          tailf:snmp-oid "1.3.6.1.6.3.18.1.2.1.2";

          default "2048";
        }
        leaf enabled {
          type boolean;
          default "true";
        }
      }
    }
    container snmpTargetParamsTable {
      list snmpTargetParamsEntry {
        key "snmpTargetParamsName";


        leaf snmpTargetParamsName {
          type snmpTargetParamsNameType;

        }
        leaf snmpTargetParamsMPModel {
          type SNMP_FRAMEWORK_MIB:SnmpMessageProcessingModel;
          mandatory true;

        }
        leaf snmpTargetParamsSecurityModel {
          type snmpTargetParamsSecurityModelType;
          mandatory true;

        }
        leaf snmpTargetParamsSecurityName {
          type SNMP_FRAMEWORK_MIB:SnmpAdminString;
          mandatory true;

        }
        leaf snmpTargetParamsSecurityLevel {
          type SNMP_FRAMEWORK_MIB:SnmpSecurityLevel;
          mandatory true;

        }
        leaf snmpTargetParamsStorageType {
          type SNMPv2_TC:StorageType;

          default "nonVolatile";
        }
      }
    }
  }

  typedef snmpTargetAddrEngineIDType {
    type tailf:hex-list {
      pattern "(((([0-9A-Fa-f]{2}):){4,31})([0-9A-Fa-f]{2}))?";
      tailf:value-length "min .. 32";
    }
  }

  typedef snmpTargetAddrMMSType {
    type int32 {
      range "0 | 484 .. 2147483647";
    }
  }

  typedef SnmpTagValue {
    type string {
      length "min .. 255";
    }
  }

  typedef SnmpTagList {
    type string {
      length "min .. 255";
    }
  }

  typedef snmpTargetAddrNameType {
    type string {
      length "1 .. 32";
    }
  }

  typedef snmpTargetAddrRetryCountType {
    type int32 {
      range "0 .. 255";
    }
  }

  typedef snmpTargetAddrParamsType {
    type string {
      length "1 .. 32";
    }
  }

  typedef snmpTargetParamsNameType {
    type string {
      length "1 .. 32";
    }
  }

  typedef snmpTargetParamsSecurityModelType {
    type int32 {
      range "1 .. 2147483647";
    }
  }
}

module cisco-iosxr-nc-7.3 {
  yang-version 1.1;
  namespace "http://tail-f.com/ns/ned-id/cisco-iosxr-nc-7.3";
  prefix cisco-iosxr-nc-7.3;

  import cisco-iosxr-nc {
    prefix family;
  }

  identity cisco-iosxr-nc-7.3 {
    base family:cisco-iosxr-nc;
  }
}

module cisco-iosxr-cli-7.33 {
  yang-version 1.1;
  namespace "http://tail-f.com/ns/ned-id/cisco-iosxr-cli-7.33";
  prefix cisco-iosxr-cli-7.33;

  import cisco-iosxr-cli {
    prefix family;
  }

  identity cisco-iosxr-cli-7.33 {
    base family:cisco-iosxr-cli;
  }
}
